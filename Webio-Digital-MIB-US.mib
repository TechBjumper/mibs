Webio-Digital-MIB-US DEFINITIONS ::= BEGIN
----------------------------------------------------------------
-- Revison: 1.50
----------------------------------------------------------------
-- 21.01.2011 	TrapReceiver 
--		Syntax correction
----------------------------------------------------------------
-- Revison: 1.49
----------------------------------------------------------------
-- 27.07.2010 	Update TrapReceiver
--		 
----------------------------------------------------------------
-- Revison: 1.48
----------------------------------------------------------------
-- 22.06.2010 	Webio
--		Syntax correction
----------------------------------------------------------------
-- Revison: 1.47
----------------------------------------------------------------
-- 23.04.2010 	New: TrapReceiver Reports
----------------------------------------------------------------
-- Revison: 1.46
----------------------------------------------------------------
-- 02.02.2010 	New: 57638: ERP-Gateway PoE: Internal 24V
--                   57655: IP-Watcher PoE: Internal 24V
--		     57656: TrapReceiver 2x2
----------------------------------------------------------------
-- Revison: 1.45
----------------------------------------------------------------
-- 07.01.2010 	New: 57654: IP List Alias Names
--		
----------------------------------------------------------------
-- Revison: 1.44
----------------------------------------------------------------
-- 24.11.2009 	New: 57652: Add on Rate of Change
--		UDP Remote Port
----------------------------------------------------------------
-- Revison: 1.43
----------------------------------------------------------------
-- 06.11.2009 	New: 57637: WebIO Digital 2x2 mit interner 24V
--			    Versorgung
----------------------------------------------------------------
-- Revison: 1.42
----------------------------------------------------------------
-- 11.08.2009 	Syntax correction 
--		
----------------------------------------------------------------
-- Revison: 1.41
----------------------------------------------------------------
-- 15.06.2009 	New: 57652: Rate of change 
--		
----------------------------------------------------------------
-- Revison: 1.40
----------------------------------------------------------------
-- 17.04.2009 	New: IP Watcher 57654 
--		New: ERP Gateway 2x2 Digital 57635
--		New: ERP Gateway 6xRelais 57636
--		
----------------------------------------------------------------
-- Revison: 1.39
----------------------------------------------------------------
-- 03.02.2009 	New: WebIO Digital 6x6 Logger 57650 
--		
----------------------------------------------------------------
-- Revison: 1.37
----------------------------------------------------------------
-- 17.11.2008 	Correction numbering OutputPortEntry 
--		
----------------------------------------------------------------
-- Revison: 1.36
----------------------------------------------------------------
-- 03.09.2008 	New: Web-Count 57652 
--		
----------------------------------------------------------------
-- Revison: 1.35
----------------------------------------------------------------
-- 20.08.2008 	New: US Release Text 
--		Extensions
----------------------------------------------------------------
-- Revison: 1.34
----------------------------------------------------------------
-- 08.08.2008 	New: Web-Alarm 57651 
--		Extensions
----------------------------------------------------------------
-- Revison: 1.33
----------------------------------------------------------------
-- 24.06.2008 	All: OutputState in group xxxInOut now read-write
--		 
----------------------------------------------------------------
-- Revison: 1.32
----------------------------------------------------------------
-- 14.03.2008 	WebAlarm 6x6
--		 
----------------------------------------------------------------
-- Revison: 1.31
----------------------------------------------------------------
-- 23.05.2007 	Webio Digital
--		new: Read(Write) Inputs/Outputs bitwise 
----------------------------------------------------------------
-- Revison: 1.30
----------------------------------------------------------------
-- 08.12.2006 	Webio Digital
--		new: 57634 
----------------------------------------------------------------
-- Revison: 1.29
----------------------------------------------------------------
-- 09.11.2006 	Webio Digital
--		DHCP enable 
----------------------------------------------------------------
-- Revison: 1.28
----------------------------------------------------------------
-- 04.05.2006 	#57632, Webio Digital
--		new OEM device 
----------------------------------------------------------------
-- Revison: 1.27
----------------------------------------------------------------
-- 10.02.2006 	#57630/1, Webio Digital
--		Incremental Counter
--		New: #57633 2x2 Webio Digital
----------------------------------------------------------------
-- Revison: 1.26
----------------------------------------------------------------
-- 05.08.2005 	#57630/1/2, Webio Digital
--		CRON time functions
--		FTP functions
----------------------------------------------------------------
-- Revison: 1.25
----------------------------------------------------------------
-- 02.06.2005 	#57630/1/2, Webio Digital
--		Trap NMS annotations
----------------------------------------------------------------
-- Revison: 1.24
----------------------------------------------------------------
-- 10.05.2005 	#57630/1/2, Webio Digital
--		Binary Mode: BIN-TCP-CLIENT-SERVER-HTTP-PORT
--		Binary Mode: BIN-TCP-SERVER-CLIENT-HTTP-PORT
----------------------------------------------------------------
-- Revison: 1.23
----------------------------------------------------------------
-- 19.04.2005 	#57630/1/2, Webio Digital
--		Mail Authentication
--		PortInputMode: Change detection enable
----------------------------------------------------------------
-- Revison: 1.22
----------------------------------------------------------------
-- 15.03.2005 	#57630/1/2, Webio Digital
--		variable HTTP port
--	
----------------------------------------------------------------
-- Revison: 1.21
----------------------------------------------------------------
-- 17.02.2005 	#57630/1/2, Webio Digital
--		4 additional traps; new input/output alarm trigger
--	
----------------------------------------------------------------
-- Revison: 1.20
----------------------------------------------------------------
-- 13.12.2004 	#57630/1/2, Webio Digital
--		New: Size setoutput, alarminputtrigger, alarmoutputtrigger
--	
----------------------------------------------------------------
-- Revison: 1.19
----------------------------------------------------------------
-- 02.11.2004 	#57630/1/2, Webio Digital
--		New: Syslog
--		     
----------------------------------------------------------------
-- Revison: 1.18
----------------------------------------------------------------
-- 12.07.2004 	#57630/1/2, Webio Digital
--		New: HTTP Input Trigger
--		     Diagnosis
----------------------------------------------------------------
-- Revison: 1.17
----------------------------------------------------------------
-- 28.06.2004 	#57630/1/2, Webio Digital
--		Neu: Pulse Mode
----------------------------------------------------------------
-- Revison: 1.16
----------------------------------------------------------------
-- 16.04.2004 	New: #57632, Webio Digital EA24oem
--
--		#57630/1, Webio Digital EA12x12
--		New:
--			wtWebioEA12x12InputCounterClear
----------------------------------------------------------------
-- Revison: 1.15
----------------------------------------------------------------
-- 27.02.2004 	#57630/1, Webio Digital EA12x12
--		New:
--		Length changed to 32 Bit:
--			wtWebioEA12x12InputValue
--			wtWebioEA12x12OutputValue
--			wtWebioEA12x12LoadControlView
--			wtWebioEA12x12LCShutDownView
--			wtWebioEA12x12SetOutput
--			wtWebioEA12x12AlarmInputTrigger
--			wtWebioEA12x12AlarmOutputTrigger
--			wtWebioEA12x12PortOutputSafetyState
----------------------------------------------------------------
-- Revison: 1.14
----------------------------------------------------------------
-- 16.02.2004 	#57630/1, Webio Digital EA12x12
--		New:
--		Text: Location, Contact
--		SNMP: ColdStart, WarmStart, ComunityString Read/RW
--		Alarm: ColdStart / WarmStart trigger
--
-- 	 	#57601, 1xWebThermometer
--		#57603, 2xWebThermometer		
--		#57604, 8xWebThermometer
--		New:
--		Alarm Hysteresis 
--		Alarm Clear Traps and Mails
----------------------------------------------------------------
-- Revison: 1.13
----------------------------------------------------------------
-- 05.02.2004 	#57601, 1xWebThermometer
--		#57603, 2xWebThermometer		
--		#57604, 8xWebThermometer
--		New:
--		Text: Location, Contact
--		SNMP: ColdStart, WarmStart, ComunityString Read/RW
--		Alarm: ColdStart / WarmStart trigger
----------------------------------------------------------------
-- Revison: 1.12
----------------------------------------------------------------
-- 05.11.2003 	#57601, 1xWebThermometer
--		#57603, 2xWebThermometer		
--		#57604, 8xWebThermometer
--		New features:
--		Mail  : Option CSV attachment
--		Port  : Offset calibration
--		Alarm : TCP Client mode		
----------------------------------------------------------------
-- Revison: 1.11
----------------------------------------------------------------
-- 28.10.2003 	#57630/1, Webio Digital EA12x12
--		New features:
--		Alarm : TCP Client mode		
--		Inputs: Pulse filter
----------------------------------------------------------------
-- Revison: 1.10
----------------------------------------------------------------
-- 22.07.2003 	#57630, Webio Digital EA12x12
--		New navigation tree, new binary modes		
--
----------------------------------------------------------------
-- Revison: 1.09
----------------------------------------------------------------
-- 24.03.2003 	Trap Enterprise (Type 1, 2) corrected 
----------------------------------------------------------------
-- Revison: 1.08
----------------------------------------------------------------
-- 04.03.2003 	reconciled the language versions DE/US
----------------------------------------------------------------
-- Revison: 1.07
----------------------------------------------------------------
-- 25.02.2003 	Correction: wtWebioEA12x12LoadControl
----------------------------------------------------------------
-- Revison: 1.06
----------------------------------------------------------------
-- 24.02.2003 	New:
--		#57630, Webio EA12x12, LoadControl Group
--		Correction: Trap variable names
----------------------------------------------------------------
-- Revison: 1.05
----------------------------------------------------------------
-- 21.01.2003 	New:
--		#57630, Webio EA12x12
----------------------------------------------------------------
-- Revison: 1.04
----------------------------------------------------------------
-- 02.01.2003 	New:
--		#57601, 1xWebThermometer
--		#57603, 2xWebThermometer, 8 alarms
----------------------------------------------------------------
-- Revison: 1.03
----------------------------------------------------------------
-- 21.11.2002 	New:
--		#57604, 2xWebThermometer, BOOTP, StartupSite
--		#57603, 8xWebThermometer, BOOTP, StartupSite
----------------------------------------------------------------
-- Revison: 1.02
----------------------------------------------------------------
-- 26.07.2002 	New:
--		#57604, 2xWebThermometer
--		#57603, 8xWebThermometer
-- 		

    IMPORTS

    OBJECT-TYPE                                        FROM RFC-1212
    TRAP-TYPE                                          FROM RFC-1215
    DisplayString, PhysAddress                         FROM RFC1213-MIB
    enterprises, TimeTicks, IpAddress, NetworkAddress  FROM RFC1155-SMI;

 
--    IpAddress ::=
--        [APPLICATION 0]
--            IMPLICIT OCTET STRING (SIZE (4))
--    Counter ::=
--        [APPLICATION 1]
--            IMPLICIT INTEGER (0..4294967295)
--    Gauge ::=
--        [APPLICATION 2]
--            IMPLICIT INTEGER (0..4294967295)
--    TimeTicks ::=
--        [APPLICATION 3]
--            IMPLICIT INTEGER (0..4294967295)


--    DisplayString ::= OCTET STRING
--    PhysAddress   ::= OCTET STRING

--    internet         OBJECT IDENTIFIER ::= { iso org(3) dod(6) 1 }
--    privat           OBJECT IDENTIFIER ::= { internet 4 }
--    enterprises      OBJECT IDENTIFIER ::= { privat 1 }



--  Wiesemann & Theis Com-Server MIB

    wut                			OBJECT IDENTIFIER ::= { enterprises 5040 }
    wtComServer        			OBJECT IDENTIFIER ::= { wut 1 }
    wtWebio            			OBJECT IDENTIFIER ::= { wtComServer 2 }

--  wtWebio Tree

    wtWebioEA12x12     			OBJECT IDENTIFIER ::= { wtWebio 4 }
    wtWebioEA2x2     			OBJECT IDENTIFIER ::= { wtWebio 13 }
    wtWebioEA24oem     			OBJECT IDENTIFIER ::= { wtWebio 14 }
    wtWebioEA12x6Rel   			OBJECT IDENTIFIER ::= { wtWebio 19 }
    wtWebAlarm6x6  			OBJECT IDENTIFIER ::= { wtWebio 20 }
    wtWebCount6  			OBJECT IDENTIFIER ::= { wtWebio 22 }
    wtWebioEA6x6 			OBJECT IDENTIFIER ::= { wtWebio 24 }
    wtWebioEA2x2ERP    			OBJECT IDENTIFIER ::= { wtWebio 25 }
    wtWebioEA12x6RelERP   		OBJECT IDENTIFIER ::= { wtWebio 26 }
    wtIpWatcher   			OBJECT IDENTIFIER ::= { wtWebio 27 }
    wtWebioEA2x2-24V   			OBJECT IDENTIFIER ::= { wtWebio 30 }
    wtWebioEA2x2ERP-24V			OBJECT IDENTIFIER ::= { wtWebio 31 }
    wtIpWatcher-24V   			OBJECT IDENTIFIER ::= { wtWebio 32 }
    wtTrapReceiver2x2			OBJECT IDENTIFIER ::= { wtWebio 33 }
    
--  wtWebioEA2x2 Tree

    wtWebioEA2x2InOut      		OBJECT IDENTIFIER ::= { wtWebioEA2x2 1 }
    wtWebioEA2x2SessCntrl 		OBJECT IDENTIFIER ::= { wtWebioEA2x2 2 }
    wtWebioEA2x2Config    		OBJECT IDENTIFIER ::= { wtWebioEA2x2 3 }
    wtWebioEA2x2Diag  			OBJECT IDENTIFIER ::= { wtWebioEA2x2 4 }

--  wtWebioEA2x2Config Tree

    wtWebioEA2x2Device    		OBJECT IDENTIFIER ::= { wtWebioEA2x2Config 1 }
    wtWebioEA2x2Ports     		OBJECT IDENTIFIER ::= { wtWebioEA2x2Config 2 }	
    wtWebioEA2x2Manufact  		OBJECT IDENTIFIER ::= { wtWebioEA2x2Config 3 }
    
--  wtWebioEA2x2Device Tree

    wtWebioEA2x2Text			OBJECT IDENTIFIER ::= { wtWebioEA2x2Device 1 }
    wtWebioEA2x2TimeDate 		OBJECT IDENTIFIER ::= { wtWebioEA2x2Device 2 }
    wtWebioEA2x2Basic 			OBJECT IDENTIFIER ::= { wtWebioEA2x2Device 3 }
    wtWebioEA2x2OutputMode		OBJECT IDENTIFIER ::= { wtWebioEA2x2Device 4 }
    wtWebioEA2x2Alarm			OBJECT IDENTIFIER ::= { wtWebioEA2x2Device 5 }

--  wtWebioEA2x2Basic Tree

    wtWebioEA2x2Network			OBJECT IDENTIFIER ::= { wtWebioEA2x2Basic 1 }
    wtWebioEA2x2HTTP	 		OBJECT IDENTIFIER ::= { wtWebioEA2x2Basic 2 }
    wtWebioEA2x2Mail			OBJECT IDENTIFIER ::= { wtWebioEA2x2Basic 3 }	
    wtWebioEA2x2SNMP	 		OBJECT IDENTIFIER ::= { wtWebioEA2x2Basic 4 }
    wtWebioEA2x2UDP			OBJECT IDENTIFIER ::= { wtWebioEA2x2Basic 5 }	
    wtWebioEA2x2Binary			OBJECT IDENTIFIER ::= { wtWebioEA2x2Basic 6 }
    wtWebioEA2x2Syslog			OBJECT IDENTIFIER ::= { wtWebioEA2x2Basic 7 }
    wtWebioEA2x2FTP			OBJECT IDENTIFIER ::= { wtWebioEA2x2Basic 8 }
    
--  wtWebioEA2x2TimeDate Tree

    wtWebioEA2x2TimeZone		OBJECT IDENTIFIER ::= { wtWebioEA2x2TimeDate 1 }
    wtWebioEA2x2TimeServer		OBJECT IDENTIFIER ::= { wtWebioEA2x2TimeDate 2 }	
    wtWebioEA2x2DeviceClock		OBJECT IDENTIFIER ::= { wtWebioEA2x2TimeDate 3 }    
    
--  wtWebioEA12x12 Tree

    wtWebioEA12x12InOut      		OBJECT IDENTIFIER ::= { wtWebioEA12x12 1 }
    wtWebioEA12x12SessCntrl 		OBJECT IDENTIFIER ::= { wtWebioEA12x12 2 }
    wtWebioEA12x12Config    		OBJECT IDENTIFIER ::= { wtWebioEA12x12 3 }
    wtWebioEA12x12Diag  		OBJECT IDENTIFIER ::= { wtWebioEA12x12 4 }

--  wtWebioEA12x12Config Tree

    wtWebioEA12x12Device    		OBJECT IDENTIFIER ::= { wtWebioEA12x12Config 1 }
    wtWebioEA12x12Ports     		OBJECT IDENTIFIER ::= { wtWebioEA12x12Config 2 }	
    wtWebioEA12x12Manufact  		OBJECT IDENTIFIER ::= { wtWebioEA12x12Config 3 }
    
--  wtWebioEA12x12Device Tree

    wtWebioEA12x12Text			OBJECT IDENTIFIER ::= { wtWebioEA12x12Device 1 }
    wtWebioEA12x12TimeDate 		OBJECT IDENTIFIER ::= { wtWebioEA12x12Device 2 }
    wtWebioEA12x12Basic 		OBJECT IDENTIFIER ::= { wtWebioEA12x12Device 3 }
    wtWebioEA12x12OutputMode		OBJECT IDENTIFIER ::= { wtWebioEA12x12Device 4 }
    wtWebioEA12x12Alarm			OBJECT IDENTIFIER ::= { wtWebioEA12x12Device 5 }

--  wtWebioEA12x12Basic Tree

    wtWebioEA12x12Network		OBJECT IDENTIFIER ::= { wtWebioEA12x12Basic 1 }
    wtWebioEA12x12HTTP	 		OBJECT IDENTIFIER ::= { wtWebioEA12x12Basic 2 }
    wtWebioEA12x12Mail			OBJECT IDENTIFIER ::= { wtWebioEA12x12Basic 3 }	
    wtWebioEA12x12SNMP	 		OBJECT IDENTIFIER ::= { wtWebioEA12x12Basic 4 }
    wtWebioEA12x12UDP			OBJECT IDENTIFIER ::= { wtWebioEA12x12Basic 5 }	
    wtWebioEA12x12Binary		OBJECT IDENTIFIER ::= { wtWebioEA12x12Basic 6 }
    wtWebioEA12x12Syslog		OBJECT IDENTIFIER ::= { wtWebioEA12x12Basic 7 }
    wtWebioEA12x12FTP			OBJECT IDENTIFIER ::= { wtWebioEA12x12Basic 8 }
    
--  wtWebioEA12x12TimeDate Tree

    wtWebioEA12x12TimeZone		OBJECT IDENTIFIER ::= { wtWebioEA12x12TimeDate 1 }
    wtWebioEA12x12TimeServer		OBJECT IDENTIFIER ::= { wtWebioEA12x12TimeDate 2 }	
    wtWebioEA12x12DeviceClock		OBJECT IDENTIFIER ::= { wtWebioEA12x12TimeDate 3 }    
    
--  wtWebioEA24oem Tree

    wtWebioEA24oemInOut      		OBJECT IDENTIFIER ::= { wtWebioEA24oem 1 }
    wtWebioEA24oemSessCntrl 		OBJECT IDENTIFIER ::= { wtWebioEA24oem 2 }
    wtWebioEA24oemConfig    		OBJECT IDENTIFIER ::= { wtWebioEA24oem 3 }
    wtWebioEA24oemDiag  		OBJECT IDENTIFIER ::= { wtWebioEA24oem 4 }

--  wtWebioEA24oemConfig Tree

    wtWebioEA24oemDevice    		OBJECT IDENTIFIER ::= { wtWebioEA24oemConfig 1 }
    wtWebioEA24oemPorts     		OBJECT IDENTIFIER ::= { wtWebioEA24oemConfig 2 }	
    wtWebioEA24oemManufact  		OBJECT IDENTIFIER ::= { wtWebioEA24oemConfig 3 }
    
--  wtWebioEA24oemDevice Tree

    wtWebioEA24oemText			OBJECT IDENTIFIER ::= { wtWebioEA24oemDevice 1 }
    wtWebioEA24oemTimeDate 		OBJECT IDENTIFIER ::= { wtWebioEA24oemDevice 2 }
    wtWebioEA24oemBasic 		OBJECT IDENTIFIER ::= { wtWebioEA24oemDevice 3 }
    wtWebioEA24oemOutputMode		OBJECT IDENTIFIER ::= { wtWebioEA24oemDevice 4 }
    wtWebioEA24oemAlarm			OBJECT IDENTIFIER ::= { wtWebioEA24oemDevice 5 }

--  wtWebioEA24oemBasic Tree

    wtWebioEA24oemNetwork		OBJECT IDENTIFIER ::= { wtWebioEA24oemBasic 1 }
    wtWebioEA24oemHTTP	 		OBJECT IDENTIFIER ::= { wtWebioEA24oemBasic 2 }
    wtWebioEA24oemMail			OBJECT IDENTIFIER ::= { wtWebioEA24oemBasic 3 }	
    wtWebioEA24oemSNMP	 		OBJECT IDENTIFIER ::= { wtWebioEA24oemBasic 4 }
    wtWebioEA24oemUDP			OBJECT IDENTIFIER ::= { wtWebioEA24oemBasic 5 }	
    wtWebioEA24oemBinary		OBJECT IDENTIFIER ::= { wtWebioEA24oemBasic 6 }
    wtWebioEA24oemSyslog		OBJECT IDENTIFIER ::= { wtWebioEA24oemBasic 7 }
    wtWebioEA24oemFTP			OBJECT IDENTIFIER ::= { wtWebioEA24oemBasic 8 }
    
--  wtWebioEA24oemTimeDate Tree

    wtWebioEA24oemTimeZone		OBJECT IDENTIFIER ::= { wtWebioEA24oemTimeDate 1 }
    wtWebioEA24oemTimeServer		OBJECT IDENTIFIER ::= { wtWebioEA24oemTimeDate 2 }	
    wtWebioEA24oemDeviceClock		OBJECT IDENTIFIER ::= { wtWebioEA24oemTimeDate 3 }    
    
--  wtWebioEA12x6Rel Tree

    wtWebioEA12x6RelInOut      		OBJECT IDENTIFIER ::= { wtWebioEA12x6Rel 1 }
    wtWebioEA12x6RelSessCntrl 		OBJECT IDENTIFIER ::= { wtWebioEA12x6Rel 2 }
    wtWebioEA12x6RelConfig    		OBJECT IDENTIFIER ::= { wtWebioEA12x6Rel 3 }
    wtWebioEA12x6RelDiag  		OBJECT IDENTIFIER ::= { wtWebioEA12x6Rel 4 }

--  wtWebioEA12x6RelConfig Tree

    wtWebioEA12x6RelDevice    		OBJECT IDENTIFIER ::= { wtWebioEA12x6RelConfig 1 }
    wtWebioEA12x6RelPorts     		OBJECT IDENTIFIER ::= { wtWebioEA12x6RelConfig 2 }	
    wtWebioEA12x6RelManufact  		OBJECT IDENTIFIER ::= { wtWebioEA12x6RelConfig 3 }
    
--  wtWebioEA12x6RelDevice Tree

    wtWebioEA12x6RelText		OBJECT IDENTIFIER ::= { wtWebioEA12x6RelDevice 1 }
    wtWebioEA12x6RelTimeDate 		OBJECT IDENTIFIER ::= { wtWebioEA12x6RelDevice 2 }
    wtWebioEA12x6RelBasic 		OBJECT IDENTIFIER ::= { wtWebioEA12x6RelDevice 3 }
    wtWebioEA12x6RelOutputMode		OBJECT IDENTIFIER ::= { wtWebioEA12x6RelDevice 4 }
    wtWebioEA12x6RelAlarm		OBJECT IDENTIFIER ::= { wtWebioEA12x6RelDevice 5 }

--  wtWebioEA12x6RelBasic Tree

    wtWebioEA12x6RelNetwork		OBJECT IDENTIFIER ::= { wtWebioEA12x6RelBasic 1 }
    wtWebioEA12x6RelHTTP		OBJECT IDENTIFIER ::= { wtWebioEA12x6RelBasic 2 }
    wtWebioEA12x6RelMail		OBJECT IDENTIFIER ::= { wtWebioEA12x6RelBasic 3 }	
    wtWebioEA12x6RelSNMP		OBJECT IDENTIFIER ::= { wtWebioEA12x6RelBasic 4 }
    wtWebioEA12x6RelUDP			OBJECT IDENTIFIER ::= { wtWebioEA12x6RelBasic 5 }	
    wtWebioEA12x6RelBinary		OBJECT IDENTIFIER ::= { wtWebioEA12x6RelBasic 6 }
    wtWebioEA12x6RelSyslog		OBJECT IDENTIFIER ::= { wtWebioEA12x6RelBasic 7 }
    wtWebioEA12x6RelFTP			OBJECT IDENTIFIER ::= { wtWebioEA12x6RelBasic 8 }
    
--  wtWebioEA12x6RelTimeDate Tree

    wtWebioEA12x6RelTimeZone		OBJECT IDENTIFIER ::= { wtWebioEA12x6RelTimeDate 1 }
    wtWebioEA12x6RelTimeServer		OBJECT IDENTIFIER ::= { wtWebioEA12x6RelTimeDate 2 }	
    wtWebioEA12x6RelDeviceClock		OBJECT IDENTIFIER ::= { wtWebioEA12x6RelTimeDate 3 }    
    
--  wtWebAlarm6x6 Tree

    wtWebAlarm6x6InOut      		OBJECT IDENTIFIER ::= { wtWebAlarm6x6 1 }
    wtWebAlarm6x6SessCntrl 		OBJECT IDENTIFIER ::= { wtWebAlarm6x6 2 }
    wtWebAlarm6x6Config    		OBJECT IDENTIFIER ::= { wtWebAlarm6x6 3 }
    wtWebAlarm6x6Diag  			OBJECT IDENTIFIER ::= { wtWebAlarm6x6 4 }

--  wtWebAlarm6x6Config Tree

    wtWebAlarm6x6Device    		OBJECT IDENTIFIER ::= { wtWebAlarm6x6Config 1 }
    wtWebAlarm6x6Ports     		OBJECT IDENTIFIER ::= { wtWebAlarm6x6Config 2 }	
    wtWebAlarm6x6Manufact  		OBJECT IDENTIFIER ::= { wtWebAlarm6x6Config 3 }
    
--  wtWebAlarm6x6Device Tree

    wtWebAlarm6x6Text			OBJECT IDENTIFIER ::= { wtWebAlarm6x6Device 1 }
    wtWebAlarm6x6TimeDate 		OBJECT IDENTIFIER ::= { wtWebAlarm6x6Device 2 }
    wtWebAlarm6x6Basic 			OBJECT IDENTIFIER ::= { wtWebAlarm6x6Device 3 }
    wtWebAlarm6x6Alarm			OBJECT IDENTIFIER ::= { wtWebAlarm6x6Device 5 }

--  wtWebAlarm6x6Basic Tree

    wtWebAlarm6x6Network		OBJECT IDENTIFIER ::= { wtWebAlarm6x6Basic 1 }
    wtWebAlarm6x6HTTP			OBJECT IDENTIFIER ::= { wtWebAlarm6x6Basic 2 }
    wtWebAlarm6x6Mail			OBJECT IDENTIFIER ::= { wtWebAlarm6x6Basic 3 }	
    wtWebAlarm6x6SNMP			OBJECT IDENTIFIER ::= { wtWebAlarm6x6Basic 4 }
    wtWebAlarm6x6UDP			OBJECT IDENTIFIER ::= { wtWebAlarm6x6Basic 5 }	
    wtWebAlarm6x6Syslog			OBJECT IDENTIFIER ::= { wtWebAlarm6x6Basic 7 }
    wtWebAlarm6x6FTP			OBJECT IDENTIFIER ::= { wtWebAlarm6x6Basic 8 }
    
--  wtWebAlarm6x6TimeDate Tree

    wtWebAlarm6x6TimeZone		OBJECT IDENTIFIER ::= { wtWebAlarm6x6TimeDate 1 }
    wtWebAlarm6x6TimeServer		OBJECT IDENTIFIER ::= { wtWebAlarm6x6TimeDate 2 }	
    wtWebAlarm6x6DeviceClock		OBJECT IDENTIFIER ::= { wtWebAlarm6x6TimeDate 3 }   
    
--  wtWebCount6 Tree

    wtWebCount6InOut      		OBJECT IDENTIFIER ::= { wtWebCount6 1 }
    wtWebCount6SessCntrl 		OBJECT IDENTIFIER ::= { wtWebCount6 2 }
    wtWebCount6Config    		OBJECT IDENTIFIER ::= { wtWebCount6 3 }
    wtWebCount6Diag  			OBJECT IDENTIFIER ::= { wtWebCount6 4 }

--  wtWebCount6Config Tree

    wtWebCount6Device    		OBJECT IDENTIFIER ::= { wtWebCount6Config 1 }
    wtWebCount6Ports     		OBJECT IDENTIFIER ::= { wtWebCount6Config 2 }	
    wtWebCount6Manufact  		OBJECT IDENTIFIER ::= { wtWebCount6Config 3 }
    
--  wtWebCount6Device Tree

    wtWebCount6Text			OBJECT IDENTIFIER ::= { wtWebCount6Device 1 }
    wtWebCount6TimeDate 		OBJECT IDENTIFIER ::= { wtWebCount6Device 2 }
    wtWebCount6Basic 			OBJECT IDENTIFIER ::= { wtWebCount6Device 3 }
    wtWebCount6Report			OBJECT IDENTIFIER ::= { wtWebCount6Device 5 }

--  wtWebCount6Basic Tree

    wtWebCount6Network			OBJECT IDENTIFIER ::= { wtWebCount6Basic 1 }
    wtWebCount6HTTP			OBJECT IDENTIFIER ::= { wtWebCount6Basic 2 }
    wtWebCount6Mail			OBJECT IDENTIFIER ::= { wtWebCount6Basic 3 }	
    wtWebCount6SNMP			OBJECT IDENTIFIER ::= { wtWebCount6Basic 4 }
    wtWebCount6UDP			OBJECT IDENTIFIER ::= { wtWebCount6Basic 5 }	
    wtWebCount6Syslog			OBJECT IDENTIFIER ::= { wtWebCount6Basic 7 }
    wtWebCount6FTP			OBJECT IDENTIFIER ::= { wtWebCount6Basic 8 }
    
--  wtWebCount6TimeDate Tree

    wtWebCount6TimeZone			OBJECT IDENTIFIER ::= { wtWebCount6TimeDate 1 }
    wtWebCount6TimeServer		OBJECT IDENTIFIER ::= { wtWebCount6TimeDate 2 }	
    wtWebCount6DeviceClock		OBJECT IDENTIFIER ::= { wtWebCount6TimeDate 3 }
    
--  wtWebioEA6x6 Tree

    wtWebioEA6x6InOut      		OBJECT IDENTIFIER ::= { wtWebioEA6x6 1 }
    wtWebioEA6x6SessCntrl 		OBJECT IDENTIFIER ::= { wtWebioEA6x6 2 }
    wtWebioEA6x6Config    		OBJECT IDENTIFIER ::= { wtWebioEA6x6 3 }
    wtWebioEA6x6Diag  			OBJECT IDENTIFIER ::= { wtWebioEA6x6 4 }

--  wtWebioEA6x6Config Tree

    wtWebioEA6x6Device    		OBJECT IDENTIFIER ::= { wtWebioEA6x6Config 1 }
    wtWebioEA6x6Ports     		OBJECT IDENTIFIER ::= { wtWebioEA6x6Config 2 }	
    wtWebioEA6x6Manufact  		OBJECT IDENTIFIER ::= { wtWebioEA6x6Config 3 }
    
--  wtWebioEA6x6Device Tree

    wtWebioEA6x6Text			OBJECT IDENTIFIER ::= { wtWebioEA6x6Device 1 }
    wtWebioEA6x6TimeDate 		OBJECT IDENTIFIER ::= { wtWebioEA6x6Device 2 }
    wtWebioEA6x6Basic 			OBJECT IDENTIFIER ::= { wtWebioEA6x6Device 3 }
    wtWebioEA6x6OutputMode		OBJECT IDENTIFIER ::= { wtWebioEA6x6Device 4 }
    wtWebioEA6x6Alarm			OBJECT IDENTIFIER ::= { wtWebioEA6x6Device 5 }

--  wtWebioEA6x6Basic Tree

    wtWebioEA6x6Network			OBJECT IDENTIFIER ::= { wtWebioEA6x6Basic 1 }
    wtWebioEA6x6HTTP	 		OBJECT IDENTIFIER ::= { wtWebioEA6x6Basic 2 }
    wtWebioEA6x6Mail			OBJECT IDENTIFIER ::= { wtWebioEA6x6Basic 3 }	
    wtWebioEA6x6SNMP	 		OBJECT IDENTIFIER ::= { wtWebioEA6x6Basic 4 }
    wtWebioEA6x6UDP			OBJECT IDENTIFIER ::= { wtWebioEA6x6Basic 5 }	
    wtWebioEA6x6Binary			OBJECT IDENTIFIER ::= { wtWebioEA6x6Basic 6 }
    wtWebioEA6x6Syslog			OBJECT IDENTIFIER ::= { wtWebioEA6x6Basic 7 }
    wtWebioEA6x6FTP			OBJECT IDENTIFIER ::= { wtWebioEA6x6Basic 8 }
    
--  wtWebioEA6x6TimeDate Tree

    wtWebioEA6x6TimeZone		OBJECT IDENTIFIER ::= { wtWebioEA6x6TimeDate 1 }
    wtWebioEA6x6TimeServer		OBJECT IDENTIFIER ::= { wtWebioEA6x6TimeDate 2 }	
    wtWebioEA6x6DeviceClock		OBJECT IDENTIFIER ::= { wtWebioEA6x6TimeDate 3 }

--  wtWebioEA2x2ERP Tree

    wtWebioEA2x2ERPInOut      		OBJECT IDENTIFIER ::= { wtWebioEA2x2ERP 1 }
    wtWebioEA2x2ERPSessCntrl 		OBJECT IDENTIFIER ::= { wtWebioEA2x2ERP 2 }
    wtWebioEA2x2ERPConfig    		OBJECT IDENTIFIER ::= { wtWebioEA2x2ERP 3 }
    wtWebioEA2x2ERPDiag  		OBJECT IDENTIFIER ::= { wtWebioEA2x2ERP 4 }

--  wtWebioEA2x2ERPConfig Tree

    wtWebioEA2x2ERPDevice    		OBJECT IDENTIFIER ::= { wtWebioEA2x2ERPConfig 1 }
    wtWebioEA2x2ERPPorts     		OBJECT IDENTIFIER ::= { wtWebioEA2x2ERPConfig 2 }	
    wtWebioEA2x2ERPManufact  		OBJECT IDENTIFIER ::= { wtWebioEA2x2ERPConfig 3 }
    
--  wtWebioEA2x2ERPDevice Tree

    wtWebioEA2x2ERPText			OBJECT IDENTIFIER ::= { wtWebioEA2x2ERPDevice 1 }
    wtWebioEA2x2ERPTimeDate 		OBJECT IDENTIFIER ::= { wtWebioEA2x2ERPDevice 2 }
    wtWebioEA2x2ERPBasic 		OBJECT IDENTIFIER ::= { wtWebioEA2x2ERPDevice 3 }
    wtWebioEA2x2ERPOutputMode		OBJECT IDENTIFIER ::= { wtWebioEA2x2ERPDevice 4 }
    wtWebioEA2x2ERPAlarm		OBJECT IDENTIFIER ::= { wtWebioEA2x2ERPDevice 5 }

--  wtWebioEA2x2ERPBasic Tree

    wtWebioEA2x2ERPNetwork		OBJECT IDENTIFIER ::= { wtWebioEA2x2ERPBasic 1 }
    wtWebioEA2x2ERPHTTP	 		OBJECT IDENTIFIER ::= { wtWebioEA2x2ERPBasic 2 }
    wtWebioEA2x2ERPMail			OBJECT IDENTIFIER ::= { wtWebioEA2x2ERPBasic 3 }	
    wtWebioEA2x2ERPSNMP	 		OBJECT IDENTIFIER ::= { wtWebioEA2x2ERPBasic 4 }
    wtWebioEA2x2ERPUDP			OBJECT IDENTIFIER ::= { wtWebioEA2x2ERPBasic 5 }	
    wtWebioEA2x2ERPBinary		OBJECT IDENTIFIER ::= { wtWebioEA2x2ERPBasic 6 }
    wtWebioEA2x2ERPSyslog		OBJECT IDENTIFIER ::= { wtWebioEA2x2ERPBasic 7 }
    wtWebioEA2x2ERPFTP			OBJECT IDENTIFIER ::= { wtWebioEA2x2ERPBasic 8 }
    wtWebioEA2x2ERPWayBack		OBJECT IDENTIFIER ::= { wtWebioEA2x2ERPBasic 10 }
    
--  wtWebioEA2x2ERPTimeDate Tree

    wtWebioEA2x2ERPTimeZone		OBJECT IDENTIFIER ::= { wtWebioEA2x2ERPTimeDate 1 }
    wtWebioEA2x2ERPTimeServer		OBJECT IDENTIFIER ::= { wtWebioEA2x2ERPTimeDate 2 }	
    wtWebioEA2x2ERPDeviceClock		OBJECT IDENTIFIER ::= { wtWebioEA2x2ERPTimeDate 3 }    

--  wtWebioEA12x6RelERP Tree

    wtWebioEA12x6RelERPInOut      	OBJECT IDENTIFIER ::= { wtWebioEA12x6RelERP 1 }
    wtWebioEA12x6RelERPSessCntrl 	OBJECT IDENTIFIER ::= { wtWebioEA12x6RelERP 2 }
    wtWebioEA12x6RelERPConfig    	OBJECT IDENTIFIER ::= { wtWebioEA12x6RelERP 3 }
    wtWebioEA12x6RelERPDiag  		OBJECT IDENTIFIER ::= { wtWebioEA12x6RelERP 4 }

--  wtWebioEA12x6RelERPConfig Tree

    wtWebioEA12x6RelERPDevice    	OBJECT IDENTIFIER ::= { wtWebioEA12x6RelERPConfig 1 }
    wtWebioEA12x6RelERPPorts     	OBJECT IDENTIFIER ::= { wtWebioEA12x6RelERPConfig 2 }	
    wtWebioEA12x6RelERPManufact  	OBJECT IDENTIFIER ::= { wtWebioEA12x6RelERPConfig 3 }
    
--  wtWebioEA12x6RelERPDevice Tree

    wtWebioEA12x6RelERPText		OBJECT IDENTIFIER ::= { wtWebioEA12x6RelERPDevice 1 }
    wtWebioEA12x6RelERPTimeDate 	OBJECT IDENTIFIER ::= { wtWebioEA12x6RelERPDevice 2 }
    wtWebioEA12x6RelERPBasic 		OBJECT IDENTIFIER ::= { wtWebioEA12x6RelERPDevice 3 }
    wtWebioEA12x6RelERPOutputMode	OBJECT IDENTIFIER ::= { wtWebioEA12x6RelERPDevice 4 }
    wtWebioEA12x6RelERPAlarm		OBJECT IDENTIFIER ::= { wtWebioEA12x6RelERPDevice 5 }

--  wtWebioEA12x6RelERPBasic Tree

    wtWebioEA12x6RelERPNetwork		OBJECT IDENTIFIER ::= { wtWebioEA12x6RelERPBasic 1 }
    wtWebioEA12x6RelERPHTTP		OBJECT IDENTIFIER ::= { wtWebioEA12x6RelERPBasic 2 }
    wtWebioEA12x6RelERPMail		OBJECT IDENTIFIER ::= { wtWebioEA12x6RelERPBasic 3 }	
    wtWebioEA12x6RelERPSNMP		OBJECT IDENTIFIER ::= { wtWebioEA12x6RelERPBasic 4 }
    wtWebioEA12x6RelERPUDP		OBJECT IDENTIFIER ::= { wtWebioEA12x6RelERPBasic 5 }	
    wtWebioEA12x6RelERPBinary		OBJECT IDENTIFIER ::= { wtWebioEA12x6RelERPBasic 6 }
    wtWebioEA12x6RelERPSyslog		OBJECT IDENTIFIER ::= { wtWebioEA12x6RelERPBasic 7 }
    wtWebioEA12x6RelERPFTP		OBJECT IDENTIFIER ::= { wtWebioEA12x6RelERPBasic 8 }
    wtWebioEA12x6RelERPWayBack		OBJECT IDENTIFIER ::= { wtWebioEA12x6RelERPBasic 10 }
    
--  wtWebioEA12x6RelERPTimeDate Tree

    wtWebioEA12x6RelERPTimeZone		OBJECT IDENTIFIER ::= { wtWebioEA12x6RelERPTimeDate 1 }
    wtWebioEA12x6RelERPTimeServer	OBJECT IDENTIFIER ::= { wtWebioEA12x6RelERPTimeDate 2 }	
    wtWebioEA12x6RelERPDeviceClock	OBJECT IDENTIFIER ::= { wtWebioEA12x6RelERPTimeDate 3 }    

--  wtIpWatcher Tree

    wtIpWatcherInOut      		OBJECT IDENTIFIER ::= { wtIpWatcher 1 }
    wtIpWatcherSessCntrl 		OBJECT IDENTIFIER ::= { wtIpWatcher 2 }
    wtIpWatcherConfig    		OBJECT IDENTIFIER ::= { wtIpWatcher 3 }
    wtIpWatcherDiag  			OBJECT IDENTIFIER ::= { wtIpWatcher 4 }

--  wtIpWatcherConfig Tree

    wtIpWatcherDevice    		OBJECT IDENTIFIER ::= { wtIpWatcherConfig 1 }
    wtIpWatcherPorts     		OBJECT IDENTIFIER ::= { wtIpWatcherConfig 2 }	
    wtIpWatcherManufact  		OBJECT IDENTIFIER ::= { wtIpWatcherConfig 3 }
    
--  wtIpWatcherDevice Tree

    wtIpWatcherText			OBJECT IDENTIFIER ::= { wtIpWatcherDevice 1 }
    wtIpWatcherTimeDate 		OBJECT IDENTIFIER ::= { wtIpWatcherDevice 2 }
    wtIpWatcherBasic 			OBJECT IDENTIFIER ::= { wtIpWatcherDevice 3 }
    wtIpWatcherAlarm			OBJECT IDENTIFIER ::= { wtIpWatcherDevice 5 }

--  wtIpWatcherBasic Tree

    wtIpWatcherNetwork			OBJECT IDENTIFIER ::= { wtIpWatcherBasic 1 }
    wtIpWatcherHTTP	 		OBJECT IDENTIFIER ::= { wtIpWatcherBasic 2 }
    wtIpWatcherMail			OBJECT IDENTIFIER ::= { wtIpWatcherBasic 3 }	
    wtIpWatcherSNMP	 		OBJECT IDENTIFIER ::= { wtIpWatcherBasic 4 }
    wtIpWatcherUDP			OBJECT IDENTIFIER ::= { wtIpWatcherBasic 5 }	
    wtIpWatcherSyslog			OBJECT IDENTIFIER ::= { wtIpWatcherBasic 7 }
    wtIpWatcherFTP			OBJECT IDENTIFIER ::= { wtIpWatcherBasic 8 }
    wtIpWatcherIpList			OBJECT IDENTIFIER ::= { wtIpWatcherBasic 11 }
    
--  wtIpWatcherTimeDate Tree

    wtIpWatcherTimeZone			OBJECT IDENTIFIER ::= { wtIpWatcherTimeDate 1 }
    wtIpWatcherTimeServer		OBJECT IDENTIFIER ::= { wtIpWatcherTimeDate 2 }	
    wtIpWatcherDeviceClock		OBJECT IDENTIFIER ::= { wtIpWatcherTimeDate 3 }   
    
--  wtWebioEA2x2-24V Tree

    wtWebioEA2x2-24VInOut      		OBJECT IDENTIFIER ::= { wtWebioEA2x2-24V 1 }
    wtWebioEA2x2-24VSessCntrl 		OBJECT IDENTIFIER ::= { wtWebioEA2x2-24V 2 }
    wtWebioEA2x2-24VConfig    		OBJECT IDENTIFIER ::= { wtWebioEA2x2-24V 3 }
    wtWebioEA2x2-24VDiag  		OBJECT IDENTIFIER ::= { wtWebioEA2x2-24V 4 }

--  wtWebioEA2x2-24VConfig Tree

    wtWebioEA2x2-24VDevice    		OBJECT IDENTIFIER ::= { wtWebioEA2x2-24VConfig 1 }
    wtWebioEA2x2-24VPorts     		OBJECT IDENTIFIER ::= { wtWebioEA2x2-24VConfig 2 }	
    wtWebioEA2x2-24VManufact  		OBJECT IDENTIFIER ::= { wtWebioEA2x2-24VConfig 3 }
    
--  wtWebioEA2x2-24VDevice Tree

    wtWebioEA2x2-24VText		OBJECT IDENTIFIER ::= { wtWebioEA2x2-24VDevice 1 }
    wtWebioEA2x2-24VTimeDate 		OBJECT IDENTIFIER ::= { wtWebioEA2x2-24VDevice 2 }
    wtWebioEA2x2-24VBasic 		OBJECT IDENTIFIER ::= { wtWebioEA2x2-24VDevice 3 }
    wtWebioEA2x2-24VOutputMode		OBJECT IDENTIFIER ::= { wtWebioEA2x2-24VDevice 4 }
    wtWebioEA2x2-24VAlarm		OBJECT IDENTIFIER ::= { wtWebioEA2x2-24VDevice 5 }

--  wtWebioEA2x2-24VBasic Tree

    wtWebioEA2x2-24VNetwork		OBJECT IDENTIFIER ::= { wtWebioEA2x2-24VBasic 1 }
    wtWebioEA2x2-24VHTTP	 	OBJECT IDENTIFIER ::= { wtWebioEA2x2-24VBasic 2 }
    wtWebioEA2x2-24VMail		OBJECT IDENTIFIER ::= { wtWebioEA2x2-24VBasic 3 }	
    wtWebioEA2x2-24VSNMP	 	OBJECT IDENTIFIER ::= { wtWebioEA2x2-24VBasic 4 }
    wtWebioEA2x2-24VUDP			OBJECT IDENTIFIER ::= { wtWebioEA2x2-24VBasic 5 }	
    wtWebioEA2x2-24VBinary		OBJECT IDENTIFIER ::= { wtWebioEA2x2-24VBasic 6 }
    wtWebioEA2x2-24VSyslog		OBJECT IDENTIFIER ::= { wtWebioEA2x2-24VBasic 7 }
    wtWebioEA2x2-24VFTP			OBJECT IDENTIFIER ::= { wtWebioEA2x2-24VBasic 8 }
    
--  wtWebioEA2x2-24VTimeDate Tree

    wtWebioEA2x2-24VTimeZone		OBJECT IDENTIFIER ::= { wtWebioEA2x2-24VTimeDate 1 }
    wtWebioEA2x2-24VTimeServer		OBJECT IDENTIFIER ::= { wtWebioEA2x2-24VTimeDate 2 }	
    wtWebioEA2x2-24VDeviceClock		OBJECT IDENTIFIER ::= { wtWebioEA2x2-24VTimeDate 3 }    
    
 --  wtWebioEA2x2ERP-24V Tree

    wtWebioEA2x2ERP-24VInOut      	OBJECT IDENTIFIER ::= { wtWebioEA2x2ERP-24V 1 }
    wtWebioEA2x2ERP-24VSessCntrl 	OBJECT IDENTIFIER ::= { wtWebioEA2x2ERP-24V 2 }
    wtWebioEA2x2ERP-24VConfig    	OBJECT IDENTIFIER ::= { wtWebioEA2x2ERP-24V 3 }
    wtWebioEA2x2ERP-24VDiag  		OBJECT IDENTIFIER ::= { wtWebioEA2x2ERP-24V 4 }

--  wtWebioEA2x2ERP-24VConfig Tree

    wtWebioEA2x2ERP-24VDevice    	OBJECT IDENTIFIER ::= { wtWebioEA2x2ERP-24VConfig 1 }
    wtWebioEA2x2ERP-24VPorts     	OBJECT IDENTIFIER ::= { wtWebioEA2x2ERP-24VConfig 2 }	
    wtWebioEA2x2ERP-24VManufact  	OBJECT IDENTIFIER ::= { wtWebioEA2x2ERP-24VConfig 3 }
    
--  wtWebioEA2x2ERP-24VDevice Tree

    wtWebioEA2x2ERP-24VText		OBJECT IDENTIFIER ::= { wtWebioEA2x2ERP-24VDevice 1 }
    wtWebioEA2x2ERP-24VTimeDate 	OBJECT IDENTIFIER ::= { wtWebioEA2x2ERP-24VDevice 2 }
    wtWebioEA2x2ERP-24VBasic 		OBJECT IDENTIFIER ::= { wtWebioEA2x2ERP-24VDevice 3 }
    wtWebioEA2x2ERP-24VOutputMode	OBJECT IDENTIFIER ::= { wtWebioEA2x2ERP-24VDevice 4 }
    wtWebioEA2x2ERP-24VAlarm		OBJECT IDENTIFIER ::= { wtWebioEA2x2ERP-24VDevice 5 }

--  wtWebioEA2x2ERP-24VBasic Tree

    wtWebioEA2x2ERP-24VNetwork		OBJECT IDENTIFIER ::= { wtWebioEA2x2ERP-24VBasic 1 }
    wtWebioEA2x2ERP-24VHTTP	 	OBJECT IDENTIFIER ::= { wtWebioEA2x2ERP-24VBasic 2 }
    wtWebioEA2x2ERP-24VMail		OBJECT IDENTIFIER ::= { wtWebioEA2x2ERP-24VBasic 3 }	
    wtWebioEA2x2ERP-24VSNMP	 	OBJECT IDENTIFIER ::= { wtWebioEA2x2ERP-24VBasic 4 }
    wtWebioEA2x2ERP-24VUDP		OBJECT IDENTIFIER ::= { wtWebioEA2x2ERP-24VBasic 5 }	
    wtWebioEA2x2ERP-24VBinary		OBJECT IDENTIFIER ::= { wtWebioEA2x2ERP-24VBasic 6 }
    wtWebioEA2x2ERP-24VSyslog		OBJECT IDENTIFIER ::= { wtWebioEA2x2ERP-24VBasic 7 }
    wtWebioEA2x2ERP-24VFTP		OBJECT IDENTIFIER ::= { wtWebioEA2x2ERP-24VBasic 8 }
    wtWebioEA2x2ERP-24VWayBack		OBJECT IDENTIFIER ::= { wtWebioEA2x2ERP-24VBasic 10 }
    
--  wtWebioEA2x2ERP-24VTimeDate Tree

    wtWebioEA2x2ERP-24VTimeZone		OBJECT IDENTIFIER ::= { wtWebioEA2x2ERP-24VTimeDate 1 }
    wtWebioEA2x2ERP-24VTimeServer	OBJECT IDENTIFIER ::= { wtWebioEA2x2ERP-24VTimeDate 2 }	
    wtWebioEA2x2ERP-24VDeviceClock	OBJECT IDENTIFIER ::= { wtWebioEA2x2ERP-24VTimeDate 3 }    


--  wtIpWatcher-24V Tree

    wtIpWatcher-24VInOut      		OBJECT IDENTIFIER ::= { wtIpWatcher-24V 1 }
    wtIpWatcher-24VSessCntrl 		OBJECT IDENTIFIER ::= { wtIpWatcher-24V 2 }
    wtIpWatcher-24VConfig    		OBJECT IDENTIFIER ::= { wtIpWatcher-24V 3 }
    wtIpWatcher-24VDiag  		OBJECT IDENTIFIER ::= { wtIpWatcher-24V 4 }

--  wtIpWatcher-24VConfig Tree

    wtIpWatcher-24VDevice    		OBJECT IDENTIFIER ::= { wtIpWatcher-24VConfig 1 }
    wtIpWatcher-24VPorts     		OBJECT IDENTIFIER ::= { wtIpWatcher-24VConfig 2 }	
    wtIpWatcher-24VManufact  		OBJECT IDENTIFIER ::= { wtIpWatcher-24VConfig 3 }

--  wtIpWatcher-24VDevice Tree

    wtIpWatcher-24VText			OBJECT IDENTIFIER ::= { wtIpWatcher-24VDevice 1 }
    wtIpWatcher-24VTimeDate 		OBJECT IDENTIFIER ::= { wtIpWatcher-24VDevice 2 }
    wtIpWatcher-24VBasic 		OBJECT IDENTIFIER ::= { wtIpWatcher-24VDevice 3 }
    wtIpWatcher-24VOutputMode		OBJECT IDENTIFIER ::= { wtIpWatcher-24VDevice 4 }
    wtIpWatcher-24VAlarm		OBJECT IDENTIFIER ::= { wtIpWatcher-24VDevice 5 }

--  wtIpWatcher-24VBasic Tree

    wtIpWatcher-24VNetwork		OBJECT IDENTIFIER ::= { wtIpWatcher-24VBasic 1 }
    wtIpWatcher-24VHTTP	 		OBJECT IDENTIFIER ::= { wtIpWatcher-24VBasic 2 }
    wtIpWatcher-24VMail			OBJECT IDENTIFIER ::= { wtIpWatcher-24VBasic 3 }	
    wtIpWatcher-24VSNMP	 		OBJECT IDENTIFIER ::= { wtIpWatcher-24VBasic 4 }
    wtIpWatcher-24VUDP			OBJECT IDENTIFIER ::= { wtIpWatcher-24VBasic 5 }	
    wtIpWatcher-24VSyslog		OBJECT IDENTIFIER ::= { wtIpWatcher-24VBasic 7 }
    wtIpWatcher-24VFTP			OBJECT IDENTIFIER ::= { wtIpWatcher-24VBasic 8 }
    wtIpWatcher-24VIpList		OBJECT IDENTIFIER ::= { wtIpWatcher-24VBasic 11 }

--  wtIpWatcher-24VTimeDate Tree

    wtIpWatcher-24VTimeZone		OBJECT IDENTIFIER ::= { wtIpWatcher-24VTimeDate 1 }
    wtIpWatcher-24VTimeServer		OBJECT IDENTIFIER ::= { wtIpWatcher-24VTimeDate 2 }	
    wtIpWatcher-24VDeviceClock		OBJECT IDENTIFIER ::= { wtIpWatcher-24VTimeDate 3 }


--  wtTrapReceiver2x2 Tree

    wtTrapReceiver2x2InOut      	OBJECT IDENTIFIER ::= { wtTrapReceiver2x2 1 }
    wtTrapReceiver2x2SessCntrl 		OBJECT IDENTIFIER ::= { wtTrapReceiver2x2 2 }
    wtTrapReceiver2x2Config    		OBJECT IDENTIFIER ::= { wtTrapReceiver2x2 3 }
    wtTrapReceiver2x2Diag  		OBJECT IDENTIFIER ::= { wtTrapReceiver2x2 4 }

--  wtTrapReceiver2x2Config Tree

    wtTrapReceiver2x2Device    		OBJECT IDENTIFIER ::= { wtTrapReceiver2x2Config 1 }
    wtTrapReceiver2x2Ports     		OBJECT IDENTIFIER ::= { wtTrapReceiver2x2Config 2 }	
    wtTrapReceiver2x2Manufact  		OBJECT IDENTIFIER ::= { wtTrapReceiver2x2Config 3 }

--  wtTrapReceiver2x2Device Tree

    wtTrapReceiver2x2Text		OBJECT IDENTIFIER ::= { wtTrapReceiver2x2Device 1 }
    wtTrapReceiver2x2TimeDate 		OBJECT IDENTIFIER ::= { wtTrapReceiver2x2Device 2 }
    wtTrapReceiver2x2Basic 		OBJECT IDENTIFIER ::= { wtTrapReceiver2x2Device 3 }
    wtTrapReceiver2x2OutputMode		OBJECT IDENTIFIER ::= { wtTrapReceiver2x2Device 4 }
    wtTrapReceiver2x2Action		OBJECT IDENTIFIER ::= { wtTrapReceiver2x2Device 5 }
    wtTrapReceiver2x2PrepareInEvents	OBJECT IDENTIFIER ::= { wtTrapReceiver2x2Device 6 }
    wtTrapReceiver2x2PrepareOutEvents	OBJECT IDENTIFIER ::= { wtTrapReceiver2x2Device 7 }
    

--  wtTrapReceiver2x2Basic Tree

    wtTrapReceiver2x2Network		OBJECT IDENTIFIER ::= { wtTrapReceiver2x2Basic 1 }
    wtTrapReceiver2x2HTTP	 	OBJECT IDENTIFIER ::= { wtTrapReceiver2x2Basic 2 }
    wtTrapReceiver2x2Mail		OBJECT IDENTIFIER ::= { wtTrapReceiver2x2Basic 3 }	
    wtTrapReceiver2x2SNMP	 	OBJECT IDENTIFIER ::= { wtTrapReceiver2x2Basic 4 }
    wtTrapReceiver2x2UDP		OBJECT IDENTIFIER ::= { wtTrapReceiver2x2Basic 5 }	
    wtTrapReceiver2x2Syslog		OBJECT IDENTIFIER ::= { wtTrapReceiver2x2Basic 7 }
    wtTrapReceiver2x2FTP		OBJECT IDENTIFIER ::= { wtTrapReceiver2x2Basic 8 }
    
--  wtTrapReceiver2x2TimeDate Tree

    wtTrapReceiver2x2TimeZone		OBJECT IDENTIFIER ::= { wtTrapReceiver2x2TimeDate 1 }
    wtTrapReceiver2x2TimeServer		OBJECT IDENTIFIER ::= { wtTrapReceiver2x2TimeDate 2 }	
    wtTrapReceiver2x2DeviceClock	OBJECT IDENTIFIER ::= { wtTrapReceiver2x2TimeDate 3 }   

-- wtTrapReceiver2x2PrepareInEvents
    wtTrapReceiver2x2WatchList		OBJECT IDENTIFIER ::= { wtTrapReceiver2x2PrepareInEvents 1 }
    wtTrapReceiver2x2InEvSystemTimer	OBJECT IDENTIFIER ::= { wtTrapReceiver2x2PrepareInEvents 2 }
    wtTrapReceiver2x2InEvButtons	OBJECT IDENTIFIER ::= { wtTrapReceiver2x2PrepareInEvents 3 }
    wtTrapReceiver2x2InEvInputs		OBJECT IDENTIFIER ::= { wtTrapReceiver2x2PrepareInEvents 4 }

-- wtTrapReceiver2x2PrepareOutEvents
    wtTrapReceiver2x2OutEvOutputs	OBJECT IDENTIFIER ::= { wtTrapReceiver2x2PrepareOutEvents 1 }
    
--------------------------------------------------------------------------------
--------------------------------------------------------------------------------
--------------------------------------------------------------------------------

-- wtWebioEA2x2InOut Group
------------------------

wtWebioEA2x2Inputs OBJECT-TYPE
    SYNTAX INTEGER (1..2)
    ACCESS read-only
    STATUS mandatory
    DESCRIPTION
        "Number of idependent inputs."
    ::= { wtWebioEA2x2InOut 1 }

wtWebioEA2x2Outputs OBJECT-TYPE
    SYNTAX INTEGER (1..2)
    ACCESS read-only
    STATUS mandatory
    DESCRIPTION
        "Number of idependent outputs."
    ::= { wtWebioEA2x2InOut 2 }

-- Input Interface Table

wtWebioEA2x2InputTable OBJECT-TYPE
    SYNTAX SEQUENCE OF WtWebioEA2x2InputEntry
    ACCESS not-accessible
    STATUS mandatory
    DESCRIPTION
        "List of input indices."
    ::= { wtWebioEA2x2InOut 3 }

wtWebioEA2x2InputEntry OBJECT-TYPE
    SYNTAX WtWebioEA2x2InputEntry
    ACCESS not-accessible
    STATUS mandatory
    DESCRIPTION
        "Number of the inputs."
    INDEX  { wtWebioEA2x2InputNo }
    ::= { wtWebioEA2x2InputTable 1 }

WtWebioEA2x2InputEntry ::= SEQUENCE {
    wtWebioEA2x2InputNo INTEGER,
    wtWebioEA2x2InputCounter INTEGER,
    wtWebioEA2x2InputCounterClear INTEGER,
    wtWebioEA2x2InputState INTEGER
    
}

wtWebioEA2x2InputNo OBJECT-TYPE
    SYNTAX INTEGER (1)
    ACCESS read-only
    STATUS mandatory
    DESCRIPTION
        "Index numbers of the inputs."
    ::= { wtWebioEA2x2InputEntry 1 }

wtWebioEA2x2InputCounter OBJECT-TYPE
    SYNTAX INTEGER (1)
    ACCESS read-only
    STATUS mandatory
    DESCRIPTION
        "Value of the input counter."
    ::= { wtWebioEA2x2InputEntry 2 }
    
wtWebioEA2x2InputCounterClear OBJECT-TYPE
    SYNTAX INTEGER
    ACCESS read-only
    STATUS mandatory
    DESCRIPTION
        "Clears the input counter after returning its value."
    ::= { wtWebioEA2x2InputEntry 3 }
    
wtWebioEA2x2InputState OBJECT-TYPE
    SYNTAX INTEGER{
    wtWebioEA2x2InputState-OFF(0),
    wtWebioEA2x2InputState-ON(1)
    }
    ACCESS read-only
    STATUS mandatory
    DESCRIPTION
        "Value of a single input bit."
    ::= { wtWebioEA2x2InputEntry 4 }    
    
wtWebioEA2x2InputValue OBJECT-TYPE
    SYNTAX INTEGER 
    ACCESS read-only
    STATUS mandatory
    DESCRIPTION
        "This variable is used to read the inputs of the digital I/O port.
        The OCTETS are interpreted bit-by-bit, with each bit corresponding to an output.
        Bit 0 corresponds to the LSB.
        OCTET 1: unused
        OCTET 2: unused
        OCTET 3: unused
        OCTET 4, Bit 0-1: Digital outputs 0-1"
    ::= { wtWebioEA2x2InOut 4 }
    

-- Output Interface Table

wtWebioEA2x2OutputTable OBJECT-TYPE
    SYNTAX SEQUENCE OF WtWebioEA2x2OutputEntry
    ACCESS not-accessible
    STATUS mandatory
    DESCRIPTION
        "List of output indices."
    ::= { wtWebioEA2x2InOut 5 }

wtWebioEA2x2OutputEntry OBJECT-TYPE
    SYNTAX WtWebioEA2x2OutputEntry
    ACCESS not-accessible
    STATUS mandatory
    DESCRIPTION
        "Number of the outputs."
    INDEX  { wtWebioEA2x2OutputNo }
    ::= { wtWebioEA2x2OutputTable 1 }

WtWebioEA2x2OutputEntry ::= SEQUENCE {
    wtWebioEA2x2OutputNo INTEGER,
    wtWebioEA2x2OutputState INTEGER    
}

wtWebioEA2x2OutputNo OBJECT-TYPE
    SYNTAX INTEGER (1)
    ACCESS read-only
    STATUS mandatory
    DESCRIPTION
        "Output number."
    ::= { wtWebioEA2x2OutputEntry 1 }

wtWebioEA2x2OutputState OBJECT-TYPE
    SYNTAX INTEGER{
    wtWebioEA2x2OutputState-OFF(0),
    wtWebioEA2x2OutputState-ON(1)
    }
    ACCESS read-write
    STATUS mandatory
    DESCRIPTION
        "Value of a single output bit."
    ::= { wtWebioEA2x2OutputEntry 2 }
    

wtWebioEA2x2OutputValue OBJECT-TYPE
    SYNTAX INTEGER
    ACCESS read-write
    STATUS mandatory
    DESCRIPTION
        "This variable is used to read and write the outputs of the digital I/O port. 
        The OCTETS are interpreted bit-by-bit, with each bit corresponding to an output. 
        Bit 0 corresponds to the LSB.
        OCTET 1: unused
        OCTET 2: unused
        OCTET 3: unused
        OCTET 4, Bit 0-1: Digital outputs 0-1
        	 Bit 2-7: ungenutzt"
    ::= { wtWebioEA2x2InOut 6 }
    
wtWebioEA2x2SetOutput OBJECT-TYPE
    SYNTAX OCTET STRING (SIZE (8))
    ACCESS read-write			-- write-only
    STATUS mandatory
    DESCRIPTION
        "This variable allows setting of individual digital outputs. The OCTETS are 
        interpreted bit-by-bit, with each bit corresponding to an output. Bit 0 corresponds 
        to the LSB.
        The first two OCTETS contain the mask which determines which of the outputs are to 
        be set (corresponding bit = 1) and which outputs are to remain unchanged 
        (corresponding bit = 0):
	OCTET 1 : unused
	OCTET 2 : unused
	OCTET 3 : unused
	OCTET 4, Bit 0-1: Mask for digital outputs 0-1
	
	OCTETS 5-8 contain the level (1=HIGH, 0=LOW) which the outputs 
	should assume:
	OCTET 5 : unused
	OCTET 6 : unused
	OCTET 7 : unused
        OCTET 8, Bit 0-1: Level of digital outputs 0-1"
    ::= { wtWebioEA2x2InOut 7 }
    
-- wtWebioEA2x2SessCntrl Group
--------------------------------

wtWebioEA2x2SessCntrlPassword OBJECT-TYPE
    SYNTAX OCTET STRING 
    ACCESS read-write
    STATUS mandatory
    DESCRIPTION
        "Entering this password opens a session which is ended by writing a 1 to 
        wtWebioEA2x2SessCntrlLogout. When read this variable provides a string of
        length zero."
    ::= { wtWebioEA2x2SessCntrl 1 }

wtWebioEA2x2SessCntrlConfigMode OBJECT-TYPE
    SYNTAX INTEGER {
    wtWebioEA2x2SessCntrl-NoSession(0),
    wtWebioEA2x2SessCntrl-Session(1)
    }
    ACCESS read-only
    STATUS mandatory
    DESCRIPTION
        "When the device is in SNMP configuration mode, the value 1 is
        returned, otherwise 0. If the read value is 0 even though the password
        was written, the device is already in config mode and the variables
        can only be read."
    ::= { wtWebioEA2x2SessCntrl 2 }

wtWebioEA2x2SessCntrlLogout OBJECT-TYPE
    SYNTAX INTEGER 
    ACCESS read-write
    STATUS mandatory
    DESCRIPTION
        "If the device is in configuration mode and the session was opened by
        this SNMP Manager, writing a 1 to this variable will end the session 
        and all parameters are stored.
        Writing a 2 discards all entries again. When read this variable
        provides the value 0."
    ::= { wtWebioEA2x2SessCntrl 3 }

wtWebioEA2x2SessCntrlAdminPassword OBJECT-TYPE
    SYNTAX OCTET STRING 
    ACCESS read-write
    STATUS mandatory
    DESCRIPTION
        "This password protects access to the variables with administrator rights.
        It can only be changed by the administrator. If no password was assigned,
        the valid password is public."
    ::= { wtWebioEA2x2SessCntrl 4 }

wtWebioEA2x2SessCntrlConfigPassword OBJECT-TYPE
    SYNTAX OCTET STRING 
    ACCESS read-write
    STATUS mandatory
    DESCRIPTION
        "This password protects access to the variables with configurator rights. It can
        be changed by the administrator and by the configurator. If no password was assigned, 
        the valid password is public. When read this variable provides a null-pointer."
    ::= { wtWebioEA2x2SessCntrl 5 }
    
-- wtWebioEA2x2Text Group
------------------------

wtWebioEA2x2DeviceName OBJECT-TYPE
    SYNTAX OCTET STRING 
    ACCESS read-write
    STATUS mandatory
    DESCRIPTION
        "Name of the Webio, which is user definable."
    ::= { wtWebioEA2x2Text 1 }

wtWebioEA2x2DeviceText OBJECT-TYPE
    SYNTAX OCTET STRING 
    ACCESS read-write
    STATUS mandatory
    DESCRIPTION
        "Description of the Webio, which is user definable."
    ::= { wtWebioEA2x2Text 2 }
    
wtWebioEA2x2DeviceLocation OBJECT-TYPE
    SYNTAX OCTET STRING 
    ACCESS read-write
    STATUS mandatory
    DESCRIPTION
        "Description of the location of the Webio, which is user definable."
    ::= { wtWebioEA2x2Text 3 }

wtWebioEA2x2DeviceContact OBJECT-TYPE
    SYNTAX OCTET STRING 
    ACCESS read-write
    STATUS mandatory
    DESCRIPTION
        "Contact address of the system operator of the Webio, which is user definable."
    ::= { wtWebioEA2x2Text 4 }    

-- wtWebioEA2x2TimeZone Group
----------------------------

wtWebioEA2x2TzOffsetHrs OBJECT-TYPE
    SYNTAX INTEGER 
    ACCESS read-write
    STATUS mandatory
    DESCRIPTION
        "Offset hours for the time zone (winter time) with respect to UTC."
    ::= { wtWebioEA2x2TimeZone 1 }

wtWebioEA2x2TzOffsetMin OBJECT-TYPE
    SYNTAX INTEGER 
    ACCESS read-write
    STATUS mandatory
    DESCRIPTION
        "Offset minutes for the time zone (winter time) with respect to UTC."
    ::= { wtWebioEA2x2TimeZone 2 }

wtWebioEA2x2TzEnable OBJECT-TYPE
    SYNTAX OCTET STRING (SIZE(4))
    ACCESS read-write
    STATUS mandatory
    DESCRIPTION
        "Binary coded conditions:
        Octet 1: unused
        Octet 2: unused
        Octet 3: unused
        Octet 4:
        	Bit 1-7: unused
	        Bit 0  : Apply Timezone"
    ::= { wtWebioEA2x2TimeZone 3 }

wtWebioEA2x2StTzOffsetHrs OBJECT-TYPE
    SYNTAX INTEGER 
    ACCESS read-write
    STATUS mandatory
    DESCRIPTION
        "Offset hours of the time zone (summer time) with respect to UTC."
    ::= { wtWebioEA2x2TimeZone 4 }

wtWebioEA2x2StTzOffsetMin OBJECT-TYPE
    SYNTAX INTEGER 
    ACCESS read-write
    STATUS mandatory
    DESCRIPTION
        "Offset minutes of the time zone (summer time) with respect to UTC."
    ::= { wtWebioEA2x2TimeZone 5 }

wtWebioEA2x2StTzEnable OBJECT-TYPE
    SYNTAX OCTET STRING (SIZE(4))
    ACCESS read-write
    STATUS mandatory
    DESCRIPTION
        "Binary coded conditions:
        Octet 1: unused
        Octet 2: unused
        Octet 3: unused
        Octet 4:
        	Bit 1-7: unused
	        Bit 0  : Apply Summertime"
    ::= { wtWebioEA2x2TimeZone 6 }

wtWebioEA2x2StTzStartMonth OBJECT-TYPE
    SYNTAX INTEGER {
    	wtWebioEA2x2StartMonth-January(1),
    	wtWebioEA2x2StartMonth-February(2),
    	wtWebioEA2x2StartMonth-March(3),
    	wtWebioEA2x2StartMonth-April(4),
    	wtWebioEA2x2StartMonth-May(5),
    	wtWebioEA2x2StartMonth-June(6),
    	wtWebioEA2x2StartMonth-July(7),
    	wtWebioEA2x2StartMonth-August(8),
    	wtWebioEA2x2StartMonth-September(9),
    	wtWebioEA2x2StartMonth-October(10),
    	wtWebioEA2x2StartMonth-November(11),
    	wtWebioEA2x2StartMonth-December(12)
    	}
    	
    ACCESS read-write
    STATUS mandatory
    DESCRIPTION
        "Month in which the change is made from winter time to summer time."
    ::= { wtWebioEA2x2TimeZone 7 }

wtWebioEA2x2StTzStartMode OBJECT-TYPE
    SYNTAX INTEGER {
    	wtWebioEA2x2StartMode-first(1),
    	wtWebioEA2x2StartMode-second(2),
    	wtWebioEA2x2StartMode-third(3),
    	wtWebioEA2x2StartMode-fourth(4),
    	wtWebioEA2x2StartMode-last(5)
    	}
    	
    ACCESS read-write
    STATUS mandatory
    DESCRIPTION
        "Mode of the day of the week for which the change is made from winter time to summer time."
    ::= { wtWebioEA2x2TimeZone 8 }

wtWebioEA2x2StTzStartWday OBJECT-TYPE
    SYNTAX INTEGER {
    	wtWebioEA2x2StartWday-Sunday(1),
    	wtWebioEA2x2StartWday-Monday(2),
    	wtWebioEA2x2StartWday-Tuesday(3),
    	wtWebioEA2x2StartWday-Thursday(4),
    	wtWebioEA2x2StartWday-Wednesday(5),
    	wtWebioEA2x2StartWday-Friday(6),
    	wtWebioEA2x2StartWday-Saturday(7)
    	}
    	
    ACCESS read-write
    STATUS mandatory
    DESCRIPTION
        "Day of the week on which the change is made from winter time to summer time"
    ::= { wtWebioEA2x2TimeZone 9 }
    
wtWebioEA2x2StTzStartHrs OBJECT-TYPE
    SYNTAX INTEGER 
    ACCESS read-write
    STATUS mandatory
    DESCRIPTION
        "Hour in which the time zone is changed from winter to summer time with
        respect to UTC."
    ::= { wtWebioEA2x2TimeZone 10 }

wtWebioEA2x2StTzStartMin OBJECT-TYPE
    SYNTAX INTEGER 
    ACCESS read-write
    STATUS mandatory
    DESCRIPTION
        "Minute in which the time zone is changed from winter to summer time with
        respect to UTC."
    ::= { wtWebioEA2x2TimeZone 11 }
 
wtWebioEA2x2StTzStopMonth OBJECT-TYPE
    SYNTAX INTEGER {
    	wtWebioEA2x2StopMonth-January(1),
    	wtWebioEA2x2StopMonth-February(2),
    	wtWebioEA2x2StopMonth-March(3),
    	wtWebioEA2x2StopMonth-April(4),
    	wtWebioEA2x2StopMonth-May(5),
    	wtWebioEA2x2StopMonth-June(6),
    	wtWebioEA2x2StopMonth-July(7),
    	wtWebioEA2x2StopMonth-August(8),
    	wtWebioEA2x2StopMonth-September(9),
    	wtWebioEA2x2StopMonth-October(10),
    	wtWebioEA2x2StopMonth-November(11),
    	wtWebioEA2x2StopMonth-December(12)
    	}
    ACCESS read-write
    STATUS mandatory
    DESCRIPTION
        "Month in which the change is made from summer time to winter time."
   ::= { wtWebioEA2x2TimeZone 12 }

wtWebioEA2x2StTzStopMode OBJECT-TYPE
    SYNTAX INTEGER {
    	wtWebioEA2x2StopMode-first(1),
    	wtWebioEA2x2StopMode-second(2),
    	wtWebioEA2x2StopMode-third(3),
    	wtWebioEA2x2StopMode-fourth(4),
    	wtWebioEA2x2StopMode-last(5)
    	}
    ACCESS read-write
    STATUS mandatory
    DESCRIPTION
        "Mode of the week day on which the change is made from summer time to winter time."
    ::= { wtWebioEA2x2TimeZone 13 }

wtWebioEA2x2StTzStopWday OBJECT-TYPE
    SYNTAX INTEGER {
    	wtWebioEA2x2StopWday-Sunday(1),
    	wtWebioEA2x2StopWday-Monday(2),
    	wtWebioEA2x2StopWday-Tuesday(3),
    	wtWebioEA2x2StopWday-Thursday(4),
    	wtWebioEA2x2StopWday-Wednesday(5),
    	wtWebioEA2x2StopWday-Friday(6),
    	wtWebioEA2x2StopWday-Saturday(7)
    	}
    ACCESS read-write
    STATUS mandatory
    DESCRIPTION
        "Day of the week on which the change is made from summer time to winter time."
    ::= { wtWebioEA2x2TimeZone 14 }
    
wtWebioEA2x2StTzStopHrs OBJECT-TYPE
    SYNTAX INTEGER 
    ACCESS read-write
    STATUS mandatory
    DESCRIPTION
        "Hour at which the time zone is changed from summer to winter time with
        respect to UTC."
    ::= { wtWebioEA2x2TimeZone 15 }

wtWebioEA2x2StTzStopMin OBJECT-TYPE
    SYNTAX INTEGER 
    ACCESS read-write
    STATUS mandatory
    DESCRIPTION
        "Minute at which the time zone is changed from summer to winter time with
        respect to UTC."
    ::= { wtWebioEA2x2TimeZone 16 }

-- wtWebioEA2x2TimeServer Group
----------------------------

wtWebioEA2x2TimeServer1 OBJECT-TYPE
    SYNTAX OCTET STRING 
    ACCESS read-write
    STATUS mandatory
    DESCRIPTION
        "IP address or name of the 1st time server in ASCII"
    ::= { wtWebioEA2x2TimeServer 1 }

wtWebioEA2x2TimeServer2 OBJECT-TYPE
    SYNTAX OCTET STRING 
    ACCESS read-write
    STATUS mandatory
    DESCRIPTION
        "IP address or name of the 2nd time server in ASCII"
    ::= { wtWebioEA2x2TimeServer 2 }

wtWebioEA2x2TsEnable OBJECT-TYPE
    SYNTAX OCTET STRING (SIZE(4))
    ACCESS read-write
    STATUS mandatory
    DESCRIPTION
        "Binary coded conditions:
        Octet 1: unused
        Octet 2: unused
        Octet 3: unused
        Octet 4:
        	Bit 1-7: unused
	        Bit 0  : Apply Time Server"
    ::= { wtWebioEA2x2TimeServer 3 }

wtWebioEA2x2TsSyncTime OBJECT-TYPE
    SYNTAX INTEGER 
    ACCESS read-write
    STATUS mandatory
    DESCRIPTION
        "Daily synchronisation time with the time server (hour: 0-23)."
    ::= { wtWebioEA2x2TimeServer 4 }
      
    
-- wtWebioEA2x2DeviceClock Group
----------------------------

wtWebioEA2x2ClockHrs OBJECT-TYPE
    SYNTAX INTEGER (0..23)
    ACCESS read-write
    STATUS mandatory
    DESCRIPTION
        "Clock hours taking into account the time zone settings."
    ::= { wtWebioEA2x2DeviceClock 1 }

wtWebioEA2x2ClockMin OBJECT-TYPE
    SYNTAX INTEGER (0..59)
    ACCESS read-write
    STATUS mandatory
    DESCRIPTION
        "Clock minutes taking into account the time zone settings."
    ::= { wtWebioEA2x2DeviceClock 2 }

wtWebioEA2x2ClockDay OBJECT-TYPE
    SYNTAX INTEGER (1..31)
    ACCESS read-write
    STATUS mandatory
    DESCRIPTION
        "Date: Day of the month, taking into account the time zone settings."
    ::= { wtWebioEA2x2DeviceClock 3 }

wtWebioEA2x2ClockMonth OBJECT-TYPE
   SYNTAX INTEGER {
    	wtWebioEA2x2ClockMonth-January(1),
    	wtWebioEA2x2ClockMonth-February(2),
    	wtWebioEA2x2ClockMonth-March(3),
    	wtWebioEA2x2ClockMonth-April(4),
    	wtWebioEA2x2ClockMonth-May(5),
    	wtWebioEA2x2ClockMonth-June(6),
    	wtWebioEA2x2ClockMonth-July(7),
    	wtWebioEA2x2ClockMonth-August(8),
    	wtWebioEA2x2ClockMonth-September(9),
    	wtWebioEA2x2ClockMonth-October(10),
    	wtWebioEA2x2ClockMonth-November(11),
    	wtWebioEA2x2ClockMonth-December(12)
    	}
    ACCESS read-write
    STATUS mandatory
    DESCRIPTION
        "Date: Month, taking into account the time zone settings."
    ::= { wtWebioEA2x2DeviceClock 4 }

wtWebioEA2x2ClockYear OBJECT-TYPE
    SYNTAX INTEGER (0..65535)
    ACCESS read-write
    STATUS mandatory
    DESCRIPTION
        "Date: Year, taking into account the time zone settings."
    ::= { wtWebioEA2x2DeviceClock 5 }

-- wtWebioEA2x2Network Group
------------------------

wtWebioEA2x2IpAddress OBJECT-TYPE
    SYNTAX IpAddress
    ACCESS read-write
    STATUS mandatory
    DESCRIPTION
        "IP address of the Webio"
    ::= { wtWebioEA2x2Network 1 }

wtWebioEA2x2SubnetMask OBJECT-TYPE
    SYNTAX IpAddress
    ACCESS read-write
    STATUS mandatory
    DESCRIPTION
        "Subnet mask of the Webio"
    ::= { wtWebioEA2x2Network 2 }

wtWebioEA2x2Gateway OBJECT-TYPE
    SYNTAX IpAddress
    ACCESS read-write
    STATUS mandatory
    DESCRIPTION
        "Gateway of the Webio"
    ::= { wtWebioEA2x2Network 3 }

wtWebioEA2x2DnsServer1 OBJECT-TYPE
    SYNTAX OCTET STRING 
    ACCESS read-write
    STATUS mandatory
    DESCRIPTION
        "IP address of the 1st DNS server in ASCII"
    ::= { wtWebioEA2x2Network 4 }

wtWebioEA2x2DnsServer2 OBJECT-TYPE
    SYNTAX OCTET STRING 
    ACCESS read-write
    STATUS mandatory
    DESCRIPTION
        "IP address of the 2nd DNS server in ASCII"
    ::= { wtWebioEA2x2Network 5 }

wtWebioEA2x2AddConfig OBJECT-TYPE
    SYNTAX OCTET STRING 
    ACCESS read-write
    STATUS mandatory
    DESCRIPTION
        "Additional configuration (1=ON):
        Octet 1: unused
        Octet 2: unused
        Octet 3: unused
        Octet 4:
	        Bit 1: DHCP  enable
	        Bit 0: BOOTP enable"
    ::= { wtWebioEA2x2Network 6 }

--  wtWebioEA2x2HTTP Group
--------------------------------

wtWebioEA2x2Startup OBJECT-TYPE
    SYNTAX OCTET STRING 
    ACCESS read-write
    STATUS mandatory
    DESCRIPTION
        "Binary coded start page, more than one page must not be selected:
        Octet 1: unused
        Octet 2: unused
        Octet 3: unused
        Octet 4:
        	Bit 2: user.htm
        	Bit 1: home.htm
	        Bit 0: index.htm"
    ::= { wtWebioEA2x2HTTP 1 }

wtWebioEA2x2GetHeaderEnable OBJECT-TYPE
    SYNTAX OCTET STRING 
    ACCESS read-write
    STATUS mandatory
    DESCRIPTION
        "If bits are set, every answer of a short form GET question will be lead
        by the IP-address and name of the device (Header) or a HTTP header (HTTP):
        Octet 1: unused
        Octet 2: unused
        Octet 3: unused
        Octet 4:
        	Bit 2-7: unused
        	Bit 1  : GET HTTP enable
                Bit 0  : GET Header enable"
    ::= { wtWebioEA2x2HTTP 2 }

wtWebioEA2x2HttpInputTrigger OBJECT-TYPE
    SYNTAX OCTET STRING (SIZE (4))
    ACCESS read-write
    STATUS mandatory
    DESCRIPTION
        "Every change on the inputs causes their state to be transmitted to the 
        remote device. To minimize data traffic, individual inputs may be exempted 
        from this rule. Nevertheless every transmission will contain all input bits.
        If a bit is set (1), a change of state on the corresponding input 
        triggers a transmission. If the bit is not set (0), no transmission 
        takes place.
        The OCTETS are interpreted bit-by-bit, with each bit corresponding to an input. 
        Bit 0 corresponds to the LSB.
        OCTET 1: unused
        OCTET 2: unused
        OCTET 3: unused
        OCTET 4, Bit 0-1: Digital inputs 0-1"
    ::= { wtWebioEA2x2HTTP 3 }

wtWebioEA2x2HttpPort OBJECT-TYPE
    SYNTAX INTEGER (1..65534)
    ACCESS read-write
    STATUS mandatory
    DESCRIPTION
       "Definition of the standard HTML port (Default: 80)."
    ::= { wtWebioEA2x2HTTP 4 }        
    
    
-- wtWebioEA2x2Mail Group
--------------------------------

wtWebioEA2x2MailAdName OBJECT-TYPE
    SYNTAX OCTET STRING 
    ACCESS read-write
    STATUS mandatory
    DESCRIPTION
        "Device name for mail administration."
    ::= { wtWebioEA2x2Mail 1 }
    
wtWebioEA2x2MailReply OBJECT-TYPE
    SYNTAX OCTET STRING 
    ACCESS read-write
    STATUS mandatory
    DESCRIPTION
        "Reply address for the mail server."
    ::= { wtWebioEA2x2Mail 2 }
    
wtWebioEA2x2MailServer OBJECT-TYPE
    SYNTAX OCTET STRING 
    ACCESS read-write
    STATUS mandatory
    DESCRIPTION
        "Name or IP address of the mail server."
    ::= { wtWebioEA2x2Mail 3 }
    
wtWebioEA2x2MailEnable OBJECT-TYPE
    SYNTAX OCTET STRING 
    ACCESS read-write
    STATUS mandatory
    DESCRIPTION
        "Set this bit to enable the sending of mails:
        Octet 1: unused
        Octet 2: unused
        Octet 3: unused
        Octet 4:
        	Bit 1-7: unused
                Bit 0  : Mail enable"
    ::= { wtWebioEA2x2Mail 4 }

wtWebioEA2x2MailAuthentication OBJECT-TYPE
    SYNTAX OCTET STRING (SIZE (4))
    ACCESS read-write
    STATUS mandatory
    DESCRIPTION
        "Selection of the authentication modi:
        The OCTETS are interpreted bit-by-bit,
        Bit 0 corresponds to the LSB.
        OCTET 1: unused
        OCTET 2: unused
        OCTET 3: unused
        OCTET 4: Bit 3-7: unused
        	 Bit 2  : POP3 before SMTP
        	 Bit 1  : ESMTP, authentication
        	 Bit 0  : SMTP, no authentication"
    ::= { wtWebioEA2x2Mail 5 }
    
wtWebioEA2x2MailAuthUser OBJECT-TYPE
    SYNTAX OCTET STRING 
    ACCESS read-write
    STATUS mandatory
    DESCRIPTION
        "Name of the user to be authenticated."
    ::= { wtWebioEA2x2Mail 6 }    
    
wtWebioEA2x2MailAuthPassword OBJECT-TYPE
    SYNTAX OCTET STRING 
    ACCESS read-write
    STATUS mandatory
    DESCRIPTION
        "Authentication password."
    ::= { wtWebioEA2x2Mail 7 }    
    
wtWebioEA2x2MailPop3Server OBJECT-TYPE
    SYNTAX OCTET STRING 
    ACCESS read-write
    STATUS mandatory
    DESCRIPTION
        "Name or Ip-address of the POP3 Servers."
    ::= { wtWebioEA2x2Mail 8 }        
    

--  wtWebioEA2x2Snmp Group
--------------------------------

wtWebioEA2x2SnmpEnable OBJECT-TYPE
    SYNTAX OCTET STRING 
    ACCESS read-write
    STATUS mandatory
    DESCRIPTION
        "Set bit 0 to enable SNMP.
        If disabled, the device did not respond to any SNMP requests.
        Bit 1 decided wether the community string of read operations 
        is compared with the system password or not:
        Octet 1: unused
        Octet 2: unused
        Octet 3: unused
        Octet 4:
        	Bit 1-7: unused
        	Bit 0  : SNMP enable"
    ::= { wtWebioEA2x2SNMP 1 }
    
wtWebioEA2x2SnmpCommunityStringRead OBJECT-TYPE
    SYNTAX OCTET STRING
    ACCESS read-write
    STATUS mandatory
    DESCRIPTION
        "Community string read only"
    ::= { wtWebioEA2x2SNMP 2 }

wtWebioEA2x2SnmpCommunityStringReadWrite OBJECT-TYPE
    SYNTAX OCTET STRING
    ACCESS read-write
    STATUS mandatory
    DESCRIPTION
        "Community string read / write"
    ::= { wtWebioEA2x2SNMP 3 }

wtWebioEA2x2SnmpSystemTrapManagerIP OBJECT-TYPE
    SYNTAX OCTET STRING 
    ACCESS read-write
    STATUS mandatory
    DESCRIPTION
        "Name or IP address of the TCP server which accepts the system trap."
    ::= { wtWebioEA2x2SNMP 4 }
    
wtWebioEA2x2SnmpSystemTrapEnable OBJECT-TYPE
    SYNTAX OCTET STRING (SIZE(4))
    ACCESS read-write
    STATUS mandatory
    DESCRIPTION
        "Binary coded trigger conditions:
        Octet 1: unused
        Octet 2: unused
        Octet 3: unused
        Octet 4:
	        Bit 0:   ColdStart
	        Bit 1:   WarmStart
	        Bit 2:   Diag messages
	        Bit 3-7: unused"
    ::= { wtWebioEA2x2SNMP 5 }    

-- wtWebioEA2x2UDP Group
--------------------------------   

wtWebioEA2x2UdpAdminPort OBJECT-TYPE
    SYNTAX INTEGER
    ACCESS read-write
    STATUS mandatory
    DESCRIPTION
        "Udp port to which the Udp queries ( short form GET requests) can be sent. This
        port number must be unique within the device."
    ::= { wtWebioEA2x2UDP 1 }

wtWebioEA2x2UdpEnable OBJECT-TYPE
    SYNTAX OCTET STRING 
    ACCESS read-write
    STATUS mandatory
    DESCRIPTION
        "Set this bit to enable UDP support:
        Octet 1: unused
        Octet 2: unused
        Octet 3: unused
        Octet 4:
        	Bit 1-7: unused
                Bit 0  : UDP enable"
    ::= { wtWebioEA2x2UDP 2 }

wtWebioEA2x2UdpRemotePort OBJECT-TYPE
    SYNTAX INTEGER
    ACCESS read-write
    STATUS mandatory
    DESCRIPTION
        "Udp remote port setting.
        If this value is set to zero, the source port read from a request will be used 
        as destination port for the answer.
        A non zero value forced the destination port to this value."
    ::= { wtWebioEA2x2UDP 3 }
    
--  wtWebioEA2x2Binary Group
--------------------------------

wtWebioEA2x2BinaryModeCount OBJECT-TYPE
    SYNTAX INTEGER (1..2)
    ACCESS read-only
    STATUS mandatory
    DESCRIPTION
        "Number of independent binary channels."
    ::= { wtWebioEA2x2Binary 1 }
    
-- Binary Interface Table

wtWebioEA2x2BinaryIfTable OBJECT-TYPE
    SYNTAX SEQUENCE OF WtWebioEA2x2BinaryIfEntry
    ACCESS not-accessible
    STATUS mandatory
    DESCRIPTION
        "Table of indices."
    ::= { wtWebioEA2x2Binary 2 }

wtWebioEA2x2BinaryIfEntry OBJECT-TYPE
    SYNTAX WtWebioEA2x2BinaryIfEntry
    ACCESS not-accessible
    STATUS mandatory
    DESCRIPTION
        "Indices of the binary channels."
    INDEX  { wtWebioEA2x2BinaryModeNo }
    ::= { wtWebioEA2x2BinaryIfTable 1 }

WtWebioEA2x2BinaryIfEntry ::= SEQUENCE {
    wtWebioEA2x2BinaryModeNo INTEGER
}

wtWebioEA2x2BinaryModeNo OBJECT-TYPE
    SYNTAX INTEGER (1..2)
    ACCESS read-only
    STATUS mandatory
    DESCRIPTION
        "Number of the binary channel."
    ::= { wtWebioEA2x2BinaryIfEntry 1 }

-- Binary Table
--------------------------------

wtWebioEA2x2BinaryTable OBJECT-TYPE
    SYNTAX SEQUENCE OF WtWebioEA2x2BinaryEntry
    ACCESS not-accessible
    STATUS mandatory
    DESCRIPTION
        "Table of properties of the binary mode."
    ::= { wtWebioEA2x2Binary 3 }

wtWebioEA2x2BinaryEntry OBJECT-TYPE
    SYNTAX WtWebioEA2x2BinaryEntry
    ACCESS not-accessible
    STATUS mandatory
    DESCRIPTION
        "Binary properties."
    INDEX  { wtWebioEA2x2BinaryModeNo }
    ::= { wtWebioEA2x2BinaryTable 1 }

WtWebioEA2x2BinaryEntry ::= SEQUENCE {
    wtWebioEA2x2BinaryOperationMode			OCTET STRING,
    wtWebioEA2x2BinaryTcpServerLocalPort		INTEGER,
    wtWebioEA2x2BinaryTcpServerInputTrigger		OCTET STRING,
    wtWebioEA2x2BinaryTcpServerApplicationMode		OCTET STRING,
    wtWebioEA2x2BinaryTcpClientLocalPort		INTEGER,
    wtWebioEA2x2BinaryTcpClientServerPort		INTEGER,
    wtWebioEA2x2BinaryTcpClientServerIpAddr		OCTET STRING,
    wtWebioEA2x2BinaryTcpClientServerPassword		OCTET STRING,
    wtWebioEA2x2BinaryTcpClientInactivity		INTEGER,
    wtWebioEA2x2BinaryTcpClientInputTrigger		OCTET STRING,
    wtWebioEA2x2BinaryTcpClientInterval			INTEGER,
    wtWebioEA2x2BinaryTcpClientApplicationMode		OCTET STRING,
    wtWebioEA2x2BinaryUdpPeerLocalPort			INTEGER,
    wtWebioEA2x2BinaryUdpPeerRemotePort			INTEGER,
    wtWebioEA2x2BinaryUdpPeerRemoteIpAddr		OCTET STRING,
    wtWebioEA2x2BinaryUdpPeerInputTrigger		OCTET STRING,
    wtWebioEA2x2BinaryUdpPeerInterval			INTEGER,
    wtWebioEA2x2BinaryUdpPeerApplicationMode		OCTET STRING,
    wtWebioEA2x2BinaryConnectedPort			INTEGER,
    wtWebioEA2x2BinaryConnectedIpAddr			IpAddress,
    wtWebioEA2x2BinaryTcpServerClientHttpPort		INTEGER,
    wtWebioEA2x2BinaryTcpClientServerHttpPort		INTEGER
    
}

wtWebioEA2x2BinaryOperationMode OBJECT-TYPE
    SYNTAX OCTET STRING (SIZE (4))
    ACCESS read-write
    STATUS mandatory
    DESCRIPTION
        "Selection of the operation mode:
        The OCTETS are interpreted bit-by-bit,
        Bit 0 corresponds to the LSB.
        OCTET 1: unused
        OCTET 2: unused
        OCTET 3: unused
        OCTET 4: Bit 3-7: unused
        	 Bit 2  : UDP Peer
        	 Bit 1  : TCP Client
        	 Bit 0  : TCP Server"
    ::= { wtWebioEA2x2BinaryEntry 1 }

wtWebioEA2x2BinaryTcpServerLocalPort OBJECT-TYPE
    SYNTAX INTEGER (1..65535)
    ACCESS read-write
    STATUS mandatory
    DESCRIPTION
        "Local TCP port for data exchange in this server mode.
        This port number must be unique within the device.
	Reserved port number must not be used (refere to the manual)."
    ::= { wtWebioEA2x2BinaryEntry 2 }

wtWebioEA2x2BinaryTcpServerInputTrigger OBJECT-TYPE
    SYNTAX OCTET STRING (SIZE (4))
    ACCESS read-write
    STATUS mandatory
    DESCRIPTION
        "Every change on the inputs causes their state to be transmitted to the 
        remote device. To minimize data traffic, individual inputs may be exempted 
        from this rule. Nevertheless every transmission will contain all input bits.
        If a bit is set (1), a change of state on the corresponding input 
        triggers a transmission. If the bit is not set (0), no transmission 
        takes place.
        The OCTETS are interpreted bit-by-bit, with each bit corresponding to an input. 
        Bit 0 corresponds to the LSB.
        OCTET 1: unused
        OCTET 2: unused
        OCTET 3: unused
        OCTET 4, Bit 0-1: Digital inputs 0-1"
    ::= { wtWebioEA2x2BinaryEntry 3 }

wtWebioEA2x2BinaryTcpServerApplicationMode OBJECT-TYPE
    SYNTAX OCTET STRING (SIZE (4))
    ACCESS read-write
    STATUS mandatory
    DESCRIPTION
        "Selection of the application mode:
        The OCTETS are interpreted bit-by-bit,
        Bit 0 corresponds to the LSB.
        OCTET 1: unused
        OCTET 2: unused
        OCTET 3: unused
        OCTET 4: Bit 4-7: unused
        	 Bit 3  : OPC Device
        	 Bit 2  : Box2Box Slave
        	 Bit 1  : Compatible 50xxx
        	 Bit 0  : Default"
    ::= { wtWebioEA2x2BinaryEntry 4 }
    
wtWebioEA2x2BinaryTcpClientLocalPort OBJECT-TYPE
    SYNTAX INTEGER (1..65535)
    ACCESS read-write
    STATUS mandatory
    DESCRIPTION
        "Local TCP port for data exchange in this client mode.
        This port number must be unique within the device.
	Reserved port number must not be used (refere to the manual)."
    ::= { wtWebioEA2x2BinaryEntry 5 }

wtWebioEA2x2BinaryTcpClientServerPort OBJECT-TYPE
    SYNTAX INTEGER (1..65535)
    ACCESS read-write
    STATUS mandatory
    DESCRIPTION
        "Port number of the server. A complete set of port number, IP address
        and a valid input/output mask starts this mode.
        No data exchange take place when setting the server port to zero."
    ::= { wtWebioEA2x2BinaryEntry 6 }

wtWebioEA2x2BinaryTcpClientServerIpAddr OBJECT-TYPE
    SYNTAX OCTET STRING
    ACCESS read-write
    STATUS mandatory
    DESCRIPTION
        "Ip address of the server. A complete set of port number, IP address
        and a valid input/output mask starts this mode.
        No data exchange take place when setting the server IP address to 0.0.0.0."
    ::= { wtWebioEA2x2BinaryEntry 7 }

wtWebioEA2x2BinaryTcpClientServerPassword OBJECT-TYPE
    SYNTAX OCTET STRING
    ACCESS read-write
    STATUS mandatory
    DESCRIPTION
        "Building a connection may be protected by the 
        administrator password of the server. Enter the server password
        to establish the connection, if a server administrator password
        exists."
    ::= { wtWebioEA2x2BinaryEntry 8 }

wtWebioEA2x2BinaryTcpClientInactivity OBJECT-TYPE
    SYNTAX INTEGER 
    ACCESS read-write
    STATUS mandatory
    DESCRIPTION
        "Connection timeout in 100ms. If no data are exchanged within the specified  
        time, the device closes the connection to the server.
        The value 0 deactivates the timer. Using the Box2Box mode this function is
        disabled."
    ::= { wtWebioEA2x2BinaryEntry 9 }
    
wtWebioEA2x2BinaryTcpClientInputTrigger OBJECT-TYPE
    SYNTAX OCTET STRING (SIZE (4))
    ACCESS read-write
    STATUS mandatory
    DESCRIPTION
        "Every change on the inputs causes their state to be transmitted to the 
        remote device. To minimize data traffic, individual inputs may be exempted 
        from this rule. Nevertheless every transmission will contain all input bits.
        If a bit is set (1), a change of state on the corresponding input 
        triggers a transmission. If the bit is not set (0), no transmission 
        takes place.
        The OCTETS are interpreted bit-by-bit, with each bit corresponding to an input. 
        Bit 0 corresponds to the LSB.
        OCTET 1: unused
        OCTET 2: unused
        OCTET 3: unused
        OCTET 4, Bit 0-1: Digital inputs 0-1"
    ::= { wtWebioEA2x2BinaryEntry 10 }
 
wtWebioEA2x2BinaryTcpClientInterval OBJECT-TYPE
    SYNTAX INTEGER (0..65535)
    ACCESS read-write
    STATUS mandatory
    DESCRIPTION
        "Configurable interval with a 100ms base, in which the Webio device sends
        data to the configured application. A interval of zero stopps the 
        periodical sending."
    ::= { wtWebioEA2x2BinaryEntry 11 }

wtWebioEA2x2BinaryTcpClientApplicationMode OBJECT-TYPE
    SYNTAX OCTET STRING (SIZE (4))
    ACCESS read-write
    STATUS mandatory
    DESCRIPTION
        "Selection of the application mode:
        The OCTETS are interpreted bit-by-bit,
        Bit 0 corresponds to the LSB.
        OCTET 1: unused
        OCTET 2: unused
        OCTET 3: unused
        OCTET 4: Bit 3-7: unused
        	 Bit 2  : Box2Box Slave
        	 Bit 1  : Compatible 50xxx
        	 Bit 0  : Default"
    ::= { wtWebioEA2x2BinaryEntry 12 }

wtWebioEA2x2BinaryUdpPeerLocalPort OBJECT-TYPE
    SYNTAX INTEGER (1..65535)
    ACCESS read-write
    STATUS mandatory
    DESCRIPTION
        "Local UDP port for data exchange in this peer to peer mode.
        This port number must be unique within the device.
	Reserved port number must not be used (refere to the manual)."
    ::= { wtWebioEA2x2BinaryEntry 13 }

wtWebioEA2x2BinaryUdpPeerRemotePort OBJECT-TYPE
    SYNTAX INTEGER (1..65535)
    ACCESS read-write
    STATUS mandatory
    DESCRIPTION
        "Port number of the remote device. A complete set of port number, IP address
        and a valid input/output mask starts this mode.
        No data exchange take place when setting the remote port to zero."
    ::= { wtWebioEA2x2BinaryEntry 14 }

wtWebioEA2x2BinaryUdpPeerRemoteIpAddr OBJECT-TYPE
    SYNTAX OCTET STRING
    ACCESS read-write
    STATUS mandatory
    DESCRIPTION
        "Ip address of the remote device. A complete set of port number, IP address
        and a valid input/output mask starts this mode.
        No data exchange take place when setting the remote device IP address to 0.0.0.0."
    ::= { wtWebioEA2x2BinaryEntry 15 }

wtWebioEA2x2BinaryUdpPeerInputTrigger OBJECT-TYPE
    SYNTAX OCTET STRING (SIZE (4))
    ACCESS read-write
    STATUS mandatory
    DESCRIPTION
        "Every change on the inputs causes their state to be transmitted to the 
        remote device. To minimize data traffic, individual inputs may be exempted 
        from this rule. Nevertheless every transmission will contain all input bits.
        If a bit is set (1), a change of state on the corresponding input 
        triggers a transmission. If the bit is not set (0), no transmission 
        takes place.
        The OCTETS are interpreted bit-by-bit, with each bit corresponding to an input. 
        Bit 0 corresponds to the LSB.
        OCTET 1: unused
        OCTET 2: unused
        OCTET 3: unused
        OCTET 4, Bit 0-1: Digital inputs 0-1"
    ::= { wtWebioEA2x2BinaryEntry 16 }

wtWebioEA2x2BinaryUdpPeerInterval OBJECT-TYPE
    SYNTAX INTEGER (0..65535)
    ACCESS read-write
    STATUS mandatory
    DESCRIPTION
        "Configurable interval with a 100ms base, in which the Webio device sends
        data to the configured remote device. A interval of zero stopps the 
        periodical sending."
    ::= { wtWebioEA2x2BinaryEntry 17 }

wtWebioEA2x2BinaryUdpPeerApplicationMode OBJECT-TYPE
    SYNTAX OCTET STRING (SIZE (4))
    ACCESS read-write
    STATUS mandatory
    DESCRIPTION
        "Selection of the application mode:
        The OCTETS are interpreted bit-by-bit, with each bit corresponding to an output. 
        Bit 0 corresponds to the LSB.
        OCTET 1: unused
        OCTET 2: unused
        OCTET 3: unused
        OCTET 4: Bit 3-7: unused
        	 Bit 2  : Box2Box Slave
        	 Bit 1  : Compatible 50xxx
        	 Bit 0  : Default"
    ::= { wtWebioEA2x2BinaryEntry 18 }

wtWebioEA2x2BinaryConnectedPort OBJECT-TYPE
    SYNTAX INTEGER (1..65535)
    ACCESS read-only
    STATUS mandatory
    DESCRIPTION
        "Port number of the remote device, after connection has been established.
        In case of no connection or missing port informations a zero will be read."
    ::= { wtWebioEA2x2BinaryEntry 19 }

wtWebioEA2x2BinaryConnectedIpAddr OBJECT-TYPE
    SYNTAX IpAddress
    ACCESS read-only
    STATUS mandatory
    DESCRIPTION
        "IP address of the remote device, after connection has been established.
        In case of no connection or missing port informations 0.0.0.0 will be read."
    ::= { wtWebioEA2x2BinaryEntry 20 } 

wtWebioEA2x2BinaryTcpServerClientHttpPort OBJECT-TYPE
    SYNTAX INTEGER (1..65535)
    ACCESS read-write
    STATUS mandatory
    DESCRIPTION
        "HTTP port number of the remote device at TCP Server Mode. If an mailfunction occurs 
        status informations will be send to this port. 
        Not used at mode Compatible 50xxx."
    ::= { wtWebioEA2x2BinaryEntry 21 }
    
wtWebioEA2x2BinaryTcpClientServerHttpPort OBJECT-TYPE
    SYNTAX INTEGER (1..65535)
    ACCESS read-write
    STATUS mandatory
    DESCRIPTION
        "HTTP port number of the remote device at TCP Client Mode. In the operating mode
        Box2Box connection status informations will be exchanged through this port."
    ::= { wtWebioEA2x2BinaryEntry 22 }            
    
--  wtWebioEA2x2Syslog Group
--------------------------------
    
wtWebioEA2x2SyslogServerIP OBJECT-TYPE
    SYNTAX OCTET STRING 
    ACCESS read-write
    STATUS mandatory
    DESCRIPTION
        "Name or IP address of the Syslog server, which accepts the Syslog messgaes."
    ::= { wtWebioEA2x2Syslog 1 }
    
wtWebioEA2x2SyslogServerPort OBJECT-TYPE
    SYNTAX INTEGER
    ACCESS read-write
    STATUS mandatory
    DESCRIPTION
        "Portnumber of the Syslog servers, default 514."
    ::= { wtWebioEA2x2Syslog 2 }

wtWebioEA2x2SyslogSystemMessagesEnable OBJECT-TYPE
    SYNTAX OCTET STRING (SIZE(4))
    ACCESS read-write
    STATUS mandatory
    DESCRIPTION
        "Binary coded trigger conditions:
        Octet 1: unused
        Octet 2: unused
        Octet 3: unused
        Octet 4:
	        Bit 0:   ColdStart
	        Bit 1:   WarmStart
	        Bit 2:   Diag Messages
	        Bit 3-7: unused"
    ::= { wtWebioEA2x2Syslog 3 }    

wtWebioEA2x2SyslogEnable OBJECT-TYPE
    SYNTAX OCTET STRING 
    ACCESS read-write
    STATUS mandatory
    DESCRIPTION
        "Set bit 0to enable Syslog:
        Octet 1: unused
        Octet 2: unused
        Octet 3: unused
        Octet 4:
        	Bit 1-7: unused
                Bit 0  : Syslog enable"
    ::= { wtWebioEA2x2Syslog 4 }

--  wtWebioEA2x2FTP Group
--------------------------------

wtWebioEA2x2FTPServerIP OBJECT-TYPE
    SYNTAX OCTET STRING 
    ACCESS read-write
    STATUS mandatory
    DESCRIPTION
        "Name or IP address of the FTP server, which accepts the FTP messages."
    ::= { wtWebioEA2x2FTP 1 }
    
wtWebioEA2x2FTPServerControlPort OBJECT-TYPE
    SYNTAX INTEGER
    ACCESS read-write
    STATUS mandatory
    DESCRIPTION
        "Portnumber of the control port of the FTP server, default 21."
    ::= { wtWebioEA2x2FTP 2 }
    
wtWebioEA2x2FTPUserName OBJECT-TYPE
    SYNTAX OCTET STRING 
    ACCESS read-write
    STATUS mandatory
    DESCRIPTION
        "FTP Loggin: user name."
    ::= { wtWebioEA2x2FTP 3 }
    
wtWebioEA2x2FTPPassword OBJECT-TYPE
    SYNTAX OCTET STRING 
    ACCESS read-write
    STATUS mandatory
    DESCRIPTION
        "FTP Loggin: user password."
    ::= { wtWebioEA2x2FTP 4 }

wtWebioEA2x2FTPAccount OBJECT-TYPE
    SYNTAX OCTET STRING 
    ACCESS read-write
    STATUS mandatory
    DESCRIPTION
        "FTP Loggin: name of account."
    ::= { wtWebioEA2x2FTP 5 }

wtWebioEA2x2FTPOption OBJECT-TYPE
    SYNTAX OCTET STRING 
    ACCESS read-write
    STATUS mandatory
    DESCRIPTION
        "Bit 0 switches the FTP Server in Passiv-Mode,
        the Client controls the data connection on its own:
        Octet 1: unused
        Octet 2: unused
        Octet 3: unused
        Octet 4:
        	Bit 1-7: unused
                Bit 0  : PASV enable"
    ::= { wtWebioEA2x2FTP 6 }
    
wtWebioEA2x2FTPEnable OBJECT-TYPE
    SYNTAX OCTET STRING 
    ACCESS read-write
    STATUS mandatory
    DESCRIPTION
        "Set Bit 0 to enable FTP:
        Octet 1: unused
        Octet 2: unused
        Octet 3: unused
        Octet 4:
        	Bit 1-7: unused
                Bit 0  : FTP enable"
    ::= { wtWebioEA2x2FTP 7 }  
    
--  wtWebioEA2x2OutputMode Group
--------------------------------

-- OutputMode Table

wtWebioEA2x2OutputModeTable OBJECT-TYPE
    SYNTAX SEQUENCE OF WtWebioEA2x2OutputModeEntry
    ACCESS not-accessible
    STATUS mandatory
    DESCRIPTION
        "Table of output mode configurations dependent on the output indices."
    ::= { wtWebioEA2x2OutputMode 1 }

wtWebioEA2x2OutputModeEntry OBJECT-TYPE
    SYNTAX WtWebioEA2x2OutputModeEntry
    ACCESS not-accessible
    STATUS mandatory
    DESCRIPTION
        "Output mode configurations of the individual outputs."
    INDEX  { wtWebioEA2x2OutputNo }
    ::= { wtWebioEA2x2OutputModeTable 1 }

WtWebioEA2x2OutputModeEntry ::= SEQUENCE {
    wtWebioEA2x2OutputModeBit	OCTET STRING
}

wtWebioEA2x2OutputModeBit OBJECT-TYPE
    SYNTAX OCTET STRING (SIZE (4))
    ACCESS read-write
    STATUS mandatory
    DESCRIPTION
        "This binary coded output mode defines the individual operation mode for any
        output. More than one mode must not be selected.
        The OCTETS are interpreted bit-by-bit, with each bit corresponding to an output. 
        Bit 0 corresponds to the LSB.
        OCTET 1: unused
        OCTET 2: unused
        OCTET 3: unused
        OCTET 4: Bit 6-7: unused
        	 Bit 5  : Logic
        	 Bit 4  : Binary 2
        	 Bit 3  : Binary 1
        	 Bit 2  : SNMP
        	 Bit 1  : UDP ASCII
        	 Bit 0  : HTTP"
    ::= { wtWebioEA2x2OutputModeEntry 1 }
    
wtWebioEA2x2SafetyTimeout OBJECT-TYPE
    SYNTAX INTEGER (0..65535)
    ACCESS read-write
    STATUS mandatory
    DESCRIPTION
        "After this period of time (multiple of 100ms) without receiving data
        outputs switch to their Safety States. For each output a independend safety state
        could be defined."
    ::= { wtWebioEA2x2OutputMode 2 }
 
 wtWebioEA2x2LoadControlEnable OBJECT-TYPE
    SYNTAX OCTET STRING 
    ACCESS read-write
    STATUS mandatory
    DESCRIPTION
        "Here the function of automatic load control can be enabled. All output were tested in 
        pairs (0-1). If an error occours at one output,
        both output of an pair will be switched of. For a properly function of the load control
        each output of a pair have to has a load. If there is no existing load, a pull down resistor
        can be used.
        Outputs with no load are automaticly detected and not part of the control function.
        The OCTETS are interpreted bit-by-bit, with each bit corresponding to an output. 
        Bit 0 corresponds to the LSB.
        Octet 1: unused
        Octet 2: unused
        Octet 3: unused
        Octet 4:
        	Bit 1-7: unused
                Bit 0  : Load Control enable"
    ::= { wtWebioEA2x2OutputMode 3 }

    
-- wtWebioEA2x2Alarm Group
----------------------------

wtWebioEA2x2AlarmCount OBJECT-TYPE
    SYNTAX INTEGER (1..4)
    ACCESS read-only
    STATUS mandatory
    DESCRIPTION
        "Number of independent alarms."
    ::= { wtWebioEA2x2Alarm 1 }
    
-- Alarm Interface Table

wtWebioEA2x2AlarmIfTable OBJECT-TYPE
    SYNTAX SEQUENCE OF WtWebioEA2x2AlarmIfEntry
    ACCESS not-accessible
    STATUS mandatory
    DESCRIPTION
        "List of alarm indices."
    ::= { wtWebioEA2x2Alarm 2 }

wtWebioEA2x2AlarmIfEntry OBJECT-TYPE
    SYNTAX WtWebioEA2x2AlarmIfEntry
    ACCESS not-accessible
    STATUS mandatory
    DESCRIPTION
        "Numbers of the alarms."
    INDEX  { wtWebioEA2x2AlarmNo }
    ::= { wtWebioEA2x2AlarmIfTable 1 }

WtWebioEA2x2AlarmIfEntry ::= SEQUENCE {
    wtWebioEA2x2AlarmNo INTEGER
}

wtWebioEA2x2AlarmNo OBJECT-TYPE
    SYNTAX INTEGER (1..4)
    ACCESS read-only
    STATUS mandatory
    DESCRIPTION
        "Numbers of the alarms."
    ::= { wtWebioEA2x2AlarmIfEntry 1 }

-- Alarm Table

wtWebioEA2x2AlarmTable OBJECT-TYPE
    SYNTAX SEQUENCE OF WtWebioEA2x2AlarmEntry
    ACCESS not-accessible
    STATUS mandatory
    DESCRIPTION
        "List of settings depending on the alarm number."
    ::= { wtWebioEA2x2Alarm 3 }

wtWebioEA2x2AlarmEntry OBJECT-TYPE
    SYNTAX WtWebioEA2x2AlarmEntry
    ACCESS not-accessible
    STATUS mandatory
    DESCRIPTION
        "Alarm parameters of the individual alarms."
    INDEX  { wtWebioEA2x2AlarmNo }
    ::= { wtWebioEA2x2AlarmTable 1 }

WtWebioEA2x2AlarmEntry ::= SEQUENCE {
    wtWebioEA2x2AlarmInputTrigger	OCTET STRING,
    wtWebioEA2x2AlarmOutputTrigger	OCTET STRING,
    wtWebioEA2x2AlarmSystemTrigger	OCTET STRING,
    wtWebioEA2x2AlarmMaxCounterValue	OCTET STRING,
    wtWebioEA2x2AlarmInterval		OCTET STRING,
    wtWebioEA2x2AlarmEnable		OCTET STRING,
    wtWebioEA2x2AlarmMailAddr		OCTET STRING,
    wtWebioEA2x2AlarmMailSubject	OCTET STRING,
    wtWebioEA2x2AlarmMailText		OCTET STRING,
    wtWebioEA2x2AlarmSnmpManagerIP	OCTET STRING,
    wtWebioEA2x2AlarmSnmpTrapText	OCTET STRING,
    wtWebioEA2x2AlarmUdpIpAddr		OCTET STRING,
    wtWebioEA2x2AlarmUdpPort		INTEGER,
    wtWebioEA2x2AlarmUdpText		OCTET STRING,
    wtWebioEA2x2AlarmTcpIpAddr		OCTET STRING,
    wtWebioEA2x2AlarmTcpPort		INTEGER,
    wtWebioEA2x2AlarmTcpText		OCTET STRING,    
    wtWebioEA2x2AlarmSyslogIpAddr	OCTET STRING,
    wtWebioEA2x2AlarmSyslogPort		INTEGER,
    wtWebioEA2x2AlarmSyslogText		OCTET STRING,
    wtWebioEA2x2AlarmFtpDataPort	OCTET STRING,
    wtWebioEA2x2AlarmFtpFileName	OCTET STRING,
    wtWebioEA2x2AlarmFtpText		OCTET STRING,
    wtWebioEA2x2AlarmFtpOption		OCTET STRING,
    wtWebioEA2x2AlarmTimerCron		OCTET STRING,
    
    wtWebioEA2x2AlarmMailReleaseSubject		OCTET STRING,
    wtWebioEA2x2AlarmMailReleaseText		OCTET STRING,
    wtWebioEA2x2AlarmSnmpTrapReleaseText	OCTET STRING,
    wtWebioEA2x2AlarmUdpReleaseText		OCTET STRING,
    wtWebioEA2x2AlarmTcpReleaseText		OCTET STRING,    
    wtWebioEA2x2AlarmSyslogReleaseText		OCTET STRING,
    wtWebioEA2x2AlarmFtpReleaseText		OCTET STRING    
    
}

wtWebioEA2x2AlarmInputTrigger OBJECT-TYPE
    SYNTAX OCTET STRING (SIZE(12))
    ACCESS read-write
    STATUS mandatory
    DESCRIPTION
        "This variable allows setting of individual input trigger conditions. 
        The OCTETS are interpreted bit-by-bit, with each bit corresponding to an input. 
        Bit 0 corresponds to the LSB.
	The first four OCTETS contain the mask which determines which of the inputs are to 
	be considered (corresponding bit = 1) and which inputs are to ignore 
	(corresponding bit = 0):
	OCTET 1 : unused
	OCTET 2 : unused
	OCTET 3 : unused
	OCTET 4, Bit 0-1: Mask for digital inputs 0-1
	
	OCTETS 5-8 contain the level (1=HIGH, 0=LOW) which the inputs 
	should assume:
	OCTET 5 : unused
	OCTET 6 : unused
	OCTET 7 : unused
        OCTET 8, Bit 0-1: Level of digital inputs 0-1
        
	OCTETS 9-12 contain the ANY bit (1=ON, 0=OFF). Inputs masked with the any bit trigger with any change 
	of the corresponding input bit. Settings in OCTET 5-9 are then unused:
	OCTET 9: unused
	OCTET 10: unused
	OCTET 11: unused
	OCTET 12, Bit 0-1: ANY bits of digital inputs 0-1"
        
    ::= { wtWebioEA2x2AlarmEntry 1 }

wtWebioEA2x2AlarmOutputTrigger OBJECT-TYPE
    SYNTAX OCTET STRING (SIZE(12))
    ACCESS read-write
    STATUS mandatory
    DESCRIPTION
        "This variable allows setting of individual output trigger conditions. 
        The OCTETS are interpreted bit-by-bit, with each bit corresponding to an output. 
        Bit 0 corresponds to the LSB.
	The first four OCTETS contain the mask which determines which of the outputs are to 
	be considered (corresponding bit = 1) and which outputs are to ignore 
	(corresponding bit = 0):
	OCTET 1 : unused
	OCTET 2 : unused
	OCTET 3 : unused
	OCTET 4, Bit 0-1: Mask for digital outputs 0-1
	
	OCTETS 5-8 contain the level (1=HIGH, 0=LOW) which the outputs 
	should assume:
	OCTET 5 : unused
	OCTET 6 : unused
	OCTET 7 : unused
        OCTET 8, Bit 0-1: Level of digital outputs 0-1

	OCTETS 9-12 contain the ANY bit (1=ON, 0=OFF). Outputs masked with the any bit trigger with any change 
	of the corresponding output bit. Settings in OCTET 5-9 are then unused:
	OCTET 9: unused
	OCTET 10: unused
	OCTET 11: unused
	OCTET 12, Bit 0-1: ANY bits of digital outputs 0-1"
        
    ::= { wtWebioEA2x2AlarmEntry 2 }
    
wtWebioEA2x2AlarmSystemTrigger OBJECT-TYPE
    SYNTAX OCTET STRING (SIZE(4))
    ACCESS read-write
    STATUS mandatory
    DESCRIPTION
        "Binary coded trigger conditions:
        The OCTETS are interpreted bit-by-bit.
        Bit 0 corresponds to the LSB.
        OCTET 1: unused
        OCTET 2: unused
        OCTET 3: unused
        OCTET 4, 
        	 Bit 4-7: unused
        	 Bit 3  : Warm Start
        	 Bit 2  : Cold Start
        	 Bit 1  : Timer
        	 Bit 0  : Load Control"
    ::= { wtWebioEA2x2AlarmEntry 3 }

wtWebioEA2x2AlarmMaxCounterValue OBJECT-TYPE
    SYNTAX OCTET STRING 
    ACCESS read-write
    STATUS mandatory
    DESCRIPTION
        "This variable configures a max. counter value. If an input counter value
        exceeds this max. value, the corresponding alarm is triggered. Input counters with
        its mask bit unset in wtWebioEA2x2AlarmInputTrigger are not considered."
    ::= { wtWebioEA2x2AlarmEntry 4 }

wtWebioEA2x2AlarmInterval OBJECT-TYPE
    SYNTAX OCTET STRING 
    ACCESS read-write
    STATUS mandatory
    DESCRIPTION
        "Send interval for alarm messages."
    ::= { wtWebioEA2x2AlarmEntry 5 }

wtWebioEA2x2AlarmEnable OBJECT-TYPE
    SYNTAX OCTET STRING (SIZE(4))
    ACCESS read-write
    STATUS mandatory
    DESCRIPTION
        "Binary coded alarm enable:
        Octet 1: unused
        Octet 2: unused
        Octet 3: unused
        Octet 4:
		Bit 0:	Mail Enable
        	Bit 1:	SNMP Trap enable
        	Bit 2:  UDP enable
        	Bit 3:  Send inputs to pending TCP connections
        	Bit 4:  TCP Client enable
        	Bit 5:	Syslog Messages enable
        	Bit 6-7: unused"
    ::= { wtWebioEA2x2AlarmEntry 6 }

wtWebioEA2x2AlarmMailAddr OBJECT-TYPE
    SYNTAX OCTET STRING 
    ACCESS read-write
    STATUS mandatory
    DESCRIPTION
        "E-Mail address for sending the alarm mail to."
    ::= { wtWebioEA2x2AlarmEntry 7 }

wtWebioEA2x2AlarmMailSubject OBJECT-TYPE
    SYNTAX OCTET STRING 
    ACCESS read-write
    STATUS mandatory
    DESCRIPTION
        "Subject line for alarm mail."
    ::= { wtWebioEA2x2AlarmEntry 8 }

wtWebioEA2x2AlarmMailText OBJECT-TYPE
    SYNTAX OCTET STRING 
    ACCESS read-write
    STATUS mandatory
    DESCRIPTION
        "Alarm mail text: 
        States of the Webio device can be included by using special tags.
        Please refer to the respective Webio manual"
    ::= { wtWebioEA2x2AlarmEntry 9 }

wtWebioEA2x2AlarmSnmpManagerIP OBJECT-TYPE
    SYNTAX OCTET STRING 
    ACCESS read-write
    STATUS mandatory
    DESCRIPTION
        "IP address of the SNMP Manager to which the Webio device should send SNMP traps."
    ::= { wtWebioEA2x2AlarmEntry 10 }

wtWebioEA2x2AlarmSnmpTrapText OBJECT-TYPE
    SYNTAX OCTET STRING 
    ACCESS read-write
    STATUS mandatory
    DESCRIPTION
        "This text appears in the trap body."
    ::= { wtWebioEA2x2AlarmEntry 11 }
    
wtWebioEA2x2AlarmUdpIpAddr OBJECT-TYPE
    SYNTAX OCTET STRING 
    ACCESS read-write
    STATUS mandatory
    DESCRIPTION
        "IP address of the UDP listener to which the Webio device should send UDP traps."
    ::= { wtWebioEA2x2AlarmEntry 12 }    

wtWebioEA2x2AlarmUdpPort OBJECT-TYPE
    SYNTAX INTEGER (1..65535) 
    ACCESS read-write
    STATUS mandatory
    DESCRIPTION
        "Port number of the UDP listener to which the Webio device should send UDP traps."
    ::= { wtWebioEA2x2AlarmEntry 13 }    

wtWebioEA2x2AlarmUdpText OBJECT-TYPE
    SYNTAX OCTET STRING 
    ACCESS read-write
    STATUS mandatory
    DESCRIPTION
        "This text appears in the UDP trap body."
    ::= { wtWebioEA2x2AlarmEntry 14 }
    
wtWebioEA2x2AlarmTcpIpAddr OBJECT-TYPE
    SYNTAX OCTET STRING
    ACCESS read-write
    STATUS mandatory
    DESCRIPTION
        "IP address of the TCP listener to which the Webio device should send TCP traps."
    ::= { wtWebioEA2x2AlarmEntry 15 }    

wtWebioEA2x2AlarmTcpPort OBJECT-TYPE
    SYNTAX INTEGER (1..65535) 
    ACCESS read-write
    STATUS mandatory
    DESCRIPTION
        "Port number of the TCP listener to which the Webio device should send TCP traps."
    ::= { wtWebioEA2x2AlarmEntry 16 }    

wtWebioEA2x2AlarmTcpText OBJECT-TYPE
    SYNTAX OCTET STRING 
    ACCESS read-write
    STATUS mandatory
    DESCRIPTION
        "This text appears in the TCP trap body."
    ::= { wtWebioEA2x2AlarmEntry 17 }

wtWebioEA2x2AlarmSyslogIpAddr OBJECT-TYPE
    SYNTAX OCTET STRING 
    ACCESS read-write
    STATUS mandatory
    DESCRIPTION
        "IP address of the syslog server to which the Webio device should send syslog messages."
    ::= { wtWebioEA2x2AlarmEntry 18 }    

wtWebioEA2x2AlarmSyslogPort OBJECT-TYPE
    SYNTAX INTEGER (1..65535) 
    ACCESS read-write
    STATUS mandatory
    DESCRIPTION
        "Port number of the syslog server to which the Webio device should send syslog messages."
    ::= { wtWebioEA2x2AlarmEntry 19 }    

wtWebioEA2x2AlarmSyslogText OBJECT-TYPE
    SYNTAX OCTET STRING 
    ACCESS read-write
    STATUS mandatory
    DESCRIPTION
        "Every message starts with the priority key, a time stamp and the host ip address, according RFC3164.
        This text appears in the following syslog message body."
    ::= { wtWebioEA2x2AlarmEntry 20 }    
    
wtWebioEA2x2AlarmFtpDataPort OBJECT-TYPE
    SYNTAX OCTET STRING 
    ACCESS read-write
    STATUS mandatory
    DESCRIPTION
        "Local data port: 1..65535 or AUTO: the next free port will be assigned."
    ::= { wtWebioEA2x2AlarmEntry 21 }
    
wtWebioEA2x2AlarmFtpFileName OBJECT-TYPE
    SYNTAX OCTET STRING 
    ACCESS read-write
    STATUS mandatory
    DESCRIPTION
        "Name of the file including path informations."
    ::= { wtWebioEA2x2AlarmEntry 22 }
    
wtWebioEA2x2AlarmFtpText OBJECT-TYPE
    SYNTAX OCTET STRING 
    ACCESS read-write
    STATUS mandatory
    DESCRIPTION
        "Message text to store on the FTP server."
    ::= { wtWebioEA2x2AlarmEntry 23 }

wtWebioEA2x2AlarmFtpOption OBJECT-TYPE
    SYNTAX OCTET STRING (SIZE(4))
    ACCESS read-write
    STATUS mandatory
    DESCRIPTION
        "Binary coded options, select only one option at the same time:
        STORE  = replace file
        APPEND = append message at the end of the file
        
        Octet 1: unused
        Octet 2: unused
        Octet 3: unused
        Octet 4:
		Bit 0  :	STORE
		Bit 1  :	APPEND
        	Bit 2-7:	unused"
    ::= { wtWebioEA2x2AlarmEntry 24 }      
    
wtWebioEA2x2AlarmTimerCron OBJECT-TYPE
    SYNTAX OCTET STRING
    ACCESS read-write
    STATUS mandatory
    DESCRIPTION
        "This entry contains 5 space or tab seperated text fields for time trigger definition.
        Each field must match with the actual time to trigger a message, weekday and day of month
        are interpreted separatley.
        1: Minutes	Range 0-59
        2. Hours	Range 0-23, 0 is midnight
        3: Day of month	Range 1-31
        4: Month	Range 1-12
        5: Weekday	Range 0-6, 0 is sunday
        
        Syntax for every field:
         - an asterix (*) enables every possible setting of a field
         - single numbers seperated by commas
         - a partition within the allowed range (1-5)
         - step size within an partition of the allowed range (0-59/2: every second minute)."
    ::= { wtWebioEA2x2AlarmEntry 25 }      

wtWebioEA2x2AlarmMailReleaseSubject OBJECT-TYPE
    SYNTAX OCTET STRING 
    ACCESS read-write
    STATUS mandatory
    DESCRIPTION
       "Subject line for alarm mail."
    ::= { wtWebioEA2x2AlarmEntry 26 }

wtWebioEA2x2AlarmMailReleaseText OBJECT-TYPE
    SYNTAX OCTET STRING 
    ACCESS read-write
    STATUS mandatory
    DESCRIPTION
        "Release Alarm mail text: 
        States of the Webio device can be included by using special tags.
        Please refer to the respective Webio manual"
    ::= { wtWebioEA2x2AlarmEntry 27 }    

wtWebioEA2x2AlarmSnmpTrapReleaseText OBJECT-TYPE
    SYNTAX OCTET STRING 
    ACCESS read-write
    STATUS mandatory
    DESCRIPTION
        "This text appears in the trap body."
    ::= { wtWebioEA2x2AlarmEntry 28 }

wtWebioEA2x2AlarmUdpReleaseText OBJECT-TYPE
    SYNTAX OCTET STRING 
    ACCESS read-write
    STATUS mandatory
    DESCRIPTION
        "This text appears in the UDP trap body."
    ::= { wtWebioEA2x2AlarmEntry 29 }

wtWebioEA2x2AlarmTcpReleaseText OBJECT-TYPE
    SYNTAX OCTET STRING 
    ACCESS read-write
    STATUS mandatory
    DESCRIPTION
        "This text appears in the TCP trap body."
    ::= { wtWebioEA2x2AlarmEntry 30 }

wtWebioEA2x2AlarmSyslogReleaseText OBJECT-TYPE
    SYNTAX OCTET STRING 
    ACCESS read-write
    STATUS mandatory
    DESCRIPTION
        "Every message starts with the priority key, a time stamp and the host ip address, according RFC3164.
        This text appears in the following syslog message body."
    ::= { wtWebioEA2x2AlarmEntry 31 }

wtWebioEA2x2AlarmFtpReleaseText OBJECT-TYPE
    SYNTAX OCTET STRING 
    ACCESS read-write
    STATUS mandatory
    DESCRIPTION
        "Message text to store on the FTP server."
    ::= { wtWebioEA2x2AlarmEntry 32 }

-- wtWebioEA2x2LoadControl
----------------------------

wtWebioEA2x2LoadControlView OBJECT-TYPE
    SYNTAX OCTET STRING (SIZE(4))
    ACCESS read-only
    STATUS mandatory
    DESCRIPTION
        "Here the result of automatic load control can be read. All output were tested in 
        pairs (0-1). If an error occours at one output,
        both output of an pair will be switched of. For a properly function of the load control
        each output of a pair have to has a load. If there is no existing load, a pull down resistor
        can be used.
        Outputs with no load are automaticly detected and not part of the control function.
        The OCTETS are interpreted bit-by-bit, with each bit corresponding to an output. 
        Bit 0 corresponds to the LSB.
        Octet 1: unused
        Octet 2: unused
        Octet 3: unused
        Octet 4: 
	        Bit 0-1: outputs 0-1."
    ::= { wtWebioEA2x2Alarm 4 }

wtWebioEA2x2LCShutDownView OBJECT-TYPE
    SYNTAX OCTET STRING (SIZE(4))
    ACCESS read-write
    STATUS mandatory
    DESCRIPTION
        "Here the result of the automatic load control shut down can be read. All outputs remain switched of,
        until a zero is written into this variable. But previously all loads should be inspected.
        High current (short circuit), a broken supply line or a defect load (i.e. lamp) may be a shut down reason.
        If no load is detected, the load control unit suspend automaticly the control of the corresponding output pair.
        All controlled output could be identified reading the variable wtWebioEA2x2LoadControlEnable.
        The OCTETS are interpreted bit-by-bit, with each bit corresponding to an ouput.
        Bit 0 corresponds to the LSB.
        
        Octet 1: unused
        Octet 2: unused
        Octet 3: unused
        Octet 4: Bit 0-1: outputs 0-1."
    ::= { wtWebioEA2x2Alarm 5 }

-- wtWebioEA2x2Ports Group
----------------------------

-- Input Port Table

wtWebioEA2x2InputPortTable OBJECT-TYPE
    SYNTAX SEQUENCE OF WtWebioEA2x2InputPortEntry
    ACCESS not-accessible
    STATUS mandatory
    DESCRIPTION
        "List of settings depending on the input number."
    ::= { wtWebioEA2x2Ports 1 }

wtWebioEA2x2InputPortEntry OBJECT-TYPE
    SYNTAX WtWebioEA2x2InputPortEntry
    ACCESS not-accessible
    STATUS mandatory
    DESCRIPTION
        "Input parameter for the individual inputs."
    INDEX  { wtWebioEA2x2InputNo }
    ::= { wtWebioEA2x2InputPortTable 1 }

WtWebioEA2x2InputPortEntry ::= SEQUENCE {
    wtWebioEA2x2PortInputName			OCTET STRING,
    wtWebioEA2x2PortInputText			OCTET STRING,
    wtWebioEA2x2PortInputMode			OCTET STRING,
    wtWebioEA2x2PortInputFilter			INTEGER,
    wtWebioEA2x2PortInputBicountPulsePolarity	OCTET STRING,
    wtWebioEA2x2PortInputBicountInactivTimeout	INTEGER
    
}

wtWebioEA2x2PortInputName OBJECT-TYPE
    SYNTAX OCTET STRING 
    ACCESS read-write
    STATUS mandatory
    DESCRIPTION
        "Name of the input."
    ::= { wtWebioEA2x2InputPortEntry 1 }

wtWebioEA2x2PortInputText OBJECT-TYPE
    SYNTAX OCTET STRING 
    ACCESS read-write
    STATUS mandatory
    DESCRIPTION
        "Description of the input."
    ::= { wtWebioEA2x2InputPortEntry 2 }

wtWebioEA2x2PortInputMode OBJECT-TYPE
    SYNTAX OCTET STRING (SIZE(4))
    ACCESS read-write
    STATUS mandatory
    DESCRIPTION
        "Binary coded modes:
        Selecting short pulse detection enable by setting the corresponding bit to 1 enables 
        interrupt support for counting. Only positive edges are accepted as trigger 
        source. The maximum counting frequenz equals 2000 Hz.
        This mode is available for inputs 0-3 only.
        Selecting counter clear on read by setting the corresponding bit to 1 enables
        the corresponding counter to be cleared automatically every time it is read,
        except HTTP reading with user rights.
        The OCTETS are interpreted bit-by-bit,
        Bit 0 corresponds to the LSB.
        Selection for input 0-1:
        OCTET 1: unused
        OCTET 2: unused
        OCTET 3: unused
        OCTET 4, Bit 4-7: unused
		 Bit 3	: Bidirectional counter enable
        	 Bit 2  : Counter clear on read
        	 Bit 1  : Change detection enable (default)
        	 Bit 0  : Short Pulse detection enable"
    ::= { wtWebioEA2x2InputPortEntry 3 }    
    
wtWebioEA2x2PortInputFilter OBJECT-TYPE
    SYNTAX INTEGER 
    ACCESS read-write
    STATUS mandatory
    DESCRIPTION
        "Pulses with a duration shorter than here specified (duration in 1/1000 sec),
	are ignored."
    ::= { wtWebioEA2x2InputPortEntry 4 }
    
wtWebioEA2x2PortInputBicountPulsePolarity OBJECT-TYPE
    SYNTAX OCTET STRING (SIZE (4))
    ACCESS read-write
    STATUS mandatory
    DESCRIPTION
        "This value defines the polarity of the input pulse.
        OCTET 1: unused
        OCTET 2: unused
        OCTET 3: unused
        	OCTET 4: 
        	 Bit 0   : negative polarity
        	 Bit 1   : positive polarity
        	 Bit 2-7 : unused"
    ::= { wtWebioEA2x2InputPortEntry 5 }

wtWebioEA2x2PortInputBicountInactivTimeout OBJECT-TYPE
    SYNTAX INTEGER 
    ACCESS read-write
    STATUS mandatory
    DESCRIPTION
        "Pulse chains with a duration shorter than here specified (in 1/10 sek),
	are ignored."
    ::= { wtWebioEA2x2InputPortEntry 6 }
        
-- Output Port Table

wtWebioEA2x2OutputPortTable OBJECT-TYPE
    SYNTAX SEQUENCE OF WtWebioEA2x2OutputPortEntry
    ACCESS not-accessible
    STATUS mandatory
    DESCRIPTION
        "List of settings depending on the output number."
    ::= { wtWebioEA2x2Ports 2 }

wtWebioEA2x2OutputPortEntry OBJECT-TYPE
    SYNTAX WtWebioEA2x2OutputPortEntry
    ACCESS not-accessible
    STATUS mandatory
    DESCRIPTION
        "Output parameters of the individual outputs."
    INDEX  { wtWebioEA2x2OutputNo }
    ::= { wtWebioEA2x2OutputPortTable 1 }

WtWebioEA2x2OutputPortEntry ::= SEQUENCE {
    wtWebioEA2x2PortOutputName			OCTET STRING,
    wtWebioEA2x2PortOutputText			OCTET STRING,
    wtWebioEA2x2PortOutputGroupMode		OCTET STRING,
    wtWebioEA2x2PortOutputSafetyState		OCTET STRING,
    wtWebioEA2x2PortLogicInputMask		OCTET STRING,
    wtWebioEA2x2PortLogicInputInverter		OCTET STRING,
    wtWebioEA2x2PortLogicFunction		OCTET STRING,
    wtWebioEA2x2PortLogicOutputInverter		OCTET STRING,
    wtWebioEA2x2PortPulseDuration		INTEGER,
    wtWebioEA2x2PortPulsePolarity		OCTET STRING
    
}

wtWebioEA2x2PortOutputName OBJECT-TYPE
    SYNTAX OCTET STRING 
    ACCESS read-write
    STATUS mandatory
    DESCRIPTION
        "Name of the output."
    ::= { wtWebioEA2x2OutputPortEntry 1 }

wtWebioEA2x2PortOutputText OBJECT-TYPE
    SYNTAX OCTET STRING 
    ACCESS read-write
    STATUS mandatory
    DESCRIPTION
        "Description of the output."
    ::= { wtWebioEA2x2OutputPortEntry 2 }

wtWebioEA2x2PortOutputGroupMode OBJECT-TYPE
    SYNTAX OCTET STRING 
    ACCESS read-write
    STATUS mandatory
    DESCRIPTION
        "It is possible to connect outputs together to increase the output current.
        This could be done by connecting 2 or 4 outputs in a group together. All bits
        of such a group has to be set all together in the same way. This variable
        configures this group scheme. If one ouput bit of a group is set, all other 
        output bits of the same group will be set in the same manner.
        More than one configuration must not be selected.
	Selection for ouputs 0-1:
        Octet 1: unused
        Octet 2: unused
        Octet 3: unused
        OCTET 4: Bit 0   : ouputs 0,1 disconnected (default)
        	 Bit 1   : ouputs 0+1 connected"
    ::= { wtWebioEA2x2OutputPortEntry 3 }

wtWebioEA2x2PortOutputSafetyState OBJECT-TYPE
    SYNTAX OCTET STRING 
    ACCESS read-write
    STATUS mandatory
    DESCRIPTION
        "This variable allows setting of individual digital outputs. The OCTETS are 
        interpreted bit-by-bit, with each bit corresponding to an output. Bit 0 corresponds 
        to the LSB.
        The first four OCTETS contain the mask which determines which of the outputs are to 
        be set (corresponding bit = 1) and which outputs are to remain unchanged 
        (corresponding bit = 0):
        OCTET 1		: unused
        OCTET 2		: unused
        OCTET 3		: unused
        OCTET 4, Bit 1-7: unused
        	 Bit 0	: Mask for digital output
        OCTETS 5-8 contain the level (1=HIGH, 0=LOW) which the outputs to be changed 
        should assume:
        OCTET 5		: unused
        OCTET 6		: unused
        OCTET 7		: unused
        OCTET 8, Bit 1-7: unused
        	 Bit 0  : Level of digital output"
    ::= { wtWebioEA2x2OutputPortEntry 4 }

wtWebioEA2x2PortLogicInputMask OBJECT-TYPE
    SYNTAX OCTET STRING (SIZE (4))
    ACCESS read-write
    STATUS mandatory
    DESCRIPTION
        "Selecting one of these inputs by setting the corresponding bit to 1 
        enables the logic function for the output identified by the index within 
        this table. The calculation take place in 4 steps:
        1. Selecting inputs				(wtWebioEA2x2PortLogicInputMask)
        2. Inverting inputs if necessary	(wtWebioEA2x2PortLogicInputInverter)
        3. Logical combination				(wtWebioEA2x2PortLogicFunction)
        4. Inverting the result if necessary	(wtWebioEA2x2PortLogicOutputInverter)
        OCTET 1: unused
        OCTET 2: unused
        OCTET 3: unused
        OCTET 4: Bit 0-1 : inputs 0-1"
    ::= { wtWebioEA2x2OutputPortEntry 5 }

wtWebioEA2x2PortLogicInputInverter OBJECT-TYPE
    SYNTAX OCTET STRING (SIZE (4))
    ACCESS read-write
    STATUS mandatory
    DESCRIPTION
        "Every input bit selected here will be inverted.
        OCTET 1: unused
        OCTET 2: unused
        OCTET 3: unused
        OCTET 4: Bit 0-1 : inputs 0-1"
    ::= { wtWebioEA2x2OutputPortEntry 6 }

wtWebioEA2x2PortLogicFunction OBJECT-TYPE
    SYNTAX OCTET STRING (SIZE (4))
    ACCESS read-write
    STATUS mandatory
    DESCRIPTION
        "This determines the logic function. No more than one function
        may be selected.
        OCTET 1: unused
        OCTET 2: unused
        OCTET 3: unused
        OCTET 4: 
        	 Bit 0   : logic function OR (default)
        	 Bit 1   : logic function AND
        	 Bit 2-7 : unused"
    ::= { wtWebioEA2x2OutputPortEntry 7 }

wtWebioEA2x2PortLogicOutputInverter OBJECT-TYPE
    SYNTAX OCTET STRING (SIZE (4))
    ACCESS read-write
    STATUS mandatory
    DESCRIPTION
        "The logical operation result could be inverteted by setting the corresponding
        bit to 1.
        OCTET 1: unused
        OCTET 2: unused
        OCTET 3: unused
        	OCTET 4: 
        	 Bit 0   : Output Inverter enable
        	 Bit 1-7 : unused"
    ::= { wtWebioEA2x2OutputPortEntry 8 }

wtWebioEA2x2PortPulseDuration OBJECT-TYPE
    SYNTAX INTEGER
    ACCESS read-write
    STATUS mandatory
    DESCRIPTION
        "Pulse length in 1/1000 sec. Setting this value to zero, disables the pulse output."
    ::= { wtWebioEA2x2OutputPortEntry 9 }

wtWebioEA2x2PortPulsePolarity OBJECT-TYPE
    SYNTAX OCTET STRING (SIZE (4))
    ACCESS read-write
    STATUS mandatory
    DESCRIPTION
        "This value defines the polarity of the output pulse, if wtWebioEA2x2PortPulseDuration is not set to zero.
        After the pulse is finished, the output switches back to the opposite state.
        OCTET 1: unused
        OCTET 2: unused
        OCTET 3: unused
        	OCTET 4: 
        	 Bit 0   : negative polarity
        	 Bit 1   : positive polarity
        	 Bit 2-7 : unused"
    ::= { wtWebioEA2x2OutputPortEntry 10 }

-- wtWebioEA2x2Manufact Group
----------------------------

wtWebioEA2x2MfName OBJECT-TYPE
    SYNTAX OCTET STRING 
    ACCESS read-write
    STATUS mandatory
    DESCRIPTION
        "Manufacturer company name"
    ::= { wtWebioEA2x2Manufact 1 }

wtWebioEA2x2MfAddr OBJECT-TYPE
    SYNTAX OCTET STRING 
    ACCESS read-write
    STATUS mandatory
    DESCRIPTION
        "Manufacturer address."
    ::= { wtWebioEA2x2Manufact 2 }

wtWebioEA2x2MfHotline OBJECT-TYPE
    SYNTAX OCTET STRING 
    ACCESS read-write
    STATUS mandatory
    DESCRIPTION
        "Manufacturer hotline."
    ::= { wtWebioEA2x2Manufact 3 }

wtWebioEA2x2MfInternet OBJECT-TYPE
    SYNTAX OCTET STRING 
    ACCESS read-write
    STATUS mandatory
    DESCRIPTION
        "Manufacturer Internet address."
    ::= { wtWebioEA2x2Manufact 4 }

wtWebioEA2x2MfDeviceTyp OBJECT-TYPE
    SYNTAX OCTET STRING 
    ACCESS read-write
    STATUS mandatory
    DESCRIPTION
        "Manufacturer device name (model number)."
    ::= { wtWebioEA2x2Manufact 5 }

-- wtWebioEA2x2Diag Group
----------------------------

wtWebioEA2x2DiagErrorCount OBJECT-TYPE
    SYNTAX INTEGER
    ACCESS read-only
    STATUS mandatory
    DESCRIPTION
        "Number of entries in the error memory."
    ::= { wtWebioEA2x2Diag 1 }

wtWebioEA2x2DiagBinaryError OBJECT-TYPE
    SYNTAX OCTET STRING 
    ACCESS read-only
    STATUS mandatory
    DESCRIPTION
        "Error causes coded bit-by-bit."
    ::= { wtWebioEA2x2Diag 2 }

wtWebioEA2x2DiagErrorIndex OBJECT-TYPE
    SYNTAX INTEGER
    ACCESS read-write
    STATUS mandatory
    DESCRIPTION
        "The value of this variable is used as an index to read 
        an error massege from wtWebioEA2x2DiagErrorMessage.
        Errors are numbered from 1 to wtWebioEA2x2DiagErrorCount.
        Writing a valid value into this variable, making the appropriate 
        message readable from wtWebioEA2x2DiagErrorMessage."
    ::= { wtWebioEA2x2Diag 3 }

wtWebioEA2x2DiagErrorMessage OBJECT-TYPE
    SYNTAX OCTET STRING 
    ACCESS read-only
    STATUS mandatory
    DESCRIPTION
        "Using wtWebioEA2x2DiagErrorIndex as an index, the appropriate message is available."
    ::= { wtWebioEA2x2Diag 4 }
    
wtWebioEA2x2DiagErrorClear OBJECT-TYPE
    SYNTAX INTEGER
    ACCESS write-only
    STATUS mandatory
    DESCRIPTION
        "Writing 1 into this variable clears all diagnosis messages."
    ::= { wtWebioEA2x2Diag 5 }


-- TRAP DEFINITIONS

-- Diese SNMP-Traps werden gesendet, wenn die Alarmtriggerbedingungen zutreffen 

wtWebioEA2x2Alert1 TRAP-TYPE
    ENTERPRISE  wtWebioEA2x2
    VARIABLES   { wtWebioEA2x2AlarmSnmpTrapText }
    DESCRIPTION
        "This SNMP trap is generated when Alarm 1 was triggered,
        SNMP trap enable is set and
        SNMP is enabled."
    -- NMS trap annotation
    --#TYPE "Webio Digital Alarm 1"
    --#SUMMARY "Alarm 1: %s"
    --#ARGUMENTS {0}
    --#SEVERITY INFORMATIONAL
    --#TIMEINDEX 99
    --#STATE OPERATIONAL    
    ::= 41

wtWebioEA2x2Alert2 TRAP-TYPE
    ENTERPRISE  wtWebioEA2x2
    VARIABLES   { wtWebioEA2x2AlarmSnmpTrapText }
    DESCRIPTION
        "This SNMP trap is generated when Alarm 2 was triggered,
        SNMP trap enable is set and
        SNMP is enabled."
    -- NMS trap annotation
    --#TYPE "Webio Digital Alarm 2"
    --#SUMMARY "Alarm 2: %s"
    --#ARGUMENTS {0}
    --#SEVERITY INFORMATIONAL
    --#TIMEINDEX 99
    --#STATE OPERATIONAL    
    ::= 42

wtWebioEA2x2Alert3 TRAP-TYPE
    ENTERPRISE  wtWebioEA2x2
    VARIABLES   { wtWebioEA2x2AlarmSnmpTrapText }
    DESCRIPTION
        "This SNMP trap is generated when Alarm 3 was triggered,
        SNMP trap enable is set and
        SNMP is enabled."
    -- NMS trap annotation
    --#TYPE "Webio Digital Alarm 3"
    --#SUMMARY "Alarm 3: %s"
    --#ARGUMENTS {0}
    --#SEVERITY INFORMATIONAL
    --#TIMEINDEX 99
    --#STATE OPERATIONAL    
    ::= 43

wtWebioEA2x2Alert4 TRAP-TYPE
    ENTERPRISE  wtWebioEA2x2
    VARIABLES   { wtWebioEA2x2AlarmSnmpTrapText }
    DESCRIPTION
        "This SNMP trap is generated when Alarm 4 was triggered,
        SNMP trap enable is set and
        SNMP is enabled."
    -- NMS trap annotation
    --#TYPE "Webio Digital Alarm 4"
    --#SUMMARY "Alarm 4: %s"
    --#ARGUMENTS {0}
    --#SEVERITY INFORMATIONAL
    --#TIMEINDEX 99
    --#STATE OPERATIONAL    
    ::= 44

wtWebioEA2x2Alert5 TRAP-TYPE
    ENTERPRISE  wtWebioEA2x2
    VARIABLES   { wtWebioEA2x2AlarmSnmpTrapText }
    DESCRIPTION
        "This SNMP trap is generated when Alarm 5 was triggered,
        SNMP trap enable is set and
        SNMP is enabled."
    -- NMS trap annotation
    --#TYPE "Webio Digital Alarm 5"
    --#SUMMARY "Alarm 5: %s"
    --#ARGUMENTS {0}
    --#SEVERITY INFORMATIONAL
    --#TIMEINDEX 99
    --#STATE OPERATIONAL    
    ::= 45

wtWebioEA2x2Alert6 TRAP-TYPE
    ENTERPRISE  wtWebioEA2x2
    VARIABLES   { wtWebioEA2x2AlarmSnmpTrapText }
    DESCRIPTION
        "This SNMP trap is generated when Alarm 6 was triggered,
        SNMP trap enable is set and
        SNMP is enabled."
    -- NMS trap annotation
    --#TYPE "Webio Digital Alarm 6"
    --#SUMMARY "Alarm 6: %s"
    --#ARGUMENTS {0}
    --#SEVERITY INFORMATIONAL
    --#TIMEINDEX 99
    --#STATE OPERATIONAL    
    ::= 46

wtWebioEA2x2Alert7 TRAP-TYPE
    ENTERPRISE  wtWebioEA2x2
    VARIABLES   { wtWebioEA2x2AlarmSnmpTrapText }
    DESCRIPTION
        "This SNMP trap is generated when Alarm 7 was triggered,
        SNMP trap enable is set and
        SNMP is enabled."
    -- NMS trap annotation
    --#TYPE "Webio Digital Alarm 7"
    --#SUMMARY "Alarm 7: %s"
    --#ARGUMENTS {0}
    --#SEVERITY INFORMATIONAL
    --#TIMEINDEX 99
    --#STATE OPERATIONAL    
    ::= 47

wtWebioEA2x2Alert8 TRAP-TYPE
    ENTERPRISE  wtWebioEA2x2
    VARIABLES   { wtWebioEA2x2AlarmSnmpTrapText }
    DESCRIPTION
        "This SNMP trap is generated when Alarm 8 was triggered,
        SNMP trap enable is set and
        SNMP is enabled."
    -- NMS trap annotation
    --#TYPE "Webio Digital Alarm 8"
    --#SUMMARY "Alarm 8: %s"
    --#ARGUMENTS {0}
    --#SEVERITY INFORMATIONAL
    --#TIMEINDEX 99
    --#STATE OPERATIONAL    
    ::= 48

wtWebioEA2x2Alert9 TRAP-TYPE
    ENTERPRISE  wtWebioEA2x2
    VARIABLES   { wtWebioEA2x2AlarmSnmpTrapText }
    DESCRIPTION
        "This SNMP trap is generated when Alarm 9 was triggered,
        SNMP trap enable is set and
        SNMP is enabled."
    -- NMS trap annotation
    --#TYPE "Webio Digital Alarm 9"
    --#SUMMARY "Alarm 9: %s"
    --#ARGUMENTS {0}
    --#SEVERITY INFORMATIONAL
    --#TIMEINDEX 99
    --#STATE OPERATIONAL    
    ::= 49

wtWebioEA2x2Alert10 TRAP-TYPE
    ENTERPRISE  wtWebioEA2x2
    VARIABLES   { wtWebioEA2x2AlarmSnmpTrapText }
    DESCRIPTION
        "This SNMP trap is generated when Alarm 10 was triggered,
        SNMP trap enable is set and
        SNMP is enabled."
    -- NMS trap annotation
    --#TYPE "Webio Digital Alarm 10"
    --#SUMMARY "Alarm 10: %s"
    --#ARGUMENTS {0}
    --#SEVERITY INFORMATIONAL
    --#TIMEINDEX 99
    --#STATE OPERATIONAL    
    ::= 50

wtWebioEA2x2Alert11 TRAP-TYPE
    ENTERPRISE  wtWebioEA2x2
    VARIABLES   { wtWebioEA2x2AlarmSnmpTrapText }
    DESCRIPTION
        "This SNMP trap is generated when Alarm 11 was triggered,
        SNMP trap enable is set and
        SNMP is enabled."
    -- NMS trap annotation
    --#TYPE "Webio Digital Alarm 11"
    --#SUMMARY "Alarm 11: %s"
    --#ARGUMENTS {0}
    --#SEVERITY INFORMATIONAL
    --#TIMEINDEX 99
    --#STATE OPERATIONAL    
    ::= 51

wtWebioEA2x2Alert12 TRAP-TYPE
    ENTERPRISE  wtWebioEA2x2
    VARIABLES   { wtWebioEA2x2AlarmSnmpTrapText }
    DESCRIPTION
        "This SNMP trap is generated when Alarm 12 was triggered,
        SNMP trap enable is set and
        SNMP is enabled."
    -- NMS trap annotation
    --#TYPE "Webio Digital Alarm 12"
    --#SUMMARY "Alarm 12: %s"
    --#ARGUMENTS {0}
    --#SEVERITY INFORMATIONAL
    --#TIMEINDEX 99
    --#STATE OPERATIONAL    
    ::= 52

wtWebioEA2x2Alert13 TRAP-TYPE
    ENTERPRISE  wtWebioEA2x2
    VARIABLES   { wtWebioEA2x2AlarmSnmpTrapReleaseText }
    DESCRIPTION
        "This SNMP trap is generated when Alarm 1 was released,
        SNMP trap enable is set and
        SNMP is enabled."
    -- NMS trap annotation
    --#TYPE "Webio Digital Release Alarm 1"
    --#SUMMARY "Release Alarm 1: %s"
    --#ARGUMENTS {0}
    --#SEVERITY INFORMATIONAL
    --#TIMEINDEX 99
    --#STATE OPERATIONAL    
    ::= 71

wtWebioEA2x2Alert14 TRAP-TYPE
    ENTERPRISE  wtWebioEA2x2
    VARIABLES   { wtWebioEA2x2AlarmSnmpTrapReleaseText }
    DESCRIPTION
        "This SNMP trap is generated when Alarm 2 was released,
        SNMP trap enable is set and
        SNMP is enabled."
    -- NMS trap annotation
    --#TYPE "Webio Digital Release Alarm 2"
    --#SUMMARY "Release Alarm 2: %s"
    --#ARGUMENTS {0}
    --#SEVERITY INFORMATIONAL
    --#TIMEINDEX 99
    --#STATE OPERATIONAL    
    ::= 72

wtWebioEA2x2Alert15 TRAP-TYPE
    ENTERPRISE  wtWebioEA2x2
    VARIABLES   { wtWebioEA2x2AlarmSnmpTrapReleaseText }
    DESCRIPTION
        "This SNMP trap is generated when Alarm 3 was released,
        SNMP trap enable is set and
        SNMP is enabled."
    -- NMS trap annotation
    --#TYPE "Webio Digital Release Alarm 3"
    --#SUMMARY "Release Alarm 3: %s"
    --#ARGUMENTS {0}
    --#SEVERITY INFORMATIONAL
    --#TIMEINDEX 99
    --#STATE OPERATIONAL    
    ::= 73

wtWebioEA2x2Alert16 TRAP-TYPE
    ENTERPRISE  wtWebioEA2x2
    VARIABLES   { wtWebioEA2x2AlarmSnmpTrapReleaseText }
    DESCRIPTION
        "This SNMP trap is generated when Alarm 4 was released,
        SNMP trap enable is set and
        SNMP is enabled."
    -- NMS trap annotation
    --#TYPE "Webio Digital Release Alarm 4"
    --#SUMMARY "Release Alarm 4: %s"
    --#ARGUMENTS {0}
    --#SEVERITY INFORMATIONAL
    --#TIMEINDEX 99
    --#STATE OPERATIONAL    
    ::= 74

wtWebioEA2x2Alert17 TRAP-TYPE
    ENTERPRISE  wtWebioEA2x2
    VARIABLES   { wtWebioEA2x2AlarmSnmpTrapReleaseText }
    DESCRIPTION
        "This SNMP trap is generated when Alarm 5 was released,
        SNMP trap enable is set and
        SNMP is enabled."
    -- NMS trap annotation
    --#TYPE "Webio Digital Release Alarm 5"
    --#SUMMARY "Release Alarm 5: %s"
    --#ARGUMENTS {0}
    --#SEVERITY INFORMATIONAL
    --#TIMEINDEX 99
    --#STATE OPERATIONAL    
    ::= 75

wtWebioEA2x2Alert18 TRAP-TYPE
    ENTERPRISE  wtWebioEA2x2
    VARIABLES   { wtWebioEA2x2AlarmSnmpTrapReleaseText }
    DESCRIPTION
        "This SNMP trap is generated when Alarm 6 was released,
        SNMP trap enable is set and
        SNMP is enabled."
    -- NMS trap annotation
    --#TYPE "Webio Digital Release Alarm 6"
    --#SUMMARY "Release Alarm 6: %s"
    --#ARGUMENTS {0}
    --#SEVERITY INFORMATIONAL
    --#TIMEINDEX 99
    --#STATE OPERATIONAL    
    ::= 76

wtWebioEA2x2Alert19 TRAP-TYPE
    ENTERPRISE  wtWebioEA2x2
    VARIABLES   { wtWebioEA2x2AlarmSnmpTrapReleaseText }
    DESCRIPTION
        "This SNMP trap is generated when Alarm 7 was released,
        SNMP trap enable is set and
        SNMP is enabled."
    -- NMS trap annotation
    --#TYPE "Webio Digital Release Alarm 7"
    --#SUMMARY "Release Alarm 7: %s"
    --#ARGUMENTS {0}
    --#SEVERITY INFORMATIONAL
    --#TIMEINDEX 99
    --#STATE OPERATIONAL    
    ::= 77

wtWebioEA2x2Alert20 TRAP-TYPE
    ENTERPRISE  wtWebioEA2x2
    VARIABLES   { wtWebioEA2x2AlarmSnmpTrapReleaseText }
    DESCRIPTION
        "This SNMP trap is generated when Alarm 8 was released,
        SNMP trap enable is set and
        SNMP is enabled."
    -- NMS trap annotation
    --#TYPE "Webio Digital Release Alarm 8"
    --#SUMMARY "Release Alarm 8: %s"
    --#ARGUMENTS {0}
    --#SEVERITY INFORMATIONAL
    --#TIMEINDEX 99
    --#STATE OPERATIONAL    
    ::= 78

wtWebioEA2x2Alert21 TRAP-TYPE
    ENTERPRISE  wtWebioEA2x2
    VARIABLES   { wtWebioEA2x2AlarmSnmpTrapReleaseText }
    DESCRIPTION
        "This SNMP trap is generated when Alarm 9 was released,
        SNMP trap enable is set and
        SNMP is enabled."
    -- NMS trap annotation
    --#TYPE "Webio Digital Release Alarm 9"
    --#SUMMARY "Release Alarm 9: %s"
    --#ARGUMENTS {0}
    --#SEVERITY INFORMATIONAL
    --#TIMEINDEX 99
    --#STATE OPERATIONAL    
    ::= 79

wtWebioEA2x2Alert22 TRAP-TYPE
    ENTERPRISE  wtWebioEA2x2
    VARIABLES   { wtWebioEA2x2AlarmSnmpTrapReleaseText }
    DESCRIPTION
        "This SNMP trap is generated when Alarm 10 was released,
        SNMP trap enable is set and
        SNMP is enabled."
    -- NMS trap annotation
    --#TYPE "Webio Digital Release Alarm 10"
    --#SUMMARY "Release Alarm 10: %s"
    --#ARGUMENTS {0}
    --#SEVERITY INFORMATIONAL
    --#TIMEINDEX 99
    --#STATE OPERATIONAL    
    ::= 80

wtWebioEA2x2Alert23 TRAP-TYPE
    ENTERPRISE  wtWebioEA2x2
    VARIABLES   { wtWebioEA2x2AlarmSnmpTrapReleaseText }
    DESCRIPTION
        "This SNMP trap is generated when Alarm 11 was released,
        SNMP trap enable is set and
        SNMP is enabled."
    -- NMS trap annotation
    --#TYPE "Webio Digital Release Alarm 11"
    --#SUMMARY "Release Alarm 11: %s"
    --#ARGUMENTS {0}
    --#SEVERITY INFORMATIONAL
    --#TIMEINDEX 99
    --#STATE OPERATIONAL    
    ::= 81

wtWebioEA2x2Alert24 TRAP-TYPE
    ENTERPRISE  wtWebioEA2x2
    VARIABLES   { wtWebioEA2x2AlarmSnmpTrapReleaseText }
    DESCRIPTION
        "This SNMP trap is generated when Alarm 12 was released,
        SNMP trap enable is set and
        SNMP is enabled."
    -- NMS trap annotation
    --#TYPE "Webio Digital Release Alarm 12"
    --#SUMMARY "Release Alarm 12: %s"
    --#ARGUMENTS {0}
    --#SEVERITY INFORMATIONAL
    --#TIMEINDEX 99
    --#STATE OPERATIONAL    
    ::= 82

wtWebioEA2x2AlertDiag TRAP-TYPE
    ENTERPRISE  wtWebioEA2x2
    VARIABLES   { 	
    		wtWebioEA2x2DiagErrorIndex,
    	  	wtWebioEA2x2DiagErrorMessage
    		}
    DESCRIPTION
        "This SNMP trap is generated when a diagnosis/error message was triggered,
        SNMP trap enable is set and
        SNMP is enabled."
    -- NMS trap annotation
    --#TYPE "Webio Digital Diagnose Error"
    --#SUMMARY "Diagnose error index: %d, Message: %s."
    --#ARGUMENTS {0,1}
    --#SEVERITY MAJOR
    --#TIMEINDEX 99
    --#STATE DEGRADED    
    ::= 110

--------------------------------------------------------------------------------
--------------------------------------------------------------------------------
--------------------------------------------------------------------------------

-- wtWebioEA12x12InOut Group
------------------------

wtWebioEA12x12Inputs OBJECT-TYPE
    SYNTAX INTEGER (1..12)
    ACCESS read-only
    STATUS mandatory
    DESCRIPTION
        "Number of idependent inputs."
    ::= { wtWebioEA12x12InOut 1 }

wtWebioEA12x12Outputs OBJECT-TYPE
    SYNTAX INTEGER (1..12)
    ACCESS read-only
    STATUS mandatory
    DESCRIPTION
        "Number of idependent outputs."
    ::= { wtWebioEA12x12InOut 2 }

-- Input Interface Table

wtWebioEA12x12InputTable OBJECT-TYPE
    SYNTAX SEQUENCE OF WtWebioEA12x12InputEntry
    ACCESS not-accessible
    STATUS mandatory
    DESCRIPTION
        "List of input indices."
    ::= { wtWebioEA12x12InOut 3 }

wtWebioEA12x12InputEntry OBJECT-TYPE
    SYNTAX WtWebioEA12x12InputEntry
    ACCESS not-accessible
    STATUS mandatory
    DESCRIPTION
        "Number of the inputs."
    INDEX  { wtWebioEA12x12InputNo }
    ::= { wtWebioEA12x12InputTable 1 }

WtWebioEA12x12InputEntry ::= SEQUENCE {
    wtWebioEA12x12InputNo INTEGER,
    wtWebioEA12x12InputCounter INTEGER,
    wtWebioEA12x12InputCounterClear INTEGER,
    wtWebioEA12x12InputState INTEGER
}

wtWebioEA12x12InputNo OBJECT-TYPE
    SYNTAX INTEGER (1)
    ACCESS read-only
    STATUS mandatory
    DESCRIPTION
        "Index numbers of the inputs."
    ::= { wtWebioEA12x12InputEntry 1 }

wtWebioEA12x12InputCounter OBJECT-TYPE
    SYNTAX INTEGER (1)
    ACCESS read-only
    STATUS mandatory
    DESCRIPTION
        "Value of the input counter."
    ::= { wtWebioEA12x12InputEntry 2 }
    
wtWebioEA12x12InputCounterClear OBJECT-TYPE
    SYNTAX INTEGER
    ACCESS read-only
    STATUS mandatory
    DESCRIPTION
        "Clears the input counter after returning its value."
    ::= { wtWebioEA12x12InputEntry 3 }

wtWebioEA12x12InputState OBJECT-TYPE
    SYNTAX INTEGER{
    wtWebioEA12x12InputState-OFF(0),
    wtWebioEA12x12InputState-ON(1)
    }
    ACCESS read-only
    STATUS mandatory
    DESCRIPTION
        "Value of a single input bit."
    ::= { wtWebioEA12x12InputEntry 4 }    
    
wtWebioEA12x12InputValue OBJECT-TYPE
    SYNTAX INTEGER 
    ACCESS read-only
    STATUS mandatory
    DESCRIPTION
        "This variable is used to read the inputs of the digital I/O port.
        The OCTETS are interpreted bit-by-bit, with each bit corresponding to an output.
        Bit 0 corresponds to the LSB.
        OCTET 1: unused
        OCTET 2: unused
        OCTET 3, Bit 0-3: Digital outputs 8-11
                 Bit 4-7: unused
        OCTET 4, Bit 0-7: Digital outputs 0-7"
    ::= { wtWebioEA12x12InOut 4 }
    

-- Output Interface Table

wtWebioEA12x12OutputTable OBJECT-TYPE
    SYNTAX SEQUENCE OF WtWebioEA12x12OutputEntry
    ACCESS not-accessible
    STATUS mandatory
    DESCRIPTION
        "List of output indices."
    ::= { wtWebioEA12x12InOut 5 }

wtWebioEA12x12OutputEntry OBJECT-TYPE
    SYNTAX WtWebioEA12x12OutputEntry
    ACCESS not-accessible
    STATUS mandatory
    DESCRIPTION
        "Number of the outputs."
    INDEX  { wtWebioEA12x12OutputNo }
    ::= { wtWebioEA12x12OutputTable 1 }

WtWebioEA12x12OutputEntry ::= SEQUENCE {
    wtWebioEA12x12OutputNo INTEGER,
    wtWebioEA12x12OutputState INTEGER
}

wtWebioEA12x12OutputNo OBJECT-TYPE
    SYNTAX INTEGER (1)
    ACCESS read-only
    STATUS mandatory
    DESCRIPTION
        "Output number."
    ::= { wtWebioEA12x12OutputEntry 1 }
    
wtWebioEA12x12OutputState OBJECT-TYPE
    SYNTAX INTEGER{
    wtWebioEA12x12OutputState-OFF(0),
    wtWebioEA12x12OutputState-ON(1)
    }
    ACCESS read-write
    STATUS mandatory
    DESCRIPTION
        "Value of a single output bit."
    ::= { wtWebioEA12x12OutputEntry 2 }    

wtWebioEA12x12OutputValue OBJECT-TYPE
    SYNTAX INTEGER
    ACCESS read-write
    STATUS mandatory
    DESCRIPTION
        "This variable is used to read and write the outputs of the digital I/O port. 
        The OCTETS are interpreted bit-by-bit, with each bit corresponding to an output. 
        Bit 0 corresponds to the LSB.
        OCTET 1: unused
        OCTET 2: unused
        OCTET 3, Bit 0-3: Digital outputs 8-11
                 Bit 4-7: unused
        OCTET 4, Bit 0-7: Digital outputs 0-7"
    ::= { wtWebioEA12x12InOut 6 }
    
wtWebioEA12x12SetOutput OBJECT-TYPE
    SYNTAX OCTET STRING (SIZE (8))
    ACCESS read-write			-- write-only
    STATUS mandatory
    DESCRIPTION
        "This variable allows setting of individual digital outputs. The OCTETS are 
        interpreted bit-by-bit, with each bit corresponding to an output. Bit 0 corresponds 
        to the LSB.
        The first two OCTETS contain the mask which determines which of the outputs are to 
        be set (corresponding bit = 1) and which outputs are to remain unchanged 
        (corresponding bit = 0):
	OCTET 1 : unused
	OCTET 2 : unused
	OCTET 3, Bit 0-3: Mask for digital outputs 8-11
		 Bit 4-7: unused
	OCTET 4, Bit 0-7: Mask for digital outputs 0-7
	
	OCTETS 5-8 contain the level (1=HIGH, 0=LOW) which the inputs 
	should assume:
	OCTET 5 : unused
	OCTET 6 : unused
	OCTET 7, Bit 0-3: Level of digital outputs 8-11
		 Bit 4-7: unused
        OCTET 8, Bit 0-7: Level of digital outputs 0-7"
    ::= { wtWebioEA12x12InOut 7 }
    
-- wtWebioEA12x12SessCntrl Group
--------------------------------

wtWebioEA12x12SessCntrlPassword OBJECT-TYPE
    SYNTAX OCTET STRING 
    ACCESS read-write
    STATUS mandatory
    DESCRIPTION
        "Entering this password opens a session which is ended by writing a 1 to 
        wtWebioEA12x12SessCntrlLogout. When read this variable provides a string of
        length zero."
    ::= { wtWebioEA12x12SessCntrl 1 }

wtWebioEA12x12SessCntrlConfigMode OBJECT-TYPE
    SYNTAX INTEGER {
    wtWebioEA12x12SessCntrl-NoSession(0),
    wtWebioEA12x12SessCntrl-Session(1)
    }
    ACCESS read-only
    STATUS mandatory
    DESCRIPTION
        "When the device is in SNMP configuration mode, the value 1 is
        returned, otherwise 0. If the read value is 0 even though the password
        was written, the device is already in config mode and the variables
        can only be read."
    ::= { wtWebioEA12x12SessCntrl 2 }

wtWebioEA12x12SessCntrlLogout OBJECT-TYPE
    SYNTAX INTEGER 
    ACCESS read-write
    STATUS mandatory
    DESCRIPTION
        "If the device is in configuration mode and the session was opened by
        this SNMP Manager, writing a 1 to this variable will end the session 
        and all parameters are stored.
        Writing a 2 discards all entries again. When read this variable
        provides the value 0."
    ::= { wtWebioEA12x12SessCntrl 3 }

wtWebioEA12x12SessCntrlAdminPassword OBJECT-TYPE
    SYNTAX OCTET STRING 
    ACCESS read-write
    STATUS mandatory
    DESCRIPTION
        "This password protects access to the variables with administrator rights.
        It can only be changed by the administrator. If no password was assigned,
        the valid password is public."
    ::= { wtWebioEA12x12SessCntrl 4 }

wtWebioEA12x12SessCntrlConfigPassword OBJECT-TYPE
    SYNTAX OCTET STRING 
    ACCESS read-write
    STATUS mandatory
    DESCRIPTION
        "This password protects access to the variables with configurator rights. It can
        be changed by the administrator and by the configurator. If no password was assigned, 
        the valid password is public. When read this variable provides a null-pointer."
    ::= { wtWebioEA12x12SessCntrl 5 }
    
-- wtWebioEA12x12Text Group
------------------------

wtWebioEA12x12DeviceName OBJECT-TYPE
    SYNTAX OCTET STRING 
    ACCESS read-write
    STATUS mandatory
    DESCRIPTION
        "Name of the Webio, which is user definable."
    ::= { wtWebioEA12x12Text 1 }

wtWebioEA12x12DeviceText OBJECT-TYPE
    SYNTAX OCTET STRING 
    ACCESS read-write
    STATUS mandatory
    DESCRIPTION
        "Description of the Webio, which is user definable."
    ::= { wtWebioEA12x12Text 2 }
    
wtWebioEA12x12DeviceLocation OBJECT-TYPE
    SYNTAX OCTET STRING 
    ACCESS read-write
    STATUS mandatory
    DESCRIPTION
        "Description of the location of the Webio, which is user definable."
    ::= { wtWebioEA12x12Text 3 }

wtWebioEA12x12DeviceContact OBJECT-TYPE
    SYNTAX OCTET STRING 
    ACCESS read-write
    STATUS mandatory
    DESCRIPTION
        "Contact address of the system operator of the Webio, which is user definable."
    ::= { wtWebioEA12x12Text 4 }    

-- wtWebioEA12x12TimeZone Group
----------------------------

wtWebioEA12x12TzOffsetHrs OBJECT-TYPE
    SYNTAX INTEGER 
    ACCESS read-write
    STATUS mandatory
    DESCRIPTION
        "Offset hours for the time zone (winter time) with respect to UTC."
    ::= { wtWebioEA12x12TimeZone 1 }

wtWebioEA12x12TzOffsetMin OBJECT-TYPE
    SYNTAX INTEGER 
    ACCESS read-write
    STATUS mandatory
    DESCRIPTION
        "Offset minutes for the time zone (winter time) with respect to UTC."
    ::= { wtWebioEA12x12TimeZone 2 }

wtWebioEA12x12TzEnable OBJECT-TYPE
    SYNTAX OCTET STRING (SIZE(4))
    ACCESS read-write
    STATUS mandatory
    DESCRIPTION
        "Binary coded conditions:
        Octet 1: unused
        Octet 2: unused
        Octet 3: unused
        Octet 4:
        	Bit 1-7: unused
	        Bit 0  : Apply Timezone"
    ::= { wtWebioEA12x12TimeZone 3 }

wtWebioEA12x12StTzOffsetHrs OBJECT-TYPE
    SYNTAX INTEGER 
    ACCESS read-write
    STATUS mandatory
    DESCRIPTION
        "Offset hours of the time zone (summer time) with respect to UTC."
    ::= { wtWebioEA12x12TimeZone 4 }

wtWebioEA12x12StTzOffsetMin OBJECT-TYPE
    SYNTAX INTEGER 
    ACCESS read-write
    STATUS mandatory
    DESCRIPTION
        "Offset minutes of the time zone (summer time) with respect to UTC."
    ::= { wtWebioEA12x12TimeZone 5 }

wtWebioEA12x12StTzEnable OBJECT-TYPE
    SYNTAX OCTET STRING (SIZE(4))
    ACCESS read-write
    STATUS mandatory
    DESCRIPTION
        "Binary coded conditions:
        Octet 1: unused
        Octet 2: unused
        Octet 3: unused
        Octet 4:
        	Bit 1-7: unused
	        Bit 0  : Apply Summertime"
    ::= { wtWebioEA12x12TimeZone 6 }

wtWebioEA12x12StTzStartMonth OBJECT-TYPE
    SYNTAX INTEGER {
    	wtWebioEA12x12StartMonth-January(1),
    	wtWebioEA12x12StartMonth-February(2),
    	wtWebioEA12x12StartMonth-March(3),
    	wtWebioEA12x12StartMonth-April(4),
    	wtWebioEA12x12StartMonth-May(5),
    	wtWebioEA12x12StartMonth-June(6),
    	wtWebioEA12x12StartMonth-July(7),
    	wtWebioEA12x12StartMonth-August(8),
    	wtWebioEA12x12StartMonth-September(9),
    	wtWebioEA12x12StartMonth-October(10),
    	wtWebioEA12x12StartMonth-November(11),
    	wtWebioEA12x12StartMonth-December(12)
    	}
    	
    ACCESS read-write
    STATUS mandatory
    DESCRIPTION
        "Month in which the change is made from winter time to summer time."
    ::= { wtWebioEA12x12TimeZone 7 }

wtWebioEA12x12StTzStartMode OBJECT-TYPE
    SYNTAX INTEGER {
    	wtWebioEA12x12StartMode-first(1),
    	wtWebioEA12x12StartMode-second(2),
    	wtWebioEA12x12StartMode-third(3),
    	wtWebioEA12x12StartMode-fourth(4),
    	wtWebioEA12x12StartMode-last(5)
    	}
    	
    ACCESS read-write
    STATUS mandatory
    DESCRIPTION
        "Mode of the day of the week for which the change is made from winter time to summer time."
    ::= { wtWebioEA12x12TimeZone 8 }

wtWebioEA12x12StTzStartWday OBJECT-TYPE
    SYNTAX INTEGER {
    	wtWebioEA12x12StartWday-Sunday(1),
    	wtWebioEA12x12StartWday-Monday(2),
    	wtWebioEA12x12StartWday-Tuesday(3),
    	wtWebioEA12x12StartWday-Thursday(4),
    	wtWebioEA12x12StartWday-Wednesday(5),
    	wtWebioEA12x12StartWday-Friday(6),
    	wtWebioEA12x12StartWday-Saturday(7)
    	}
    	
    ACCESS read-write
    STATUS mandatory
    DESCRIPTION
        "Day of the week on which the change is made from winter time to summer time"
    ::= { wtWebioEA12x12TimeZone 9 }
    
wtWebioEA12x12StTzStartHrs OBJECT-TYPE
    SYNTAX INTEGER 
    ACCESS read-write
    STATUS mandatory
    DESCRIPTION
        "Hour in which the time zone is changed from winter to summer time with
        respect to UTC."
    ::= { wtWebioEA12x12TimeZone 10 }

wtWebioEA12x12StTzStartMin OBJECT-TYPE
    SYNTAX INTEGER 
    ACCESS read-write
    STATUS mandatory
    DESCRIPTION
        "Minute in which the time zone is changed from winter to summer time with
        respect to UTC."
    ::= { wtWebioEA12x12TimeZone 11 }
 
wtWebioEA12x12StTzStopMonth OBJECT-TYPE
    SYNTAX INTEGER {
    	wtWebioEA12x12StopMonth-January(1),
    	wtWebioEA12x12StopMonth-February(2),
    	wtWebioEA12x12StopMonth-March(3),
    	wtWebioEA12x12StopMonth-April(4),
    	wtWebioEA12x12StopMonth-May(5),
    	wtWebioEA12x12StopMonth-June(6),
    	wtWebioEA12x12StopMonth-July(7),
    	wtWebioEA12x12StopMonth-August(8),
    	wtWebioEA12x12StopMonth-September(9),
    	wtWebioEA12x12StopMonth-October(10),
    	wtWebioEA12x12StopMonth-November(11),
    	wtWebioEA12x12StopMonth-December(12)
    	}
    ACCESS read-write
    STATUS mandatory
    DESCRIPTION
        "Month in which the change is made from summer time to winter time."
   ::= { wtWebioEA12x12TimeZone 12 }

wtWebioEA12x12StTzStopMode OBJECT-TYPE
    SYNTAX INTEGER {
    	wtWebioEA12x12StopMode-first(1),
    	wtWebioEA12x12StopMode-second(2),
    	wtWebioEA12x12StopMode-third(3),
    	wtWebioEA12x12StopMode-fourth(4),
    	wtWebioEA12x12StopMode-last(5)
    	}
    ACCESS read-write
    STATUS mandatory
    DESCRIPTION
        "Mode of the week day on which the change is made from summer time to winter time."
    ::= { wtWebioEA12x12TimeZone 13 }

wtWebioEA12x12StTzStopWday OBJECT-TYPE
    SYNTAX INTEGER {
    	wtWebioEA12x12StopWday-Sunday(1),
    	wtWebioEA12x12StopWday-Monday(2),
    	wtWebioEA12x12StopWday-Tuesday(3),
    	wtWebioEA12x12StopWday-Thursday(4),
    	wtWebioEA12x12StopWday-Wednesday(5),
    	wtWebioEA12x12StopWday-Friday(6),
    	wtWebioEA12x12StopWday-Saturday(7)
    	}
    ACCESS read-write
    STATUS mandatory
    DESCRIPTION
        "Day of the week on which the change is made from summer time to winter time."
    ::= { wtWebioEA12x12TimeZone 14 }
    
wtWebioEA12x12StTzStopHrs OBJECT-TYPE
    SYNTAX INTEGER 
    ACCESS read-write
    STATUS mandatory
    DESCRIPTION
        "Hour at which the time zone is changed from summer to winter time with
        respect to UTC."
    ::= { wtWebioEA12x12TimeZone 15 }

wtWebioEA12x12StTzStopMin OBJECT-TYPE
    SYNTAX INTEGER 
    ACCESS read-write
    STATUS mandatory
    DESCRIPTION
        "Minute at which the time zone is changed from summer to winter time with
        respect to UTC."
    ::= { wtWebioEA12x12TimeZone 16 }

-- wtWebioEA12x12TimeServer Group
----------------------------

wtWebioEA12x12TimeServer1 OBJECT-TYPE
    SYNTAX OCTET STRING 
    ACCESS read-write
    STATUS mandatory
    DESCRIPTION
        "IP address or name of the 1st time server in ASCII"
    ::= { wtWebioEA12x12TimeServer 1 }

wtWebioEA12x12TimeServer2 OBJECT-TYPE
    SYNTAX OCTET STRING 
    ACCESS read-write
    STATUS mandatory
    DESCRIPTION
        "IP address or name of the 2nd time server in ASCII"
    ::= { wtWebioEA12x12TimeServer 2 }

wtWebioEA12x12TsEnable OBJECT-TYPE
    SYNTAX OCTET STRING (SIZE(4))
    ACCESS read-write
    STATUS mandatory
    DESCRIPTION
        "Binary coded conditions:
        Octet 1: unused
        Octet 2: unused
        Octet 3: unused
        Octet 4:
        	Bit 1-7: unused
	        Bit 0  : Apply Time Server"
    ::= { wtWebioEA12x12TimeServer 3 }

wtWebioEA12x12TsSyncTime OBJECT-TYPE
    SYNTAX INTEGER 
    ACCESS read-write
    STATUS mandatory
    DESCRIPTION
        "Daily synchronisation time with the time server (hour: 0-23)."
    ::= { wtWebioEA12x12TimeServer 4 }
      
    
-- wtWebioEA12x12DeviceClock Group
----------------------------

wtWebioEA12x12ClockHrs OBJECT-TYPE
    SYNTAX INTEGER (0..23)
    ACCESS read-write
    STATUS mandatory
    DESCRIPTION
        "Clock hours taking into account the time zone settings."
    ::= { wtWebioEA12x12DeviceClock 1 }

wtWebioEA12x12ClockMin OBJECT-TYPE
    SYNTAX INTEGER (0..59)
    ACCESS read-write
    STATUS mandatory
    DESCRIPTION
        "Clock minutes taking into account the time zone settings."
    ::= { wtWebioEA12x12DeviceClock 2 }

wtWebioEA12x12ClockDay OBJECT-TYPE
    SYNTAX INTEGER (1..31)
    ACCESS read-write
    STATUS mandatory
    DESCRIPTION
        "Date: Day of the month, taking into account the time zone settings."
    ::= { wtWebioEA12x12DeviceClock 3 }

wtWebioEA12x12ClockMonth OBJECT-TYPE
   SYNTAX INTEGER {
    	wtWebioEA12x12ClockMonth-January(1),
    	wtWebioEA12x12ClockMonth-February(2),
    	wtWebioEA12x12ClockMonth-March(3),
    	wtWebioEA12x12ClockMonth-April(4),
    	wtWebioEA12x12ClockMonth-May(5),
    	wtWebioEA12x12ClockMonth-June(6),
    	wtWebioEA12x12ClockMonth-July(7),
    	wtWebioEA12x12ClockMonth-August(8),
    	wtWebioEA12x12ClockMonth-September(9),
    	wtWebioEA12x12ClockMonth-October(10),
    	wtWebioEA12x12ClockMonth-November(11),
    	wtWebioEA12x12ClockMonth-December(12)
    	}
    ACCESS read-write
    STATUS mandatory
    DESCRIPTION
        "Date: Month, taking into account the time zone settings."
    ::= { wtWebioEA12x12DeviceClock 4 }

wtWebioEA12x12ClockYear OBJECT-TYPE
    SYNTAX INTEGER (0..65535)
    ACCESS read-write
    STATUS mandatory
    DESCRIPTION
        "Date: Year, taking into account the time zone settings."
    ::= { wtWebioEA12x12DeviceClock 5 }

-- wtWebioEA12x12Network Group
------------------------

wtWebioEA12x12IpAddress OBJECT-TYPE
    SYNTAX IpAddress
    ACCESS read-write
    STATUS mandatory
    DESCRIPTION
        "IP address of the Webio"
    ::= { wtWebioEA12x12Network 1 }

wtWebioEA12x12SubnetMask OBJECT-TYPE
    SYNTAX IpAddress
    ACCESS read-write
    STATUS mandatory
    DESCRIPTION
        "Subnet mask of the Webio"
    ::= { wtWebioEA12x12Network 2 }

wtWebioEA12x12Gateway OBJECT-TYPE
    SYNTAX IpAddress
    ACCESS read-write
    STATUS mandatory
    DESCRIPTION
        "Gateway of the Webio"
    ::= { wtWebioEA12x12Network 3 }

wtWebioEA12x12DnsServer1 OBJECT-TYPE
    SYNTAX OCTET STRING 
    ACCESS read-write
    STATUS mandatory
    DESCRIPTION
        "IP address of the 1st DNS server in ASCII"
    ::= { wtWebioEA12x12Network 4 }

wtWebioEA12x12DnsServer2 OBJECT-TYPE
    SYNTAX OCTET STRING 
    ACCESS read-write
    STATUS mandatory
    DESCRIPTION
        "IP address of the 2nd DNS server in ASCII"
    ::= { wtWebioEA12x12Network 5 }

wtWebioEA12x12AddConfig OBJECT-TYPE
    SYNTAX OCTET STRING 
    ACCESS read-write
    STATUS mandatory
    DESCRIPTION
        "Additional configuration (1=ON):
        Octet 1: unused
        Octet 2: unused
        Octet 3: unused
        Octet 4:
	        Bit 1: DHCP  enable
	        Bit 0: BOOTP enable"
    ::= { wtWebioEA12x12Network 6 }

--  wtWebioEA12x12HTTP Group
--------------------------------

wtWebioEA12x12Startup OBJECT-TYPE
    SYNTAX OCTET STRING 
    ACCESS read-write
    STATUS mandatory
    DESCRIPTION
        "Binary coded start page, more than one page must not be selected:
        Octet 1: unused
        Octet 2: unused
        Octet 3: unused
        Octet 4:
        	Bit 2: user.htm
        	Bit 1: home.htm
	        Bit 0: index.htm"
    ::= { wtWebioEA12x12HTTP 1 }

wtWebioEA12x12GetHeaderEnable OBJECT-TYPE
    SYNTAX OCTET STRING 
    ACCESS read-write
    STATUS mandatory
    DESCRIPTION
        "If bits are set, every answer of a short form GET question will be lead
        by the IP-address and name of the device (Header) or a HTTP header (HTTP):
        Octet 1: unused
        Octet 2: unused
        Octet 3: unused
        Octet 4:
        	Bit 2-7: unused
        	Bit 1  : GET HTTP enable
                Bit 0  : GET Header enable"
    ::= { wtWebioEA12x12HTTP 2 }

wtWebioEA12x12HttpInputTrigger OBJECT-TYPE
    SYNTAX OCTET STRING (SIZE (4))
    ACCESS read-write
    STATUS mandatory
    DESCRIPTION
        "Every change on the inputs causes their state to be transmitted to the 
        remote device. To minimize data traffic, individual inputs may be exempted 
        from this rule. Nevertheless every transmission will contain all input bits.
        If a bit is set (1), a change of state on the corresponding input 
        triggers a transmission. If the bit is not set (0), no transmission 
        takes place.
        The OCTETS are interpreted bit-by-bit, with each bit corresponding to an output. 
        Bit 0 corresponds to the LSB.
        OCTET 1: unused
        OCTET 2: unused
        OCTET 3, Bit 0-3: Digital inputs 8-11
                 Bit 4-7: unused
        OCTET 4, Bit 0-7: Digital inputs 0-7"
    ::= { wtWebioEA12x12HTTP 3 }

wtWebioEA12x12HttpPort OBJECT-TYPE
    SYNTAX INTEGER (1..65534)
    ACCESS read-write
    STATUS mandatory
    DESCRIPTION
       "Definition of the standard HTML port (Default: 80)."
    ::= { wtWebioEA12x12HTTP 4 }        
    
    
-- wtWebioEA12x12Mail Group
--------------------------------

wtWebioEA12x12MailAdName OBJECT-TYPE
    SYNTAX OCTET STRING 
    ACCESS read-write
    STATUS mandatory
    DESCRIPTION
        "Device name for mail administration."
    ::= { wtWebioEA12x12Mail 1 }
    
wtWebioEA12x12MailReply OBJECT-TYPE
    SYNTAX OCTET STRING 
    ACCESS read-write
    STATUS mandatory
    DESCRIPTION
        "Reply address for the mail server."
    ::= { wtWebioEA12x12Mail 2 }
    
wtWebioEA12x12MailServer OBJECT-TYPE
    SYNTAX OCTET STRING 
    ACCESS read-write
    STATUS mandatory
    DESCRIPTION
        "Name or IP address of the mail server."
    ::= { wtWebioEA12x12Mail 3 }
    
wtWebioEA12x12MailEnable OBJECT-TYPE
    SYNTAX OCTET STRING 
    ACCESS read-write
    STATUS mandatory
    DESCRIPTION
        "Set this bit to enable the sending of mails:
        Octet 1: unused
        Octet 2: unused
        Octet 3: unused
        Octet 4:
        	Bit 1-7: unused
                Bit 0  : Mail enable"
    ::= { wtWebioEA12x12Mail 4 }

wtWebioEA12x12MailAuthentication OBJECT-TYPE
    SYNTAX OCTET STRING (SIZE (4))
    ACCESS read-write
    STATUS mandatory
    DESCRIPTION
        "Selection of the authentication modi:
        The OCTETS are interpreted bit-by-bit,
        Bit 0 corresponds to the LSB.
        OCTET 1: unused
        OCTET 2: unused
        OCTET 3: unused
        OCTET 4: Bit 3-7: unused
        	 Bit 2  : POP3 before SMTP
        	 Bit 1  : ESMTP, authentication
        	 Bit 0  : SMTP, no authentication"
    ::= { wtWebioEA12x12Mail 5 }
    
wtWebioEA12x12MailAuthUser OBJECT-TYPE
    SYNTAX OCTET STRING 
    ACCESS read-write
    STATUS mandatory
    DESCRIPTION
        "Name of the user to be authenticated."
    ::= { wtWebioEA12x12Mail 6 }    
    
wtWebioEA12x12MailAuthPassword OBJECT-TYPE
    SYNTAX OCTET STRING 
    ACCESS read-write
    STATUS mandatory
    DESCRIPTION
        "Authentication password."
    ::= { wtWebioEA12x12Mail 7 }    
    
wtWebioEA12x12MailPop3Server OBJECT-TYPE
    SYNTAX OCTET STRING 
    ACCESS read-write
    STATUS mandatory
    DESCRIPTION
        "Name or Ip-address of the POP3 Servers."
    ::= { wtWebioEA12x12Mail 8 }        
    

--  wtWebioEA12x12Snmp Group
--------------------------------

wtWebioEA12x12SnmpEnable OBJECT-TYPE
    SYNTAX OCTET STRING 
    ACCESS read-write
    STATUS mandatory
    DESCRIPTION
        "Set bit 0 to enable SNMP.
        If disabled, the device did not respond to any SNMP requests.
        Bit 1 decided wether the community string of read operations 
        is compared with the system password or not:
        Octet 1: unused
        Octet 2: unused
        Octet 3: unused
        Octet 4:
        	Bit 1-7: unused
        	Bit 0  : SNMP enable"
    ::= { wtWebioEA12x12SNMP 1 }
    
wtWebioEA12x12SnmpCommunityStringRead OBJECT-TYPE
    SYNTAX OCTET STRING
    ACCESS read-write
    STATUS mandatory
    DESCRIPTION
        "Community string read only"
    ::= { wtWebioEA12x12SNMP 2 }

wtWebioEA12x12SnmpCommunityStringReadWrite OBJECT-TYPE
    SYNTAX OCTET STRING
    ACCESS read-write
    STATUS mandatory
    DESCRIPTION
        "Community string read / write"
    ::= { wtWebioEA12x12SNMP 3 }

wtWebioEA12x12SnmpSystemTrapManagerIP OBJECT-TYPE
    SYNTAX OCTET STRING 
    ACCESS read-write
    STATUS mandatory
    DESCRIPTION
        "Name or IP address of the TCP server which accepts the system trap."
    ::= { wtWebioEA12x12SNMP 4 }
    
wtWebioEA12x12SnmpSystemTrapEnable OBJECT-TYPE
    SYNTAX OCTET STRING (SIZE(4))
    ACCESS read-write
    STATUS mandatory
    DESCRIPTION
        "Binary coded trigger conditions:
        Octet 1: unused
        Octet 2: unused
        Octet 3: unused
        Octet 4:
	        Bit 0:   ColdStart
	        Bit 1:   WarmStart
	        Bit 2:   Diag messages
	        Bit 3-7: unused"
    ::= { wtWebioEA12x12SNMP 5 }    

-- wtWebioEA12x12Udp Group
--------------------------------   

wtWebioEA12x12UdpAdminPort OBJECT-TYPE
    SYNTAX INTEGER
    ACCESS read-write
    STATUS mandatory
    DESCRIPTION
        "Udp port to which the Udp queries ( short form GET requests) can be sent. This
        port number must be unique within the device."
    ::= { wtWebioEA12x12UDP 1 }

wtWebioEA12x12UdpEnable OBJECT-TYPE
    SYNTAX OCTET STRING 
    ACCESS read-write
    STATUS mandatory
    DESCRIPTION
        "Set this bit to enable UDP support:
        Octet 1: unused
        Octet 2: unused
        Octet 3: unused
        Octet 4:
        	Bit 1-7: unused
                Bit 0  : UDP enable"
    ::= { wtWebioEA12x12UDP 2 }

wtWebioEA12x12UdpRemotePort OBJECT-TYPE
    SYNTAX INTEGER
    ACCESS read-write
    STATUS mandatory
    DESCRIPTION
        "Udp remote port setting.
        If this value is set to zero, the source port read from a request will be used 
        as destination port for the answer.
        A non zero value forced the destination port to this value."
    ::= { wtWebioEA12x12UDP 3 }
    
--  wtWebioEA12x12Binary Group
--------------------------------

wtWebioEA12x12BinaryModeCount OBJECT-TYPE
    SYNTAX INTEGER (1..2)
    ACCESS read-only
    STATUS mandatory
    DESCRIPTION
        "Number of independent binary channels."
    ::= { wtWebioEA12x12Binary 1 }
    
-- Binary Interface Table

wtWebioEA12x12BinaryIfTable OBJECT-TYPE
    SYNTAX SEQUENCE OF WtWebioEA12x12BinaryIfEntry
    ACCESS not-accessible
    STATUS mandatory
    DESCRIPTION
        "Table of indices."
    ::= { wtWebioEA12x12Binary 2 }

wtWebioEA12x12BinaryIfEntry OBJECT-TYPE
    SYNTAX WtWebioEA12x12BinaryIfEntry
    ACCESS not-accessible
    STATUS mandatory
    DESCRIPTION
        "Indices of the binary channels."
    INDEX  { wtWebioEA12x12BinaryModeNo }
    ::= { wtWebioEA12x12BinaryIfTable 1 }

WtWebioEA12x12BinaryIfEntry ::= SEQUENCE {
    wtWebioEA12x12BinaryModeNo INTEGER
}

wtWebioEA12x12BinaryModeNo OBJECT-TYPE
    SYNTAX INTEGER (1..2)
    ACCESS read-only
    STATUS mandatory
    DESCRIPTION
        "Number of the binary channel."
    ::= { wtWebioEA12x12BinaryIfEntry 1 }

-- Binary Table
--------------------------------

wtWebioEA12x12BinaryTable OBJECT-TYPE
    SYNTAX SEQUENCE OF WtWebioEA12x12BinaryEntry
    ACCESS not-accessible
    STATUS mandatory
    DESCRIPTION
        "Table of properties of the binary mode."
    ::= { wtWebioEA12x12Binary 3 }

wtWebioEA12x12BinaryEntry OBJECT-TYPE
    SYNTAX WtWebioEA12x12BinaryEntry
    ACCESS not-accessible
    STATUS mandatory
    DESCRIPTION
        "Binary properties."
    INDEX  { wtWebioEA12x12BinaryModeNo }
    ::= { wtWebioEA12x12BinaryTable 1 }

WtWebioEA12x12BinaryEntry ::= SEQUENCE {
    wtWebioEA12x12BinaryOperationMode			OCTET STRING,
    wtWebioEA12x12BinaryTcpServerLocalPort		INTEGER,
    wtWebioEA12x12BinaryTcpServerInputTrigger		OCTET STRING,
    wtWebioEA12x12BinaryTcpServerApplicationMode	OCTET STRING,
    wtWebioEA12x12BinaryTcpClientLocalPort		INTEGER,
    wtWebioEA12x12BinaryTcpClientServerPort		INTEGER,
    wtWebioEA12x12BinaryTcpClientServerIpAddr		OCTET STRING,
    wtWebioEA12x12BinaryTcpClientServerPassword		OCTET STRING,
    wtWebioEA12x12BinaryTcpClientInactivity		INTEGER,
    wtWebioEA12x12BinaryTcpClientInputTrigger		OCTET STRING,
    wtWebioEA12x12BinaryTcpClientInterval		INTEGER,
    wtWebioEA12x12BinaryTcpClientApplicationMode	OCTET STRING,
    wtWebioEA12x12BinaryUdpPeerLocalPort		INTEGER,
    wtWebioEA12x12BinaryUdpPeerRemotePort		INTEGER,
    wtWebioEA12x12BinaryUdpPeerRemoteIpAddr		OCTET STRING,
    wtWebioEA12x12BinaryUdpPeerInputTrigger		OCTET STRING,
    wtWebioEA12x12BinaryUdpPeerInterval			INTEGER,
    wtWebioEA12x12BinaryUdpPeerApplicationMode		OCTET STRING,
    wtWebioEA12x12BinaryConnectedPort			INTEGER,
    wtWebioEA12x12BinaryConnectedIpAddr			IpAddress,
    wtWebioEA12x12BinaryTcpServerClientHttpPort		INTEGER,
    wtWebioEA12x12BinaryTcpClientServerHttpPort		INTEGER
    
}

wtWebioEA12x12BinaryOperationMode OBJECT-TYPE
    SYNTAX OCTET STRING (SIZE (4))
    ACCESS read-write
    STATUS mandatory
    DESCRIPTION
        "Selection of the operation mode:
        The OCTETS are interpreted bit-by-bit,
        Bit 0 corresponds to the LSB.
        OCTET 1: unused
        OCTET 2: unused
        OCTET 3: unused
        OCTET 4: Bit 3-7: unused
        	 Bit 2  : UDP Peer
        	 Bit 1  : TCP Client
        	 Bit 0  : TCP Server"
    ::= { wtWebioEA12x12BinaryEntry 1 }

wtWebioEA12x12BinaryTcpServerLocalPort OBJECT-TYPE
    SYNTAX INTEGER (1..65535)
    ACCESS read-write
    STATUS mandatory
    DESCRIPTION
        "Local TCP port for data exchange in this server mode.
        This port number must be unique within the device.
	Reserved port number must not be used (refere to the manual)."
    ::= { wtWebioEA12x12BinaryEntry 2 }

wtWebioEA12x12BinaryTcpServerInputTrigger OBJECT-TYPE
    SYNTAX OCTET STRING (SIZE (4))
    ACCESS read-write
    STATUS mandatory
    DESCRIPTION
        "Every change on the inputs causes their state to be transmitted to the 
        remote device. To minimize data traffic, individual inputs may be exempted 
        from this rule. Nevertheless every transmission will contain all input bits.
        If a bit is set (1), a change of state on the corresponding input 
        triggers a transmission. If the bit is not set (0), no transmission 
        takes place.
        The OCTETS are interpreted bit-by-bit, with each bit corresponding to an input. 
        Bit 0 corresponds to the LSB.
        OCTET 1: unused
        OCTET 2: unused
        OCTET 3, Bit 0-3: Digital inputs 8-11
                 Bit 4-7: unused
        OCTET 4, Bit 0-7: Digital inputs 0-7"
    ::= { wtWebioEA12x12BinaryEntry 3 }

wtWebioEA12x12BinaryTcpServerApplicationMode OBJECT-TYPE
    SYNTAX OCTET STRING (SIZE (4))
    ACCESS read-write
    STATUS mandatory
    DESCRIPTION
        "Selection of the application mode:
        The OCTETS are interpreted bit-by-bit,
        Bit 0 corresponds to the LSB.
        OCTET 1: unused
        OCTET 2: unused
        OCTET 3: unused
        OCTET 4: Bit 4-7: unused
        	 Bit 3  : OPC Device
        	 Bit 2  : Box2Box Slave
        	 Bit 1  : Compatible 50xxx
        	 Bit 0  : Default"
    ::= { wtWebioEA12x12BinaryEntry 4 }
    
wtWebioEA12x12BinaryTcpClientLocalPort OBJECT-TYPE
    SYNTAX INTEGER (1..65535)
    ACCESS read-write
    STATUS mandatory
    DESCRIPTION
        "Local TCP port for data exchange in this client mode.
        This port number must be unique within the device.
	Reserved port number must not be used (refere to the manual)."
    ::= { wtWebioEA12x12BinaryEntry 5 }

wtWebioEA12x12BinaryTcpClientServerPort OBJECT-TYPE
    SYNTAX INTEGER (1..65535)
    ACCESS read-write
    STATUS mandatory
    DESCRIPTION
        "Port number of the server. A complete set of port number, IP address
        and a valid input/output mask starts this mode.
        No data exchange take place when setting the server port to zero."
    ::= { wtWebioEA12x12BinaryEntry 6 }

wtWebioEA12x12BinaryTcpClientServerIpAddr OBJECT-TYPE
    SYNTAX OCTET STRING
    ACCESS read-write
    STATUS mandatory
    DESCRIPTION
        "Ip address of the server. A complete set of port number, IP address
        and a valid input/output mask starts this mode.
        No data exchange take place when setting the server IP address to 0.0.0.0."
    ::= { wtWebioEA12x12BinaryEntry 7 }

wtWebioEA12x12BinaryTcpClientServerPassword OBJECT-TYPE
    SYNTAX OCTET STRING
    ACCESS read-write
    STATUS mandatory
    DESCRIPTION
        "Building a connection may be protected by the 
        administrator password of the server. Enter the server password
        to establish the connection, if a server administrator password
        exists."
    ::= { wtWebioEA12x12BinaryEntry 8 }

wtWebioEA12x12BinaryTcpClientInactivity OBJECT-TYPE
    SYNTAX INTEGER 
    ACCESS read-write
    STATUS mandatory
    DESCRIPTION
        "Connection timeout in 100ms. If no data are exchanged within the specified  
        time, the device closes the connection to the server.
        The value 0 deactivates the timer. Using the Box2Box mode this function is
        disabled."
    ::= { wtWebioEA12x12BinaryEntry 9 }
    
wtWebioEA12x12BinaryTcpClientInputTrigger OBJECT-TYPE
    SYNTAX OCTET STRING (SIZE (4))
    ACCESS read-write
    STATUS mandatory
    DESCRIPTION
        "Every change on the inputs causes their state to be transmitted to the 
        remote device. To minimize data traffic, individual inputs may be exempted 
        from this rule. Nevertheless every transmission will contain all input bits.
        If a bit is set (1), a change of state on the corresponding input 
        triggers a transmission. If the bit is not set (0), no transmission 
        takes place.
        The OCTETS are interpreted bit-by-bit, with each bit corresponding to an input. 
        Bit 0 corresponds to the LSB.
        OCTET 1: unused
        OCTET 2: unused
        OCTET 3, Bit 0-3: Digital inputs 8-11
                 Bit 4-7: unused
        OCTET 4, Bit 0-7: Digital inputs 0-7"
    ::= { wtWebioEA12x12BinaryEntry 10 }
 
wtWebioEA12x12BinaryTcpClientInterval OBJECT-TYPE
    SYNTAX INTEGER (0..65535)
    ACCESS read-write
    STATUS mandatory
    DESCRIPTION
        "Configurable interval with a 100ms base, in which the Webio device sends
        data to the configured application. A interval of zero stopps the 
        periodical sending."
    ::= { wtWebioEA12x12BinaryEntry 11 }

wtWebioEA12x12BinaryTcpClientApplicationMode OBJECT-TYPE
    SYNTAX OCTET STRING (SIZE (4))
    ACCESS read-write
    STATUS mandatory
    DESCRIPTION
        "Selection of the application mode:
        The OCTETS are interpreted bit-by-bit,
        Bit 0 corresponds to the LSB.
        OCTET 1: unused
        OCTET 2: unused
        OCTET 3: unused
        OCTET 4: Bit 3-7: unused
        	 Bit 2  : Box2Box Slave
        	 Bit 1  : Compatible 50xxx
        	 Bit 0  : Default"
    ::= { wtWebioEA12x12BinaryEntry 12 }

wtWebioEA12x12BinaryUdpPeerLocalPort OBJECT-TYPE
    SYNTAX INTEGER (1..65535)
    ACCESS read-write
    STATUS mandatory
    DESCRIPTION
        "Local UDP port for data exchange in this peer to peer mode.
        This port number must be unique within the device.
	Reserved port number must not be used (refere to the manual)."
    ::= { wtWebioEA12x12BinaryEntry 13 }

wtWebioEA12x12BinaryUdpPeerRemotePort OBJECT-TYPE
    SYNTAX INTEGER (1..65535)
    ACCESS read-write
    STATUS mandatory
    DESCRIPTION
        "Port number of the remote device. A complete set of port number, IP address
        and a valid input/output mask starts this mode.
        No data exchange take place when setting the remote port to zero."
    ::= { wtWebioEA12x12BinaryEntry 14 }

wtWebioEA12x12BinaryUdpPeerRemoteIpAddr OBJECT-TYPE
    SYNTAX OCTET STRING
    ACCESS read-write
    STATUS mandatory
    DESCRIPTION
        "Ip address of the remote device. A complete set of port number, IP address
        and a valid input/output mask starts this mode.
        No data exchange take place when setting the remote device IP address to 0.0.0.0."
    ::= { wtWebioEA12x12BinaryEntry 15 }

wtWebioEA12x12BinaryUdpPeerInputTrigger OBJECT-TYPE
    SYNTAX OCTET STRING (SIZE (4))
    ACCESS read-write
    STATUS mandatory
    DESCRIPTION
        "Every change on the inputs causes their state to be transmitted to the 
        remote device. To minimize data traffic, individual inputs may be exempted 
        from this rule. Nevertheless every transmission will contain all input bits.
        If a bit is set (1), a change of state on the corresponding input 
        triggers a transmission. If the bit is not set (0), no transmission 
        takes place.
        The OCTETS are interpreted bit-by-bit, with each bit corresponding to an input. 
        Bit 0 corresponds to the LSB.
        OCTET 1: unused
        OCTET 2: unused
        OCTET 3, Bit 0-3: Digital inputs 8-11
                 Bit 4-7: unused
        OCTET 4, Bit 0-7: Digital inputs 0-7"
    ::= { wtWebioEA12x12BinaryEntry 16 }

wtWebioEA12x12BinaryUdpPeerInterval OBJECT-TYPE
    SYNTAX INTEGER (0..65535)
    ACCESS read-write
    STATUS mandatory
    DESCRIPTION
        "Configurable interval with a 100ms base, in which the Webio device sends
        data to the configured remote device. A interval of zero stopps the 
        periodical sending."
    ::= { wtWebioEA12x12BinaryEntry 17 }

wtWebioEA12x12BinaryUdpPeerApplicationMode OBJECT-TYPE
    SYNTAX OCTET STRING (SIZE (4))
    ACCESS read-write
    STATUS mandatory
    DESCRIPTION
        "Selection of the application mode:
        The OCTETS are interpreted bit-by-bit,
        Bit 0 corresponds to the LSB.
        OCTET 1: unused
        OCTET 2: unused
        OCTET 3: unused
        OCTET 4: Bit 3-7: unused
        	 Bit 2  : Box2Box Slave
        	 Bit 1  : Compatible 50xxx
        	 Bit 0  : Default"
    ::= { wtWebioEA12x12BinaryEntry 18 }

wtWebioEA12x12BinaryConnectedPort OBJECT-TYPE
    SYNTAX INTEGER (1..65535)
    ACCESS read-only
    STATUS mandatory
    DESCRIPTION
        "Port number of the remote device, after connection has been established.
        In case of no connection or missing port informations a zero will be read."
    ::= { wtWebioEA12x12BinaryEntry 19 }

wtWebioEA12x12BinaryConnectedIpAddr OBJECT-TYPE
    SYNTAX IpAddress
    ACCESS read-only
    STATUS mandatory
    DESCRIPTION
        "IP address of the remote device, after connection has been established.
        In case of no connection or missing port informations 0.0.0.0 will be read."
    ::= { wtWebioEA12x12BinaryEntry 20 } 

wtWebioEA12x12BinaryTcpServerClientHttpPort OBJECT-TYPE
    SYNTAX INTEGER (1..65535)
    ACCESS read-write
    STATUS mandatory
    DESCRIPTION
        "HTTP port number of the remote device at TCP Server Mode. If an mailfunction occurs 
        status informations will be send to this port. 
        Not used at mode Compatible 50xxx."
    ::= { wtWebioEA12x12BinaryEntry 21 }
    
wtWebioEA12x12BinaryTcpClientServerHttpPort OBJECT-TYPE
    SYNTAX INTEGER (1..65535)
    ACCESS read-write
    STATUS mandatory
    DESCRIPTION
        "HTTP port number of the remote device at TCP Client Mode. In the operating mode
        Box2Box connection status informations will be exchanged through this port."
    ::= { wtWebioEA12x12BinaryEntry 22 }            
    
--  wtWebioEA12x12Syslog Group
--------------------------------
    
wtWebioEA12x12SyslogServerIP OBJECT-TYPE
    SYNTAX OCTET STRING 
    ACCESS read-write
    STATUS mandatory
    DESCRIPTION
        "Name or IP address of the Syslog server, which accepts the Syslog messgaes."
    ::= { wtWebioEA12x12Syslog 1 }
    
wtWebioEA12x12SyslogServerPort OBJECT-TYPE
    SYNTAX INTEGER
    ACCESS read-write
    STATUS mandatory
    DESCRIPTION
        "Portnumber of the Syslog servers, default 514."
    ::= { wtWebioEA12x12Syslog 2 }

wtWebioEA12x12SyslogSystemMessagesEnable OBJECT-TYPE
    SYNTAX OCTET STRING (SIZE(4))
    ACCESS read-write
    STATUS mandatory
    DESCRIPTION
        "Binary coded trigger conditions:
        Octet 1: unused
        Octet 2: unused
        Octet 3: unused
        Octet 4:
	        Bit 0:   ColdStart
	        Bit 1:   WarmStart
	        Bit 2:   Diag Messages
	        Bit 3-7: unused"
    ::= { wtWebioEA12x12Syslog 3 }    

wtWebioEA12x12SyslogEnable OBJECT-TYPE
    SYNTAX OCTET STRING 
    ACCESS read-write
    STATUS mandatory
    DESCRIPTION
        "Set bit 0to enable Syslog:
        Octet 1: unused
        Octet 2: unused
        Octet 3: unused
        Octet 4:
        	Bit 1-7: unused
                Bit 0  : Syslog enable"
    ::= { wtWebioEA12x12Syslog 4 }

--  wtWebioEA12x12FTP Group
--------------------------------

wtWebioEA12x12FTPServerIP OBJECT-TYPE
    SYNTAX OCTET STRING 
    ACCESS read-write
    STATUS mandatory
    DESCRIPTION
        "Name or IP address of the FTP server, which accepts the FTP messages."
    ::= { wtWebioEA12x12FTP 1 }
    
wtWebioEA12x12FTPServerControlPort OBJECT-TYPE
    SYNTAX INTEGER
    ACCESS read-write
    STATUS mandatory
    DESCRIPTION
        "Portnumber of the control port of the FTP server, default 21."
    ::= { wtWebioEA12x12FTP 2 }
    
wtWebioEA12x12FTPUserName OBJECT-TYPE
    SYNTAX OCTET STRING 
    ACCESS read-write
    STATUS mandatory
    DESCRIPTION
        "FTP Loggin: user name."
    ::= { wtWebioEA12x12FTP 3 }
    
wtWebioEA12x12FTPPassword OBJECT-TYPE
    SYNTAX OCTET STRING 
    ACCESS read-write
    STATUS mandatory
    DESCRIPTION
        "FTP Loggin: user password."
    ::= { wtWebioEA12x12FTP 4 }

wtWebioEA12x12FTPAccount OBJECT-TYPE
    SYNTAX OCTET STRING 
    ACCESS read-write
    STATUS mandatory
    DESCRIPTION
        "FTP Loggin: name of account."
    ::= { wtWebioEA12x12FTP 5 }

wtWebioEA12x12FTPOption OBJECT-TYPE
    SYNTAX OCTET STRING 
    ACCESS read-write
    STATUS mandatory
    DESCRIPTION
        "Bit 0 switches the FTP Server in Passiv-Mode,
        the Client controls the data connection on its own:
        Octet 1: unused
        Octet 2: unused
        Octet 3: unused
        Octet 4:
        	Bit 1-7: unused
                Bit 0  : PASV enable"
    ::= { wtWebioEA12x12FTP 6 }
    
wtWebioEA12x12FTPEnable OBJECT-TYPE
    SYNTAX OCTET STRING 
    ACCESS read-write
    STATUS mandatory
    DESCRIPTION
        "Set Bit 0 to enable FTP:
        Octet 1: unused
        Octet 2: unused
        Octet 3: unused
        Octet 4:
        	Bit 1-7: unused
                Bit 0  : FTP enable"
    ::= { wtWebioEA12x12FTP 7 }  
    
--  wtWebioEA12x12OutputMode Group
--------------------------------

-- OutputMode Table

wtWebioEA12x12OutputModeTable OBJECT-TYPE
    SYNTAX SEQUENCE OF WtWebioEA12x12OutputModeEntry
    ACCESS not-accessible
    STATUS mandatory
    DESCRIPTION
        "Table of output mode configurations dependent on the output indices."
    ::= { wtWebioEA12x12OutputMode 1 }

wtWebioEA12x12OutputModeEntry OBJECT-TYPE
    SYNTAX WtWebioEA12x12OutputModeEntry
    ACCESS not-accessible
    STATUS mandatory
    DESCRIPTION
        "Output mode configurations of the individual outputs."
    INDEX  { wtWebioEA12x12OutputNo }
    ::= { wtWebioEA12x12OutputModeTable 1 }

WtWebioEA12x12OutputModeEntry ::= SEQUENCE {
    wtWebioEA12x12OutputModeBit	OCTET STRING
}

wtWebioEA12x12OutputModeBit OBJECT-TYPE
    SYNTAX OCTET STRING (SIZE (4))
    ACCESS read-write
    STATUS mandatory
    DESCRIPTION
        "This binary coded output mode defines the individual operation mode for any
        output. More than one mode must not be selected.
        The OCTETS are interpreted bit-by-bit, 
        Bit 0 corresponds to the LSB.
        OCTET 1: unused
        OCTET 2: unused
        OCTET 3: unused
        OCTET 4: Bit 6-7: unused
        	 Bit 5  : Logic
        	 Bit 4  : Binary 2
        	 Bit 3  : Binary 1
        	 Bit 2  : SNMP
        	 Bit 1  : UDP ASCII
        	 Bit 0  : HTTP"
    ::= { wtWebioEA12x12OutputModeEntry 1 }
    
wtWebioEA12x12SafetyTimeout OBJECT-TYPE
    SYNTAX INTEGER (0..65535)
    ACCESS read-write
    STATUS mandatory
    DESCRIPTION
        "After this period of time (multiple of 100ms) without receiving data
        outputs switch to their Safety States. For each output a independend safety state
        could be defined."
    ::= { wtWebioEA12x12OutputMode 2 }
 
 wtWebioEA12x12LoadControlEnable OBJECT-TYPE
    SYNTAX OCTET STRING 
    ACCESS read-write
    STATUS mandatory
    DESCRIPTION
        "Here the function of automatic load control can be enabled. All output were tested in 
        pairs (0-1, 2-3, 4-5, 6-7, 8-9, 10-11). If an error occours at one output,
        both output of an pair will be switched of. For a properly function of the load control
        each output of a pair have to has a load. If there is no existing load, a pull down resistor
        can be used.
        Outputs with no load are automaticly detected and not part of the control function.
        The OCTETS are interpreted bit-by-bit, with each bit corresponding to an output. 
        Bit 0 corresponds to the LSB.
        Octet 1: unused
        Octet 2: unused
        Octet 3: unused
        Octet 4:
        	Bit 1-7: unused
                Bit 0  : Load Control enable"
    ::= { wtWebioEA12x12OutputMode 3 }
    
-- wtWebioEA12x12Alarm Group
----------------------------

wtWebioEA12x12AlarmCount OBJECT-TYPE
    SYNTAX INTEGER (1..12)
    ACCESS read-only
    STATUS mandatory
    DESCRIPTION
        "Number of independent alarms."
    ::= { wtWebioEA12x12Alarm 1 }
    
-- Alarm Interface Table

wtWebioEA12x12AlarmIfTable OBJECT-TYPE
    SYNTAX SEQUENCE OF WtWebioEA12x12AlarmIfEntry
    ACCESS not-accessible
    STATUS mandatory
    DESCRIPTION
        "List of alarm indices."
    ::= { wtWebioEA12x12Alarm 2 }

wtWebioEA12x12AlarmIfEntry OBJECT-TYPE
    SYNTAX WtWebioEA12x12AlarmIfEntry
    ACCESS not-accessible
    STATUS mandatory
    DESCRIPTION
        "Numbers of the alarms."
    INDEX  { wtWebioEA12x12AlarmNo }
    ::= { wtWebioEA12x12AlarmIfTable 1 }

WtWebioEA12x12AlarmIfEntry ::= SEQUENCE {
    wtWebioEA12x12AlarmNo INTEGER
}

wtWebioEA12x12AlarmNo OBJECT-TYPE
    SYNTAX INTEGER (1..12)
    ACCESS read-only
    STATUS mandatory
    DESCRIPTION
        "Numbers of the alarms."
    ::= { wtWebioEA12x12AlarmIfEntry 1 }

-- Alarm Table

wtWebioEA12x12AlarmTable OBJECT-TYPE
    SYNTAX SEQUENCE OF WtWebioEA12x12AlarmEntry
    ACCESS not-accessible
    STATUS mandatory
    DESCRIPTION
        "List of settings depending on the alarm number."
    ::= { wtWebioEA12x12Alarm 3 }

wtWebioEA12x12AlarmEntry OBJECT-TYPE
    SYNTAX WtWebioEA12x12AlarmEntry
    ACCESS not-accessible
    STATUS mandatory
    DESCRIPTION
        "Alarm parameters of the individual alarms."
    INDEX  { wtWebioEA12x12AlarmNo }
    ::= { wtWebioEA12x12AlarmTable 1 }

WtWebioEA12x12AlarmEntry ::= SEQUENCE {
    wtWebioEA12x12AlarmInputTrigger		OCTET STRING,
    wtWebioEA12x12AlarmOutputTrigger		OCTET STRING,
    wtWebioEA12x12AlarmSystemTrigger		OCTET STRING,
    wtWebioEA12x12AlarmMaxCounterValue		OCTET STRING,
    wtWebioEA12x12AlarmInterval			OCTET STRING,
    wtWebioEA12x12AlarmEnable			OCTET STRING,
    wtWebioEA12x12AlarmMailAddr			OCTET STRING,
    wtWebioEA12x12AlarmMailSubject		OCTET STRING,
    wtWebioEA12x12AlarmMailText			OCTET STRING,
    wtWebioEA12x12AlarmSnmpManagerIP		OCTET STRING,
    wtWebioEA12x12AlarmSnmpTrapText		OCTET STRING,
    wtWebioEA12x12AlarmUdpIpAddr		OCTET STRING,
    wtWebioEA12x12AlarmUdpPort			INTEGER,
    wtWebioEA12x12AlarmUdpText			OCTET STRING,
    wtWebioEA12x12AlarmTcpIpAddr		OCTET STRING,
    wtWebioEA12x12AlarmTcpPort			INTEGER,
    wtWebioEA12x12AlarmTcpText			OCTET STRING,    
    wtWebioEA12x12AlarmSyslogIpAddr		OCTET STRING,
    wtWebioEA12x12AlarmSyslogPort		INTEGER,
    wtWebioEA12x12AlarmSyslogText		OCTET STRING,
    wtWebioEA12x12AlarmFtpDataPort		OCTET STRING,
    wtWebioEA12x12AlarmFtpFileName		OCTET STRING,
    wtWebioEA12x12AlarmFtpText			OCTET STRING,
    wtWebioEA12x12AlarmFtpOption		OCTET STRING,
    wtWebioEA12x12AlarmTimerCron		OCTET STRING,
    
    wtWebioEA12x12AlarmMailReleaseSubject	OCTET STRING,
    wtWebioEA12x12AlarmMailReleaseText		OCTET STRING,
    wtWebioEA12x12AlarmSnmpTrapReleaseText	OCTET STRING,
    wtWebioEA12x12AlarmUdpReleaseText		OCTET STRING,
    wtWebioEA12x12AlarmTcpReleaseText		OCTET STRING,    
    wtWebioEA12x12AlarmSyslogReleaseText	OCTET STRING,
    wtWebioEA12x12AlarmFtpReleaseText		OCTET STRING    
    
}

wtWebioEA12x12AlarmInputTrigger OBJECT-TYPE
    SYNTAX OCTET STRING (SIZE(12))
    ACCESS read-write
    STATUS mandatory
    DESCRIPTION
        "This variable allows setting of individual input trigger conditions. 
        The OCTETS are interpreted bit-by-bit, with each bit corresponding to an input. 
        Bit 0 corresponds to the LSB.
	The first four OCTETS contain the mask which determines which of the inputs are to 
	be considered (corresponding bit = 1) and which inputs are to ignore 
	(corresponding bit = 0):
	OCTET 1 : unused
	OCTET 2 : unused
	OCTET 3, Bit 0-3: Mask for digital inputs 8-11
		 Bit 4-7: unused
	OCTET 4, Bit 0-7: Mask for digital inputs 0-7
	
	OCTETS 5-8 contain the level (1=HIGH, 0=LOW) which the inputs 
	should assume:
	OCTET 5 : unused
	OCTET 6 : unused
	OCTET 7, Bit 0-3: Level of digital inputs 8-11
		 Bit 4-7: unused
        OCTET 8, Bit 0-7: Level of digital inputs 0-7
        
	OCTETS 9-12 contain the ANY bit (1=ON, 0=OFF). Inputs masked with the any bit trigger with any change 
	of the corresponding input bit. Settings in OCTET 5-9 are then unused:
	OCTET 9 : unused
	OCTET 10: unsused
	OCTET 11, Bit 0-7   : ANY bits of digital inputs 8-11
		  Bit 12-15 : unused
	OCTET 12, Bit 0-7   : ANY bits of digital inputs 0-7"
        
    ::= { wtWebioEA12x12AlarmEntry 1 }

wtWebioEA12x12AlarmOutputTrigger OBJECT-TYPE
    SYNTAX OCTET STRING (SIZE(12))
    ACCESS read-write
    STATUS mandatory
    DESCRIPTION
        "This variable allows setting of individual output trigger conditions. 
        The OCTETS are interpreted bit-by-bit, with each bit corresponding to an output. 
        Bit 0 corresponds to the LSB.
	The first four OCTETS contain the mask which determines which of the outputs are to 
	be considered (corresponding bit = 1) and which outputs are to ignore 
	(corresponding bit = 0):
	OCTET 1 : unused
	OCTET 2 : unused
	OCTET 3, Bit 0-3: Mask for digital outputs 8-11
		 Bit 4-7: unused
	OCTET 4, Bit 0-7: Mask for digital outputs 0-7
	
	OCTETS 5-8 contain the level (1=HIGH, 0=LOW) which the outputs 
	should assume:
	OCTET 5 : unused
	OCTET 6 : unused
	OCTET 7, Bit 0-3: Level of digital outputs 8-11
		 Bit 4-7: unused
        OCTET 8, Bit 0-7: Level of digital outputs 0-7

	OCTETS 9-12 contain the ANY bit (1=ON, 0=OFF). Outputs masked with the any bit trigger with any change 
	of the corresponding output bit. Settings in OCTET 5-9 are then unused:
	OCTET 9 : unused
	OCTET 11, Bit 0-7   : ANY bits of digital inputs 8-11
		  Bit 12-15 : unused
	OCTET 12, Bit 0-7   : ANY bits of digital inputs 0-7"
        
    ::= { wtWebioEA12x12AlarmEntry 2 }
    
wtWebioEA12x12AlarmSystemTrigger OBJECT-TYPE
    SYNTAX OCTET STRING (SIZE(4))
    ACCESS read-write
    STATUS mandatory
    DESCRIPTION
        "Binary coded trigger conditions:
        The OCTETS are interpreted bit-by-bit.
        Bit 0 corresponds to the LSB.
        OCTET 1: unused
        OCTET 2: unused
        OCTET 3: unused
        OCTET 4, 
        	 Bit 4-7: unused
        	 Bit 3  : Warm Start
        	 Bit 2  : Cold Start
        	 Bit 1  : Timer
        	 Bit 0  : Load Control"
    ::= { wtWebioEA12x12AlarmEntry 3 }

wtWebioEA12x12AlarmMaxCounterValue OBJECT-TYPE
    SYNTAX OCTET STRING 
    ACCESS read-write
    STATUS mandatory
    DESCRIPTION
        "This variable configures a max. counter value. If an input counter value
        exceeds this max. value, the corresponding alarm is triggered. Input counters with
        its mask bit unset in wtWebioEA12x12AlarmInputTrigger are not considered."
    ::= { wtWebioEA12x12AlarmEntry 4 }

wtWebioEA12x12AlarmInterval OBJECT-TYPE
    SYNTAX OCTET STRING 
    ACCESS read-write
    STATUS mandatory
    DESCRIPTION
        "Send interval for alarm messages."
    ::= { wtWebioEA12x12AlarmEntry 5 }

wtWebioEA12x12AlarmEnable OBJECT-TYPE
    SYNTAX OCTET STRING (SIZE(4))
    ACCESS read-write
    STATUS mandatory
    DESCRIPTION
        "Binary coded alarm enable:
        Octet 1: unused
        Octet 2: unused
        Octet 3: unused
        Octet 4:
		Bit 0:	Mail Enable
        	Bit 1:	SNMP Trap enable
        	Bit 2:  UDP enable
        	Bit 3:  Send inputs to pending TCP connections
        	Bit 4:  TCP Client enable
        	Bit 5:	Syslog Messages enable
        	Bit 6-7: unused"
    ::= { wtWebioEA12x12AlarmEntry 6 }

wtWebioEA12x12AlarmMailAddr OBJECT-TYPE
    SYNTAX OCTET STRING 
    ACCESS read-write
    STATUS mandatory
    DESCRIPTION
        "E-Mail address for sending the alarm mail to."
    ::= { wtWebioEA12x12AlarmEntry 7 }

wtWebioEA12x12AlarmMailSubject OBJECT-TYPE
    SYNTAX OCTET STRING 
    ACCESS read-write
    STATUS mandatory
    DESCRIPTION
        "Subject line for alarm mail."
    ::= { wtWebioEA12x12AlarmEntry 8 }

wtWebioEA12x12AlarmMailText OBJECT-TYPE
    SYNTAX OCTET STRING 
    ACCESS read-write
    STATUS mandatory
    DESCRIPTION
        "Alarm mail text: 
        States of the Webio device can be included by using special tags.
        Please refer to the respective Webio manual"
    ::= { wtWebioEA12x12AlarmEntry 9 }

wtWebioEA12x12AlarmSnmpManagerIP OBJECT-TYPE
    SYNTAX OCTET STRING 
    ACCESS read-write
    STATUS mandatory
    DESCRIPTION
        "IP address of the SNMP Manager to which the Webio device should send SNMP traps."
    ::= { wtWebioEA12x12AlarmEntry 10 }

wtWebioEA12x12AlarmSnmpTrapText OBJECT-TYPE
    SYNTAX OCTET STRING 
    ACCESS read-write
    STATUS mandatory
    DESCRIPTION
        "This text appears in the trap body."
    ::= { wtWebioEA12x12AlarmEntry 11 }
    
wtWebioEA12x12AlarmUdpIpAddr OBJECT-TYPE
    SYNTAX OCTET STRING 
    ACCESS read-write
    STATUS mandatory
    DESCRIPTION
        "IP address of the UDP listener to which the Webio device should send UDP traps."
    ::= { wtWebioEA12x12AlarmEntry 12 }    

wtWebioEA12x12AlarmUdpPort OBJECT-TYPE
    SYNTAX INTEGER (1..65535) 
    ACCESS read-write
    STATUS mandatory
    DESCRIPTION
        "Port number of the UDP listener to which the Webio device should send UDP traps."
    ::= { wtWebioEA12x12AlarmEntry 13 }    

wtWebioEA12x12AlarmUdpText OBJECT-TYPE
    SYNTAX OCTET STRING 
    ACCESS read-write
    STATUS mandatory
    DESCRIPTION
        "This text appears in the UDP trap body."
    ::= { wtWebioEA12x12AlarmEntry 14 }
    
wtWebioEA12x12AlarmTcpIpAddr OBJECT-TYPE
    SYNTAX OCTET STRING
    ACCESS read-write
    STATUS mandatory
    DESCRIPTION
        "IP address of the TCP listener to which the Webio device should send TCP traps."
    ::= { wtWebioEA12x12AlarmEntry 15 }    

wtWebioEA12x12AlarmTcpPort OBJECT-TYPE
    SYNTAX INTEGER (1..65535) 
    ACCESS read-write
    STATUS mandatory
    DESCRIPTION
        "Port number of the TCP listener to which the Webio device should send TCP traps."
    ::= { wtWebioEA12x12AlarmEntry 16 }    

wtWebioEA12x12AlarmTcpText OBJECT-TYPE
    SYNTAX OCTET STRING 
    ACCESS read-write
    STATUS mandatory
    DESCRIPTION
        "This text appears in the TCP trap body."
    ::= { wtWebioEA12x12AlarmEntry 17 }

wtWebioEA12x12AlarmSyslogIpAddr OBJECT-TYPE
    SYNTAX OCTET STRING 
    ACCESS read-write
    STATUS mandatory
    DESCRIPTION
        "IP address of the syslog server to which the Webio device should send syslog messages."
    ::= { wtWebioEA12x12AlarmEntry 18 }    

wtWebioEA12x12AlarmSyslogPort OBJECT-TYPE
    SYNTAX INTEGER (1..65535) 
    ACCESS read-write
    STATUS mandatory
    DESCRIPTION
        "Port number of the syslog server to which the Webio device should send syslog messages."
    ::= { wtWebioEA12x12AlarmEntry 19 }    

wtWebioEA12x12AlarmSyslogText OBJECT-TYPE
    SYNTAX OCTET STRING 
    ACCESS read-write
    STATUS mandatory
    DESCRIPTION
        "Every message starts with the priority key, a time stamp and the host ip address, according RFC3164.
        This text appears in the following syslog message body."
    ::= { wtWebioEA12x12AlarmEntry 20 }    
    
wtWebioEA12x12AlarmFtpDataPort OBJECT-TYPE
    SYNTAX OCTET STRING 
    ACCESS read-write
    STATUS mandatory
    DESCRIPTION
        "Local data port: 1..65535 or AUTO: the next free port will be assigned."
    ::= { wtWebioEA12x12AlarmEntry 21 }
    
wtWebioEA12x12AlarmFtpFileName OBJECT-TYPE
    SYNTAX OCTET STRING 
    ACCESS read-write
    STATUS mandatory
    DESCRIPTION
        "Name of the file including path informations."
    ::= { wtWebioEA12x12AlarmEntry 22 }
    
wtWebioEA12x12AlarmFtpText OBJECT-TYPE
    SYNTAX OCTET STRING 
    ACCESS read-write
    STATUS mandatory
    DESCRIPTION
        "Message text to store on the FTP server."
    ::= { wtWebioEA12x12AlarmEntry 23 }

wtWebioEA12x12AlarmFtpOption OBJECT-TYPE
    SYNTAX OCTET STRING (SIZE(4))
    ACCESS read-write
    STATUS mandatory
    DESCRIPTION
        "Binary coded options, select only one option at the same time:
        STORE  = replace file
        APPEND = append message at the end of the file
        
        Octet 1: unused
        Octet 2: unused
        Octet 3: unused
        Octet 4:
		Bit 0  :	STORE
		Bit 1  :	APPEND
        	Bit 2-7:	unused"
    ::= { wtWebioEA12x12AlarmEntry 24 }      
    
wtWebioEA12x12AlarmTimerCron OBJECT-TYPE
    SYNTAX OCTET STRING
    ACCESS read-write
    STATUS mandatory
    DESCRIPTION
        "This entry contains 5 space or tab seperated text fields for time trigger definition.
        Each field must match with the actual time to trigger a message, weekday and day of month
        are interpreted separatley.
        1: Minutes	Range 0-59
        2. Hours	Range 0-23, 0 is midnight
        3: Day of month	Range 1-31
        4: Month	Range 1-12
        5: Weekday	Range 0-6, 0 is sunday
        
        Syntax for every field:
         - an asterix (*) enables every possible setting of a field
         - single numbers seperated by commas
         - a partition within the allowed range (1-5)
         - step size within an partition of the allowed range (0-59/2: every second minute)."
    ::= { wtWebioEA12x12AlarmEntry 25 }      


wtWebioEA12x12AlarmMailReleaseSubject OBJECT-TYPE
    SYNTAX OCTET STRING 
    ACCESS read-write
    STATUS mandatory
    DESCRIPTION
       "Subject line for alarm mail."
    ::= { wtWebioEA12x12AlarmEntry 26 }

wtWebioEA12x12AlarmMailReleaseText OBJECT-TYPE
    SYNTAX OCTET STRING 
    ACCESS read-write
    STATUS mandatory
    DESCRIPTION
        "Release Alarm mail text: 
        States of the Webio device can be included by using special tags.
        Please refer to the respective Webio manual"
    ::= { wtWebioEA12x12AlarmEntry 27 }    

wtWebioEA12x12AlarmSnmpTrapReleaseText OBJECT-TYPE
    SYNTAX OCTET STRING 
    ACCESS read-write
    STATUS mandatory
    DESCRIPTION
        "This text appears in the trap body."
    ::= { wtWebioEA12x12AlarmEntry 28 }

wtWebioEA12x12AlarmUdpReleaseText OBJECT-TYPE
    SYNTAX OCTET STRING 
    ACCESS read-write
    STATUS mandatory
    DESCRIPTION
        "This text appears in the UDP trap body."
    ::= { wtWebioEA12x12AlarmEntry 29 }

wtWebioEA12x12AlarmTcpReleaseText OBJECT-TYPE
    SYNTAX OCTET STRING 
    ACCESS read-write
    STATUS mandatory
    DESCRIPTION
        "This text appears in the TCP trap body."
    ::= { wtWebioEA12x12AlarmEntry 30 }

wtWebioEA12x12AlarmSyslogReleaseText OBJECT-TYPE
    SYNTAX OCTET STRING 
    ACCESS read-write
    STATUS mandatory
    DESCRIPTION
        "Every message starts with the priority key, a time stamp and the host ip address, according RFC3164.
        This text appears in the following syslog message body."
    ::= { wtWebioEA12x12AlarmEntry 31 }

wtWebioEA12x12AlarmFtpReleaseText OBJECT-TYPE
    SYNTAX OCTET STRING 
    ACCESS read-write
    STATUS mandatory
    DESCRIPTION
        "Message text to store on the FTP server."
    ::= { wtWebioEA12x12AlarmEntry 32 }

-- wtWebioEA12x12LoadControl
----------------------------

wtWebioEA12x12LoadControlView OBJECT-TYPE
    SYNTAX OCTET STRING (SIZE(4))
    ACCESS read-only
    STATUS mandatory
    DESCRIPTION
        "Here the result of automatic load control can be read. All output were tested in 
        pairs (0-1, 2-3, 4-5, 6-7, 8-9, 10-11). If an error occours at one output,
        both output of an pair will be switched of. For a properly function of the load control
        each output of a pair have to has a load. If there is no existing load, a pull down resistor
        can be used.
        Outputs with no load are automaticly detected and not part of the control function.
        The OCTETS are interpreted bit-by-bit, with each bit corresponding to an output. 
        Bit 0 corresponds to the LSB.
        Octet 1: unused
        Octet 2: unused
        Octet 3:
        	Bit 4-7: unused
        	Bit 0-3: outputs 8-11
        Octet 4: 
	        Bit 0-7: outputs 0-7."
    ::= { wtWebioEA12x12Alarm 4 }

wtWebioEA12x12LCShutDownView OBJECT-TYPE
    SYNTAX OCTET STRING (SIZE(4))
    ACCESS read-write
    STATUS mandatory
    DESCRIPTION
        "Here the result of the automatic load control shut down can be read. All outputs remain switched of,
        until a zero is written into this variable. But previously all loads should be inspected.
        High current (short circuit), a broken supply line or a defect load (i.e. lamp) may be a shut down reason.
        If no load is detected, the load control unit suspend automaticly the control of the corresponding output pair.
        All controlled output could be identified reading the variable wtWebioEA12x12LoadControlEnable.
        The OCTETS are interpreted bit-by-bit, with each bit corresponding to an output.
        Bit 0 corresponds to the LSB.
        
        Octet 1: unused
        Octet 2: unused
        Octet 3:
        	Bit 4-7: unused
        	Bit 0-3: outputs 8-11
        Octet 4: 
	        Bit 0-7: outputs 0-7."
    ::= { wtWebioEA12x12Alarm 5 }

-- wtWebioEA12x12Ports Group
----------------------------

-- Input Port Table

wtWebioEA12x12InputPortTable OBJECT-TYPE
    SYNTAX SEQUENCE OF WtWebioEA12x12InputPortEntry
    ACCESS not-accessible
    STATUS mandatory
    DESCRIPTION
        "List of settings depending on the input number."
    ::= { wtWebioEA12x12Ports 1 }

wtWebioEA12x12InputPortEntry OBJECT-TYPE
    SYNTAX WtWebioEA12x12InputPortEntry
    ACCESS not-accessible
    STATUS mandatory
    DESCRIPTION
        "Input parameter for the individual inputs."
    INDEX  { wtWebioEA12x12InputNo }
    ::= { wtWebioEA12x12InputPortTable 1 }

WtWebioEA12x12InputPortEntry ::= SEQUENCE {
    wtWebioEA12x12PortInputName				OCTET STRING,
    wtWebioEA12x12PortInputText				OCTET STRING,
    wtWebioEA12x12PortInputMode				OCTET STRING,
    wtWebioEA12x12PortInputFilter			INTEGER,
    wtWebioEA12x12PortInputBicountPulsePolarity		OCTET STRING,
    wtWebioEA12x12PortInputBicountInactivTimeout	INTEGER
}

wtWebioEA12x12PortInputName OBJECT-TYPE
    SYNTAX OCTET STRING 
    ACCESS read-write
    STATUS mandatory
    DESCRIPTION
        "Name of the input."
    ::= { wtWebioEA12x12InputPortEntry 1 }

wtWebioEA12x12PortInputText OBJECT-TYPE
    SYNTAX OCTET STRING 
    ACCESS read-write
    STATUS mandatory
    DESCRIPTION
        "Description of the input."
    ::= { wtWebioEA12x12InputPortEntry 2 }

wtWebioEA12x12PortInputMode OBJECT-TYPE
    SYNTAX OCTET STRING (SIZE(4))
    ACCESS read-write
    STATUS mandatory
    DESCRIPTION
        "Binary coded modes:
        Selecting short pulse detection enable by setting the corresponding bit to 1 enables 
        interrupt support for counting. Only positive edges are accepted as trigger 
        source. The maximum counting frequenz equals 2000 Hz.
        This mode is available for inputs 0-3 only.
        Selecting counter clear on read by setting the corresponding bit to 1 enables
        the corresponding counter to be cleared automatically every time it is read,
        except HTTP reading with user rights.
        The OCTETS are interpreted bit-by-bit, with each set of octets corresponding to an input. 
        Bit 0 corresponds to the LSB.
        Selection for input 0-3:
        OCTET 1: unused
        OCTET 2: unused
        OCTET 3: unused
        OCTET 4, Bit 3-7: unused
        	 Bit 2  : Counter clear on read
        	 Bit 1  : Change detection enable (default)
        	 Bit 0  : Short Pulse detection enable
        	 
	Selection for inputs 4-11:
	OCTET 1: unused
	OCTET 2: unused
	OCTET 3: unused
	OCTET 4, Bit 2-7: unused
		 Bit 1  : Counter clear on read
		 Bit 0  : Change detection enable (default)"
    ::= { wtWebioEA12x12InputPortEntry 3 }    
    
wtWebioEA12x12PortInputFilter OBJECT-TYPE
    SYNTAX INTEGER 
    ACCESS read-write
    STATUS mandatory
    DESCRIPTION
        "Pulses with a duration shorter than here specified (duration in 1/1000 sec),
	are ignored."
    ::= { wtWebioEA12x12InputPortEntry 4 }
    
wtWebioEA12x12PortInputBicountPulsePolarity OBJECT-TYPE
    SYNTAX OCTET STRING (SIZE (4))
    ACCESS read-write
    STATUS mandatory
    DESCRIPTION
        "This value defines the polarity of the input pulse.
        OCTET 1: unused
        OCTET 2: unused
        OCTET 3: unused
        	OCTET 4: 
        	 Bit 0   : negative polarity
        	 Bit 1   : positive polarity
        	 Bit 2-7 : unused"
    ::= { wtWebioEA12x12InputPortEntry 5 }

wtWebioEA12x12PortInputBicountInactivTimeout OBJECT-TYPE
    SYNTAX INTEGER 
    ACCESS read-write
    STATUS mandatory
    DESCRIPTION
        "Pulse chains with a duration shorter than here specified (in 1/10 sek),
	are ignored."
    ::= { wtWebioEA12x12InputPortEntry 6 }
    
-- Output Port Table

wtWebioEA12x12OutputPortTable OBJECT-TYPE
    SYNTAX SEQUENCE OF WtWebioEA12x12OutputPortEntry
    ACCESS not-accessible
    STATUS mandatory
    DESCRIPTION
        "List of settings depending on the output number."
    ::= { wtWebioEA12x12Ports 2 }

wtWebioEA12x12OutputPortEntry OBJECT-TYPE
    SYNTAX WtWebioEA12x12OutputPortEntry
    ACCESS not-accessible
    STATUS mandatory
    DESCRIPTION
        "Output parameters of the individual outputs."
    INDEX  { wtWebioEA12x12OutputNo }
    ::= { wtWebioEA12x12OutputPortTable 1 }

WtWebioEA12x12OutputPortEntry ::= SEQUENCE {
    wtWebioEA12x12PortOutputName		OCTET STRING,
    wtWebioEA12x12PortOutputText		OCTET STRING,
    wtWebioEA12x12PortOutputGroupMode		OCTET STRING,
    wtWebioEA12x12PortOutputSafetyState		OCTET STRING,
    wtWebioEA12x12PortLogicInputMask		OCTET STRING,
    wtWebioEA12x12PortLogicInputInverter	OCTET STRING,
    wtWebioEA12x12PortLogicFunction		OCTET STRING,
    wtWebioEA12x12PortLogicOutputInverter	OCTET STRING,
    wtWebioEA12x12PortPulseDuration		INTEGER,
    wtWebioEA12x12PortPulsePolarity		OCTET STRING
    
}

wtWebioEA12x12PortOutputName OBJECT-TYPE
    SYNTAX OCTET STRING 
    ACCESS read-write
    STATUS mandatory
    DESCRIPTION
        "Name of the output."
    ::= { wtWebioEA12x12OutputPortEntry 1 }

wtWebioEA12x12PortOutputText OBJECT-TYPE
    SYNTAX OCTET STRING 
    ACCESS read-write
    STATUS mandatory
    DESCRIPTION
        "Description of the output."
    ::= { wtWebioEA12x12OutputPortEntry 2 }

wtWebioEA12x12PortOutputGroupMode OBJECT-TYPE
    SYNTAX OCTET STRING 
    ACCESS read-write
    STATUS mandatory
    DESCRIPTION
        "It is possible to connect outputs together to increase the output current.
        This could be done by connecting 2 or 4 outputs in a group together. All bits
        of such a group has to be set all together in the same way. This variable
        configures this group scheme. If one output bit of a group is set, all other 
        output bits of the same group will be set in the same manner.
        More than one configuration must not be selected.
	Selection for outputs 0-3:
        Octet 1: unused
        Octet 2: unused
        Octet 3: unused
        OCTET 4: Bit 0   : outputs 0,1,2,3 disconnected (default)
        	 Bit 1   : outputs 0+1, 2+3 connected
        	 Bit 2   : outputs 0+1+2+3 connected
        	 Bit 3-7 : unused
	Selection for outputs 4-7:
        Octet 1: unused
        Octet 2: unused
        Octet 3: unused
        OCTET 4: Bit 0   : outputs 4, 5, 6, 7 disconnected (default)
        	 Bit 1   : outputs 4+5, 6+7 connected
        	 Bit 2   : outputs 4+5+6+7 connected
        	 Bit 3-7 : unused        	 
	Selection for outputs 8-11:
        Octet 1: unused
        Octet 2: unused
        Octet 3: unused
        OCTET 4: Bit 0   : outputs 8, 9, 10, 11 disconnected (default)
        	 Bit 1   : outputs 8+9, 10+11 connected
        	 Bit 2   : outputs 8+9+10+11 connected
        	 Bit 3-7 : unused"
    ::= { wtWebioEA12x12OutputPortEntry 3 }

wtWebioEA12x12PortOutputSafetyState OBJECT-TYPE
    SYNTAX OCTET STRING 
    ACCESS read-write
    STATUS mandatory
    DESCRIPTION
        "This variable allows setting of individual digital outputs. The OCTETS are 
        interpreted bit-by-bit, with each bit corresponding to an output. Bit 0 corresponds 
        to the LSB.
        The first four OCTETS contain the mask which determines which of the outputs are to 
        be set (corresponding bit = 1) and which outputs are to remain unchanged 
        (corresponding bit = 0):
        OCTET 1		: unused
        OCTET 2		: unused
        OCTET 3		: unused
        OCTET 4, Bit 1-7: unused
        	 Bit 0	: Mask for digital output
        OCTETS 5-8 contain the level (1=HIGH, 0=LOW) which the outputs to be changed 
        should assume:
        OCTET 5		: unused
        OCTET 6		: unused
        OCTET 7		: unused
        OCTET 8, Bit 1-7: unused
        	 Bit 0  : Level of digital output"
    ::= { wtWebioEA12x12OutputPortEntry 4 }

wtWebioEA12x12PortLogicInputMask OBJECT-TYPE
    SYNTAX OCTET STRING (SIZE (4))
    ACCESS read-write
    STATUS mandatory
    DESCRIPTION
        "Selecting one of these inputs by setting the corresponding bit to 1 
        enables the logic function for the output identified by the index within 
        this table. The calculation take place in 4 steps:
        1. Selecting inputs				(wtWebioEA12x12PortLogicInputMask)
        2. Inverting inputs if necessary	(wtWebioEA12x12PortLogicInputInverter)
        3. Logical combination				(wtWebioEA12x12PortLogicFunction)
        4. Inverting the result if necessary	(wtWebioEA12x12PortLogicOutputInverter)
        OCTET 1: unused
        OCTET 2: unused
        OCTET 3: Bit 0-3 : inputs 8-11
        	 Bit 4-7 : unused
        OCTET 4: 
        	 Bit 0-7 : inputs 0-7"
    ::= { wtWebioEA12x12OutputPortEntry 5 }

wtWebioEA12x12PortLogicInputInverter OBJECT-TYPE
    SYNTAX OCTET STRING (SIZE (4))
    ACCESS read-write
    STATUS mandatory
    DESCRIPTION
        "Every input bit selected here will be inverted.
        OCTET 1: unused
        OCTET 2: unused
        OCTET 3: Bit 0-3 : inputs 8-11
        	 Bit 4-7 : unused
        OCTET 4: 
        	 Bit 0-7 : inputs 0-7"
    ::= { wtWebioEA12x12OutputPortEntry 6 }

wtWebioEA12x12PortLogicFunction OBJECT-TYPE
    SYNTAX OCTET STRING (SIZE (4))
    ACCESS read-write
    STATUS mandatory
    DESCRIPTION
        "This determines the logic function. No more than one function
        may be selected.
        OCTET 1: unused
        OCTET 2: unused
        OCTET 3: unused
        OCTET 4: 
        	 Bit 0   : logic function OR (default)
        	 Bit 1   : logic function AND
        	 Bit 2-7 : unused"
    ::= { wtWebioEA12x12OutputPortEntry 7 }

wtWebioEA12x12PortLogicOutputInverter OBJECT-TYPE
    SYNTAX OCTET STRING (SIZE (4))
    ACCESS read-write
    STATUS mandatory
    DESCRIPTION
        "The logical operation result could be inverteted by setting the corresponding
        bit to 1.
        OCTET 1: unused
        OCTET 2: unused
        OCTET 3: unused
        	OCTET 4: 
        	 Bit 0   : Output Inverter enable
        	 Bit 1-7 : unused"
    ::= { wtWebioEA12x12OutputPortEntry 8 }

wtWebioEA12x12PortPulseDuration OBJECT-TYPE
    SYNTAX INTEGER
    ACCESS read-write
    STATUS mandatory
    DESCRIPTION
        "Pulse length in 1/1000 sec. Setting this value to zero, disables the pulse output."
    ::= { wtWebioEA12x12OutputPortEntry 9 }

wtWebioEA12x12PortPulsePolarity OBJECT-TYPE
    SYNTAX OCTET STRING (SIZE (4))
    ACCESS read-write
    STATUS mandatory
    DESCRIPTION
        "This value defines the polarity of the output pulse, if wtWebioEA12x12PortPulseDuration is not set to zero.
        After the pulse is finished, the output switches back to the opposite state.
        OCTET 1: unused
        OCTET 2: unused
        OCTET 3: unused
        	OCTET 4: 
        	 Bit 0   : negative polarity
        	 Bit 1   : positive polarity
        	 Bit 2-7 : unused"
    ::= { wtWebioEA12x12OutputPortEntry 10 }

-- wtWebioEA12x12Manufact Group
----------------------------

wtWebioEA12x12MfName OBJECT-TYPE
    SYNTAX OCTET STRING 
    ACCESS read-write
    STATUS mandatory
    DESCRIPTION
        "Manufacturer company name"
    ::= { wtWebioEA12x12Manufact 1 }

wtWebioEA12x12MfAddr OBJECT-TYPE
    SYNTAX OCTET STRING 
    ACCESS read-write
    STATUS mandatory
    DESCRIPTION
        "Manufacturer address."
    ::= { wtWebioEA12x12Manufact 2 }

wtWebioEA12x12MfHotline OBJECT-TYPE
    SYNTAX OCTET STRING 
    ACCESS read-write
    STATUS mandatory
    DESCRIPTION
        "Manufacturer hotline."
    ::= { wtWebioEA12x12Manufact 3 }

wtWebioEA12x12MfInternet OBJECT-TYPE
    SYNTAX OCTET STRING 
    ACCESS read-write
    STATUS mandatory
    DESCRIPTION
        "Manufacturer Internet address."
    ::= { wtWebioEA12x12Manufact 4 }

wtWebioEA12x12MfDeviceTyp OBJECT-TYPE
    SYNTAX OCTET STRING 
    ACCESS read-write
    STATUS mandatory
    DESCRIPTION
        "Manufacturer device name (model number)."
    ::= { wtWebioEA12x12Manufact 5 }

-- wtWebioEA12x12Diag Group
----------------------------

wtWebioEA12x12DiagErrorCount OBJECT-TYPE
    SYNTAX INTEGER
    ACCESS read-only
    STATUS mandatory
    DESCRIPTION
        "Number of entries in the error memory."
    ::= { wtWebioEA12x12Diag 1 }

wtWebioEA12x12DiagBinaryError OBJECT-TYPE
    SYNTAX OCTET STRING 
    ACCESS read-only
    STATUS mandatory
    DESCRIPTION
        "Error causes coded bit-by-bit."
    ::= { wtWebioEA12x12Diag 2 }

wtWebioEA12x12DiagErrorIndex OBJECT-TYPE
    SYNTAX INTEGER
    ACCESS read-write
    STATUS mandatory
    DESCRIPTION
        "The value of this variable is used as an index to read 
        an error massege from wtWebioEA12x12DiagErrorMessage.
        Errors are numbered from 1 to wtWebioEA12x12DiagErrorCount.
        Writing a valid value into this variable, making the appropriate 
        message readable from wtWebioEA12x12DiagErrorMessage."
    ::= { wtWebioEA12x12Diag 3 }

wtWebioEA12x12DiagErrorMessage OBJECT-TYPE
    SYNTAX OCTET STRING 
    ACCESS read-only
    STATUS mandatory
    DESCRIPTION
        "Using wtWebioEA12x12DiagErrorIndex as an index, the appropriate message is available."
    ::= { wtWebioEA12x12Diag 4 }
    
wtWebioEA12x12DiagErrorClear OBJECT-TYPE
    SYNTAX INTEGER
    ACCESS write-only
    STATUS mandatory
    DESCRIPTION
        "Writing 1 into this variable clears all diagnosis messages."
    ::= { wtWebioEA12x12Diag 5 }


-- TRAP DEFINITIONS

-- Diese SNMP-Traps werden gesendet, wenn die Alarmtriggerbedingungen zutreffen 

wtWebioEA12x12Alert1 TRAP-TYPE
    ENTERPRISE  wtWebioEA12x12
    VARIABLES   { wtWebioEA12x12AlarmSnmpTrapText }
    DESCRIPTION
        "This SNMP trap is generated when Alarm 1 was triggered,
        SNMP trap enable is set and
        SNMP is enabled."
    -- NMS trap annotation
    --#TYPE "Webio Digital Alarm 1"
    --#SUMMARY "Alarm 1: %s"
    --#ARGUMENTS {0}
    --#SEVERITY INFORMATIONAL
    --#TIMEINDEX 99
    --#STATE OPERATIONAL    
    ::= 41

wtWebioEA12x12Alert2 TRAP-TYPE
    ENTERPRISE  wtWebioEA12x12
    VARIABLES   { wtWebioEA12x12AlarmSnmpTrapText }
    DESCRIPTION
        "This SNMP trap is generated when Alarm 2 was triggered,
        SNMP trap enable is set and
        SNMP is enabled."
    -- NMS trap annotation
    --#TYPE "Webio Digital Alarm 2"
    --#SUMMARY "Alarm 2: %s"
    --#ARGUMENTS {0}
    --#SEVERITY INFORMATIONAL
    --#TIMEINDEX 99
    --#STATE OPERATIONAL    
    ::= 42

wtWebioEA12x12Alert3 TRAP-TYPE
    ENTERPRISE  wtWebioEA12x12
    VARIABLES   { wtWebioEA12x12AlarmSnmpTrapText }
    DESCRIPTION
        "This SNMP trap is generated when Alarm 3 was triggered,
        SNMP trap enable is set and
        SNMP is enabled."
    -- NMS trap annotation
    --#TYPE "Webio Digital Alarm 3"
    --#SUMMARY "Alarm 3: %s"
    --#ARGUMENTS {0}
    --#SEVERITY INFORMATIONAL
    --#TIMEINDEX 99
    --#STATE OPERATIONAL    
    ::= 43

wtWebioEA12x12Alert4 TRAP-TYPE
    ENTERPRISE  wtWebioEA12x12
    VARIABLES   { wtWebioEA12x12AlarmSnmpTrapText }
    DESCRIPTION
        "This SNMP trap is generated when Alarm 4 was triggered,
        SNMP trap enable is set and
        SNMP is enabled."
    -- NMS trap annotation
    --#TYPE "Webio Digital Alarm 4"
    --#SUMMARY "Alarm 4: %s"
    --#ARGUMENTS {0}
    --#SEVERITY INFORMATIONAL
    --#TIMEINDEX 99
    --#STATE OPERATIONAL    
    ::= 44

wtWebioEA12x12Alert5 TRAP-TYPE
    ENTERPRISE  wtWebioEA12x12
    VARIABLES   { wtWebioEA12x12AlarmSnmpTrapText }
    DESCRIPTION
        "This SNMP trap is generated when Alarm 5 was triggered,
        SNMP trap enable is set and
        SNMP is enabled."
    -- NMS trap annotation
    --#TYPE "Webio Digital Alarm 5"
    --#SUMMARY "Alarm 5: %s"
    --#ARGUMENTS {0}
    --#SEVERITY INFORMATIONAL
    --#TIMEINDEX 99
    --#STATE OPERATIONAL    
    ::= 45

wtWebioEA12x12Alert6 TRAP-TYPE
    ENTERPRISE  wtWebioEA12x12
    VARIABLES   { wtWebioEA12x12AlarmSnmpTrapText }
    DESCRIPTION
        "This SNMP trap is generated when Alarm 6 was triggered,
        SNMP trap enable is set and
        SNMP is enabled."
    -- NMS trap annotation
    --#TYPE "Webio Digital Alarm 6"
    --#SUMMARY "Alarm 6: %s"
    --#ARGUMENTS {0}
    --#SEVERITY INFORMATIONAL
    --#TIMEINDEX 99
    --#STATE OPERATIONAL    
    ::= 46

wtWebioEA12x12Alert7 TRAP-TYPE
    ENTERPRISE  wtWebioEA12x12
    VARIABLES   { wtWebioEA12x12AlarmSnmpTrapText }
    DESCRIPTION
        "This SNMP trap is generated when Alarm 7 was triggered,
        SNMP trap enable is set and
        SNMP is enabled."
    -- NMS trap annotation
    --#TYPE "Webio Digital Alarm 7"
    --#SUMMARY "Alarm 7: %s"
    --#ARGUMENTS {0}
    --#SEVERITY INFORMATIONAL
    --#TIMEINDEX 99
    --#STATE OPERATIONAL    
    ::= 47

wtWebioEA12x12Alert8 TRAP-TYPE
    ENTERPRISE  wtWebioEA12x12
    VARIABLES   { wtWebioEA12x12AlarmSnmpTrapText }
    DESCRIPTION
        "This SNMP trap is generated when Alarm 8 was triggered,
        SNMP trap enable is set and
        SNMP is enabled."
    -- NMS trap annotation
    --#TYPE "Webio Digital Alarm 8"
    --#SUMMARY "Alarm 8: %s"
    --#ARGUMENTS {0}
    --#SEVERITY INFORMATIONAL
    --#TIMEINDEX 99
    --#STATE OPERATIONAL    
    ::= 48

wtWebioEA12x12Alert9 TRAP-TYPE
    ENTERPRISE  wtWebioEA12x12
    VARIABLES   { wtWebioEA12x12AlarmSnmpTrapText }
    DESCRIPTION
        "This SNMP trap is generated when Alarm 9 was triggered,
        SNMP trap enable is set and
        SNMP is enabled."
    -- NMS trap annotation
    --#TYPE "Webio Digital Alarm 9"
    --#SUMMARY "Alarm 9: %s"
    --#ARGUMENTS {0}
    --#SEVERITY INFORMATIONAL
    --#TIMEINDEX 99
    --#STATE OPERATIONAL    
    ::= 49

wtWebioEA12x12Alert10 TRAP-TYPE
    ENTERPRISE  wtWebioEA12x12
    VARIABLES   { wtWebioEA12x12AlarmSnmpTrapText }
    DESCRIPTION
        "This SNMP trap is generated when Alarm 10 was triggered,
        SNMP trap enable is set and
        SNMP is enabled."
    -- NMS trap annotation
    --#TYPE "Webio Digital Alarm 10"
    --#SUMMARY "Alarm 10: %s"
    --#ARGUMENTS {0}
    --#SEVERITY INFORMATIONAL
    --#TIMEINDEX 99
    --#STATE OPERATIONAL    
    ::= 50

wtWebioEA12x12Alert11 TRAP-TYPE
    ENTERPRISE  wtWebioEA12x12
    VARIABLES   { wtWebioEA12x12AlarmSnmpTrapText }
    DESCRIPTION
        "This SNMP trap is generated when Alarm 11 was triggered,
        SNMP trap enable is set and
        SNMP is enabled."
    -- NMS trap annotation
    --#TYPE "Webio Digital Alarm 11"
    --#SUMMARY "Alarm 11: %s"
    --#ARGUMENTS {0}
    --#SEVERITY INFORMATIONAL
    --#TIMEINDEX 99
    --#STATE OPERATIONAL    
    ::= 51

wtWebioEA12x12Alert12 TRAP-TYPE
    ENTERPRISE  wtWebioEA12x12
    VARIABLES   { wtWebioEA12x12AlarmSnmpTrapText }
    DESCRIPTION
        "This SNMP trap is generated when Alarm 12 was triggered,
        SNMP trap enable is set and
        SNMP is enabled."
    -- NMS trap annotation
    --#TYPE "Webio Digital Alarm 12"
    --#SUMMARY "Alarm 12: %s"
    --#ARGUMENTS {0}
    --#SEVERITY INFORMATIONAL
    --#TIMEINDEX 99
    --#STATE OPERATIONAL    
    ::= 52

wtWebioEA12x12Alert13 TRAP-TYPE
    ENTERPRISE  wtWebioEA12x12
    VARIABLES   { wtWebioEA12x12AlarmSnmpTrapReleaseText }
    DESCRIPTION
        "This SNMP trap is generated when Alarm 1 was released,
        SNMP trap enable is set and
        SNMP is enabled."
    -- NMS trap annotation
    --#TYPE "Webio Digital Release Alarm 1"
    --#SUMMARY "Release Alarm 1: %s"
    --#ARGUMENTS {0}
    --#SEVERITY INFORMATIONAL
    --#TIMEINDEX 99
    --#STATE OPERATIONAL    
    ::= 71

wtWebioEA12x12Alert14 TRAP-TYPE
    ENTERPRISE  wtWebioEA12x12
    VARIABLES   { wtWebioEA12x12AlarmSnmpTrapReleaseText }
    DESCRIPTION
        "This SNMP trap is generated when Alarm 2 was released,
        SNMP trap enable is set and
        SNMP is enabled."
    -- NMS trap annotation
    --#TYPE "Webio Digital Release Alarm 2"
    --#SUMMARY "Release Alarm 2: %s"
    --#ARGUMENTS {0}
    --#SEVERITY INFORMATIONAL
    --#TIMEINDEX 99
    --#STATE OPERATIONAL    
    ::= 72

wtWebioEA12x12Alert15 TRAP-TYPE
    ENTERPRISE  wtWebioEA12x12
    VARIABLES   { wtWebioEA12x12AlarmSnmpTrapReleaseText }
    DESCRIPTION
        "This SNMP trap is generated when Alarm 3 was released,
        SNMP trap enable is set and
        SNMP is enabled."
    -- NMS trap annotation
    --#TYPE "Webio Digital Release Alarm 3"
    --#SUMMARY "Release Alarm 3: %s"
    --#ARGUMENTS {0}
    --#SEVERITY INFORMATIONAL
    --#TIMEINDEX 99
    --#STATE OPERATIONAL    
    ::= 73

wtWebioEA12x12Alert16 TRAP-TYPE
    ENTERPRISE  wtWebioEA12x12
    VARIABLES   { wtWebioEA12x12AlarmSnmpTrapReleaseText }
    DESCRIPTION
        "This SNMP trap is generated when Alarm 4 was released,
        SNMP trap enable is set and
        SNMP is enabled."
    -- NMS trap annotation
    --#TYPE "Webio Digital Release Alarm 4"
    --#SUMMARY "Release Alarm 4: %s"
    --#ARGUMENTS {0}
    --#SEVERITY INFORMATIONAL
    --#TIMEINDEX 99
    --#STATE OPERATIONAL    
    ::= 74

wtWebioEA12x12Alert17 TRAP-TYPE
    ENTERPRISE  wtWebioEA12x12
    VARIABLES   { wtWebioEA12x12AlarmSnmpTrapReleaseText }
    DESCRIPTION
        "This SNMP trap is generated when Alarm 5 was released,
        SNMP trap enable is set and
        SNMP is enabled."
    -- NMS trap annotation
    --#TYPE "Webio Digital Release Alarm 5"
    --#SUMMARY "Release Alarm 5: %s"
    --#ARGUMENTS {0}
    --#SEVERITY INFORMATIONAL
    --#TIMEINDEX 99
    --#STATE OPERATIONAL    
    ::= 75

wtWebioEA12x12Alert18 TRAP-TYPE
    ENTERPRISE  wtWebioEA12x12
    VARIABLES   { wtWebioEA12x12AlarmSnmpTrapReleaseText }
    DESCRIPTION
        "This SNMP trap is generated when Alarm 6 was released,
        SNMP trap enable is set and
        SNMP is enabled."
    -- NMS trap annotation
    --#TYPE "Webio Digital Release Alarm 6"
    --#SUMMARY "Release Alarm 6: %s"
    --#ARGUMENTS {0}
    --#SEVERITY INFORMATIONAL
    --#TIMEINDEX 99
    --#STATE OPERATIONAL    
    ::= 76

wtWebioEA12x12Alert19 TRAP-TYPE
    ENTERPRISE  wtWebioEA12x12
    VARIABLES   { wtWebioEA12x12AlarmSnmpTrapReleaseText }
    DESCRIPTION
        "This SNMP trap is generated when Alarm 7 was released,
        SNMP trap enable is set and
        SNMP is enabled."
    -- NMS trap annotation
    --#TYPE "Webio Digital Release Alarm 7"
    --#SUMMARY "Release Alarm 7: %s"
    --#ARGUMENTS {0}
    --#SEVERITY INFORMATIONAL
    --#TIMEINDEX 99
    --#STATE OPERATIONAL    
    ::= 77

wtWebioEA12x12Alert20 TRAP-TYPE
    ENTERPRISE  wtWebioEA12x12
    VARIABLES   { wtWebioEA12x12AlarmSnmpTrapReleaseText }
    DESCRIPTION
        "This SNMP trap is generated when Alarm 8 was released,
        SNMP trap enable is set and
        SNMP is enabled."
    -- NMS trap annotation
    --#TYPE "Webio Digital Release Alarm 8"
    --#SUMMARY "Release Alarm 8: %s"
    --#ARGUMENTS {0}
    --#SEVERITY INFORMATIONAL
    --#TIMEINDEX 99
    --#STATE OPERATIONAL    
    ::= 78

wtWebioEA12x12Alert21 TRAP-TYPE
    ENTERPRISE  wtWebioEA12x12
    VARIABLES   { wtWebioEA12x12AlarmSnmpTrapReleaseText }
    DESCRIPTION
        "This SNMP trap is generated when Alarm 9 was released,
        SNMP trap enable is set and
        SNMP is enabled."
    -- NMS trap annotation
    --#TYPE "Webio Digital Release Alarm 9"
    --#SUMMARY "Release Alarm 9: %s"
    --#ARGUMENTS {0}
    --#SEVERITY INFORMATIONAL
    --#TIMEINDEX 99
    --#STATE OPERATIONAL    
    ::= 79

wtWebioEA12x12Alert22 TRAP-TYPE
    ENTERPRISE  wtWebioEA12x12
    VARIABLES   { wtWebioEA12x12AlarmSnmpTrapReleaseText }
    DESCRIPTION
        "This SNMP trap is generated when Alarm 10 was released,
        SNMP trap enable is set and
        SNMP is enabled."
    -- NMS trap annotation
    --#TYPE "Webio Digital Release Alarm 10"
    --#SUMMARY "Release Alarm 10: %s"
    --#ARGUMENTS {0}
    --#SEVERITY INFORMATIONAL
    --#TIMEINDEX 99
    --#STATE OPERATIONAL    
    ::= 80

wtWebioEA12x12Alert23 TRAP-TYPE
    ENTERPRISE  wtWebioEA12x12
    VARIABLES   { wtWebioEA12x12AlarmSnmpTrapReleaseText }
    DESCRIPTION
        "This SNMP trap is generated when Alarm 11 was released,
        SNMP trap enable is set and
        SNMP is enabled."
    -- NMS trap annotation
    --#TYPE "Webio Digital Release Alarm 11"
    --#SUMMARY "Release Alarm 11: %s"
    --#ARGUMENTS {0}
    --#SEVERITY INFORMATIONAL
    --#TIMEINDEX 99
    --#STATE OPERATIONAL    
    ::= 81

wtWebioEA12x12Alert24 TRAP-TYPE
    ENTERPRISE  wtWebioEA12x12
    VARIABLES   { wtWebioEA12x12AlarmSnmpTrapReleaseText }
    DESCRIPTION
        "This SNMP trap is generated when Alarm 12 was released,
        SNMP trap enable is set and
        SNMP is enabled."
    -- NMS trap annotation
    --#TYPE "Webio Digital Release Alarm 12"
    --#SUMMARY "Release Alarm 12: %s"
    --#ARGUMENTS {0}
    --#SEVERITY INFORMATIONAL
    --#TIMEINDEX 99
    --#STATE OPERATIONAL    
    ::= 82

wtWebioEA12x12AlertDiag TRAP-TYPE
    ENTERPRISE  wtWebioEA12x12
    VARIABLES   { 	
    		wtWebioEA12x12DiagErrorIndex,
    	  	wtWebioEA12x12DiagErrorMessage
    		}
    DESCRIPTION
        "This SNMP trap is generated when a diagnosis/error message was triggered,
        SNMP trap enable is set and
        SNMP is enabled."
    -- NMS trap annotation
    --#TYPE "Webio Digital Diagnose Error"
    --#SUMMARY "Diagnose error index: %d, Message: %s."
    --#ARGUMENTS {0,1}
    --#SEVERITY MAJOR
    --#TIMEINDEX 99
    --#STATE DEGRADED    
    ::= 110

--------------------------------------------------------------------------------
--------------------------------------------------------------------------------
--------------------------------------------------------------------------------

-- wtWebioEA24oemInOut Group
------------------------

wtWebioEA24oemInputs OBJECT-TYPE
    SYNTAX INTEGER (1..24)
    ACCESS read-only
    STATUS mandatory
    DESCRIPTION
        "Number of independent inputs."
    ::= { wtWebioEA24oemInOut 1 }

wtWebioEA24oemOutputs OBJECT-TYPE
    SYNTAX INTEGER (1..24)
    ACCESS read-only
    STATUS mandatory
    DESCRIPTION
        "Number of independent outputs."
    ::= { wtWebioEA24oemInOut 2 }

-- Input Interface Table

wtWebioEA24oemInputTable OBJECT-TYPE
    SYNTAX SEQUENCE OF WtWebioEA24oemInputEntry
    ACCESS not-accessible
    STATUS mandatory
    DESCRIPTION
        "List of input indices."
    ::= { wtWebioEA24oemInOut 3 }

wtWebioEA24oemInputEntry OBJECT-TYPE
    SYNTAX WtWebioEA24oemInputEntry
    ACCESS not-accessible
    STATUS mandatory
    DESCRIPTION
        "Numbers of the inputs."
    INDEX  { wtWebioEA24oemInputNo }
    ::= { wtWebioEA24oemInputTable 1 }

WtWebioEA24oemInputEntry ::= SEQUENCE {
    wtWebioEA24oemInputNo           	INTEGER,
    wtWebioEA24oemInputCounter      	INTEGER,
    wtWebioEA24oemInputCounterClear 	INTEGER,
    wtWebioEA24oemInputState 		INTEGER
}

wtWebioEA24oemInputNo OBJECT-TYPE
    SYNTAX INTEGER
    ACCESS read-only
    STATUS mandatory
    DESCRIPTION
        "Index numbers of the inputs."
    ::= { wtWebioEA24oemInputEntry 1 }

wtWebioEA24oemInputCounter OBJECT-TYPE
    SYNTAX INTEGER
    ACCESS read-only
    STATUS mandatory
    DESCRIPTION
        "Value of the input counter."
    ::= { wtWebioEA24oemInputEntry 2 }

wtWebioEA24oemInputCounterClear OBJECT-TYPE
    SYNTAX INTEGER
    ACCESS read-only
    STATUS mandatory
    DESCRIPTION
        "Value of the input counter. After reading this counter will be cleared."
    ::= { wtWebioEA24oemInputEntry 3 }

wtWebioEA24oemInputState OBJECT-TYPE
    SYNTAX INTEGER{
    wtWebioEA24oemInputState-OFF(0),
    wtWebioEA24oemInputState-ON(1)
    }
    ACCESS read-only
    STATUS mandatory
    DESCRIPTION
        "Value of a single input bit."
    ::= { wtWebioEA24oemInputEntry 4 }    
    
wtWebioEA24oemInputValue OBJECT-TYPE
    SYNTAX INTEGER
    ACCESS read-only
    STATUS mandatory
    DESCRIPTION
        "This variable is used to read the inputs of the digital I/O port.
	The OCTETS are interpreted bit-by-bit, with each bit corresponding to an input.
        Bit 0 corresponds to the LSB.
        OCTET 1: unused
        OCTET 2: Bit 0-7 : inputs 16 - 23
        OCTET 3: Bit 0-7 : inputs  8 - 15
        OCTET 4: Bit 0-7 : inputs  0 - 7"
    ::= { wtWebioEA24oemInOut 4 }
    

-- Output Interface Table

wtWebioEA24oemOutputTable OBJECT-TYPE
    SYNTAX SEQUENCE OF WtWebioEA24oemOutputEntry
    ACCESS not-accessible
    STATUS mandatory
    DESCRIPTION
        "List of output indices."
    ::= { wtWebioEA24oemInOut 5 }

wtWebioEA24oemOutputEntry OBJECT-TYPE
    SYNTAX WtWebioEA24oemOutputEntry
    ACCESS not-accessible
    STATUS mandatory
    DESCRIPTION
        "Numbers of the outputs."
    INDEX  { wtWebioEA24oemOutputNo }
    ::= { wtWebioEA24oemOutputTable 1 }

WtWebioEA24oemOutputEntry ::= SEQUENCE {
    wtWebioEA24oemOutputNo INTEGER,
    wtWebioEA24oemOutputState INTEGER
}

wtWebioEA24oemOutputNo OBJECT-TYPE
    SYNTAX INTEGER (1..24)
    ACCESS read-only
    STATUS mandatory
    DESCRIPTION
        "Index numbers of the outputs."
    ::= { wtWebioEA24oemOutputEntry 1 }

wtWebioEA24oemOutputState OBJECT-TYPE
    SYNTAX INTEGER{
    wtWebioEA24oemOutputState-OFF(0),
    wtWebioEA24oemOutputState-ON(1)
    }
    ACCESS read-write
    STATUS mandatory
    DESCRIPTION
        "Value of a single output bit."
    ::= { wtWebioEA24oemOutputEntry 2 }    

wtWebioEA24oemOutputValue OBJECT-TYPE
    SYNTAX INTEGER
    ACCESS read-write
    STATUS mandatory
    DESCRIPTION
        "This variable is used to read and write the outputs of the digital I/O port. 
        The OCTETS are interpreted bit-by-bit, with each bit corresponding to an output. 
        Bit 0 corresponds to the LSB.
        Octet 1: unused
        Octet 2: Bit 0-7: Digital outputs 16-23
        OCTET 3, Bit 0-7: Digital outputs 8-15
        OCTET 4, Bit 0-7: Digital outputs 0-7"
    ::= { wtWebioEA24oemInOut 6 }
    
wtWebioEA24oemSetOutput OBJECT-TYPE
    SYNTAX OCTET STRING (SIZE (8))
    ACCESS read-write			-- write-only
    STATUS mandatory
    DESCRIPTION
        "This variable allows setting of individual digital outputs. The OCTETS are 
        interpreted bit-by-bit, with each bit corresponding to an output. Bit 0 corresponds 
        to the LSB.
        The first two OCTETS contain the mask which determines which of the outputs are to 
        be set (corresponding bit = 1) and which outputs are to remain unchanged 
        (corresponding bit = 0):
	OCTET 1: unused
	OCTET 2: Bit 0-7: Mask for digital outputs 16-23
	OCTET 3, Bit 0-7: Mask for digital outputs 8-15
	OCTET 4, Bit 0-7: Mask for digital outputs 0-7
	
	OCTETS 5-8 contain the level (1=HIGH, 0=LOW) which the inputs 
	should assume:
	OCTET 5: unused
	OCTET 6: Bit 0-7: Level of digital outputs 16-23
	OCTET 7, Bit 0-7: Level of digital outputs 8-15
        OCTET 8, Bit 0-7: Level of digital outputs 0-7"
    ::= { wtWebioEA24oemInOut 7 }
    
-- wtWebioEA24oemSessCntrl Group
--------------------------------

wtWebioEA24oemSessCntrlPassword OBJECT-TYPE
    SYNTAX OCTET STRING 
    ACCESS read-write
    STATUS mandatory
    DESCRIPTION
        "Entering this password opens a session which is ended by writing a 1 to 
        wtWebioEA24oemSessCntrlLogout. When read this variable provides a string of
        length zero."
    ::= { wtWebioEA24oemSessCntrl 1 }

wtWebioEA24oemSessCntrlConfigMode OBJECT-TYPE
    SYNTAX INTEGER {
    wtWebioEA24oemSessCntrl-NoSession(0),
    wtWebioEA24oemSessCntrl-Session(1)
    }
    ACCESS read-only
    STATUS mandatory
    DESCRIPTION
        "When the device is in SNMP configuration mode, the value 1 is
        returned, otherwise 0. If the read value is 0 even though the password
        was written, the device is already in config mode and the variables
        can only be read."
    ::= { wtWebioEA24oemSessCntrl 2 }

wtWebioEA24oemSessCntrlLogout OBJECT-TYPE
    SYNTAX INTEGER 
    ACCESS read-write
    STATUS mandatory
    DESCRIPTION
        "If the device is in configuration mode and the session was opened by
        this SNMP Manager, writing a 1 to this variable will end the session 
        and all parameters are stored.
        Writing a 2 discards all entries again. When read this variable
        provides the value 0."
    ::= { wtWebioEA24oemSessCntrl 3 }

wtWebioEA24oemSessCntrlAdminPassword OBJECT-TYPE
    SYNTAX OCTET STRING 
    ACCESS read-write
    STATUS mandatory
    DESCRIPTION
        "This password protects access to the variables with administrator rights.
        It can only be changed by the administrator. If no password was assigned,
        the valid password is public."
    ::= { wtWebioEA24oemSessCntrl 4 }

wtWebioEA24oemSessCntrlConfigPassword OBJECT-TYPE
    SYNTAX OCTET STRING 
    ACCESS read-write
    STATUS mandatory
    DESCRIPTION
        "This password protects access to the variables with configurator rights. It can
        be changed by the administrator and by the configurator. If no password was assigned, 
        the valid password is public. When read this variable provides a null-pointer."
    ::= { wtWebioEA24oemSessCntrl 5 }

-- wtWebioEA24oemText Group
------------------------

wtWebioEA24oemDeviceName OBJECT-TYPE
    SYNTAX OCTET STRING 
    ACCESS read-write
    STATUS mandatory
    DESCRIPTION
        "Name of the Webio, which is user definable."
    ::= { wtWebioEA24oemText 1 }

wtWebioEA24oemDeviceText OBJECT-TYPE
    SYNTAX OCTET STRING 
    ACCESS read-write
    STATUS mandatory
    DESCRIPTION
        "Description of the Webio, which is user definable."
    ::= { wtWebioEA24oemText 2 }
    
wtWebioEA24oemDeviceLocation OBJECT-TYPE
    SYNTAX OCTET STRING 
    ACCESS read-write
    STATUS mandatory
    DESCRIPTION
        "Description of the location of the Webio, which is user definable."
    ::= { wtWebioEA24oemText 3 }

wtWebioEA24oemDeviceContact OBJECT-TYPE
    SYNTAX OCTET STRING 
    ACCESS read-write
    STATUS mandatory
    DESCRIPTION
        "Contact address of the system operator of the Webio, which is user definable."
    ::= { wtWebioEA24oemText 4 }    

-- wtWebioEA24oemTimeZone Group
----------------------------

wtWebioEA24oemTzOffsetHrs OBJECT-TYPE
    SYNTAX INTEGER 
    ACCESS read-write
    STATUS mandatory
    DESCRIPTION
        "Offset hours for the time zone (winter time) with respect to UTC."
    ::= { wtWebioEA24oemTimeZone 1 }

wtWebioEA24oemTzOffsetMin OBJECT-TYPE
    SYNTAX INTEGER 
    ACCESS read-write
    STATUS mandatory
    DESCRIPTION
        "Offset minutes for the time zone (winter time) with respect to UTC."
    ::= { wtWebioEA24oemTimeZone 2 }

wtWebioEA24oemTzEnable OBJECT-TYPE
    SYNTAX OCTET STRING (SIZE(4))
    ACCESS read-write
    STATUS mandatory
    DESCRIPTION
        "Binary coded conditions:
        Octet 1: unused
        Octet 2: unused
        Octet 3: unused
        Octet 4:
        	Bit 1-7: unused
	        Bit 0  : Apply Timezone"
    ::= { wtWebioEA24oemTimeZone 3 }

wtWebioEA24oemStTzOffsetHrs OBJECT-TYPE
    SYNTAX INTEGER 
    ACCESS read-write
    STATUS mandatory
    DESCRIPTION
        "Offset hours of the time zone (summer time) with respect to UTC."
    ::= { wtWebioEA24oemTimeZone 4 }

wtWebioEA24oemStTzOffsetMin OBJECT-TYPE
    SYNTAX INTEGER 
    ACCESS read-write
    STATUS mandatory
    DESCRIPTION
        "Offset minutes of the time zone (summer time) with respect to UTC."
    ::= { wtWebioEA24oemTimeZone 5 }
    
wtWebioEA24oemStTzEnable OBJECT-TYPE
    SYNTAX OCTET STRING (SIZE(4))
    ACCESS read-write
    STATUS mandatory
    DESCRIPTION
        "Binary coded conditions:
        Octet 1: unused
        Octet 2: unused
        Octet 3: unused
        Octet 4:
        	Bit 1-7: unused
	        Bit 0  : Apply Summertime"
    ::= { wtWebioEA24oemTimeZone 6 }

wtWebioEA24oemStTzStartMonth OBJECT-TYPE
    SYNTAX INTEGER {
    	wtWebioEA24oemStartMonth-January(1),
    	wtWebioEA24oemStartMonth-February(2),
    	wtWebioEA24oemStartMonth-March(3),
    	wtWebioEA24oemStartMonth-April(4),
    	wtWebioEA24oemStartMonth-May(5),
    	wtWebioEA24oemStartMonth-June(6),
    	wtWebioEA24oemStartMonth-July(7),
    	wtWebioEA24oemStartMonth-August(8),
    	wtWebioEA24oemStartMonth-September(9),
    	wtWebioEA24oemStartMonth-October(10),
    	wtWebioEA24oemStartMonth-November(11),
    	wtWebioEA24oemStartMonth-December(12)
    	}
    	
    ACCESS read-write
    STATUS mandatory
    DESCRIPTION
        "Month in which the change is made from winter time to summer time."
    ::= { wtWebioEA24oemTimeZone 7 }

wtWebioEA24oemStTzStartMode OBJECT-TYPE
    SYNTAX INTEGER {
    	wtWebioEA24oemStartMode-first(1),
    	wtWebioEA24oemStartMode-second(2),
    	wtWebioEA24oemStartMode-third(3),
    	wtWebioEA24oemStartMode-fourth(4),
    	wtWebioEA24oemStartMode-last(5)
    	}
    	
    ACCESS read-write
    STATUS mandatory
    DESCRIPTION
        "Mode of the day of the week for which the change is made from winter time to summer time."
    ::= { wtWebioEA24oemTimeZone 8 }

wtWebioEA24oemStTzStartWday OBJECT-TYPE
    SYNTAX INTEGER {
    	wtWebioEA24oemStartWday-Sunday(1),
    	wtWebioEA24oemStartWday-Monday(2),
    	wtWebioEA24oemStartWday-Tuesday(3),
    	wtWebioEA24oemStartWday-Thursday(4),
    	wtWebioEA24oemStartWday-Wednesday(5),
    	wtWebioEA24oemStartWday-Friday(6),
    	wtWebioEA24oemStartWday-Saturday(7)
    	}
    	
    ACCESS read-write
    STATUS mandatory
    DESCRIPTION
        "Day of the week on which the change is made from winter time to summer time"
    ::= { wtWebioEA24oemTimeZone 9 }
    
wtWebioEA24oemStTzStartHrs OBJECT-TYPE
    SYNTAX INTEGER 
    ACCESS read-write
    STATUS mandatory
    DESCRIPTION
        "Hour in which the time zone is changed from winter to summer time with
        respect to UTC."
    ::= { wtWebioEA24oemTimeZone 10 }

wtWebioEA24oemStTzStartMin OBJECT-TYPE
    SYNTAX INTEGER 
    ACCESS read-write
    STATUS mandatory
    DESCRIPTION
        "Minute in which the time zone is changed from winter to summer time with
        respect to UTC."
    ::= { wtWebioEA24oemTimeZone 11 }
 
wtWebioEA24oemStTzStopMonth OBJECT-TYPE
    SYNTAX INTEGER {
    	wtWebioEA24oemStopMonth-January(1),
    	wtWebioEA24oemStopMonth-February(2),
    	wtWebioEA24oemStopMonth-March(3),
    	wtWebioEA24oemStopMonth-April(4),
    	wtWebioEA24oemStopMonth-May(5),
    	wtWebioEA24oemStopMonth-June(6),
    	wtWebioEA24oemStopMonth-July(7),
    	wtWebioEA24oemStopMonth-August(8),
    	wtWebioEA24oemStopMonth-September(9),
    	wtWebioEA24oemStopMonth-October(10),
    	wtWebioEA24oemStopMonth-November(11),
    	wtWebioEA24oemStopMonth-December(12)
    	}
    ACCESS read-write
    STATUS mandatory
    DESCRIPTION
        "Month in which the change is made from summer time to winter time."
   ::= { wtWebioEA24oemTimeZone 12 }

wtWebioEA24oemStTzStopMode OBJECT-TYPE
    SYNTAX INTEGER {
    	wtWebioEA24oemStopMode-first(1),
    	wtWebioEA24oemStopMode-second(2),
    	wtWebioEA24oemStopMode-third(3),
    	wtWebioEA24oemStopMode-fourth(4),
    	wtWebioEA24oemStopMode-last(5)
    	}
    ACCESS read-write
    STATUS mandatory
    DESCRIPTION
        "Mode of the week day on which the change is made from summer time to winter time."
    ::= { wtWebioEA24oemTimeZone 13 }

wtWebioEA24oemStTzStopWday OBJECT-TYPE
    SYNTAX INTEGER {
    	wtWebioEA24oemStopWday-Sunday(1),
    	wtWebioEA24oemStopWday-Monday(2),
    	wtWebioEA24oemStopWday-Tuesday(3),
    	wtWebioEA24oemStopWday-Thursday(4),
    	wtWebioEA24oemStopWday-Wednesday(5),
    	wtWebioEA24oemStopWday-Friday(6),
    	wtWebioEA24oemStopWday-Saturday(7)
    	}
    ACCESS read-write
    STATUS mandatory
    DESCRIPTION
        "Day of the week on which the change is made from summer time to winter time."
    ::= { wtWebioEA24oemTimeZone 14 }
    
wtWebioEA24oemStTzStopHrs OBJECT-TYPE
    SYNTAX INTEGER 
    ACCESS read-write
    STATUS mandatory
    DESCRIPTION
        "Hour at which the time zone is changed from summer to winter time with
        respect to UTC."
    ::= { wtWebioEA24oemTimeZone 15 }

wtWebioEA24oemStTzStopMin OBJECT-TYPE
    SYNTAX INTEGER 
    ACCESS read-write
    STATUS mandatory
    DESCRIPTION
        "Minute at which the time zone is changed from summer to winter time with
        respect to UTC."
    ::= { wtWebioEA24oemTimeZone 16 }

-- wtWebioEA24oemTimeServer Group
----------------------------

wtWebioEA24oemTimeServer1 OBJECT-TYPE
    SYNTAX OCTET STRING 
    ACCESS read-write
    STATUS mandatory
    DESCRIPTION
        "IP address or name of the 1st time server in ASCII"
    ::= { wtWebioEA24oemTimeServer 1 }

wtWebioEA24oemTimeServer2 OBJECT-TYPE
    SYNTAX OCTET STRING 
    ACCESS read-write
    STATUS mandatory
    DESCRIPTION
        "IP address or name of the 2nd time server in ASCII"
    ::= { wtWebioEA24oemTimeServer 2 }

wtWebioEA24oemTsEnable OBJECT-TYPE
    SYNTAX OCTET STRING (SIZE(4))
    ACCESS read-write
    STATUS mandatory
    DESCRIPTION
        "Binary coded conditions:
        Octet 1: unused
        Octet 2: unused
        Octet 3: unused
        Octet 4:
        	Bit 1-7: unused
	        Bit 0  : Apply Time Server"
    ::= { wtWebioEA24oemTimeServer 3 }
    
wtWebioEA24oemTsSyncTime OBJECT-TYPE
    SYNTAX INTEGER 
    ACCESS read-write
    STATUS mandatory
    DESCRIPTION
        "Daily synchronisation time with the time server (hour: 0-23)."
    ::= { wtWebioEA24oemTimeServer 4 }
          
    
-- wtWebioEA24oemDeviceClock Group
--------------------------------

wtWebioEA24oemClockHrs OBJECT-TYPE
    SYNTAX INTEGER (0..23)
    ACCESS read-write
    STATUS mandatory
    DESCRIPTION
        "Clock hours taking into account the time zone settings."
    ::= { wtWebioEA24oemDeviceClock 1 }

wtWebioEA24oemClockMin OBJECT-TYPE
    SYNTAX INTEGER (0..59)
    ACCESS read-write
    STATUS mandatory
    DESCRIPTION
        "Clock minutes taking into account the time zone settings."
    ::= { wtWebioEA24oemDeviceClock 2 }

wtWebioEA24oemClockDay OBJECT-TYPE
    SYNTAX INTEGER (1..31)
    ACCESS read-write
    STATUS mandatory
    DESCRIPTION
        "Date: Day of the month, taking into account the time zone settings."
    ::= { wtWebioEA24oemDeviceClock 3 }

wtWebioEA24oemClockMonth OBJECT-TYPE
   SYNTAX INTEGER {
    	wtWebioEA24oemClockMonth-January(1),
    	wtWebioEA24oemClockMonth-February(2),
    	wtWebioEA24oemClockMonth-March(3),
    	wtWebioEA24oemClockMonth-April(4),
    	wtWebioEA24oemClockMonth-May(5),
    	wtWebioEA24oemClockMonth-June(6),
    	wtWebioEA24oemClockMonth-July(7),
    	wtWebioEA24oemClockMonth-August(8),
    	wtWebioEA24oemClockMonth-September(9),
    	wtWebioEA24oemClockMonth-October(10),
    	wtWebioEA24oemClockMonth-November(11),
    	wtWebioEA24oemClockMonth-December(12)
    	}
    ACCESS read-write
    STATUS mandatory
    DESCRIPTION
        "Date: Month, taking into account the time zone settings."
    ::= { wtWebioEA24oemDeviceClock 4 }

wtWebioEA24oemClockYear OBJECT-TYPE
    SYNTAX INTEGER (0..65535)
    ACCESS read-write
    STATUS mandatory
    DESCRIPTION
        "Date: Year, taking into account the time zone settings."
    ::= { wtWebioEA24oemDeviceClock 5 }    

-- wtWebioEA24oemNetwork Group
--------------------------------

wtWebioEA24oemIpAddress OBJECT-TYPE
    SYNTAX IpAddress
    ACCESS read-write
    STATUS mandatory
    DESCRIPTION
        "IP address of the Webio"
    ::= { wtWebioEA24oemNetwork 1 }

wtWebioEA24oemSubnetMask OBJECT-TYPE
    SYNTAX IpAddress
    ACCESS read-write
    STATUS mandatory
    DESCRIPTION
        "Subnet mask of the Webio"
    ::= { wtWebioEA24oemNetwork 2 }

wtWebioEA24oemGateway OBJECT-TYPE
    SYNTAX IpAddress
    ACCESS read-write
    STATUS mandatory
    DESCRIPTION
        "Gateway of the Webio"
    ::= { wtWebioEA24oemNetwork 3 }

wtWebioEA24oemDnsServer1 OBJECT-TYPE
    SYNTAX OCTET STRING 
    ACCESS read-write
    STATUS mandatory
    DESCRIPTION
        "IP address of the 1st DNS server in ASCII"
    ::= { wtWebioEA24oemNetwork 4 }

wtWebioEA24oemDnsServer2 OBJECT-TYPE
    SYNTAX OCTET STRING 
    ACCESS read-write
    STATUS mandatory
    DESCRIPTION
        "IP address of the 2nd DNS server in ASCII"
    ::= { wtWebioEA24oemNetwork 5 }

wtWebioEA24oemAddConfig OBJECT-TYPE
    SYNTAX OCTET STRING 
    ACCESS read-write
    STATUS mandatory
    DESCRIPTION
        "Additional configuration (1=ON):
        Octet 1: unused
        Octet 2: unused
        Octet 3: unused
        Octet 4:
	        Bit 1: DHCP  enable
	        Bit 0: BOOTP enable"
    ::= { wtWebioEA24oemNetwork 6 }

--  wtWebioEA24oemHTTP Group
--------------------------------

wtWebioEA24oemStartup OBJECT-TYPE
    SYNTAX OCTET STRING 
    ACCESS read-write
    STATUS mandatory
    DESCRIPTION
        "Binary coded start page, more than one page must not be selected:
        Octet 1: unused
        Octet 2: unused
        Octet 3: unused
        Octet 4:
        	Bit 2: user.htm
        	Bit 1: home.htm
	        Bit 0: index.htm"
    ::= { wtWebioEA24oemHTTP 1 }

wtWebioEA24oemGetHeaderEnable OBJECT-TYPE
    SYNTAX OCTET STRING 
    ACCESS read-write
    STATUS mandatory
    DESCRIPTION
        "If bits are set, every answer of a short form GET question will be lead
        by the IP-address and name of the device (Header) or a HTTP header (HTTP):
        Octet 1: unused
        Octet 2: unused
        Octet 3: unused
        Octet 4:
        	Bit 2-7: unused
        	Bit 1  : GET HTTP enable
                Bit 0  : GET Header enable"
    ::= { wtWebioEA24oemHTTP 2 }

wtWebioEA24oemHttpInputTrigger OBJECT-TYPE
    SYNTAX OCTET STRING (SIZE (4))
    ACCESS read-write
    STATUS mandatory
    DESCRIPTION
        "Every change on the inputs causes their state to be transmitted to the 
        remote device. To minimize data traffic, individual inputs may be exempted 
        from this rule. Nevertheless every transmission will contain all input bits.
        If a bit is set (1), a change of state on the corresponding input 
        triggers a transmission. If the bit is not set (0), no transmission 
        takes place.
        The OCTETS are interpreted bit-by-bit, with each bit corresponding to an input. 
        Bit 0 corresponds to the LSB.
        OCTET 1: unused
        OCTET 2: Bit 0-7 : inputs 16 - 23
        OCTET 3: Bit 0-7 : inputs  8 - 15
        OCTET 4: Bit 0-7 : inputs  0 - 7"
    ::= { wtWebioEA24oemHTTP 3 }
    
wtWebioEA24oemHttpPort OBJECT-TYPE
    SYNTAX INTEGER (1..65534)
    ACCESS read-write
    STATUS mandatory
    DESCRIPTION
        "Definition of the standard HTML port (Default: 80)."
    ::= { wtWebioEA24oemHTTP 4 }     

--  wtWebioEA24oemMail Group
--------------------------------

wtWebioEA24oemMailAdName OBJECT-TYPE
    SYNTAX OCTET STRING 
    ACCESS read-write
    STATUS mandatory
    DESCRIPTION
        "Device name for mail administration."
    ::= { wtWebioEA24oemMail 1 }
    
wtWebioEA24oemMailReply OBJECT-TYPE
    SYNTAX OCTET STRING 
    ACCESS read-write
    STATUS mandatory
    DESCRIPTION
        "Reply address for the mail server."
    ::= { wtWebioEA24oemMail 2 }
    
wtWebioEA24oemMailServer OBJECT-TYPE
    SYNTAX OCTET STRING 
    ACCESS read-write
    STATUS mandatory
    DESCRIPTION
        "Name or IP address of the mail server."
    ::= { wtWebioEA24oemMail 3 }
    
wtWebioEA24oemMailEnable OBJECT-TYPE
    SYNTAX OCTET STRING 
    ACCESS read-write
    STATUS mandatory
    DESCRIPTION
        "Set this bit to enable the sending of mails:
        Octet 1: unused
        Octet 2: unused
        Octet 3: unused
        Octet 4:
        	Bit 1-7: unused
                Bit 0  : Mail enable"
    ::= { wtWebioEA24oemMail 4 }
    
wtWebioEA24oemMailAuthentication OBJECT-TYPE
    SYNTAX OCTET STRING (SIZE (4))
    ACCESS read-write
    STATUS mandatory
    DESCRIPTION
        "Selection of the authentication modi:
        The OCTETS are interpreted bit-by-bit,
        Bit 0 corresponds to the LSB.
        OCTET 1: unused
        OCTET 2: unused
        OCTET 3: unused
        OCTET 4: Bit 3-7: unused
        	 Bit 2  : POP3 before SMTP
        	 Bit 1  : ESMTP, authentication
        	 Bit 0  : SMTP, no authentication"
    ::= { wtWebioEA24oemMail 5 }
    
wtWebioEA24oemMailAuthUser OBJECT-TYPE
    SYNTAX OCTET STRING 
    ACCESS read-write
    STATUS mandatory
    DESCRIPTION
        "Name of the user to be authenticated."
    ::= { wtWebioEA24oemMail 6 }    
    
wtWebioEA24oemMailAuthPassword OBJECT-TYPE
    SYNTAX OCTET STRING 
    ACCESS read-write
    STATUS mandatory
    DESCRIPTION
        "Authentication password."
    ::= { wtWebioEA24oemMail 7 }    
    
wtWebioEA24oemMailPop3Server OBJECT-TYPE
    SYNTAX OCTET STRING 
    ACCESS read-write
    STATUS mandatory
    DESCRIPTION
        "Name or Ip-address of the POP3 Servers."
    ::= { wtWebioEA24oemMail 8 }        
    

--  wtWebioEA24oemSnmp Group
--------------------------------

wtWebioEA24oemSnmpEnable OBJECT-TYPE
    SYNTAX OCTET STRING 
    ACCESS read-write
    STATUS mandatory
    DESCRIPTION
        "Set bit 0 to enable SNMP.
        If disabled, the device did not respond to any SNMP requests.
        Bit 1 decided wether the community string of read operations 
        is compared with the system password or not:
        Octet 1: unused
        Octet 2: unused
        Octet 3: unused
        Octet 4:
        	Bit 1-7: unused
        	Bit 0  : SNMP enable"
    ::= { wtWebioEA24oemSNMP 1 }
    
wtWebioEA24oemSnmpCommunityStringRead OBJECT-TYPE
    SYNTAX OCTET STRING
    ACCESS read-write
    STATUS mandatory
    DESCRIPTION
        "Community string read only"
    ::= { wtWebioEA24oemSNMP 2 }

wtWebioEA24oemSnmpCommunityStringReadWrite OBJECT-TYPE
    SYNTAX OCTET STRING
    ACCESS read-write
    STATUS mandatory
    DESCRIPTION
        "Community string read / write"
    ::= { wtWebioEA24oemSNMP 3 }

wtWebioEA24oemSnmpSystemTrapManagerIP OBJECT-TYPE
    SYNTAX OCTET STRING 
    ACCESS read-write
    STATUS mandatory
    DESCRIPTION
        "Name or IP address of the TCP server which accepts the system trap."
    ::= { wtWebioEA24oemSNMP 4 }
    
wtWebioEA24oemSnmpSystemTrapEnable OBJECT-TYPE
    SYNTAX OCTET STRING (SIZE(4))
    ACCESS read-write
    STATUS mandatory
    DESCRIPTION
        "Binary coded trigger conditions:
        Octet 1: unused
        Octet 2: unused
        Octet 3: unused
        Octet 4:
	        Bit 0:   ColdStart
	        Bit 1:   WarmStart
	        Bit 2-7: unused"
    ::= { wtWebioEA24oemSNMP 5 }    

--  wtWebioEA24oemUdp Group
--------------------------------

wtWebioEA24oemUdpAdminPort OBJECT-TYPE
    SYNTAX INTEGER
    ACCESS read-write
    STATUS mandatory
    DESCRIPTION
        "Udp port to which the Udp queries ( short form GET requests) can be sent. This
        port number must be unique within the device."
    ::= { wtWebioEA24oemUDP 1 }

wtWebioEA24oemUdpEnable OBJECT-TYPE
    SYNTAX OCTET STRING 
    ACCESS read-write
    STATUS mandatory
    DESCRIPTION
        "Set this bit to enable UDP support:
        Octet 1: unused
        Octet 2: unused
        Octet 3: unused
        Octet 4:
        	Bit 1-7: unused
                Bit 0  : UDP enable"
    ::= { wtWebioEA24oemUDP 2 }

wtWebioEA24oemUdpRemotePort OBJECT-TYPE
    SYNTAX INTEGER
    ACCESS read-write
    STATUS mandatory
    DESCRIPTION
        "Udp remote port setting.
        If this value is set to zero, the source port read from a request will be used 
        as destination port for the answer.
        A non zero value forced the destination port to this value."
    ::= { wtWebioEA24oemUDP 3 }
    
--  wtWebioEA24oemBinary Group
--------------------------------

wtWebioEA24oemBinaryModeCount OBJECT-TYPE
    SYNTAX INTEGER (1..2)
    ACCESS read-only
    STATUS mandatory
    DESCRIPTION
        "Number of independent binary channels."
    ::= { wtWebioEA24oemBinary 1 }
    
-- Binary Interface Table

wtWebioEA24oemBinaryIfTable OBJECT-TYPE
    SYNTAX SEQUENCE OF WtWebioEA24oemBinaryIfEntry
    ACCESS not-accessible
    STATUS mandatory
    DESCRIPTION
        "Table of indices."
    ::= { wtWebioEA24oemBinary 2 }

wtWebioEA24oemBinaryIfEntry OBJECT-TYPE
    SYNTAX WtWebioEA24oemBinaryIfEntry
    ACCESS not-accessible
    STATUS mandatory
    DESCRIPTION
        "Indices of the binary channels."
    INDEX  { wtWebioEA24oemBinaryModeNo }
    ::= { wtWebioEA24oemBinaryIfTable 1 }

WtWebioEA24oemBinaryIfEntry ::= SEQUENCE {
    wtWebioEA24oemBinaryModeNo INTEGER
}

wtWebioEA24oemBinaryModeNo OBJECT-TYPE
    SYNTAX INTEGER (1..2)
    ACCESS read-only
    STATUS mandatory
    DESCRIPTION
        "Number of the binary channel."
    ::= { wtWebioEA24oemBinaryIfEntry 1 }

-- Binary Table
--------------------------------

wtWebioEA24oemBinaryTable OBJECT-TYPE
    SYNTAX SEQUENCE OF WtWebioEA24oemBinaryEntry
    ACCESS not-accessible
    STATUS mandatory
    DESCRIPTION
        "Table of properties of the binary mode."
    ::= { wtWebioEA24oemBinary 3 }

wtWebioEA24oemBinaryEntry OBJECT-TYPE
    SYNTAX WtWebioEA24oemBinaryEntry
    ACCESS not-accessible
    STATUS mandatory
    DESCRIPTION
        "Binary properties."
    INDEX  { wtWebioEA24oemBinaryModeNo }
    ::= { wtWebioEA24oemBinaryTable 1 }

WtWebioEA24oemBinaryEntry ::= SEQUENCE {
    wtWebioEA24oemBinaryOperationMode			OCTET STRING,
    wtWebioEA24oemBinaryTcpServerLocalPort		INTEGER,
    wtWebioEA24oemBinaryTcpServerInputTrigger		OCTET STRING,
    wtWebioEA24oemBinaryTcpServerApplicationMode	OCTET STRING,
    wtWebioEA24oemBinaryTcpClientLocalPort		INTEGER,
    wtWebioEA24oemBinaryTcpClientServerPort		INTEGER,
    wtWebioEA24oemBinaryTcpClientServerIpAddr		OCTET STRING,
    wtWebioEA24oemBinaryTcpClientServerPassword		OCTET STRING,
    wtWebioEA24oemBinaryTcpClientInactivity		INTEGER,
    wtWebioEA24oemBinaryTcpClientInputTrigger		OCTET STRING,
    wtWebioEA24oemBinaryTcpClientInterval		INTEGER,
    wtWebioEA24oemBinaryTcpClientApplicationMode	OCTET STRING,
    wtWebioEA24oemBinaryUdpPeerLocalPort		INTEGER,
    wtWebioEA24oemBinaryUdpPeerRemotePort		INTEGER,
    wtWebioEA24oemBinaryUdpPeerRemoteIpAddr		OCTET STRING,
    wtWebioEA24oemBinaryUdpPeerInputTrigger		OCTET STRING,
    wtWebioEA24oemBinaryUdpPeerInterval			INTEGER,
    wtWebioEA24oemBinaryUdpPeerApplicationMode		OCTET STRING,
    wtWebioEA24oemBinaryConnectedPort			INTEGER,
    wtWebioEA24oemBinaryConnectedIpAddr			IpAddress,
    wtWebioEA24oemBinaryTcpServerClientHttpPort		INTEGER,  
    wtWebioEA24oemBinaryTcpClientServerHttpPort		INTEGER
    
    
}

wtWebioEA24oemBinaryOperationMode OBJECT-TYPE
    SYNTAX OCTET STRING (SIZE (4))
    ACCESS read-write
    STATUS mandatory
    DESCRIPTION
        "Selection of the operation mode:
        The OCTETS are interpreted bit-by-bit, 
        Bit 0 corresponds to the LSB.
        OCTET 1: unused
        OCTET 2: unused
        OCTET 3: unused
        OCTET 4: Bit 3-7: unused
        	 Bit 2  : UDP Peer
        	 Bit 1  : TCP Client
        	 Bit 0  : TCP Server"
    ::= { wtWebioEA24oemBinaryEntry 1 }

wtWebioEA24oemBinaryTcpServerLocalPort OBJECT-TYPE
    SYNTAX INTEGER (1..65535)
    ACCESS read-write
    STATUS mandatory
    DESCRIPTION
        "Local TCP port for data exchange in this server mode.
        This port number must be unique within the device.
	Reserved port number must not be used (refere to the manual)."
    ::= { wtWebioEA24oemBinaryEntry 2 }

wtWebioEA24oemBinaryTcpServerInputTrigger OBJECT-TYPE
    SYNTAX OCTET STRING (SIZE (4))
    ACCESS read-write
    STATUS mandatory
    DESCRIPTION
        "Every change on the inputs causes their state to be transmitted to the 
        remote device. To minimize data traffic, individual inputs may be exempted 
        from this rule. Nevertheless every transmission will contain all input bits.
        If a bit is set (1), a change of state on the corresponding input 
        triggers a transmission. If the bit is not set (0), no transmission 
        takes place.
        The OCTETS are interpreted bit-by-bit, with each bit corresponding to an input. 
        Bit 0 corresponds to the LSB.
        OCTET 1: unused
        OCTET 2: Bit 0-7 : inputs 16 - 23
        OCTET 3: Bit 0-7 : inputs  8 - 15
        OCTET 4: Bit 0-7 : inputs  0 - 7"
    ::= { wtWebioEA24oemBinaryEntry 3 }

wtWebioEA24oemBinaryTcpServerApplicationMode OBJECT-TYPE
    SYNTAX OCTET STRING (SIZE (4))
    ACCESS read-write
    STATUS mandatory
    DESCRIPTION
        "Selection of the application mode:
        The OCTETS are interpreted bit-by-bit,
        Bit 0 corresponds to the LSB.
        OCTET 1: unused
        OCTET 2: unused
        OCTET 3: unused
        OCTET 4: Bit 4-7: unused
        	 Bit 3  : OPC Device
        	 Bit 2  : Box2Box Slave
        	 Bit 1  : Compatible 50xxx
        	 Bit 0  : Default"
    ::= { wtWebioEA24oemBinaryEntry 4 }
    
wtWebioEA24oemBinaryTcpClientLocalPort OBJECT-TYPE
    SYNTAX INTEGER (1..65535)
    ACCESS read-write
    STATUS mandatory
    DESCRIPTION
        "Local TCP port for data exchange in this client mode.
        This port number must be unique within the device.
	Reserved port number must not be used (refere to the manual)."
    ::= { wtWebioEA24oemBinaryEntry 5 }

wtWebioEA24oemBinaryTcpClientServerPort OBJECT-TYPE
    SYNTAX INTEGER (1..65535)
    ACCESS read-write
    STATUS mandatory
    DESCRIPTION
        "Port number of the server. A complete set of port number, IP address
        and a valid input/output mask starts this mode.
        No data exchange take place when setting the server port to zero."
    ::= { wtWebioEA24oemBinaryEntry 6 }

wtWebioEA24oemBinaryTcpClientServerIpAddr OBJECT-TYPE
    SYNTAX OCTET STRING
    ACCESS read-write
    STATUS mandatory
    DESCRIPTION
        "Ip address of the server. A complete set of port number, IP address
        and a valid input/output mask starts this mode.
        No data exchange take place when setting the server IP address to 0.0.0.0."
    ::= { wtWebioEA24oemBinaryEntry 7 }

wtWebioEA24oemBinaryTcpClientServerPassword OBJECT-TYPE
    SYNTAX OCTET STRING
    ACCESS read-write
    STATUS mandatory
    DESCRIPTION
        "Building a connection may be protected by the 
        administrator password of the server. Enter the server password
        to establish the connection, if a server administrator password
        exists."
    ::= { wtWebioEA24oemBinaryEntry 8 }

wtWebioEA24oemBinaryTcpClientInactivity OBJECT-TYPE
    SYNTAX INTEGER 
    ACCESS read-write
    STATUS mandatory
    DESCRIPTION
        "Connection timeout in 100ms. If no data are exchanged within the specified  
        time, the device closes the connection to the server.
        The value 0 deactivates the timer. Using the Box2Box mode this function is
        disabled."
    ::= { wtWebioEA24oemBinaryEntry 9 }
    
wtWebioEA24oemBinaryTcpClientInputTrigger OBJECT-TYPE
    SYNTAX OCTET STRING (SIZE (4))
    ACCESS read-write
    STATUS mandatory
    DESCRIPTION
        "Every change on the inputs causes their state to be transmitted to the 
        remote device. To minimize data traffic, individual inputs may be exempted 
        from this rule. Nevertheless every transmission will contain all input bits.
        If a bit is set (1), a change of state on the corresponding input 
        triggers a transmission. If the bit is not set (0), no transmission 
        takes place.
        The OCTETS are interpreted bit-by-bit, with each bit corresponding to an input. 
        Bit 0 corresponds to the LSB.
        OCTET 1: unused
        OCTET 2: Bit 0-7 : inputs 16 - 23
        OCTET 3: Bit 0-7 : inputs  8 - 15
        OCTET 4: Bit 0-7 : inputs  0 - 7"
    ::= { wtWebioEA24oemBinaryEntry 10 }
 
wtWebioEA24oemBinaryTcpClientInterval OBJECT-TYPE
    SYNTAX INTEGER (0..65535)
    ACCESS read-write
    STATUS mandatory
    DESCRIPTION
        "Configurable interval with a 100ms base, in which the Webio device sends
        data to the configured application. A interval of zero stopps the 
        periodical sending."
    ::= { wtWebioEA24oemBinaryEntry 11 }

wtWebioEA24oemBinaryTcpClientApplicationMode OBJECT-TYPE
    SYNTAX OCTET STRING (SIZE (4))
    ACCESS read-write
    STATUS mandatory
    DESCRIPTION
        "Selection of the application mode:
        The OCTETS are interpreted bit-by-bit,
        Bit 0 corresponds to the LSB.
        OCTET 1: unused
        OCTET 2: unused
        OCTET 3: unused
        OCTET 4: Bit 3-7: unused
        	 Bit 2  : Box2Box Slave
        	 Bit 1  : Compatible 50xxx
        	 Bit 0  : Default"
    ::= { wtWebioEA24oemBinaryEntry 12 }

wtWebioEA24oemBinaryUdpPeerLocalPort OBJECT-TYPE
    SYNTAX INTEGER (1..65535)
    ACCESS read-write
    STATUS mandatory
    DESCRIPTION
        "Local UDP port for data exchange in this peer to peer mode.
        This port number must be unique within the device.
	Reserved port number must not be used (refere to the manual)."
    ::= { wtWebioEA24oemBinaryEntry 13 }

wtWebioEA24oemBinaryUdpPeerRemotePort OBJECT-TYPE
    SYNTAX INTEGER (1..65535)
    ACCESS read-write
    STATUS mandatory
    DESCRIPTION
        "Port number of the remote device. A complete set of port number, IP address
        and a valid input/output mask starts this mode.
        No data exchange take place when setting the remote port to zero."
    ::= { wtWebioEA24oemBinaryEntry 14 }

wtWebioEA24oemBinaryUdpPeerRemoteIpAddr OBJECT-TYPE
    SYNTAX OCTET STRING
    ACCESS read-write
    STATUS mandatory
    DESCRIPTION
        "Ip address of the remote device. A complete set of port number, IP address
        and a valid input/output mask starts this mode.
        No data exchange take place when setting the remote device IP address to 0.0.0.0."
    ::= { wtWebioEA24oemBinaryEntry 15 }

wtWebioEA24oemBinaryUdpPeerInputTrigger OBJECT-TYPE
    SYNTAX OCTET STRING (SIZE (4))
    ACCESS read-write
    STATUS mandatory
    DESCRIPTION
        "Every change on the inputs causes their state to be transmitted to the 
        remote device. To minimize data traffic, individual inputs may be exempted 
        from this rule. Nevertheless every transmission will contain all input bits.
        If a bit is set (1), a change of state on the corresponding input 
        triggers a transmission. If the bit is not set (0), no transmission 
        takes place.
        The OCTETS are interpreted bit-by-bit, with each bit corresponding to an input. 
        Bit 0 corresponds to the LSB.
        OCTET 1: unused
        OCTET 2: Bit 0-7 : inputs 16 - 23
        OCTET 3: Bit 0-7 : inputs  8 - 15
        OCTET 4: Bit 0-7 : inputs  0 - 7"
    ::= { wtWebioEA24oemBinaryEntry 16 }

wtWebioEA24oemBinaryUdpPeerInterval OBJECT-TYPE
    SYNTAX INTEGER (0..65535)
    ACCESS read-write
    STATUS mandatory
    DESCRIPTION
        "Configurable interval with a 100ms base, in which the Webio device sends
        data to the configured remote device. A interval of zero stopps the 
        periodical sending."
    ::= { wtWebioEA24oemBinaryEntry 17 }

wtWebioEA24oemBinaryUdpPeerApplicationMode OBJECT-TYPE
    SYNTAX OCTET STRING (SIZE (4))
    ACCESS read-write
    STATUS mandatory
    DESCRIPTION
        "Selection of the application mode:
        The OCTETS are interpreted bit-by-bit,
        Bit 0 corresponds to the LSB.
        OCTET 1: unused
        OCTET 2: unused
        OCTET 3: unused
        OCTET 4: Bit 3-7: unused
        	 Bit 2  : Box2Box Slave
        	 Bit 1  : Compatible 50xxx
        	 Bit 0  : Default"
    ::= { wtWebioEA24oemBinaryEntry 18 }

wtWebioEA24oemBinaryConnectedPort OBJECT-TYPE
    SYNTAX INTEGER (1..65535)
    ACCESS read-only
    STATUS mandatory
    DESCRIPTION
        "Port number of the remote device, after connection has been established.
        In case of no connection or missing port informations a zero will be read."
    ::= { wtWebioEA24oemBinaryEntry 19 }

wtWebioEA24oemBinaryConnectedIpAddr OBJECT-TYPE
    SYNTAX IpAddress
    ACCESS read-only
    STATUS mandatory
    DESCRIPTION
        "IP address of the remote device, after connection has been established.
        In case of no connection or missing port informations 0.0.0.0 will be read."
    ::= { wtWebioEA24oemBinaryEntry 20 }
    
wtWebioEA24oemBinaryTcpServerClientHttpPort OBJECT-TYPE
    SYNTAX INTEGER (1..65535)
    ACCESS read-write
    STATUS mandatory
    DESCRIPTION
        "HTTP port number of the remote device at TCP Server Mode. If an mailfunction occurs 
        status informations will be send to this port. 
        Not used at mode Compatible 50xxx."
    ::= { wtWebioEA24oemBinaryEntry 21 }
    
wtWebioEA24oemBinaryTcpClientServerHttpPort OBJECT-TYPE
    SYNTAX INTEGER (1..65535)
    ACCESS read-write
    STATUS mandatory
    DESCRIPTION
        "HTTP port number of the remote device at TCP Client Mode. In the operating mode
        Box2Box connection status informations will be exchanged through this port."
    ::= { wtWebioEA24oemBinaryEntry 22 }        
    
--  wtWebioEA24oemSyslog Group
--------------------------------
    
wtWebioEA24oemSyslogServerIP OBJECT-TYPE
    SYNTAX OCTET STRING 
    ACCESS read-write
    STATUS mandatory
    DESCRIPTION
        "Name or IP address of the Syslog server, which accepts the Syslog messgaes."
    ::= { wtWebioEA24oemSyslog 1 }
    
wtWebioEA24oemSyslogServerPort OBJECT-TYPE
    SYNTAX INTEGER
    ACCESS read-write
    STATUS mandatory
    DESCRIPTION
        "Portnumber of the Syslog servers, default 514."
    ::= { wtWebioEA24oemSyslog 2 }

wtWebioEA24oemSyslogSystemMessagesEnable OBJECT-TYPE
    SYNTAX OCTET STRING (SIZE(4))
    ACCESS read-write
    STATUS mandatory
    DESCRIPTION
        "Binary coded trigger conditions:
        Octet 1: unused
        Octet 2: unused
        Octet 3: unused
        Octet 4:
	        Bit 0:   ColdStart
	        Bit 1:   WarmStart
	        Bit 2:   Diag Messages
	        Bit 3-7: unused"
    ::= { wtWebioEA24oemSyslog 3 }    

wtWebioEA24oemSyslogEnable OBJECT-TYPE
    SYNTAX OCTET STRING 
    ACCESS read-write
    STATUS mandatory
    DESCRIPTION
        "Set bit 0to enable Syslog:
        Octet 1: unused
        Octet 2: unused
        Octet 3: unused
        Octet 4:
        	Bit 1-7: unused
                Bit 0  : Syslog enable"
    ::= { wtWebioEA24oemSyslog 4 }    

--  wtWebioEA24oemFTP Group
--------------------------------

wtWebioEA24oemFTPServerIP OBJECT-TYPE
    SYNTAX OCTET STRING 
    ACCESS read-write
    STATUS mandatory
    DESCRIPTION
        "Name or IP address of the FTP server, which accepts the FTP messages."
    ::= { wtWebioEA24oemFTP 1 }
    
wtWebioEA24oemFTPServerControlPort OBJECT-TYPE
    SYNTAX INTEGER
    ACCESS read-write
    STATUS mandatory
    DESCRIPTION
        "Portnumber of the control port of the FTP server, default 21."
    ::= { wtWebioEA24oemFTP 2 }
    
wtWebioEA24oemFTPUserName OBJECT-TYPE
    SYNTAX OCTET STRING 
    ACCESS read-write
    STATUS mandatory
    DESCRIPTION
        "FTP Loggin: user name."
    ::= { wtWebioEA24oemFTP 3 }
    
wtWebioEA24oemFTPPassword OBJECT-TYPE
    SYNTAX OCTET STRING 
    ACCESS read-write
    STATUS mandatory
    DESCRIPTION
        "FTP Loggin: user password."
    ::= { wtWebioEA24oemFTP 4 }

wtWebioEA24oemFTPAccount OBJECT-TYPE
    SYNTAX OCTET STRING 
    ACCESS read-write
    STATUS mandatory
    DESCRIPTION
        "FTP Loggin: name of account."
    ::= { wtWebioEA24oemFTP 5 }

wtWebioEA24oemFTPOption OBJECT-TYPE
    SYNTAX OCTET STRING 
    ACCESS read-write
    STATUS mandatory
    DESCRIPTION
        "Bit 0 switches the FTP Server in Passiv-Mode,
        the Client controls the data connection on its own:
        Octet 1: unused
        Octet 2: unused
        Octet 3: unused
        Octet 4:
        	Bit 1-7: unused
                Bit 0  : PASV enable"
    ::= { wtWebioEA24oemFTP 6 }
    
wtWebioEA24oemFTPEnable OBJECT-TYPE
    SYNTAX OCTET STRING 
    ACCESS read-write
    STATUS mandatory
    DESCRIPTION
        "Set Bit 0 to enable FTP:
        Octet 1: unused
        Octet 2: unused
        Octet 3: unused
        Octet 4:
        	Bit 1-7: unused
                Bit 0  : FTP enable"
    ::= { wtWebioEA24oemFTP 7 }  
    
--  wtWebioEA24oemOutputMode Group
--------------------------------

-- OutputMode Table

wtWebioEA24oemOutputModeTable OBJECT-TYPE
    SYNTAX SEQUENCE OF WtWebioEA24oemOutputModeEntry
    ACCESS not-accessible
    STATUS mandatory
    DESCRIPTION
        "Table of output mode configurations dependent on the output indices."
    ::= { wtWebioEA24oemOutputMode 1 }

wtWebioEA24oemOutputModeEntry OBJECT-TYPE
    SYNTAX WtWebioEA24oemOutputModeEntry
    ACCESS not-accessible
    STATUS mandatory
    DESCRIPTION
        "Output mode configurations of the individual outputs."
    INDEX  { wtWebioEA24oemOutputNo }
    ::= { wtWebioEA24oemOutputModeTable 1 }

WtWebioEA24oemOutputModeEntry ::= SEQUENCE {
    wtWebioEA24oemOutputModeBit	OCTET STRING
}

wtWebioEA24oemOutputModeBit OBJECT-TYPE
    SYNTAX OCTET STRING (SIZE (4))
    ACCESS read-write
    STATUS mandatory
    DESCRIPTION
        "This binary coded output mode defines the individual operation mode for any
        output. More than one mode must not be selected.
        The OCTETS are interpreted bit-by-bit,
        Bit 0 corresponds to the LSB.
        OCTET 1: unused
        OCTET 2: unused
        OCTET 3: unused
        OCTET 4: Bit 6-7: unused
        	 Bit 5  : Logic
        	 Bit 4  : Binary 2
        	 Bit 3  : Binary 1
        	 Bit 2  : SNMP
        	 Bit 1  : UDP ASCII
        	 Bit 0  : HTTP"
    ::= { wtWebioEA24oemOutputModeEntry 1 }
    
wtWebioEA24oemSafetyTimeout OBJECT-TYPE
    SYNTAX INTEGER (0..65535)
    ACCESS read-write
    STATUS mandatory
    DESCRIPTION
        "After this period of time (multiple of 100ms) without receiving data
        outputs switch to their Safety States. For each output a independend safety state
        could be defined."
    ::= { wtWebioEA24oemOutputMode 2 }
    
wtWebioEA24oemLoadControlEnable OBJECT-TYPE
    SYNTAX OCTET STRING 
    ACCESS read-write
    STATUS mandatory
    DESCRIPTION
        "Here the function of automatic load control can be enabled. All output were tested in 
        pairs (0-1, 2-3, 4-5, 6-7, 8-9, 10-11). If an error occours at one output,
        both output of an pair will be switched of. For a properly function of the load control
        each output of a pair have to has a load. If there is no existing load, a pull down resistor
        can be used.
        Outputs with no load are automaticly detected and not part of the control function.
        The OCTETS are interpreted bit-by-bit, with each bit corresponding to an output. 
        Bit 0 corresponds to the LSB.
        Octet 1: unused
        Octet 2: unused
        Octet 3: unused
        Octet 4:
        	Bit 1-7: unused
                Bit 0  : Load Control enable"
    ::= { wtWebioEA24oemOutputMode 3 }

-- wtWebioEA24oemAlarm Group
----------------------------

wtWebioEA24oemAlarmCount OBJECT-TYPE
    SYNTAX INTEGER (1..12)
    ACCESS read-only
    STATUS mandatory
    DESCRIPTION
        "Number of independent alarms."
    ::= { wtWebioEA24oemAlarm 1 }
    
-- Alarm Interface Table

wtWebioEA24oemAlarmIfTable OBJECT-TYPE
    SYNTAX SEQUENCE OF WtWebioEA24oemAlarmIfEntry
    ACCESS not-accessible
    STATUS mandatory
    DESCRIPTION
        "List of alarm indices."
    ::= { wtWebioEA24oemAlarm 2 }

wtWebioEA24oemAlarmIfEntry OBJECT-TYPE
    SYNTAX WtWebioEA24oemAlarmIfEntry
    ACCESS not-accessible
    STATUS mandatory
    DESCRIPTION
        "Numbers of the alarms."
    INDEX  { wtWebioEA24oemAlarmNo }
    ::= { wtWebioEA24oemAlarmIfTable 1 }

WtWebioEA24oemAlarmIfEntry ::= SEQUENCE {
    wtWebioEA24oemAlarmNo INTEGER
}

wtWebioEA24oemAlarmNo OBJECT-TYPE
    SYNTAX INTEGER (1..12)
    ACCESS read-only
    STATUS mandatory
    DESCRIPTION
        "Numbers of the alarms."
    ::= { wtWebioEA24oemAlarmIfEntry 1 }

-- Alarm Table

wtWebioEA24oemAlarmTable OBJECT-TYPE
    SYNTAX SEQUENCE OF WtWebioEA24oemAlarmEntry
    ACCESS not-accessible
    STATUS mandatory
    DESCRIPTION
        "List of settings depending on the alarm number."
    ::= { wtWebioEA24oemAlarm 3 }

wtWebioEA24oemAlarmEntry OBJECT-TYPE
    SYNTAX WtWebioEA24oemAlarmEntry
    ACCESS not-accessible
    STATUS mandatory
    DESCRIPTION
        "Alarm parameters of the individual alarms."
    INDEX  { wtWebioEA24oemAlarmNo }
    ::= { wtWebioEA24oemAlarmTable 1 }

WtWebioEA24oemAlarmEntry ::= SEQUENCE {
    wtWebioEA24oemAlarmInputTrigger	OCTET STRING,
    wtWebioEA24oemAlarmOutputTrigger	OCTET STRING,
    wtWebioEA24oemAlarmSystemTrigger	OCTET STRING,
    wtWebioEA24oemAlarmMaxCounterValue	OCTET STRING,
    wtWebioEA24oemAlarmInterval		OCTET STRING,
    wtWebioEA24oemAlarmEnable		OCTET STRING,
    wtWebioEA24oemAlarmMailAddr		OCTET STRING,
    wtWebioEA24oemAlarmMailSubject	OCTET STRING,
    wtWebioEA24oemAlarmMailText		OCTET STRING,
    wtWebioEA24oemAlarmSnmpManagerIP	OCTET STRING,
    wtWebioEA24oemAlarmSnmpTrapText	OCTET STRING,
    wtWebioEA24oemAlarmUdpIpAddr	OCTET STRING,
    wtWebioEA24oemAlarmUdpPort		INTEGER,
    wtWebioEA24oemAlarmUdpText		OCTET STRING,
    wtWebioEA24oemAlarmTcpIpAddr	OCTET STRING,
    wtWebioEA24oemAlarmTcpPort		INTEGER,
    wtWebioEA24oemAlarmTcpText		OCTET STRING,    
    wtWebioEA24oemAlarmSyslogIpAddr	OCTET STRING,
    wtWebioEA24oemAlarmSyslogPort	INTEGER,
    wtWebioEA24oemAlarmSyslogText	OCTET STRING,
    wtWebioEA24oemAlarmFtpDataPort	OCTET STRING,
    wtWebioEA24oemAlarmFtpFileName	OCTET STRING,
    wtWebioEA24oemAlarmFtpText		OCTET STRING,
    wtWebioEA24oemAlarmFtpOption	OCTET STRING,
    wtWebioEA24oemAlarmTimerCron	OCTET STRING
       
}

wtWebioEA24oemAlarmInputTrigger OBJECT-TYPE
    SYNTAX OCTET STRING (SIZE(12))
    ACCESS read-write
    STATUS mandatory
    DESCRIPTION
        "This variable allows setting of individual input trigger conditions. 
        The OCTETS are interpreted bit-by-bit, with each bit corresponding to an input. 
        Bit 0 corresponds to the LSB.
	The first four OCTETS contain the mask which determines which of the inputs are to 
	be considered (corresponding bit = 1) and which inputs are to ignore 
	(corresponding bit = 0):
	OCTET 1 : unused
	OCTET 2: Bit 0-7: Mask for digital inputs 16-23
	OCTET 3, Bit 0-7: Mask for digital inputs 8-15
	OCTET 4, Bit 0-7: Mask for digital inputs 0-7
	
	OCTETS 5-8 contain the level (1=HIGH, 0=LOW) which the inputs 
	should assume:
	OCTET 5 : unused
	OCTET 6: Bit 0-7: Level of digital inputs 16-23
	OCTET 7, Bit 0-7: Level of digital inputs 8-15
        OCTET 8, Bit 0-7: Level of digital inputs 0-7
        
	OCTETS 9-12 contain the ANY bit (1=ON, 0=OFF). Inputs masked with the any bit trigger with any change 
	of the corresponding input bit. Settings in OCTET 5-9 are then unused:
	OCTET 9: unused
	OCTET 10, Bit 0-7: ANY bits of digital inputs 16-23
	OCTET 11, Bit 0-7: ANY bits of digital inputs 8-15
	OCTET 12, Bit 0-7: ANY bits of digital inputs 0-7"
        
    ::= { wtWebioEA24oemAlarmEntry 1 }

wtWebioEA24oemAlarmOutputTrigger OBJECT-TYPE
    SYNTAX OCTET STRING (SIZE(12))
    ACCESS read-write
    STATUS mandatory
    DESCRIPTION
        "This variable allows setting of individual output trigger conditions. 
        The OCTETS are interpreted bit-by-bit, with each bit corresponding to an output. 
        Bit 0 corresponds to the LSB.
	The first four OCTETS contain the mask which determines which of the outputs are to 
	be considered (corresponding bit = 1) and which outputs are to ignore 
	(corresponding bit = 0):
	OCTET 1 : unused
	OCTET 2: Bit 0-7: Mask for digital outputs 16-23
	OCTET 3, Bit 0-7: Mask for digital outputs 8-15
	OCTET 4, Bit 0-7: Mask for digital outputs 0-7
	
	OCTETS 5-8 contain the level (1=HIGH, 0=LOW) which the outputs 
	should assume:
	OCTET 5 : unused
	OCTET 6: Bit 0-7: Level of digital outputs 16-23
	OCTET 7, Bit 0-7: Level of digital outputs 8-15
        OCTET 8, Bit 0-7: Level of digital outputs 0-7

	OCTETS 9-12 contain the ANY bit (1=ON, 0=OFF). Outputs masked with the any bit trigger with any change 
	of the corresponding output bit. Settings in OCTET 5-9 are then unused:
	OCTET 9: unused
	OCTET 10, Bit 0-7: ANY bits of digital outputs 16-23
	OCTET 11, Bit 0-7: ANY bits of digital outputs 8-15
	OCTET 12, Bit 0-7: ANY bits of digital outputs 0-7"
        
    ::= { wtWebioEA24oemAlarmEntry 2 }
    
wtWebioEA24oemAlarmSystemTrigger OBJECT-TYPE
    SYNTAX OCTET STRING (SIZE(4))
    ACCESS read-write
    STATUS mandatory
    DESCRIPTION
        "Binary coded trigger conditions:
        The OCTETS are interpreted bit-by-bit.
        Bit 0 corresponds to the LSB.
        OCTET 1: unused
        OCTET 2: unused
        OCTET 3: unused
        OCTET 4, 
        	 Bit 4-7: unused
        	 Bit 3  : Warm Start
        	 Bit 2  : Cold Start
        	 Bit 1  : Timer
        	 Bit 0  : Load Control"
    ::= { wtWebioEA24oemAlarmEntry 3 }

wtWebioEA24oemAlarmMaxCounterValue OBJECT-TYPE
    SYNTAX OCTET STRING 
    ACCESS read-write
    STATUS mandatory
    DESCRIPTION
        "This variable configures a max. counter value. If an input counter value
        exceeds this max. value, the corresponding alarm is triggered. Input counters with
        its mask bit unset in wtWebioEA24oemAlarmInputTrigger are not considered."
    ::= { wtWebioEA24oemAlarmEntry 4 }

wtWebioEA24oemAlarmInterval OBJECT-TYPE
    SYNTAX OCTET STRING 
    ACCESS read-write
    STATUS mandatory
    DESCRIPTION
        "Send interval for alarm messages."
    ::= { wtWebioEA24oemAlarmEntry 5 }

wtWebioEA24oemAlarmEnable OBJECT-TYPE
    SYNTAX OCTET STRING (SIZE(4))
    ACCESS read-write
    STATUS mandatory
    DESCRIPTION
        "Binary coded alarm enable:
        Octet 1: unused
        Octet 2: unused
        Octet 3: unused
        Octet 4:
		Bit 0:	Mail Enable
        	Bit 1:	SNMP Trap enable
        	Bit 2:  UDP enable
        	Bit 3:  Send inputs to pending TCP connections
        	Bit 4-7: unused"
    ::= { wtWebioEA24oemAlarmEntry 6 }

wtWebioEA24oemAlarmMailAddr OBJECT-TYPE
    SYNTAX OCTET STRING 
    ACCESS read-write
    STATUS mandatory
    DESCRIPTION
        "E-Mail address for sending the alarm mail to."
    ::= { wtWebioEA24oemAlarmEntry 7 }

wtWebioEA24oemAlarmMailSubject OBJECT-TYPE
    SYNTAX OCTET STRING 
    ACCESS read-write
    STATUS mandatory
    DESCRIPTION
        "Subject line for alarm mail."
    ::= { wtWebioEA24oemAlarmEntry 8 }

wtWebioEA24oemAlarmMailText OBJECT-TYPE
    SYNTAX OCTET STRING 
    ACCESS read-write
    STATUS mandatory
    DESCRIPTION
        "Alarm mail text: 
        States of the Webio device can be included by using special tags.
        Please refer to the respective Webio manual"
    ::= { wtWebioEA24oemAlarmEntry 9 }

wtWebioEA24oemAlarmSnmpManagerIP OBJECT-TYPE
    SYNTAX OCTET STRING 
    ACCESS read-write
    STATUS mandatory
    DESCRIPTION
        "IP address of the SNMP Manager to which the Webio device should send SNMP traps."
    ::= { wtWebioEA24oemAlarmEntry 10 }

wtWebioEA24oemAlarmSnmpTrapText OBJECT-TYPE
    SYNTAX OCTET STRING 
    ACCESS read-write
    STATUS mandatory
    DESCRIPTION
        "This text appears in the trap body."
    ::= { wtWebioEA24oemAlarmEntry 11 }
    
wtWebioEA24oemAlarmUdpIpAddr OBJECT-TYPE
    SYNTAX OCTET STRING 
    ACCESS read-write
    STATUS mandatory
    DESCRIPTION
        "IP address of the UDP listener to which the Webio device should send UDP traps."
    ::= { wtWebioEA24oemAlarmEntry 12 }    

wtWebioEA24oemAlarmUdpPort OBJECT-TYPE
    SYNTAX INTEGER (1..65535) 
    ACCESS read-write
    STATUS mandatory
    DESCRIPTION
        "Port number of the UDP listener to which the Webio device should send UDP traps."
    ::= { wtWebioEA24oemAlarmEntry 13 }    

wtWebioEA24oemAlarmUdpText OBJECT-TYPE
    SYNTAX OCTET STRING 
    ACCESS read-write
    STATUS mandatory
    DESCRIPTION
        "This text appears in the UDP trap body."
    ::= { wtWebioEA24oemAlarmEntry 14 }
    
wtWebioEA24oemAlarmTcpIpAddr OBJECT-TYPE
    SYNTAX OCTET STRING 
    ACCESS read-write
    STATUS mandatory
    DESCRIPTION
        "IP address of the TCP listener to which the Webio device should send TCP traps."
    ::= { wtWebioEA24oemAlarmEntry 15 }    

wtWebioEA24oemAlarmTcpPort OBJECT-TYPE
    SYNTAX INTEGER (1..65535) 
    ACCESS read-write
    STATUS mandatory
    DESCRIPTION
        "Port number of the TCP listener to which the Webio device should send TCP traps."
    ::= { wtWebioEA24oemAlarmEntry 16 }    

wtWebioEA24oemAlarmTcpText OBJECT-TYPE
    SYNTAX OCTET STRING 
    ACCESS read-write
    STATUS mandatory
    DESCRIPTION
        "This text appears in the TCP trap body."
    ::= { wtWebioEA24oemAlarmEntry 17 }
    
wtWebioEA24oemAlarmSyslogIpAddr OBJECT-TYPE
    SYNTAX OCTET STRING 
    ACCESS read-write
    STATUS mandatory
    DESCRIPTION
        "IP address of the syslog server to which the Webio device should send syslog messages."
    ::= { wtWebioEA24oemAlarmEntry 18 }    

wtWebioEA24oemAlarmSyslogPort OBJECT-TYPE
    SYNTAX INTEGER (1..65535) 
    ACCESS read-write
    STATUS mandatory
    DESCRIPTION
        "Port number of the syslog server to which the Webio device should send syslog messages."
    ::= { wtWebioEA24oemAlarmEntry 19 }    

wtWebioEA24oemAlarmSyslogText OBJECT-TYPE
    SYNTAX OCTET STRING 
    ACCESS read-write
    STATUS mandatory
    DESCRIPTION
        "Every message starts with the priority key, a time stamp and the host ip address, according RFC3164.
        This text appears in the following syslog message body."
    ::= { wtWebioEA24oemAlarmEntry 20 }    
    
wtWebioEA24oemAlarmFtpDataPort OBJECT-TYPE
    SYNTAX OCTET STRING 
    ACCESS read-write
    STATUS mandatory
    DESCRIPTION
        "Local data port: 1..65535 or AUTO: the next free port will be assigned."
    ::= { wtWebioEA24oemAlarmEntry 21 }
    
wtWebioEA24oemAlarmFtpFileName OBJECT-TYPE
    SYNTAX OCTET STRING 
    ACCESS read-write
    STATUS mandatory
    DESCRIPTION
        "Name of the file including path informations."
    ::= { wtWebioEA24oemAlarmEntry 22 }
    
wtWebioEA24oemAlarmFtpText OBJECT-TYPE
    SYNTAX OCTET STRING 
    ACCESS read-write
    STATUS mandatory
    DESCRIPTION
        "Message text to store on the FTP server."
    ::= { wtWebioEA24oemAlarmEntry 23 }

wtWebioEA24oemAlarmFtpOption OBJECT-TYPE
    SYNTAX OCTET STRING (SIZE(4))
    ACCESS read-write
    STATUS mandatory
    DESCRIPTION
        "Binary coded options, select only one option at the same time:
        STORE  = replace file
        APPEND = append message at the end of the file
        
        Octet 1: unused
        Octet 2: unused
        Octet 3: unused
        Octet 4:
		Bit 0  :	STORE
		Bit 1  :	APPEND
        	Bit 2-7:	unused"
    ::= { wtWebioEA24oemAlarmEntry 24 }      
    
wtWebioEA24oemAlarmTimerCron OBJECT-TYPE
    SYNTAX OCTET STRING
    ACCESS read-write
    STATUS mandatory
    DESCRIPTION
        "This entry contains 5 space or tab seperated text fields for time trigger definition.
        Each field must match with the actual time to trigger a message, weekday and day of month
        are interpreted separatley.
        1: Minutes	Range 0-59
        2. Hours	Range 0-23, 0 is midnight
        3: Day of month	Range 1-31
        4: Month	Range 1-12
        5: Weekday	Range 0-6, 0 is sunday
        
        Syntax for every field:
         - an asterix (*) enables every possible setting of a field
         - single numbers seperated by commas
         - a partition within the allowed range (1-5)
         - step size within an partition of the allowed range (0-59/2: every second minute)."
    ::= { wtWebioEA24oemAlarmEntry 25 }      

-- wtWebioEA24oemLoadControl
----------------------------

wtWebioEA24oemLoadControlView OBJECT-TYPE
    SYNTAX OCTET STRING (SIZE(4))
    ACCESS read-only
    STATUS mandatory
    DESCRIPTION
        "Here the result of automatic load control can be read. All output were tested in 
        pairs (0-1, 2-3, 4-5, 6-7, 8-9, 10-11). If an error occours at one output,
        both output of an pair will be switched of. For a properly function of the load control
        each output of a pair have to has a load. If there is no existing load, a pull down resistor
        can be used.
        Outputs with no load are automaticly detected and not part of the control function.
        The OCTETS are interpreted bit-by-bit, with each bit corresponding to an output. 
        Bit 0 corresponds to the LSB.
        Octet 1: unused
        OCTET 2: Bit 0-7 : outputs 16 - 23
        OCTET 3: Bit 0-7 : outputs  8 - 15
        OCTET 4: Bit 0-7 : outputs  0 - 7"
    ::= { wtWebioEA24oemAlarm 4 }

wtWebioEA24oemLCShutDownView OBJECT-TYPE
    SYNTAX OCTET STRING (SIZE(4))
    ACCESS read-write
    STATUS mandatory
    DESCRIPTION
        "Here the result of the automatic load control shut down can be read. All outputs remain switched of,
        until a zero is written into this variable. But previously all loads should be inspected.
        High current (short circuit), a broken supply line or a defect load (i.e. lamp) may be a shut down reason.
        If no load is detected, the load control unit suspend automaticly the control of the corresponding output pair.
        All controlled output could be identified reading the variable wtWebioEA24oemLoadControlEnable.
        The OCTETS are interpreted bit-by-bit, with each bit corresponding to an output.
        Bit 0 corresponds to the LSB.
        
        Octet 1: unused
        OCTET 2: Bit 0-7 : outputs 16 - 23
        OCTET 3: Bit 0-7 : outputs  8 - 15
        OCTET 4: Bit 0-7 : outputs  0 - 7"
    ::= { wtWebioEA24oemAlarm 5 }


-- wtWebioEA24oemPorts Group
----------------------------

-- Input Port Table

wtWebioEA24oemInputPortTable OBJECT-TYPE
    SYNTAX SEQUENCE OF WtWebioEA24oemInputPortEntry
    ACCESS not-accessible
    STATUS mandatory
    DESCRIPTION
        "List of settings depending on the input number."
    ::= { wtWebioEA24oemPorts 1 }

wtWebioEA24oemInputPortEntry OBJECT-TYPE
    SYNTAX WtWebioEA24oemInputPortEntry
    ACCESS not-accessible
    STATUS mandatory
    DESCRIPTION
        "Input parameter for the individual inputs."
    INDEX  { wtWebioEA24oemInputNo }
    ::= { wtWebioEA24oemInputPortTable 1 }

WtWebioEA24oemInputPortEntry ::= SEQUENCE {
    wtWebioEA24oemPortInputName		OCTET STRING,
    wtWebioEA24oemPortInputText		OCTET STRING,
    wtWebioEA24oemPortInputMode		OCTET STRING,
    wtWebioEA24oemPortInputFilter	INTEGER
}

wtWebioEA24oemPortInputName OBJECT-TYPE
    SYNTAX OCTET STRING 
    ACCESS read-write
    STATUS mandatory
    DESCRIPTION
        "Name of the input."
    ::= { wtWebioEA24oemInputPortEntry 1 }

wtWebioEA24oemPortInputText OBJECT-TYPE
    SYNTAX OCTET STRING 
    ACCESS read-write
    STATUS mandatory
    DESCRIPTION
        "Description of the input."
    ::= { wtWebioEA24oemInputPortEntry 2 }

wtWebioEA24oemPortInputMode OBJECT-TYPE
    SYNTAX OCTET STRING (SIZE(4))
    ACCESS read-write
    STATUS mandatory
    DESCRIPTION
        "Binary coded modes:
        Selecting short pulse detection enable by setting the corresponding bit to 1 enables 
        interrupt support for counting. Only positive edges are accepted as trigger 
        source. The maximum counting frequenz equals 2000 Hz.
        This mode is available for inputs 0-3 only.
        Selecting counter clear on read by setting the corresponding bit to 1 enables
        the corresponding counter to be cleared automatically every time it is read,
        except HTTP reading with user rights.
        The OCTETS are interpreted bit-by-bit, with each set of octets corresponding to an input. 
        Bit 0 corresponds to the LSB.
        Selection for input 0-3:
        OCTET 1: unused
        OCTET 2: unused
        OCTET 3: unused
        OCTET 4, Bit 2-7: unused
        	 Bit 2  : Counter clear on read
        	 Bit 1  : Change detection enable (default)
        	 Bit 0  : Short Pulse detection enable
        	 
	Selection for inputs 4-11:
	OCTET 1: unused
	OCTET 2: unused
	OCTET 3: unused
	OCTET 4, Bit 2-7: unused
		 Bit 1  : Counter clear on read
		 Bit 0  : Change detection enable (default)"
    ::= { wtWebioEA24oemInputPortEntry 3 }
   
wtWebioEA24oemPortInputFilter OBJECT-TYPE
    SYNTAX INTEGER 
    ACCESS read-write
    STATUS mandatory
    DESCRIPTION
        "Pulses with a duration shorter than here specified (duration in 1/1000 sec),
	are ignored."
    ::= { wtWebioEA24oemInputPortEntry 4 }
        
-- Output Port Table

wtWebioEA24oemOutputPortTable OBJECT-TYPE
    SYNTAX SEQUENCE OF WtWebioEA24oemOutputPortEntry
    ACCESS not-accessible
    STATUS mandatory
    DESCRIPTION
        "List of settings depending on the output number."
    ::= { wtWebioEA24oemPorts 2 }

wtWebioEA24oemOutputPortEntry OBJECT-TYPE
    SYNTAX WtWebioEA24oemOutputPortEntry
    ACCESS not-accessible
    STATUS mandatory
    DESCRIPTION
        "Output parameters of the individual outputs."
    INDEX  { wtWebioEA24oemOutputNo }
    ::= { wtWebioEA24oemOutputPortTable 1 }

WtWebioEA24oemOutputPortEntry ::= SEQUENCE {
    wtWebioEA24oemPortOutputName		OCTET STRING,
    wtWebioEA24oemPortOutputText		OCTET STRING,
    wtWebioEA24oemPortOutputGroupMode		OCTET STRING,
    wtWebioEA24oemPortOutputSafetyState		OCTET STRING,
    wtWebioEA24oemPortLogicInputMask		OCTET STRING,
    wtWebioEA24oemPortLogicInputInverter	OCTET STRING,
    wtWebioEA24oemPortLogicFunction		OCTET STRING,
    wtWebioEA24oemPortLogicOutputInverter	OCTET STRING,
    wtWebioEA24oemPortPulseDuration		INTEGER,
    wtWebioEA24oemPortPulsePolarity		OCTET STRING
    
}

wtWebioEA24oemPortOutputName OBJECT-TYPE
    SYNTAX OCTET STRING 
    ACCESS read-write
    STATUS mandatory
    DESCRIPTION
        "Name of the output."
    ::= { wtWebioEA24oemOutputPortEntry 1 }

wtWebioEA24oemPortOutputText OBJECT-TYPE
    SYNTAX OCTET STRING 
    ACCESS read-write
    STATUS mandatory
    DESCRIPTION
        "Description of the output."
    ::= { wtWebioEA24oemOutputPortEntry 2 }

wtWebioEA24oemPortOutputGroupMode OBJECT-TYPE
    SYNTAX OCTET STRING 
    ACCESS read-write
    STATUS mandatory
    DESCRIPTION
        "It is possible to connect outputs together to increase the output current.
        This could be done by connecting 2 or 4 outputs in a group together. All bits
        of such a group has to be set all together in the same way. This variable
        configures this group scheme. If one output bit of a group is set, all other 
        output bits of the same group will be set in the same manner.
        More than one configuration must not be selected.
	Selection for outputs 0-3:
        Octet 1: unused
        Octet 2: unused
        Octet 3: unused
        OCTET 4: Bit 0   : outputs 0,1,2,3 disconnected (default)
        	 Bit 1   : outputs 0+1, 2+3 connected
        	 Bit 2   : outputs 0+1+2+3 connected
        	 Bit 3-7 : unused
	Selection for outputs 4-7:
        Octet 1: unused
        Octet 2: unused
        Octet 3: unused
        OCTET 4: Bit 0   : outputs 4, 5, 6, 7 disconnected (default)
        	 Bit 1   : outputs 4+5, 6+7 connected
        	 Bit 2   : outputs 4+5+6+7 connected
        	 Bit 3-7 : unused        	 
	Selection for outputs 8-11:
        Octet 1: unused
        Octet 2: unused
        Octet 3: unused
        OCTET 4: Bit 0   : outputs 8, 9, 10, 11 disconnected (default)
        	 Bit 1   : outputs 8+9, 10+11 connected
        	 Bit 2   : outputs 8+9+10+11 connected
        	 Bit 3-7 : unused

	Selection for outputs 12-15:
	OCTET 1: unused
	OCTET 2: unused
	OCTET 3: unused
	OCTET 4: Bit 0   : outputs 12,13,14,15 disconnected (default)
		 Bit 1   : outputs 12+13,14+15 connected
		 Bit 2   : outputs 12+13+14+15 connected
	 	 Bit 3-7 : unused

	Selection for outputs 16-19:
        OCTET 1: unused
        OCTET 2: unused
        OCTET 3: unused
        OCTET 4: Bit 0   : outputs 16,17,18,19 disconnected (default)
        	 Bit 1   : outputs 16+17,18+19 connected
        	 Bit 2   : outputs 16+17+18+19 connected
        	 Bit 3-7 : unused
        	 
	Selection for outputs 20-23:
        OCTET 1: unused
        OCTET 2: unused
        OCTET 3: unused
        OCTET 4: Bit 0   : outputs 20,21,22,23 disconnected (default)
        	 Bit 1   : outputs 20+21,22+23 connected
        	 Bit 2   : outputs 20+21+22+23 connected
        	 Bit 3-7 : unused"
        	 
    ::= { wtWebioEA24oemOutputPortEntry 3 }

wtWebioEA24oemPortOutputSafetyState OBJECT-TYPE
    SYNTAX OCTET STRING 
    ACCESS read-write
    STATUS mandatory
    DESCRIPTION
        "This variable allows setting of individual digital outputs. The OCTETS are 
        interpreted bit-by-bit, with each bit corresponding to an output. Bit 0 corresponds 
        to the LSB.
        The first four OCTETS contain the mask which determines which of the outputs are to 
        be set (corresponding bit = 1) and which outputs are to remain unchanged 
        (corresponding bit = 0):
        OCTET 1		: unused
        OCTET 2		: unused
        OCTET 3		: unused
        OCTET 4, Bit 1-7: unused
        	 Bit 0	: Mask for digital output
        OCTETS 5-8 contain the level (1=HIGH, 0=LOW) which the outputs to be changed 
        should assume:
        OCTET 5		: unused
        OCTET 6		: unused
        OCTET 7		: unused
        OCTET 8, Bit 1-7: unused
        	 Bit 0  : Level of digital output"
    ::= { wtWebioEA24oemOutputPortEntry 4 }

wtWebioEA24oemPortLogicInputMask OBJECT-TYPE
    SYNTAX OCTET STRING (SIZE (4))
    ACCESS read-write
    STATUS mandatory
    DESCRIPTION
        "Selecting one of these inputs by setting the corresponding bit to 1 
        enables the logic function for the output identified by the index within 
        this table. The calculation take place in 4 steps:
        1. Selecting inputs			(wtWebioEA24oemPortLogicInputMask)
        2. Inverting inputs if necessary	(wtWebioEA24oemPortLogicInputInverter)
        3. Logical combination			(wtWebioEA24oemPortLogicFunction)
        4. Inverting the result if necessary	(wtWebioEA24oemPortLogicOutputInverter)
        OCTET 1: unused
        OCTET 2: Bit 0-7 : inputs 16 - 23
        OCTET 3: Bit 0-7 : inputs  8 - 15
        OCTET 4: Bit 0-7 : inputs  0 - 7"
    ::= { wtWebioEA24oemOutputPortEntry 5 }

wtWebioEA24oemPortLogicInputInverter OBJECT-TYPE
    SYNTAX OCTET STRING (SIZE (4))
    ACCESS read-write
    STATUS mandatory
    DESCRIPTION
        "Every input bit selected here will be inverted.
        OCTET 1: unused
        OCTET 2: Bit 0-7 : inputs 16 - 23
        OCTET 3: Bit 0-7 : inputs  8 - 15
        OCTET 4: Bit 0-7 : inputs  0 - 7"
    ::= { wtWebioEA24oemOutputPortEntry 6 }

wtWebioEA24oemPortLogicFunction OBJECT-TYPE
    SYNTAX OCTET STRING (SIZE (4))
    ACCESS read-write
    STATUS mandatory
    DESCRIPTION
        "This determines the logic function. No more than one function
        may be selected.
        OCTET 1: unused
        OCTET 2: unused
        OCTET 3: unused
        OCTET 4: 
        	 Bit 0   : logic function OR (default)
        	 Bit 1   : logic function AND
        	 Bit 2-7 : unused"
    ::= { wtWebioEA24oemOutputPortEntry 7 }

wtWebioEA24oemPortLogicOutputInverter OBJECT-TYPE
    SYNTAX OCTET STRING (SIZE (4))
    ACCESS read-write
    STATUS mandatory
    DESCRIPTION
        "The logical operation result could be inverteted by setting the corresponding
        bit to 1.
        OCTET 1: unused
        OCTET 2: unused
        OCTET 3: unused
        	OCTET 4: 
        	 Bit 0   : Output Inverter enable
        	 Bit 1-7 : unused"
    ::= { wtWebioEA24oemOutputPortEntry 8 }

wtWebioEA24oemPortPulseDuration OBJECT-TYPE
    SYNTAX INTEGER
    ACCESS read-write
    STATUS mandatory
    DESCRIPTION
        "Pulse length in 1/1000 sec. Setting this value to zero, disables the pulse output."
    ::= { wtWebioEA24oemOutputPortEntry 9 }

wtWebioEA24oemPortPulsePolarity OBJECT-TYPE
    SYNTAX OCTET STRING (SIZE (4))
    ACCESS read-write
    STATUS mandatory
    DESCRIPTION
        "This value defines the polarity of the output pulse, if wtWebioEA24oemPortPulseDuration is not set to zero.
        After the pulse is finished, the output switches back to the opposite state.
        OCTET 1: unused
        OCTET 2: unused
        OCTET 3: unused
        	OCTET 4: 
        	 Bit 0   : negative polarity
        	 Bit 1   : positive polarity
        	 Bit 2-7 : ungenutzt"
    ::= { wtWebioEA24oemOutputPortEntry 10 }


-- wtWebioEA24oemManufact Group
----------------------------

wtWebioEA24oemMfName OBJECT-TYPE
    SYNTAX OCTET STRING 
    ACCESS read-write
    STATUS mandatory
    DESCRIPTION
        "Manufacturer company name"
    ::= { wtWebioEA24oemManufact 1 }

wtWebioEA24oemMfAddr OBJECT-TYPE
    SYNTAX OCTET STRING 
    ACCESS read-write
    STATUS mandatory
    DESCRIPTION
        "Manufacturer address."
    ::= { wtWebioEA24oemManufact 2 }

wtWebioEA24oemMfHotline OBJECT-TYPE
    SYNTAX OCTET STRING 
    ACCESS read-write
    STATUS mandatory
    DESCRIPTION
        "Manufacturer hotline."
    ::= { wtWebioEA24oemManufact 3 }

wtWebioEA24oemMfInternet OBJECT-TYPE
    SYNTAX OCTET STRING 
    ACCESS read-write
    STATUS mandatory
    DESCRIPTION
        "Manufacturer Internet address."
    ::= { wtWebioEA24oemManufact 4 }

wtWebioEA24oemMfDeviceTyp OBJECT-TYPE
    SYNTAX OCTET STRING 
    ACCESS read-write
    STATUS mandatory
    DESCRIPTION
        "Manufacturer device name (model number)."
    ::= { wtWebioEA24oemManufact 5 }

-- wtWebioEA24oemDiag Group
----------------------------

wtWebioEA24oemDiagErrorCount OBJECT-TYPE
    SYNTAX INTEGER
    ACCESS read-only
    STATUS mandatory
    DESCRIPTION
        "Number of entries in the error memory."
    ::= { wtWebioEA24oemDiag 1 }

wtWebioEA24oemDiagBinaryError OBJECT-TYPE
    SYNTAX OCTET STRING 
    ACCESS read-only
    STATUS mandatory
    DESCRIPTION
        "Error causes coded bit-by-bit."
    ::= { wtWebioEA24oemDiag 2 }

wtWebioEA24oemDiagErrorIndex OBJECT-TYPE
    SYNTAX INTEGER
    ACCESS read-write
    STATUS mandatory
    DESCRIPTION
        "The value of this variable is used as an index to read 
        an error massege from wtWebioEA24oemDiagErrorMessage.
        Errors are numbered from 1 to wtWebioEA24oemDiagErrorCount.
        Writing a valid value into this variable, making the appropriate 
        message readable from wtWebioEA24oemDiagErrorMessage."
    ::= { wtWebioEA24oemDiag 3 }

wtWebioEA24oemDiagErrorMessage OBJECT-TYPE
    SYNTAX OCTET STRING 
    ACCESS read-only
    STATUS mandatory
    DESCRIPTION
        "Using wtWebioEA24oemDiagErrorIndex as an index, the appropriate message is available."
    ::= { wtWebioEA24oemDiag 4 }
    
wtWebioEA24oemDiagErrorClear OBJECT-TYPE
    SYNTAX INTEGER
    ACCESS write-only
    STATUS mandatory
    DESCRIPTION
        "Writing 1 into this variable clears all diagnosis messages."
    ::= { wtWebioEA24oemDiag 5 }

-- TRAP DEFINITIONS

-- Diese SNMP-Traps werden gesendet, wenn die Alarmtriggerbedingungen zutreffen 

wtWebioEA24oemAlert1 TRAP-TYPE
    ENTERPRISE  wtWebioEA24oem
    VARIABLES   { wtWebioEA24oemAlarmSnmpTrapText }
    DESCRIPTION
        "This SNMP trap is generated when Alarm 1 was triggered,
        SNMP trap enable is set and SNMP is enabled."
    -- NMS trap annotation
    --#TYPE "Webio Digital Alarm 1"
    --#SUMMARY "Alarm 1: %s"
    --#ARGUMENTS {0}
    --#SEVERITY INFORMATIONAL
    --#TIMEINDEX 99
    --#STATE OPERATIONAL    
    ::= 53

wtWebioEA24oemAlert2 TRAP-TYPE
    ENTERPRISE  wtWebioEA24oem
    VARIABLES   { wtWebioEA24oemAlarmSnmpTrapText }
    DESCRIPTION
        "This SNMP trap is generated when Alarm 2 was triggered,
        SNMP trap enable is set and SNMP is enabled."
    -- NMS trap annotation
    --#TYPE "Webio Digital Alarm 2"
    --#SUMMARY "Alarm 2: %s"
    --#ARGUMENTS {0}
    --#SEVERITY INFORMATIONAL
    --#TIMEINDEX 99
    --#STATE OPERATIONAL    
    ::= 54

wtWebioEA24oemAlert3 TRAP-TYPE
    ENTERPRISE  wtWebioEA24oem
    VARIABLES   { wtWebioEA24oemAlarmSnmpTrapText }
    DESCRIPTION
        "This SNMP trap is generated when Alarm 3 was triggered,
        SNMP trap enable is set and SNMP is enabled."
    -- NMS trap annotation
    --#TYPE "Webio Digital Alarm 3"
    --#SUMMARY "Alarm 3: %s"
    --#ARGUMENTS {0}
    --#SEVERITY INFORMATIONAL
    --#TIMEINDEX 99
    --#STATE OPERATIONAL    
    ::= 55

wtWebioEA24oemAlert4 TRAP-TYPE
    ENTERPRISE  wtWebioEA24oem
    VARIABLES   { wtWebioEA24oemAlarmSnmpTrapText }
    DESCRIPTION
        "This SNMP trap is generated when Alarm 4 was triggered,
        SNMP trap enable is set and SNMP is enabled."
    -- NMS trap annotation
    --#TYPE "Webio Digital Alarm 4"
    --#SUMMARY "Alarm 4: %s"
    --#ARGUMENTS {0}
    --#SEVERITY INFORMATIONAL
    --#TIMEINDEX 99
    --#STATE OPERATIONAL    
    ::= 56

wtWebioEA24oemAlert5 TRAP-TYPE
    ENTERPRISE  wtWebioEA24oem
    VARIABLES   { wtWebioEA24oemAlarmSnmpTrapText }
    DESCRIPTION
        "This SNMP trap is generated when Alarm 5 was triggered,
        SNMP trap enable is set and SNMP is enabled."
    -- NMS trap annotation
    --#TYPE "Webio Digital Alarm 5"
    --#SUMMARY "Alarm 5: %s"
    --#ARGUMENTS {0}
    --#SEVERITY INFORMATIONAL
    --#TIMEINDEX 99
    --#STATE OPERATIONAL    
    ::= 57

wtWebioEA24oemAlert6 TRAP-TYPE
    ENTERPRISE  wtWebioEA24oem
    VARIABLES   { wtWebioEA24oemAlarmSnmpTrapText }
    DESCRIPTION
        "This SNMP trap is generated when Alarm 6 was triggered,
        SNMP trap enable is set and SNMP is enabled."
    -- NMS trap annotation
    --#TYPE "Webio Digital Alarm 6"
    --#SUMMARY "Alarm 6: %s"
    --#ARGUMENTS {0}
    --#SEVERITY INFORMATIONAL
    --#TIMEINDEX 99
    --#STATE OPERATIONAL    
    ::= 58

wtWebioEA24oemAlert7 TRAP-TYPE
    ENTERPRISE  wtWebioEA24oem
    VARIABLES   { wtWebioEA24oemAlarmSnmpTrapText }
    DESCRIPTION
        "This SNMP trap is generated when Alarm 7 was triggered,
        SNMP trap enable is set and SNMP is enabled."
    -- NMS trap annotation
    --#TYPE "Webio Digital Alarm 7"
    --#SUMMARY "Alarm 7: %s"
    --#ARGUMENTS {0}
    --#SEVERITY INFORMATIONAL
    --#TIMEINDEX 99
    --#STATE OPERATIONAL    
    ::= 59

wtWebioEA24oemAlert8 TRAP-TYPE
    ENTERPRISE  wtWebioEA24oem
    VARIABLES   { wtWebioEA24oemAlarmSnmpTrapText }
    DESCRIPTION
        "This SNMP trap is generated when Alarm 8 was triggered,
        SNMP trap enable is set and SNMP is enabled."
    -- NMS trap annotation
    --#TYPE "Webio Digital Alarm 8"
    --#SUMMARY "Alarm 8: %s"
    --#ARGUMENTS {0}
    --#SEVERITY INFORMATIONAL
    --#TIMEINDEX 99
    --#STATE OPERATIONAL    
    ::= 60

wtWebioEA24oemAlert9 TRAP-TYPE
    ENTERPRISE  wtWebioEA24oem
    VARIABLES   { wtWebioEA24oemAlarmSnmpTrapText }
    DESCRIPTION
        "This SNMP trap is generated when Alarm 9 was triggered,
        SNMP trap enable is set and SNMP is enabled."
    -- NMS trap annotation
    --#TYPE "Webio Digital Alarm 9"
    --#SUMMARY "Alarm 9: %s"
    --#ARGUMENTS {0}
    --#SEVERITY INFORMATIONAL
    --#TIMEINDEX 99
    --#STATE OPERATIONAL    
    ::= 61

wtWebioEA24oemAlert10 TRAP-TYPE
    ENTERPRISE  wtWebioEA24oem
    VARIABLES   { wtWebioEA24oemAlarmSnmpTrapText }
    DESCRIPTION
        "This SNMP trap is generated when Alarm 10 was triggered,
        SNMP trap enable is set and SNMP is enabled."
    -- NMS trap annotation
    --#TYPE "Webio Digital Alarm 10"
    --#SUMMARY "Alarm 10: %s"
    --#ARGUMENTS {0}
    --#SEVERITY INFORMATIONAL
    --#TIMEINDEX 99
    --#STATE OPERATIONAL    
    ::= 62

wtWebioEA24oemAlert11 TRAP-TYPE
    ENTERPRISE  wtWebioEA24oem
    VARIABLES   { wtWebioEA24oemAlarmSnmpTrapText }
    DESCRIPTION
        "This SNMP trap is generated when Alarm 11 was triggered,
        SNMP trap enable is set and SNMP is enabled."
    -- NMS trap annotation
    --#TYPE "Webio Digital Alarm 11"
    --#SUMMARY "Alarm 11: %s"
    --#ARGUMENTS {0}
    --#SEVERITY INFORMATIONAL
    --#TIMEINDEX 99
    --#STATE OPERATIONAL    
    ::= 63

wtWebioEA24oemAlert12 TRAP-TYPE
    ENTERPRISE  wtWebioEA24oem
    VARIABLES   { wtWebioEA24oemAlarmSnmpTrapText }
    DESCRIPTION
        "This SNMP trap is generated when Alarm 12 was triggered,
        SNMP trap enable is set and SNMP is enabled."
    -- NMS trap annotation
    --#TYPE "Webio Digital Alarm 12"
    --#SUMMARY "Alarm 12: %s"
    --#ARGUMENTS {0}
    --#SEVERITY INFORMATIONAL
    --#TIMEINDEX 99
    --#STATE OPERATIONAL    
    ::= 64

wtWebioEA24oemAlert13 TRAP-TYPE
    ENTERPRISE  wtWebioEA24oem
    VARIABLES   { wtWebioEA24oemAlarmSnmpTrapText }
    DESCRIPTION
        "This SNMP trap is generated when Alarm 13 was triggered,
        SNMP trap enable is set and SNMP is enabled."
    -- NMS trap annotation
    --#TYPE "Webio Digital Alarm 13"
    --#SUMMARY "Alarm 13: %s"
    --#ARGUMENTS {0}
    --#SEVERITY INFORMATIONAL
    --#TIMEINDEX 99
    --#STATE OPERATIONAL    
    ::= 65

wtWebioEA24oemAlert14 TRAP-TYPE
    ENTERPRISE  wtWebioEA24oem
    VARIABLES   { wtWebioEA24oemAlarmSnmpTrapText }
    DESCRIPTION
        "This SNMP trap is generated when Alarm 14 was triggered,
        SNMP trap enable is set and SNMP is enabled."
    -- NMS trap annotation
    --#TYPE "Webio Digital Alarm 14"
    --#SUMMARY "Alarm 14: %s"
    --#ARGUMENTS {0}
    --#SEVERITY INFORMATIONAL
    --#TIMEINDEX 99
    --#STATE OPERATIONAL    
    ::= 66

wtWebioEA24oemAlert15 TRAP-TYPE
    ENTERPRISE  wtWebioEA24oem
    VARIABLES   { wtWebioEA24oemAlarmSnmpTrapText }
    DESCRIPTION
        "This SNMP trap is generated when Alarm 15 was triggered,
        SNMP trap enable is set and SNMP is enabled."
    -- NMS trap annotation
    --#TYPE "Webio Digital Alarm 15"
    --#SUMMARY "Alarm 15: %s"
    --#ARGUMENTS {0}
    --#SEVERITY INFORMATIONAL
    --#TIMEINDEX 99
    --#STATE OPERATIONAL    
    ::= 67

wtWebioEA24oemAlert16 TRAP-TYPE
    ENTERPRISE  wtWebioEA24oem
    VARIABLES   { wtWebioEA24oemAlarmSnmpTrapText }
    DESCRIPTION
        "This SNMP trap is generated when Alarm 16 was triggered,
        SNMP trap enable is set and SNMP is enabled."
    -- NMS trap annotation
    --#TYPE "Webio Digital Alarm 16"
    --#SUMMARY "Alarm 16: %s"
    --#ARGUMENTS {0}
    --#SEVERITY INFORMATIONAL
    --#TIMEINDEX 99
    --#STATE OPERATIONAL    
    ::= 68

wtWebioEA24oemAlert17 TRAP-TYPE
    ENTERPRISE  wtWebioEA24oem
    VARIABLES   { wtWebioEA24oemAlarmSnmpTrapText }
    DESCRIPTION
        "This SNMP trap is generated when Alarm 1 was triggered,
        SNMP trap enable is set and SNMP is enabled."
    -- NMS trap annotation
    --#TYPE "Webio Digital Release Alarm 1"
    --#SUMMARY "Release Alarm 1: %s"
    --#ARGUMENTS {0}
    --#SEVERITY INFORMATIONAL
    --#TIMEINDEX 99
    --#STATE OPERATIONAL    
    ::= 71

wtWebioEA24oemAlert18 TRAP-TYPE
    ENTERPRISE  wtWebioEA24oem
    VARIABLES   { wtWebioEA24oemAlarmSnmpTrapText }
    DESCRIPTION
        "This SNMP trap is generated when Alarm 2 was released,
        SNMP trap enable is set and SNMP is enabled."
    -- NMS trap annotation
    --#TYPE "Webio Digital Release Alarm 2"
    --#SUMMARY "Release Alarm 2: %s"
    --#ARGUMENTS {0}
    --#SEVERITY INFORMATIONAL
    --#TIMEINDEX 99
    --#STATE OPERATIONAL    
    ::= 72

wtWebioEA24oemAlert19 TRAP-TYPE
    ENTERPRISE  wtWebioEA24oem
    VARIABLES   { wtWebioEA24oemAlarmSnmpTrapText }
    DESCRIPTION
        "This SNMP trap is generated when Alarm 3 was released,
        SNMP trap enable is set and SNMP is enabled."
    -- NMS trap annotation
    --#TYPE "Webio Digital Release Alarm 3"
    --#SUMMARY "Release Alarm 3: %s"
    --#ARGUMENTS {0}
    --#SEVERITY INFORMATIONAL
    --#TIMEINDEX 99
    --#STATE OPERATIONAL    
    ::= 73

wtWebioEA24oemAlert20 TRAP-TYPE
    ENTERPRISE  wtWebioEA24oem
    VARIABLES   { wtWebioEA24oemAlarmSnmpTrapText }
    DESCRIPTION
        "This SNMP trap is generated when Alarm 4 was released,
        SNMP trap enable is set and SNMP is enabled."
    -- NMS trap annotation
    --#TYPE "Webio Digital Release Alarm 4"
    --#SUMMARY "Release Alarm 4: %s"
    --#ARGUMENTS {0}
    --#SEVERITY INFORMATIONAL
    --#TIMEINDEX 99
    --#STATE OPERATIONAL    
    ::= 74

wtWebioEA24oemAlert21 TRAP-TYPE
    ENTERPRISE  wtWebioEA24oem
    VARIABLES   { wtWebioEA24oemAlarmSnmpTrapText }
    DESCRIPTION
        "This SNMP trap is generated when Alarm 5 was released,
        SNMP trap enable is set and SNMP is enabled."
    -- NMS trap annotation
    --#TYPE "Webio Digital Release Alarm 5"
    --#SUMMARY "Release Alarm 5: %s"
    --#ARGUMENTS {0}
    --#SEVERITY INFORMATIONAL
    --#TIMEINDEX 99
    --#STATE OPERATIONAL    
    ::= 75

wtWebioEA24oemAlert22 TRAP-TYPE
    ENTERPRISE  wtWebioEA24oem
    VARIABLES   { wtWebioEA24oemAlarmSnmpTrapText }
    DESCRIPTION
        "This SNMP trap is generated when Alarm 6 was released,
        SNMP trap enable is set and SNMP is enabled."
    -- NMS trap annotation
    --#TYPE "Webio Digital Release Alarm 6"
    --#SUMMARY "Release Alarm 6: %s"
    --#ARGUMENTS {0}
    --#SEVERITY INFORMATIONAL
    --#TIMEINDEX 99
    --#STATE OPERATIONAL    
    ::= 76

wtWebioEA24oemAlert23 TRAP-TYPE
    ENTERPRISE  wtWebioEA24oem
    VARIABLES   { wtWebioEA24oemAlarmSnmpTrapText }
    DESCRIPTION
        "This SNMP trap is generated when Alarm 7 was released,
        SNMP trap enable is set and SNMP is enabled."
    -- NMS trap annotation
    --#TYPE "Webio Digital Release Alarm 7"
    --#SUMMARY "Release Alarm 7: %s"
    --#ARGUMENTS {0}
    --#SEVERITY INFORMATIONAL
    --#TIMEINDEX 99
    --#STATE OPERATIONAL    
    ::= 77

wtWebioEA24oemAlert24 TRAP-TYPE
    ENTERPRISE  wtWebioEA24oem
    VARIABLES   { wtWebioEA24oemAlarmSnmpTrapText }
    DESCRIPTION
        "This SNMP trap is generated when Alarm 8 was released,
        SNMP trap enable is set and SNMP is enabled."
    -- NMS trap annotation
    --#TYPE "Webio Digital Release Alarm 8"
    --#SUMMARY "Release Alarm 8: %s"
    --#ARGUMENTS {0}
    --#SEVERITY INFORMATIONAL
    --#TIMEINDEX 99
    --#STATE OPERATIONAL    
    ::= 78

wtWebioEA24oemAlert25 TRAP-TYPE
    ENTERPRISE  wtWebioEA24oem
    VARIABLES   { wtWebioEA24oemAlarmSnmpTrapText }
    DESCRIPTION
        "This SNMP trap is generated when Alarm 9 was released,
        SNMP trap enable is set and SNMP is enabled."
    -- NMS trap annotation
    --#TYPE "Webio Digital Release Alarm 9"
    --#SUMMARY "Release Alarm 9: %s"
    --#ARGUMENTS {0}
    --#SEVERITY INFORMATIONAL
    --#TIMEINDEX 99
    --#STATE OPERATIONAL    
    ::= 79

wtWebioEA24oemAlert26 TRAP-TYPE
    ENTERPRISE  wtWebioEA24oem
    VARIABLES   { wtWebioEA24oemAlarmSnmpTrapText }
    DESCRIPTION
        "This SNMP trap is generated when Alarm 10 was released,
        SNMP trap enable is set and SNMP is enabled."
    -- NMS trap annotation
    --#TYPE "Webio Digital Release Alarm 10"
    --#SUMMARY "Release Alarm 10: %s"
    --#ARGUMENTS {0}
    --#SEVERITY INFORMATIONAL
    --#TIMEINDEX 99
    --#STATE OPERATIONAL    
    ::= 80

wtWebioEA24oemAlert27 TRAP-TYPE
    ENTERPRISE  wtWebioEA24oem
    VARIABLES   { wtWebioEA24oemAlarmSnmpTrapText }
    DESCRIPTION
        "This SNMP trap is generated when Alarm 11 was released,
        SNMP trap enable is set and SNMP is enabled."
    -- NMS trap annotation
    --#TYPE "Webio Digital Release Alarm 11"
    --#SUMMARY "Release Alarm 11: %s"
    --#ARGUMENTS {0}
    --#SEVERITY INFORMATIONAL
    --#TIMEINDEX 99
    --#STATE OPERATIONAL    
    ::= 81

wtWebioEA24oemAlert28 TRAP-TYPE
    ENTERPRISE  wtWebioEA24oem
    VARIABLES   { wtWebioEA24oemAlarmSnmpTrapText }
    DESCRIPTION
        "This SNMP trap is generated when Alarm 12 was released,
        SNMP trap enable is set and SNMP is enabled."
    -- NMS trap annotation
    --#TYPE "Webio Digital Release Alarm 12"
    --#SUMMARY "Release Alarm 12: %s"
    --#ARGUMENTS {0}
    --#SEVERITY INFORMATIONAL
    --#TIMEINDEX 99
    --#STATE OPERATIONAL    
    ::= 82

wtWebioEA24oemAlert29 TRAP-TYPE
    ENTERPRISE  wtWebioEA24oem
    VARIABLES   { wtWebioEA24oemAlarmSnmpTrapText }
    DESCRIPTION
        "This SNMP trap is generated when Alarm 13 was released,
        SNMP trap enable is set and SNMP is enabled."
    -- NMS trap annotation
    --#TYPE "Webio Digital Release Alarm 13"
    --#SUMMARY "Release Alarm 13: %s"
    --#ARGUMENTS {0}
    --#SEVERITY INFORMATIONAL
    --#TIMEINDEX 99
    --#STATE OPERATIONAL    
    ::= 83

wtWebioEA24oemAlert30 TRAP-TYPE
    ENTERPRISE  wtWebioEA24oem
    VARIABLES   { wtWebioEA24oemAlarmSnmpTrapText }
    DESCRIPTION
        "This SNMP trap is generated when Alarm 14 was released,
        SNMP trap enable is set and SNMP is enabled."
    -- NMS trap annotation
    --#TYPE "Webio Digital Release Alarm 14"
    --#SUMMARY "Release Alarm 14: %s"
    --#ARGUMENTS {0}
    --#SEVERITY INFORMATIONAL
    --#TIMEINDEX 99
    --#STATE OPERATIONAL    
    ::= 84

wtWebioEA24oemAlert31 TRAP-TYPE
    ENTERPRISE  wtWebioEA24oem
    VARIABLES   { wtWebioEA24oemAlarmSnmpTrapText }
    DESCRIPTION
        "This SNMP trap is generated when Alarm 15 was released,
        SNMP trap enable is set and SNMP is enabled."
    -- NMS trap annotation
    --#TYPE "Webio Digital Release Alarm 15"
    --#SUMMARY "Release Alarm 15: %s"
    --#ARGUMENTS {0}
    --#SEVERITY INFORMATIONAL
    --#TIMEINDEX 99
    --#STATE OPERATIONAL    
    ::= 85

wtWebioEA24oemAlert32 TRAP-TYPE
    ENTERPRISE  wtWebioEA24oem
    VARIABLES   { wtWebioEA24oemAlarmSnmpTrapText }
    DESCRIPTION
        "This SNMP trap is generated when Alarm 16 was released,
        SNMP trap enable is set and SNMP is enabled."
    -- NMS trap annotation
    --#TYPE "Webio Digital Release Alarm 16"
    --#SUMMARY "Release Alarm 16: %s"
    --#ARGUMENTS {0}
    --#SEVERITY INFORMATIONAL
    --#TIMEINDEX 99
    --#STATE OPERATIONAL    
    ::= 86

wtWebioEA24oemAlertDiag TRAP-TYPE
    ENTERPRISE  wtWebioEA24oem
    VARIABLES   { 	
    		wtWebioEA24oemDiagErrorIndex,
    	  	wtWebioEA24oemDiagErrorMessage
    		}
    DESCRIPTION
        "Dieser SNMP-Trap wird generiert, wenn eine Diagnose/Error-Message ausgelst wurde,
        das SNMP-Trap-Enable gesetzt ist und
        SNMP in Enable freigegeben ist."
    -- NMS trap annotation
    --#TYPE "Webio Digital Diagnose Error"
    --#SUMMARY "Diagnose error index: %d, Message: %s."
    --#ARGUMENTS {0,1}
    --#SEVERITY MAJOR
    --#TIMEINDEX 99
    --#STATE DEGRADED    
    ::= 110    

--------------------------------------------------------------------------------
--------------------------------------------------------------------------------
--------------------------------------------------------------------------------

-- wtWebioEA12x6RelInOut Group
------------------------

wtWebioEA12x6RelInputs OBJECT-TYPE
    SYNTAX INTEGER (1..12)
    ACCESS read-only
    STATUS mandatory
    DESCRIPTION
        "Number of idependent inputs."
    ::= { wtWebioEA12x6RelInOut 1 }

wtWebioEA12x6RelOutputs OBJECT-TYPE
    SYNTAX INTEGER (1..6)
    ACCESS read-only
    STATUS mandatory
    DESCRIPTION
        "Number of independent outputs."
    ::= { wtWebioEA12x6RelInOut 2 }

-- Input Interface Table

wtWebioEA12x6RelInputTable OBJECT-TYPE
    SYNTAX SEQUENCE OF WtWebioEA12x6RelInputEntry
    ACCESS not-accessible
    STATUS mandatory
    DESCRIPTION
        "List of input indices."
    ::= { wtWebioEA12x6RelInOut 3 }

wtWebioEA12x6RelInputEntry OBJECT-TYPE
    SYNTAX WtWebioEA12x6RelInputEntry
    ACCESS not-accessible
    STATUS mandatory
    DESCRIPTION
        "Number of the inputs."
    INDEX  { wtWebioEA12x6RelInputNo }
    ::= { wtWebioEA12x6RelInputTable 1 }

WtWebioEA12x6RelInputEntry ::= SEQUENCE {
    wtWebioEA12x6RelInputNo INTEGER,
    wtWebioEA12x6RelInputCounter INTEGER,
    wtWebioEA12x6RelInputCounterClear INTEGER
}

wtWebioEA12x6RelInputNo OBJECT-TYPE
    SYNTAX INTEGER (1)
    ACCESS read-only
    STATUS mandatory
    DESCRIPTION
        "Index numbers of the inputs."
    ::= { wtWebioEA12x6RelInputEntry 1 }

wtWebioEA12x6RelInputCounter OBJECT-TYPE
    SYNTAX INTEGER (1)
    ACCESS read-only
    STATUS mandatory
    DESCRIPTION
        "Value of the input counter."
    ::= { wtWebioEA12x6RelInputEntry 2 }
    
wtWebioEA12x6RelInputCounterClear OBJECT-TYPE
    SYNTAX INTEGER
    ACCESS read-only
    STATUS mandatory
    DESCRIPTION
        "Clears the input counter after returning its value."
    ::= { wtWebioEA12x6RelInputEntry 3 }
    
wtWebioEA12x6RelInputValue OBJECT-TYPE
    SYNTAX INTEGER 
    ACCESS read-only
    STATUS mandatory
    DESCRIPTION
        "This variable is used to read the inputs of the digital I/O port.
        The OCTETS are interpreted bit-by-bit, with each bit corresponding to an input.
        Bit 0 corresponds to the LSB.
        OCTET 1: unused
        OCTET 2: unused
        OCTET 3, Bit 0-3: Digital inputs 8-11
                 Bit 4-7: unused
        OCTET 4, Bit 0-7: Digital inputs 0-7"
    ::= { wtWebioEA12x6RelInOut 4 }
    

-- Output Interface Table

wtWebioEA12x6RelOutputTable OBJECT-TYPE
    SYNTAX SEQUENCE OF WtWebioEA12x6RelOutputEntry
    ACCESS not-accessible
    STATUS mandatory
    DESCRIPTION
        "List of output indices."
    ::= { wtWebioEA12x6RelInOut 5 }

wtWebioEA12x6RelOutputEntry OBJECT-TYPE
    SYNTAX WtWebioEA12x6RelOutputEntry
    ACCESS not-accessible
    STATUS mandatory
    DESCRIPTION
        "Number of the outputs."
    INDEX  { wtWebioEA12x6RelOutputNo }
    ::= { wtWebioEA12x6RelOutputTable 1 }

WtWebioEA12x6RelOutputEntry ::= SEQUENCE {
    wtWebioEA12x6RelOutputNo 		INTEGER,
    wtWebioEA12x6RelOutputState		INTEGER
}

wtWebioEA12x6RelOutputNo OBJECT-TYPE
    SYNTAX INTEGER (1)
    ACCESS read-only
    STATUS mandatory
    DESCRIPTION
        "Output number."
    ::= { wtWebioEA12x6RelOutputEntry 1 }
    
wtWebioEA12x6RelOutputState OBJECT-TYPE
    SYNTAX INTEGER{
    wtWebioEA12x6RelOutputState-OFF(0),
    wtWebioEA12x6OutputState-ON(1)
    }
    ACCESS read-write
    STATUS mandatory
    DESCRIPTION
        "Setting and reading of the states of the outputs."
    ::= { wtWebioEA12x6RelOutputEntry 2 }    

wtWebioEA12x6RelOutputValue OBJECT-TYPE
    SYNTAX INTEGER
    ACCESS read-write
    STATUS mandatory
    DESCRIPTION
        "This variable is used to read and write the outputs of the digital I/O port. 
        The OCTETS are interpreted bit-by-bit, with each bit corresponding to an output. 
        Bit 0 corresponds to the LSB.
        OCTET 1: unused
        OCTET 2: unused
        OCTET 3: unused
        OCTET 4: Bit 0-5: Digital outputs 0-5"
    ::= { wtWebioEA12x6RelInOut 6 }
    
wtWebioEA12x6RelSetOutput OBJECT-TYPE
    SYNTAX OCTET STRING (SIZE (8))
    ACCESS read-write			-- write-only
    STATUS mandatory
    DESCRIPTION
        "This variable allows setting of individual digital outputs. The OCTETS are 
        interpreted bit-by-bit, with each bit corresponding to an output. Bit 0 corresponds 
        to the LSB.
        The first two OCTETS contain the mask which determines which of the outputs are to 
        be set (corresponding bit = 1) and which outputs are to remain unchanged 
        (corresponding bit = 0):
	OCTET 1 : unused
	OCTET 2 : unused
	OCTET 3 : unused
	OCTET 4 : Bit 0-5: Mask for digital outputs 0-5
	
	OCTETS 5-8 contain the level (1=HIGH, 0=LOW) which the inputs 
	should assume:
	OCTET 5 : unused
	OCTET 6 : unused
	OCTET 7 : unused
        OCTET 8 : Bit 0-5: Level of digital outputs 0-5"
    ::= { wtWebioEA12x6RelInOut 7 }
    
-- wtWebioEA12x6RelSessCntrl Group
--------------------------------

wtWebioEA12x6RelSessCntrlPassword OBJECT-TYPE
    SYNTAX OCTET STRING 
    ACCESS read-write
    STATUS mandatory
    DESCRIPTION
        "Entering this password opens a session which is ended by writing a 1 to 
        wtWebioEA12x6RelSessCntrlLogout. When read this variable provides a string of
        length zero."
    ::= { wtWebioEA12x6RelSessCntrl 1 }

wtWebioEA12x6RelSessCntrlConfigMode OBJECT-TYPE
    SYNTAX INTEGER {
    wtWebioEA12x6RelSessCntrl-NoSession(0),
    wtWebioEA12x6RelSessCntrl-Session(1)
    }
    ACCESS read-only
    STATUS mandatory
    DESCRIPTION
        "When the device is in SNMP configuration mode, the value 1 is
        returned, otherwise 0. If the read value is 0 even though the password
        was written, the device is already in config mode and the variables
        can only be read."
    ::= { wtWebioEA12x6RelSessCntrl 2 }

wtWebioEA12x6RelSessCntrlLogout OBJECT-TYPE
    SYNTAX INTEGER 
    ACCESS read-write
    STATUS mandatory
    DESCRIPTION
        "If the device is in configuration mode and the session was opened by
        this SNMP Manager, writing a 1 to this variable will end the session 
        and all parameters are stored.
        Writing a 2 discards all entries again. When read this variable
        provides the value 0."
    ::= { wtWebioEA12x6RelSessCntrl 3 }

wtWebioEA12x6RelSessCntrlAdminPassword OBJECT-TYPE
    SYNTAX OCTET STRING 
    ACCESS read-write
    STATUS mandatory
    DESCRIPTION
        "This password protects access to the variables with administrator rights.
        It can only be changed by the administrator. If no password was assigned,
        the valid password is public."
    ::= { wtWebioEA12x6RelSessCntrl 4 }

wtWebioEA12x6RelSessCntrlConfigPassword OBJECT-TYPE
    SYNTAX OCTET STRING 
    ACCESS read-write
    STATUS mandatory
    DESCRIPTION
        "This password protects access to the variables with configurator rights. It can
        be changed by the administrator and by the configurator. If no password was assigned, 
        the valid password is public. When read this variable provides a null-pointer."
    ::= { wtWebioEA12x6RelSessCntrl 5 }
    
-- wtWebioEA12x6RelText Group
------------------------

wtWebioEA12x6RelDeviceName OBJECT-TYPE
    SYNTAX OCTET STRING 
    ACCESS read-write
    STATUS mandatory
    DESCRIPTION
        "Name of the Webio, which is user definable."
    ::= { wtWebioEA12x6RelText 1 }

wtWebioEA12x6RelDeviceText OBJECT-TYPE
    SYNTAX OCTET STRING 
    ACCESS read-write
    STATUS mandatory
    DESCRIPTION
        "Description of the Webio, which is user definable."
    ::= { wtWebioEA12x6RelText 2 }
    
wtWebioEA12x6RelDeviceLocation OBJECT-TYPE
    SYNTAX OCTET STRING 
    ACCESS read-write
    STATUS mandatory
    DESCRIPTION
        "Description of the location of the Webio, which is user definable."
    ::= { wtWebioEA12x6RelText 3 }

wtWebioEA12x6RelDeviceContact OBJECT-TYPE
    SYNTAX OCTET STRING 
    ACCESS read-write
    STATUS mandatory
    DESCRIPTION
        "Contact address of the system operator of the Webio, which is user definable."
    ::= { wtWebioEA12x6RelText 4 }    

-- wtWebioEA12x6RelTimeZone Group
----------------------------

wtWebioEA12x6RelTzOffsetHrs OBJECT-TYPE
    SYNTAX INTEGER 
    ACCESS read-write
    STATUS mandatory
    DESCRIPTION
        "Offset hours for the time zone (winter time) with respect to UTC."
    ::= { wtWebioEA12x6RelTimeZone 1 }

wtWebioEA12x6RelTzOffsetMin OBJECT-TYPE
    SYNTAX INTEGER 
    ACCESS read-write
    STATUS mandatory
    DESCRIPTION
        "Offset minutes for the time zone (winter time) with respect to UTC."
    ::= { wtWebioEA12x6RelTimeZone 2 }

wtWebioEA12x6RelTzEnable OBJECT-TYPE
    SYNTAX OCTET STRING (SIZE(4))
    ACCESS read-write
    STATUS mandatory
    DESCRIPTION
        "Binary coded conditions:
        Octet 1: unused
        Octet 2: unused
        Octet 3: unused
        Octet 4:
        	Bit 1-7: unused
	        Bit 0  : Apply Timezone"
    ::= { wtWebioEA12x6RelTimeZone 3 }

wtWebioEA12x6RelStTzOffsetHrs OBJECT-TYPE
    SYNTAX INTEGER 
    ACCESS read-write
    STATUS mandatory
    DESCRIPTION
        "Offset hours of the time zone (summer time) with respect to UTC."
    ::= { wtWebioEA12x6RelTimeZone 4 }

wtWebioEA12x6RelStTzOffsetMin OBJECT-TYPE
    SYNTAX INTEGER 
    ACCESS read-write
    STATUS mandatory
    DESCRIPTION
        "Offset minutes of the time zone (summer time) with respect to UTC."
    ::= { wtWebioEA12x6RelTimeZone 5 }

wtWebioEA12x6RelStTzEnable OBJECT-TYPE
    SYNTAX OCTET STRING (SIZE(4))
    ACCESS read-write
    STATUS mandatory
    DESCRIPTION
        "Binary coded conditions:
        Octet 1: unused
        Octet 2: unused
        Octet 3: unused
        Octet 4:
        	Bit 1-7: unused
	        Bit 0  : Apply Summertime"
    ::= { wtWebioEA12x6RelTimeZone 6 }

wtWebioEA12x6RelStTzStartMonth OBJECT-TYPE
    SYNTAX INTEGER {
    	wtWebioEA12x6RelStartMonth-January(1),
    	wtWebioEA12x6RelStartMonth-February(2),
    	wtWebioEA12x6RelStartMonth-March(3),
    	wtWebioEA12x6RelStartMonth-April(4),
    	wtWebioEA12x6RelStartMonth-May(5),
    	wtWebioEA12x6RelStartMonth-June(6),
    	wtWebioEA12x6RelStartMonth-July(7),
    	wtWebioEA12x6RelStartMonth-August(8),
    	wtWebioEA12x6RelStartMonth-September(9),
    	wtWebioEA12x6RelStartMonth-October(10),
    	wtWebioEA12x6RelStartMonth-November(11),
    	wtWebioEA12x6RelStartMonth-December(12)
    	}
    	
    ACCESS read-write
    STATUS mandatory
    DESCRIPTION
        "Month in which the change is made from winter time to summer time."
    ::= { wtWebioEA12x6RelTimeZone 7 }

wtWebioEA12x6RelStTzStartMode OBJECT-TYPE
    SYNTAX INTEGER {
    	wtWebioEA12x6RelStartMode-first(1),
    	wtWebioEA12x6RelStartMode-second(2),
    	wtWebioEA12x6RelStartMode-third(3),
    	wtWebioEA12x6RelStartMode-fourth(4),
    	wtWebioEA12x6RelStartMode-last(5)
    	}
    	
    ACCESS read-write
    STATUS mandatory
    DESCRIPTION
        "Mode of the day of the week for which the change is made from winter time to summer time."
    ::= { wtWebioEA12x6RelTimeZone 8 }

wtWebioEA12x6RelStTzStartWday OBJECT-TYPE
    SYNTAX INTEGER {
    	wtWebioEA12x6RelStartWday-Sunday(1),
    	wtWebioEA12x6RelStartWday-Monday(2),
    	wtWebioEA12x6RelStartWday-Tuesday(3),
    	wtWebioEA12x6RelStartWday-Thursday(4),
    	wtWebioEA12x6RelStartWday-Wednesday(5),
    	wtWebioEA12x6RelStartWday-Friday(6),
    	wtWebioEA12x6RelStartWday-Saturday(7)
    	}
    	
    ACCESS read-write
    STATUS mandatory
    DESCRIPTION
        "Day of the week on which the change is made from winter time to summer time"
    ::= { wtWebioEA12x6RelTimeZone 9 }
    
wtWebioEA12x6RelStTzStartHrs OBJECT-TYPE
    SYNTAX INTEGER 
    ACCESS read-write
    STATUS mandatory
    DESCRIPTION
        "Hour in which the time zone is changed from winter to summer time with
        respect to UTC."
    ::= { wtWebioEA12x6RelTimeZone 10 }

wtWebioEA12x6RelStTzStartMin OBJECT-TYPE
    SYNTAX INTEGER 
    ACCESS read-write
    STATUS mandatory
    DESCRIPTION
        "Minute in which the time zone is changed from winter to summer time with
        respect to UTC."
    ::= { wtWebioEA12x6RelTimeZone 11 }
 
wtWebioEA12x6RelStTzStopMonth OBJECT-TYPE
    SYNTAX INTEGER {
    	wtWebioEA12x6RelStopMonth-January(1),
    	wtWebioEA12x6RelStopMonth-February(2),
    	wtWebioEA12x6RelStopMonth-March(3),
    	wtWebioEA12x6RelStopMonth-April(4),
    	wtWebioEA12x6RelStopMonth-May(5),
    	wtWebioEA12x6RelStopMonth-June(6),
    	wtWebioEA12x6RelStopMonth-July(7),
    	wtWebioEA12x6RelStopMonth-August(8),
    	wtWebioEA12x6RelStopMonth-September(9),
    	wtWebioEA12x6RelStopMonth-October(10),
    	wtWebioEA12x6RelStopMonth-November(11),
    	wtWebioEA12x6RelStopMonth-December(12)
    	}
    ACCESS read-write
    STATUS mandatory
    DESCRIPTION
        "Month in which the change is made from summer time to winter time."
   ::= { wtWebioEA12x6RelTimeZone 12 }

wtWebioEA12x6RelStTzStopMode OBJECT-TYPE
    SYNTAX INTEGER {
    	wtWebioEA12x6RelStopMode-first(1),
    	wtWebioEA12x6RelStopMode-second(2),
    	wtWebioEA12x6RelStopMode-third(3),
    	wtWebioEA12x6RelStopMode-fourth(4),
    	wtWebioEA12x6RelStopMode-last(5)
    	}
    ACCESS read-write
    STATUS mandatory
    DESCRIPTION
        "Mode of the week day on which the change is made from summer time to winter time."
    ::= { wtWebioEA12x6RelTimeZone 13 }

wtWebioEA12x6RelStTzStopWday OBJECT-TYPE
    SYNTAX INTEGER {
    	wtWebioEA12x6RelStopWday-Sunday(1),
    	wtWebioEA12x6RelStopWday-Monday(2),
    	wtWebioEA12x6RelStopWday-Tuesday(3),
    	wtWebioEA12x6RelStopWday-Thursday(4),
    	wtWebioEA12x6RelStopWday-Wednesday(5),
    	wtWebioEA12x6RelStopWday-Friday(6),
    	wtWebioEA12x6RelStopWday-Saturday(7)
    	}
    ACCESS read-write
    STATUS mandatory
    DESCRIPTION
        "Day of the week on which the change is made from summer time to winter time."
    ::= { wtWebioEA12x6RelTimeZone 14 }
    
wtWebioEA12x6RelStTzStopHrs OBJECT-TYPE
    SYNTAX INTEGER 
    ACCESS read-write
    STATUS mandatory
    DESCRIPTION
        "Hour at which the time zone is changed from summer to winter time with
        respect to UTC."
    ::= { wtWebioEA12x6RelTimeZone 15 }

wtWebioEA12x6RelStTzStopMin OBJECT-TYPE
    SYNTAX INTEGER 
    ACCESS read-write
    STATUS mandatory
    DESCRIPTION
        "Minute at which the time zone is changed from summer to winter time with
        respect to UTC."
    ::= { wtWebioEA12x6RelTimeZone 16 }

-- wtWebioEA12x6RelTimeServer Group
----------------------------

wtWebioEA12x6RelTimeServer1 OBJECT-TYPE
    SYNTAX OCTET STRING 
    ACCESS read-write
    STATUS mandatory
    DESCRIPTION
        "IP address or name of the 1st time server in ASCII"
    ::= { wtWebioEA12x6RelTimeServer 1 }

wtWebioEA12x6RelTimeServer2 OBJECT-TYPE
    SYNTAX OCTET STRING 
    ACCESS read-write
    STATUS mandatory
    DESCRIPTION
        "IP address or name of the 2nd time server in ASCII"
    ::= { wtWebioEA12x6RelTimeServer 2 }

wtWebioEA12x6RelTsEnable OBJECT-TYPE
    SYNTAX OCTET STRING (SIZE(4))
    ACCESS read-write
    STATUS mandatory
    DESCRIPTION
        "Binary coded conditions:
        Octet 1: unused
        Octet 2: unused
        Octet 3: unused
        Octet 4:
        	Bit 1-7: unused
	        Bit 0  : Apply Time Server"
    ::= { wtWebioEA12x6RelTimeServer 3 }

wtWebioEA12x6RelTsSyncTime OBJECT-TYPE
    SYNTAX INTEGER 
    ACCESS read-write
    STATUS mandatory
    DESCRIPTION
        "Daily synchronisation time with the time server (hour: 0-23)."
    ::= { wtWebioEA12x6RelTimeServer 4 }
      
    
-- wtWebioEA12x6RelDeviceClock Group
----------------------------

wtWebioEA12x6RelClockHrs OBJECT-TYPE
    SYNTAX INTEGER (0..23)
    ACCESS read-write
    STATUS mandatory
    DESCRIPTION
        "Clock hours taking into account the time zone settings."
    ::= { wtWebioEA12x6RelDeviceClock 1 }

wtWebioEA12x6RelClockMin OBJECT-TYPE
    SYNTAX INTEGER (0..59)
    ACCESS read-write
    STATUS mandatory
    DESCRIPTION
        "Clock minutes taking into account the time zone settings."
    ::= { wtWebioEA12x6RelDeviceClock 2 }

wtWebioEA12x6RelClockDay OBJECT-TYPE
    SYNTAX INTEGER (1..31)
    ACCESS read-write
    STATUS mandatory
    DESCRIPTION
        "Date: Day of the month, taking into account the time zone settings."
    ::= { wtWebioEA12x6RelDeviceClock 3 }

wtWebioEA12x6RelClockMonth OBJECT-TYPE
   SYNTAX INTEGER {
    	wtWebioEA12x6RelClockMonth-January(1),
    	wtWebioEA12x6RelClockMonth-February(2),
    	wtWebioEA12x6RelClockMonth-March(3),
    	wtWebioEA12x6RelClockMonth-April(4),
    	wtWebioEA12x6RelClockMonth-May(5),
    	wtWebioEA12x6RelClockMonth-June(6),
    	wtWebioEA12x6RelClockMonth-July(7),
    	wtWebioEA12x6RelClockMonth-August(8),
    	wtWebioEA12x6RelClockMonth-September(9),
    	wtWebioEA12x6RelClockMonth-October(10),
    	wtWebioEA12x6RelClockMonth-November(11),
    	wtWebioEA12x6RelClockMonth-December(12)
    	}
    ACCESS read-write
    STATUS mandatory
    DESCRIPTION
        "Date: Month, taking into account the time zone settings."
    ::= { wtWebioEA12x6RelDeviceClock 4 }

wtWebioEA12x6RelClockYear OBJECT-TYPE
    SYNTAX INTEGER (0..65535)
    ACCESS read-write
    STATUS mandatory
    DESCRIPTION
        "Date: Year, taking into account the time zone settings."
    ::= { wtWebioEA12x6RelDeviceClock 5 }

-- wtWebioEA12x6RelNetwork Group
------------------------

wtWebioEA12x6RelIpAddress OBJECT-TYPE
    SYNTAX IpAddress
    ACCESS read-write
    STATUS mandatory
    DESCRIPTION
        "IP address of the Webio"
    ::= { wtWebioEA12x6RelNetwork 1 }

wtWebioEA12x6RelSubnetMask OBJECT-TYPE
    SYNTAX IpAddress
    ACCESS read-write
    STATUS mandatory
    DESCRIPTION
        "Subnet mask of the Webio"
    ::= { wtWebioEA12x6RelNetwork 2 }

wtWebioEA12x6RelGateway OBJECT-TYPE
    SYNTAX IpAddress
    ACCESS read-write
    STATUS mandatory
    DESCRIPTION
        "Gateway of the Webio"
    ::= { wtWebioEA12x6RelNetwork 3 }

wtWebioEA12x6RelDnsServer1 OBJECT-TYPE
    SYNTAX OCTET STRING 
    ACCESS read-write
    STATUS mandatory
    DESCRIPTION
        "IP address of the 1st DNS server in ASCII"
    ::= { wtWebioEA12x6RelNetwork 4 }

wtWebioEA12x6RelDnsServer2 OBJECT-TYPE
    SYNTAX OCTET STRING 
    ACCESS read-write
    STATUS mandatory
    DESCRIPTION
        "IP address of the 2nd DNS server in ASCII"
    ::= { wtWebioEA12x6RelNetwork 5 }

wtWebioEA12x6RelAddConfig OBJECT-TYPE
    SYNTAX OCTET STRING 
    ACCESS read-write
    STATUS mandatory
    DESCRIPTION
        "Additional configuration (1=ON):
        Octet 1: unused
        Octet 2: unused
        Octet 3: unused
        Octet 4:
	        Bit 1: DHCP  enable
	        Bit 0: BOOTP enable"
    ::= { wtWebioEA12x6RelNetwork 6 }

--  wtWebioEA12x6RelHTTP Group
--------------------------------

wtWebioEA12x6RelStartup OBJECT-TYPE
    SYNTAX OCTET STRING 
    ACCESS read-write
    STATUS mandatory
    DESCRIPTION
        "Binary coded start page, more than one page must not be selected:
        Octet 1: unused
        Octet 2: unused
        Octet 3: unused
        Octet 4:
        	Bit 2: user.htm
        	Bit 1: home.htm
	        Bit 0: index.htm"
    ::= { wtWebioEA12x6RelHTTP 1 }

wtWebioEA12x6RelGetHeaderEnable OBJECT-TYPE
    SYNTAX OCTET STRING 
    ACCESS read-write
    STATUS mandatory
    DESCRIPTION
        "If bits are set, every answer of a short form GET question will be lead
        by the IP-address and name of the device (Header) or a HTTP header (HTTP):
        Octet 1: unused
        Octet 2: unused
        Octet 3: unused
        Octet 4:
        	Bit 2-7: unused
        	Bit 1  : GET HTTP enable
                Bit 0  : GET Header enable"
    ::= { wtWebioEA12x6RelHTTP 2 }

wtWebioEA12x6RelHttpInputTrigger OBJECT-TYPE
    SYNTAX OCTET STRING (SIZE (4))
    ACCESS read-write
    STATUS mandatory
    DESCRIPTION
        "Every change on the inputs causes their state to be transmitted to the 
        remote device. To minimize data traffic, individual inputs may be exempted 
        from this rule. Nevertheless every transmission will contain all input bits.
        If a bit is set (1), a change of state on the corresponding input 
        triggers a transmission. If the bit is not set (0), no transmission 
        takes place.
        The OCTETS are interpreted bit-by-bit, with each bit corresponding to an input. 
        Bit 0 corresponds to the LSB.
        OCTET 1: unused
        OCTET 2: unused
        OCTET 3, Bit 0-3: Digital inputs 8-11
                 Bit 4-7: unused
        OCTET 4, Bit 0-7: Digital inputs 0-7"
    ::= { wtWebioEA12x6RelHTTP 3 }

wtWebioEA12x6RelHttpPort OBJECT-TYPE
    SYNTAX INTEGER (1..65534)
    ACCESS read-write
    STATUS mandatory
    DESCRIPTION
       "Definition of the standard HTML port (Default: 80)."
    ::= { wtWebioEA12x6RelHTTP 4 }        
    
    
-- wtWebioEA12x6RelMail Group
--------------------------------

wtWebioEA12x6RelMailAdName OBJECT-TYPE
    SYNTAX OCTET STRING 
    ACCESS read-write
    STATUS mandatory
    DESCRIPTION
        "Device name for mail administration."
    ::= { wtWebioEA12x6RelMail 1 }
    
wtWebioEA12x6RelMailReply OBJECT-TYPE
    SYNTAX OCTET STRING 
    ACCESS read-write
    STATUS mandatory
    DESCRIPTION
        "Reply address for the mail server."
    ::= { wtWebioEA12x6RelMail 2 }
    
wtWebioEA12x6RelMailServer OBJECT-TYPE
    SYNTAX OCTET STRING 
    ACCESS read-write
    STATUS mandatory
    DESCRIPTION
        "Name or IP address of the mail server."
    ::= { wtWebioEA12x6RelMail 3 }
    
wtWebioEA12x6RelMailEnable OBJECT-TYPE
    SYNTAX OCTET STRING 
    ACCESS read-write
    STATUS mandatory
    DESCRIPTION
        "Set this bit to enable the sending of mails:
        Octet 1: unused
        Octet 2: unused
        Octet 3: unused
        Octet 4:
        	Bit 1-7: unused
                Bit 0  : Mail enable"
    ::= { wtWebioEA12x6RelMail 4 }

wtWebioEA12x6RelMailAuthentication OBJECT-TYPE
    SYNTAX OCTET STRING (SIZE (4))
    ACCESS read-write
    STATUS mandatory
    DESCRIPTION
        "Selection of the authentication modi:
        The OCTETS are interpreted bit-by-bit, 
        Bit 0 corresponds to the LSB.
        OCTET 1: unused
        OCTET 2: unused
        OCTET 3: unused
        OCTET 4: Bit 3-7: unused
        	 Bit 2  : POP3 before SMTP
        	 Bit 1  : ESMTP, authentication
        	 Bit 0  : SMTP, no authentication"
    ::= { wtWebioEA12x6RelMail 5 }
    
wtWebioEA12x6RelMailAuthUser OBJECT-TYPE
    SYNTAX OCTET STRING 
    ACCESS read-write
    STATUS mandatory
    DESCRIPTION
        "Name of the user to be authenticated."
    ::= { wtWebioEA12x6RelMail 6 }    
    
wtWebioEA12x6RelMailAuthPassword OBJECT-TYPE
    SYNTAX OCTET STRING 
    ACCESS read-write
    STATUS mandatory
    DESCRIPTION
        "Authentication password."
    ::= { wtWebioEA12x6RelMail 7 }    
    
wtWebioEA12x6RelMailPop3Server OBJECT-TYPE
    SYNTAX OCTET STRING 
    ACCESS read-write
    STATUS mandatory
    DESCRIPTION
        "Name or Ip-address of the POP3 Servers."
    ::= { wtWebioEA12x6RelMail 8 }        
    

--  wtWebioEA12x6RelSnmp Group
--------------------------------

wtWebioEA12x6RelSnmpEnable OBJECT-TYPE
    SYNTAX OCTET STRING 
    ACCESS read-write
    STATUS mandatory
    DESCRIPTION
        "Set bit 0 to enable SNMP.
        If disabled, the device did not respond to any SNMP requests.
        Bit 1 decided wether the community string of read operations 
        is compared with the system password or not:
        Octet 1: unused
        Octet 2: unused
        Octet 3: unused
        Octet 4:
        	Bit 1-7: unused
        	Bit 0  : SNMP enable"
    ::= { wtWebioEA12x6RelSNMP 1 }
    
wtWebioEA12x6RelSnmpCommunityStringRead OBJECT-TYPE
    SYNTAX OCTET STRING
    ACCESS read-write
    STATUS mandatory
    DESCRIPTION
        "Community string read only"
    ::= { wtWebioEA12x6RelSNMP 2 }

wtWebioEA12x6RelSnmpCommunityStringReadWrite OBJECT-TYPE
    SYNTAX OCTET STRING
    ACCESS read-write
    STATUS mandatory
    DESCRIPTION
        "Community string read / write"
    ::= { wtWebioEA12x6RelSNMP 3 }

wtWebioEA12x6RelSnmpSystemTrapManagerIP OBJECT-TYPE
    SYNTAX OCTET STRING 
    ACCESS read-write
    STATUS mandatory
    DESCRIPTION
        "Name or IP address of the TCP server which accepts the system trap."
    ::= { wtWebioEA12x6RelSNMP 4 }
    
wtWebioEA12x6RelSnmpSystemTrapEnable OBJECT-TYPE
    SYNTAX OCTET STRING (SIZE(4))
    ACCESS read-write
    STATUS mandatory
    DESCRIPTION
        "Binary coded trigger conditions:
        Octet 1: unused
        Octet 2: unused
        Octet 3: unused
        Octet 4:
	        Bit 0:   ColdStart
	        Bit 1:   WarmStart
	        Bit 2:   Diag messages
	        Bit 3-7: unused"
    ::= { wtWebioEA12x6RelSNMP 5 }    

-- wtWebioEA12x6RelUdp Group
--------------------------------   

wtWebioEA12x6RelUdpAdminPort OBJECT-TYPE
    SYNTAX INTEGER
    ACCESS read-write
    STATUS mandatory
    DESCRIPTION
        "Udp port to which the Udp queries ( short form GET requests) can be sent. This
        port number must be unique within the device."
    ::= { wtWebioEA12x6RelUDP 1 }

wtWebioEA12x6RelUdpEnable OBJECT-TYPE
    SYNTAX OCTET STRING 
    ACCESS read-write
    STATUS mandatory
    DESCRIPTION
        "Set this bit to enable UDP support:
        Octet 1: unused
        Octet 2: unused
        Octet 3: unused
        Octet 4:
        	Bit 1-7: unused
                Bit 0  : UDP enable"
    ::= { wtWebioEA12x6RelUDP 2 }

wtWebioEA12x6RelUdpRemotePort OBJECT-TYPE
    SYNTAX INTEGER
    ACCESS read-write
    STATUS mandatory
    DESCRIPTION
        "Udp remote port setting.
        If this value is set to zero, the source port read from a request will be used 
        as destination port for the answer.
        A non zero value forced the destination port to this value."
    ::= { wtWebioEA12x6RelUDP 3 }
    
--  wtWebioEA12x6RelBinary Group
--------------------------------

wtWebioEA12x6RelBinaryModeCount OBJECT-TYPE
    SYNTAX INTEGER (1..2)
    ACCESS read-only
    STATUS mandatory
    DESCRIPTION
        "Number of independent binary channels."
    ::= { wtWebioEA12x6RelBinary 1 }
    
-- Binary Interface Table

wtWebioEA12x6RelBinaryIfTable OBJECT-TYPE
    SYNTAX SEQUENCE OF WtWebioEA12x6RelBinaryIfEntry
    ACCESS not-accessible
    STATUS mandatory
    DESCRIPTION
        "Table of indices."
    ::= { wtWebioEA12x6RelBinary 2 }

wtWebioEA12x6RelBinaryIfEntry OBJECT-TYPE
    SYNTAX WtWebioEA12x6RelBinaryIfEntry
    ACCESS not-accessible
    STATUS mandatory
    DESCRIPTION
        "Indices of the binary channels."
    INDEX  { wtWebioEA12x6RelBinaryModeNo }
    ::= { wtWebioEA12x6RelBinaryIfTable 1 }

WtWebioEA12x6RelBinaryIfEntry ::= SEQUENCE {
    wtWebioEA12x6RelBinaryModeNo INTEGER
}

wtWebioEA12x6RelBinaryModeNo OBJECT-TYPE
    SYNTAX INTEGER (1..2)
    ACCESS read-only
    STATUS mandatory
    DESCRIPTION
        "Number of the binary channel."
    ::= { wtWebioEA12x6RelBinaryIfEntry 1 }

-- Binary Table
--------------------------------

wtWebioEA12x6RelBinaryTable OBJECT-TYPE
    SYNTAX SEQUENCE OF WtWebioEA12x6RelBinaryEntry
    ACCESS not-accessible
    STATUS mandatory
    DESCRIPTION
        "Table of properties of the binary mode."
    ::= { wtWebioEA12x6RelBinary 3 }

wtWebioEA12x6RelBinaryEntry OBJECT-TYPE
    SYNTAX WtWebioEA12x6RelBinaryEntry
    ACCESS not-accessible
    STATUS mandatory
    DESCRIPTION
        "Binary properties."
    INDEX  { wtWebioEA12x6RelBinaryModeNo }
    ::= { wtWebioEA12x6RelBinaryTable 1 }

WtWebioEA12x6RelBinaryEntry ::= SEQUENCE {
    wtWebioEA12x6RelBinaryOperationMode			OCTET STRING,
    wtWebioEA12x6RelBinaryTcpServerLocalPort		INTEGER,
    wtWebioEA12x6RelBinaryTcpServerInputTrigger		OCTET STRING,
    wtWebioEA12x6RelBinaryTcpServerApplicationMode	OCTET STRING,
    wtWebioEA12x6RelBinaryTcpClientLocalPort		INTEGER,
    wtWebioEA12x6RelBinaryTcpClientServerPort		INTEGER,
    wtWebioEA12x6RelBinaryTcpClientServerIpAddr		OCTET STRING,
    wtWebioEA12x6RelBinaryTcpClientServerPassword	OCTET STRING,
    wtWebioEA12x6RelBinaryTcpClientInactivity		INTEGER,
    wtWebioEA12x6RelBinaryTcpClientInputTrigger		OCTET STRING,
    wtWebioEA12x6RelBinaryTcpClientInterval		INTEGER,
    wtWebioEA12x6RelBinaryTcpClientApplicationMode	OCTET STRING,
    wtWebioEA12x6RelBinaryUdpPeerLocalPort		INTEGER,
    wtWebioEA12x6RelBinaryUdpPeerRemotePort		INTEGER,
    wtWebioEA12x6RelBinaryUdpPeerRemoteIpAddr		OCTET STRING,
    wtWebioEA12x6RelBinaryUdpPeerInputTrigger		OCTET STRING,
    wtWebioEA12x6RelBinaryUdpPeerInterval		INTEGER,
    wtWebioEA12x6RelBinaryUdpPeerApplicationMode	OCTET STRING,
    wtWebioEA12x6RelBinaryConnectedPort			INTEGER,
    wtWebioEA12x6RelBinaryConnectedIpAddr		IpAddress,
    wtWebioEA12x6RelBinaryTcpServerClientHttpPort	INTEGER,
    wtWebioEA12x6RelBinaryTcpClientServerHttpPort	INTEGER
    
}

wtWebioEA12x6RelBinaryOperationMode OBJECT-TYPE
    SYNTAX OCTET STRING (SIZE (4))
    ACCESS read-write
    STATUS mandatory
    DESCRIPTION
        "Selection of the operation mode:
        The OCTETS are interpreted bit-by-bit,
        Bit 0 corresponds to the LSB.
        OCTET 1: unused
        OCTET 2: unused
        OCTET 3: unused
        OCTET 4: Bit 3-7: unused
        	 Bit 2  : UDP Peer
        	 Bit 1  : TCP Client
        	 Bit 0  : TCP Server"
    ::= { wtWebioEA12x6RelBinaryEntry 1 }

wtWebioEA12x6RelBinaryTcpServerLocalPort OBJECT-TYPE
    SYNTAX INTEGER (1..65535)
    ACCESS read-write
    STATUS mandatory
    DESCRIPTION
        "Local TCP port for data exchange in this server mode.
        This port number must be unique within the device.
	Reserved port number must not be used (refere to the manual)."
    ::= { wtWebioEA12x6RelBinaryEntry 2 }

wtWebioEA12x6RelBinaryTcpServerInputTrigger OBJECT-TYPE
    SYNTAX OCTET STRING (SIZE (4))
    ACCESS read-write
    STATUS mandatory
    DESCRIPTION
        "Every change on the inputs causes their state to be transmitted to the 
        remote device. To minimize data traffic, individual inputs may be exempted 
        from this rule. Nevertheless every transmission will contain all input bits.
        If a bit is set (1), a change of state on the corresponding input 
        triggers a transmission. If the bit is not set (0), no transmission 
        takes place.
        The OCTETS are interpreted bit-by-bit, with each bit corresponding to an input. 
        Bit 0 corresponds to the LSB.
        OCTET 1: unused
        OCTET 2: unused
        OCTET 3, Bit 0-3: Digital inputs 8-11
                 Bit 4-7: unused
        OCTET 4, Bit 0-7: Digital inputs 0-7"
    ::= { wtWebioEA12x6RelBinaryEntry 3 }

wtWebioEA12x6RelBinaryTcpServerApplicationMode OBJECT-TYPE
    SYNTAX OCTET STRING (SIZE (4))
    ACCESS read-write
    STATUS mandatory
    DESCRIPTION
        "Selection of the application mode:
        The OCTETS are interpreted bit-by-bit,
        Bit 0 corresponds to the LSB.
        OCTET 1: unused
        OCTET 2: unused
        OCTET 3: unused
        OCTET 4: Bit 4-7: unused
        	 Bit 3  : OPC Device
        	 Bit 2  : Box2Box Slave
        	 Bit 1  : Compatible 50xxx
        	 Bit 0  : Default"
    ::= { wtWebioEA12x6RelBinaryEntry 4 }
    
wtWebioEA12x6RelBinaryTcpClientLocalPort OBJECT-TYPE
    SYNTAX INTEGER (1..65535)
    ACCESS read-write
    STATUS mandatory
    DESCRIPTION
        "Local TCP port for data exchange in this client mode.
        This port number must be unique within the device.
	Reserved port number must not be used (refere to the manual)."
    ::= { wtWebioEA12x6RelBinaryEntry 5 }

wtWebioEA12x6RelBinaryTcpClientServerPort OBJECT-TYPE
    SYNTAX INTEGER (1..65535)
    ACCESS read-write
    STATUS mandatory
    DESCRIPTION
        "Port number of the server. A complete set of port number, IP address
        and a valid input/output mask starts this mode.
        No data exchange take place when setting the server port to zero."
    ::= { wtWebioEA12x6RelBinaryEntry 6 }

wtWebioEA12x6RelBinaryTcpClientServerIpAddr OBJECT-TYPE
    SYNTAX OCTET STRING
    ACCESS read-write
    STATUS mandatory
    DESCRIPTION
        "Ip address of the server. A complete set of port number, IP address
        and a valid input/output mask starts this mode.
        No data exchange take place when setting the server IP address to 0.0.0.0."
    ::= { wtWebioEA12x6RelBinaryEntry 7 }

wtWebioEA12x6RelBinaryTcpClientServerPassword OBJECT-TYPE
    SYNTAX OCTET STRING
    ACCESS read-write
    STATUS mandatory
    DESCRIPTION
        "Building a connection may be protected by the 
        administrator password of the server. Enter the server password
        to establish the connection, if a server administrator password
        exists."
    ::= { wtWebioEA12x6RelBinaryEntry 8 }

wtWebioEA12x6RelBinaryTcpClientInactivity OBJECT-TYPE
    SYNTAX INTEGER 
    ACCESS read-write
    STATUS mandatory
    DESCRIPTION
        "Connection timeout in 100ms. If no data are exchanged within the specified  
        time, the device closes the connection to the server.
        The value 0 deactivates the timer. Using the Box2Box mode this function is
        disabled."
    ::= { wtWebioEA12x6RelBinaryEntry 9 }
    
wtWebioEA12x6RelBinaryTcpClientInputTrigger OBJECT-TYPE
    SYNTAX OCTET STRING (SIZE (4))
    ACCESS read-write
    STATUS mandatory
    DESCRIPTION
        "Every change on the inputs causes their state to be transmitted to the 
        remote device. To minimize data traffic, individual inputs may be exempted 
        from this rule. Nevertheless every transmission will contain all input bits.
        If a bit is set (1), a change of state on the corresponding input 
        triggers a transmission. If the bit is not set (0), no transmission 
        takes place.
        The OCTETS are interpreted bit-by-bit, with each bit corresponding to an input. 
        Bit 0 corresponds to the LSB.
        OCTET 1: unused
        OCTET 2: unused
        OCTET 3, Bit 0-3: Digital inputs 8-11
                 Bit 4-7: unused
        OCTET 4, Bit 0-7: Digital inputs 0-7"
    ::= { wtWebioEA12x6RelBinaryEntry 10 }
 
wtWebioEA12x6RelBinaryTcpClientInterval OBJECT-TYPE
    SYNTAX INTEGER (0..65535)
    ACCESS read-write
    STATUS mandatory
    DESCRIPTION
        "Configurable interval with a 100ms base, in which the Webio device sends
        data to the configured application. A interval of zero stopps the 
        periodical sending."
    ::= { wtWebioEA12x6RelBinaryEntry 11 }

wtWebioEA12x6RelBinaryTcpClientApplicationMode OBJECT-TYPE
    SYNTAX OCTET STRING (SIZE (4))
    ACCESS read-write
    STATUS mandatory
    DESCRIPTION
        "Selection of the application mode:
        The OCTETS are interpreted bit-by-bit,
        Bit 0 corresponds to the LSB.
        OCTET 1: unused
        OCTET 2: unused
        OCTET 3: unused
        OCTET 4: Bit 3-7: unused
        	 Bit 2  : Box2Box Slave
        	 Bit 1  : Compatible 50xxx
        	 Bit 0  : Default"
    ::= { wtWebioEA12x6RelBinaryEntry 12 }

wtWebioEA12x6RelBinaryUdpPeerLocalPort OBJECT-TYPE
    SYNTAX INTEGER (1..65535)
    ACCESS read-write
    STATUS mandatory
    DESCRIPTION
        "Local UDP port for data exchange in this peer to peer mode.
        This port number must be unique within the device.
	Reserved port number must not be used (refere to the manual)."
    ::= { wtWebioEA12x6RelBinaryEntry 13 }

wtWebioEA12x6RelBinaryUdpPeerRemotePort OBJECT-TYPE
    SYNTAX INTEGER (1..65535)
    ACCESS read-write
    STATUS mandatory
    DESCRIPTION
        "Port number of the remote device. A complete set of port number, IP address
        and a valid input/output mask starts this mode.
        No data exchange take place when setting the remote port to zero."
    ::= { wtWebioEA12x6RelBinaryEntry 14 }

wtWebioEA12x6RelBinaryUdpPeerRemoteIpAddr OBJECT-TYPE
    SYNTAX OCTET STRING
    ACCESS read-write
    STATUS mandatory
    DESCRIPTION
        "Ip address of the remote device. A complete set of port number, IP address
        and a valid input/output mask starts this mode.
        No data exchange take place when setting the remote device IP address to 0.0.0.0."
    ::= { wtWebioEA12x6RelBinaryEntry 15 }

wtWebioEA12x6RelBinaryUdpPeerInputTrigger OBJECT-TYPE
    SYNTAX OCTET STRING (SIZE (4))
    ACCESS read-write
    STATUS mandatory
    DESCRIPTION
        "Every change on the inputs causes their state to be transmitted to the 
        remote device. To minimize data traffic, individual inputs may be exempted 
        from this rule. Nevertheless every transmission will contain all input bits.
        If a bit is set (1), a change of state on the corresponding input 
        triggers a transmission. If the bit is not set (0), no transmission 
        takes place.
        The OCTETS are interpreted bit-by-bit, with each bit corresponding to an input. 
        Bit 0 corresponds to the LSB.
        OCTET 1: unused
        OCTET 2: unused
        OCTET 3, Bit 0-3: Digital inputs 8-11
                 Bit 4-7: unused
        OCTET 4, Bit 0-7: Digital inputs 0-7"
    ::= { wtWebioEA12x6RelBinaryEntry 16 }

wtWebioEA12x6RelBinaryUdpPeerInterval OBJECT-TYPE
    SYNTAX INTEGER (0..65535)
    ACCESS read-write
    STATUS mandatory
    DESCRIPTION
        "Configurable interval with a 100ms base, in which the Webio device sends
        data to the configured remote device. A interval of zero stopps the 
        periodical sending."
    ::= { wtWebioEA12x6RelBinaryEntry 17 }

wtWebioEA12x6RelBinaryUdpPeerApplicationMode OBJECT-TYPE
    SYNTAX OCTET STRING (SIZE (4))
    ACCESS read-write
    STATUS mandatory
    DESCRIPTION
        "Selection of the application mode:
        The OCTETS are interpreted bit-by-bit,
        Bit 0 corresponds to the LSB.
        OCTET 1: unused
        OCTET 2: unused
        OCTET 3: unused
        OCTET 4: Bit 3-7: unused
        	 Bit 2  : Box2Box Slave
        	 Bit 1  : Compatible 50xxx
        	 Bit 0  : Default"
    ::= { wtWebioEA12x6RelBinaryEntry 18 }

wtWebioEA12x6RelBinaryConnectedPort OBJECT-TYPE
    SYNTAX INTEGER (1..65535)
    ACCESS read-only
    STATUS mandatory
    DESCRIPTION
        "Port number of the remote device, after connection has been established.
        In case of no connection or missing port informations a zero will be read."
    ::= { wtWebioEA12x6RelBinaryEntry 19 }

wtWebioEA12x6RelBinaryConnectedIpAddr OBJECT-TYPE
    SYNTAX IpAddress
    ACCESS read-only
    STATUS mandatory
    DESCRIPTION
        "IP address of the remote device, after connection has been established.
        In case of no connection or missing port informations 0.0.0.0 will be read."
    ::= { wtWebioEA12x6RelBinaryEntry 20 } 

wtWebioEA12x6RelBinaryTcpServerClientHttpPort OBJECT-TYPE
    SYNTAX INTEGER (1..65535)
    ACCESS read-write
    STATUS mandatory
    DESCRIPTION
        "HTTP port number of the remote device at TCP Server Mode. If an mailfunction occurs 
        status informations will be send to this port. 
        Not used at mode Compatible 50xxx."
    ::= { wtWebioEA12x6RelBinaryEntry 21 }
    
wtWebioEA12x6RelBinaryTcpClientServerHttpPort OBJECT-TYPE
    SYNTAX INTEGER (1..65535)
    ACCESS read-write
    STATUS mandatory
    DESCRIPTION
        "HTTP port number of the remote device at TCP Client Mode. In the operating mode
        Box2Box connection status informations will be exchanged through this port."
    ::= { wtWebioEA12x6RelBinaryEntry 22 }            
    
--  wtWebioEA12x6RelSyslog Group
--------------------------------
    
wtWebioEA12x6RelSyslogServerIP OBJECT-TYPE
    SYNTAX OCTET STRING 
    ACCESS read-write
    STATUS mandatory
    DESCRIPTION
        "Name or IP address of the Syslog server, which accepts the Syslog messgaes."
    ::= { wtWebioEA12x6RelSyslog 1 }
    
wtWebioEA12x6RelSyslogServerPort OBJECT-TYPE
    SYNTAX INTEGER
    ACCESS read-write
    STATUS mandatory
    DESCRIPTION
        "Portnumber of the Syslog servers, default 514."
    ::= { wtWebioEA12x6RelSyslog 2 }

wtWebioEA12x6RelSyslogSystemMessagesEnable OBJECT-TYPE
    SYNTAX OCTET STRING (SIZE(4))
    ACCESS read-write
    STATUS mandatory
    DESCRIPTION
        "Binary coded trigger conditions:
        Octet 1: unused
        Octet 2: unused
        Octet 3: unused
        Octet 4:
	        Bit 0:   ColdStart
	        Bit 1:   WarmStart
	        Bit 2:   Diag Messages
	        Bit 3-7: unused"
    ::= { wtWebioEA12x6RelSyslog 3 }    

wtWebioEA12x6RelSyslogEnable OBJECT-TYPE
    SYNTAX OCTET STRING 
    ACCESS read-write
    STATUS mandatory
    DESCRIPTION
        "Set bit 0to enable Syslog:
        Octet 1: unused
        Octet 2: unused
        Octet 3: unused
        Octet 4:
        	Bit 1-7: unused
                Bit 0  : Syslog enable"
    ::= { wtWebioEA12x6RelSyslog 4 }

--  wtWebioEA12x6RelFTP Group
--------------------------------

wtWebioEA12x6RelFTPServerIP OBJECT-TYPE
    SYNTAX OCTET STRING 
    ACCESS read-write
    STATUS mandatory
    DESCRIPTION
        "Name or IP address of the FTP server, which accepts the FTP messages."
    ::= { wtWebioEA12x6RelFTP 1 }
    
wtWebioEA12x6RelFTPServerControlPort OBJECT-TYPE
    SYNTAX INTEGER
    ACCESS read-write
    STATUS mandatory
    DESCRIPTION
        "Portnumber of the control port of the FTP server, default 21."
    ::= { wtWebioEA12x6RelFTP 2 }
    
wtWebioEA12x6RelFTPUserName OBJECT-TYPE
    SYNTAX OCTET STRING 
    ACCESS read-write
    STATUS mandatory
    DESCRIPTION
        "FTP Loggin: user name."
    ::= { wtWebioEA12x6RelFTP 3 }
    
wtWebioEA12x6RelFTPPassword OBJECT-TYPE
    SYNTAX OCTET STRING 
    ACCESS read-write
    STATUS mandatory
    DESCRIPTION
        "FTP Loggin: user password."
    ::= { wtWebioEA12x6RelFTP 4 }

wtWebioEA12x6RelFTPAccount OBJECT-TYPE
    SYNTAX OCTET STRING 
    ACCESS read-write
    STATUS mandatory
    DESCRIPTION
        "FTP Loggin: name of account."
    ::= { wtWebioEA12x6RelFTP 5 }

wtWebioEA12x6RelFTPOption OBJECT-TYPE
    SYNTAX OCTET STRING 
    ACCESS read-write
    STATUS mandatory
    DESCRIPTION
        "Bit 0 switches the FTP Server in Passiv-Mode,
        the Client controls the data connection on its own:
        Octet 1: unused
        Octet 2: unused
        Octet 3: unused
        Octet 4:
        	Bit 1-7: unused
                Bit 0  : PASV enable"
    ::= { wtWebioEA12x6RelFTP 6 }
    
wtWebioEA12x6RelFTPEnable OBJECT-TYPE
    SYNTAX OCTET STRING 
    ACCESS read-write
    STATUS mandatory
    DESCRIPTION
        "Set Bit 0 to enable FTP:
        Octet 1: unused
        Octet 2: unused
        Octet 3: unused
        Octet 4:
        	Bit 1-7: unused
                Bit 0  : FTP enable"
    ::= { wtWebioEA12x6RelFTP 7 }  
    
--  wtWebioEA12x6RelOutputMode Group
--------------------------------

-- OutputMode Table

wtWebioEA12x6RelOutputModeTable OBJECT-TYPE
    SYNTAX SEQUENCE OF WtWebioEA12x6RelOutputModeEntry
    ACCESS not-accessible
    STATUS mandatory
    DESCRIPTION
        "Table of output mode configurations dependent on the output indices."
    ::= { wtWebioEA12x6RelOutputMode 1 }

wtWebioEA12x6RelOutputModeEntry OBJECT-TYPE
    SYNTAX WtWebioEA12x6RelOutputModeEntry
    ACCESS not-accessible
    STATUS mandatory
    DESCRIPTION
        "Output mode configurations of the individual outputs."
    INDEX  { wtWebioEA12x6RelOutputNo }
    ::= { wtWebioEA12x6RelOutputModeTable 1 }

WtWebioEA12x6RelOutputModeEntry ::= SEQUENCE {
    wtWebioEA12x6RelOutputModeBit	OCTET STRING
}

wtWebioEA12x6RelOutputModeBit OBJECT-TYPE
    SYNTAX OCTET STRING (SIZE (4))
    ACCESS read-write
    STATUS mandatory
    DESCRIPTION
        "This binary coded output mode defines the individual operation mode for any
        output. More than one mode must not be selected.
        The OCTETS are interpreted bit-by-bit, with each set of octets corresponding to an output. 
        Bit 0 corresponds to the LSB.
        OCTET 1: unused
        OCTET 2: unused
        OCTET 3: unused
        OCTET 4: Bit 6-7: unused
        	 Bit 5  : Logic
        	 Bit 4  : Binary 2
        	 Bit 3  : Binary 1
        	 Bit 2  : SNMP
        	 Bit 1  : UDP ASCII
        	 Bit 0  : HTTP"
    ::= { wtWebioEA12x6RelOutputModeEntry 1 }
    
wtWebioEA12x6RelSafetyTimeout OBJECT-TYPE
    SYNTAX INTEGER (0..65535)
    ACCESS read-write
    STATUS mandatory
    DESCRIPTION
        "After this period of time (multiple of 100ms) without receiving data
        outputs switch to their Safety States. For each output a independend safety state
        could be defined."
    ::= { wtWebioEA12x6RelOutputMode 2 }
 
     
-- wtWebioEA12x6RelAlarm Group
----------------------------

wtWebioEA12x6RelAlarmCount OBJECT-TYPE
    SYNTAX INTEGER (1..12)
    ACCESS read-only
    STATUS mandatory
    DESCRIPTION
        "Number of independent alarms."
    ::= { wtWebioEA12x6RelAlarm 1 }
    
-- Alarm Interface Table

wtWebioEA12x6RelAlarmIfTable OBJECT-TYPE
    SYNTAX SEQUENCE OF WtWebioEA12x6RelAlarmIfEntry
    ACCESS not-accessible
    STATUS mandatory
    DESCRIPTION
        "List of alarm indices."
    ::= { wtWebioEA12x6RelAlarm 2 }

wtWebioEA12x6RelAlarmIfEntry OBJECT-TYPE
    SYNTAX WtWebioEA12x6RelAlarmIfEntry
    ACCESS not-accessible
    STATUS mandatory
    DESCRIPTION
        "Numbers of the alarms."
    INDEX  { wtWebioEA12x6RelAlarmNo }
    ::= { wtWebioEA12x6RelAlarmIfTable 1 }

WtWebioEA12x6RelAlarmIfEntry ::= SEQUENCE {
    wtWebioEA12x6RelAlarmNo INTEGER
}

wtWebioEA12x6RelAlarmNo OBJECT-TYPE
    SYNTAX INTEGER (1..12)
    ACCESS read-only
    STATUS mandatory
    DESCRIPTION
        "Numbers of the alarms."
    ::= { wtWebioEA12x6RelAlarmIfEntry 1 }

-- Alarm Table

wtWebioEA12x6RelAlarmTable OBJECT-TYPE
    SYNTAX SEQUENCE OF WtWebioEA12x6RelAlarmEntry
    ACCESS not-accessible
    STATUS mandatory
    DESCRIPTION
        "List of settings depending on the alarm number."
    ::= { wtWebioEA12x6RelAlarm 3 }

wtWebioEA12x6RelAlarmEntry OBJECT-TYPE
    SYNTAX WtWebioEA12x6RelAlarmEntry
    ACCESS not-accessible
    STATUS mandatory
    DESCRIPTION
        "Alarm parameters of the individual alarms."
    INDEX  { wtWebioEA12x6RelAlarmNo }
    ::= { wtWebioEA12x6RelAlarmTable 1 }

WtWebioEA12x6RelAlarmEntry ::= SEQUENCE {
    wtWebioEA12x6RelAlarmInputTrigger		OCTET STRING,
    wtWebioEA12x6RelAlarmOutputTrigger		OCTET STRING,
    wtWebioEA12x6RelAlarmSystemTrigger		OCTET STRING,
    wtWebioEA12x6RelAlarmMaxCounterValue	OCTET STRING,
    wtWebioEA12x6RelAlarmInterval		OCTET STRING,
    wtWebioEA12x6RelAlarmEnable			OCTET STRING,
    wtWebioEA12x6RelAlarmMailAddr		OCTET STRING,
    wtWebioEA12x6RelAlarmMailSubject		OCTET STRING,
    wtWebioEA12x6RelAlarmMailText		OCTET STRING,
    wtWebioEA12x6RelAlarmSnmpManagerIP		OCTET STRING,
    wtWebioEA12x6RelAlarmSnmpTrapText		OCTET STRING,
    wtWebioEA12x6RelAlarmUdpIpAddr		OCTET STRING,
    wtWebioEA12x6RelAlarmUdpPort		INTEGER,
    wtWebioEA12x6RelAlarmUdpText		OCTET STRING,
    wtWebioEA12x6RelAlarmTcpIpAddr		OCTET STRING,
    wtWebioEA12x6RelAlarmTcpPort		INTEGER,
    wtWebioEA12x6RelAlarmTcpText		OCTET STRING,    
    wtWebioEA12x6RelAlarmSyslogIpAddr		OCTET STRING,
    wtWebioEA12x6RelAlarmSyslogPort		INTEGER,
    wtWebioEA12x6RelAlarmSyslogText		OCTET STRING,
    wtWebioEA12x6RelAlarmFtpDataPort		OCTET STRING,
    wtWebioEA12x6RelAlarmFtpFileName		OCTET STRING,
    wtWebioEA12x6RelAlarmFtpText		OCTET STRING,
    wtWebioEA12x6RelAlarmFtpOption		OCTET STRING,
    wtWebioEA12x6RelAlarmTimerCron		OCTET STRING,

    wtWebioEA12x6RelAlarmMailReleaseSubject	OCTET STRING,
    wtWebioEA12x6RelAlarmMailReleaseText	OCTET STRING,
    wtWebioEA12x6RelAlarmSnmpTrapReleaseText	OCTET STRING,
    wtWebioEA12x6RelAlarmUdpReleaseText		OCTET STRING,
    wtWebioEA12x6RelAlarmTcpReleaseText		OCTET STRING,    
    wtWebioEA12x6RelAlarmSyslogReleaseText	OCTET STRING,
    wtWebioEA12x6RelAlarmFtpReleaseText		OCTET STRING        
    
}

wtWebioEA12x6RelAlarmInputTrigger OBJECT-TYPE
    SYNTAX OCTET STRING (SIZE(12))
    ACCESS read-write
    STATUS mandatory
    DESCRIPTION
        "This variable allows setting of individual input trigger conditions. 
        The OCTETS are interpreted bit-by-bit, with each bit corresponding to an input. 
        Bit 0 corresponds to the LSB.
	The first four OCTETS contain the mask which determines which of the inputs are to 
	be considered (corresponding bit = 1) and which inputs are to ignore 
	(corresponding bit = 0):
	OCTET 1 : unused
	OCTET 2 : unused
	OCTET 3, Bit 0-3: Mask for digital inputs 8-11
		 Bit 4-7: unused
	OCTET 4, Bit 0-7: Mask for digital inputs 0-7
	
	OCTETS 5-8 contain the level (1=HIGH, 0=LOW) which the inputs 
	should assume:
	OCTET 5 : unused
	OCTET 6 : unused
	OCTET 7, Bit 0-3: Level of digital inputs 8-11
		 Bit 4-7: unused
        OCTET 8, Bit 0-7: Level of digital inputs 0-7
        
	OCTETS 9-12 contain the ANY bit (1=ON, 0=OFF). Inputs masked with the any bit trigger with any change 
	of the corresponding input bit. Settings in OCTET 5-9 are then unused:
	OCTET 9 : unused
	OCTET 11, Bit 0-7   : ANY bits of digital inputs 8-11
		  Bit 12-15 : unused
	OCTET 12, Bit 0-7   : ANY bits of digital inputs 0-7"
        
    ::= { wtWebioEA12x6RelAlarmEntry 1 }

wtWebioEA12x6RelAlarmOutputTrigger OBJECT-TYPE
    SYNTAX OCTET STRING (SIZE(12))
    ACCESS read-write
    STATUS mandatory
    DESCRIPTION
        "This variable allows setting of individual output trigger conditions. 
        The OCTETS are interpreted bit-by-bit, with each bit corresponding to an output. 
        Bit 0 corresponds to the LSB.
	The first four OCTETS contain the mask which determines which of the outputs are to 
	be considered (corresponding bit = 1) and which outputs are to ignore 
	(corresponding bit = 0):
	OCTET 1 : unused
	OCTET 2 : unused
	OCTET 3 : unused
	OCTET 4, Bit 0-5: Mask for digital outputs 0-5
	
	OCTETS 5-8 contain the level (1=HIGH, 0=LOW) which the outputs 
	should assume:
	OCTET 5 : unused
	OCTET 6 : unused
	OCTET 7 : unused
        OCTET 8, Bit 0-5: Level of digital outputs 0-5

	OCTETS 9-12 contain the ANY bit (1=ON, 0=OFF). Outputs masked with the any bit trigger with any change 
	of the corresponding output bit. Settings in OCTET 5-9 are then unused:
	OCTET 9 : unused
	OCTET 10: unused
	OCTET 11: unused
	OCTET 12: Bit 0-5: ANY bits of digital outputs 0-5"
        
    ::= { wtWebioEA12x6RelAlarmEntry 2 }
    
wtWebioEA12x6RelAlarmSystemTrigger OBJECT-TYPE
    SYNTAX OCTET STRING (SIZE(4))
    ACCESS read-write
    STATUS mandatory
    DESCRIPTION
        "Binary coded trigger conditions:
        The OCTETS are interpreted bit-by-bit.
        Bit 0 corresponds to the LSB.
        OCTET 1: unused
        OCTET 2: unused
        OCTET 3: unused
        OCTET 4, 
        	 Bit 4-7: unused
        	 Bit 3  : Warm Start
        	 Bit 2  : Cold Start
        	 Bit 1  : Timer
        	 Bit 0  : Load Control"
    ::= { wtWebioEA12x6RelAlarmEntry 3 }

wtWebioEA12x6RelAlarmMaxCounterValue OBJECT-TYPE
    SYNTAX OCTET STRING 
    ACCESS read-write
    STATUS mandatory
    DESCRIPTION
        "This variable configures a max. counter value. If an input counter value
        exceeds this max. value, the corresponding alarm is triggered. Input counters with
        its mask bit unset in wtWebioEA12x6RelAlarmInputTrigger are not considered."
    ::= { wtWebioEA12x6RelAlarmEntry 4 }

wtWebioEA12x6RelAlarmInterval OBJECT-TYPE
    SYNTAX OCTET STRING 
    ACCESS read-write
    STATUS mandatory
    DESCRIPTION
        "Send interval for alarm messages."
    ::= { wtWebioEA12x6RelAlarmEntry 5 }

wtWebioEA12x6RelAlarmEnable OBJECT-TYPE
    SYNTAX OCTET STRING (SIZE(4))
    ACCESS read-write
    STATUS mandatory
    DESCRIPTION
        "Binary coded alarm enable:
        Octet 1: unused
        Octet 2: unused
        Octet 3: unused
        Octet 4:
		Bit 0:	Mail Enable
        	Bit 1:	SNMP Trap enable
        	Bit 2:  UDP enable
        	Bit 3:  Send inputs to pending TCP connections
        	Bit 4:  TCP Client enable
        	Bit 5:	Syslog Messages enable
        	Bit 6-7: unused"
    ::= { wtWebioEA12x6RelAlarmEntry 6 }

wtWebioEA12x6RelAlarmMailAddr OBJECT-TYPE
    SYNTAX OCTET STRING 
    ACCESS read-write
    STATUS mandatory
    DESCRIPTION
        "E-Mail address for sending the alarm mail to."
    ::= { wtWebioEA12x6RelAlarmEntry 7 }

wtWebioEA12x6RelAlarmMailSubject OBJECT-TYPE
    SYNTAX OCTET STRING 
    ACCESS read-write
    STATUS mandatory
    DESCRIPTION
        "Subject line for alarm mail."
    ::= { wtWebioEA12x6RelAlarmEntry 8 }

wtWebioEA12x6RelAlarmMailText OBJECT-TYPE
    SYNTAX OCTET STRING 
    ACCESS read-write
    STATUS mandatory
    DESCRIPTION
        "Alarm mail text: 
        States of the Webio device can be included by using special tags.
        Please refer to the respective Webio manual"
    ::= { wtWebioEA12x6RelAlarmEntry 9 }

wtWebioEA12x6RelAlarmSnmpManagerIP OBJECT-TYPE
    SYNTAX OCTET STRING 
    ACCESS read-write
    STATUS mandatory
    DESCRIPTION
        "IP address of the SNMP Manager to which the Webio device should send SNMP traps."
    ::= { wtWebioEA12x6RelAlarmEntry 10 }

wtWebioEA12x6RelAlarmSnmpTrapText OBJECT-TYPE
    SYNTAX OCTET STRING 
    ACCESS read-write
    STATUS mandatory
    DESCRIPTION
        "This text appears in the trap body."
    ::= { wtWebioEA12x6RelAlarmEntry 11 }
    
wtWebioEA12x6RelAlarmUdpIpAddr OBJECT-TYPE
    SYNTAX OCTET STRING 
    ACCESS read-write
    STATUS mandatory
    DESCRIPTION
        "IP address of the UDP listener to which the Webio device should send UDP traps."
    ::= { wtWebioEA12x6RelAlarmEntry 12 }    

wtWebioEA12x6RelAlarmUdpPort OBJECT-TYPE
    SYNTAX INTEGER (1..65535) 
    ACCESS read-write
    STATUS mandatory
    DESCRIPTION
        "Port number of the UDP listener to which the Webio device should send UDP traps."
    ::= { wtWebioEA12x6RelAlarmEntry 13 }    

wtWebioEA12x6RelAlarmUdpText OBJECT-TYPE
    SYNTAX OCTET STRING 
    ACCESS read-write
    STATUS mandatory
    DESCRIPTION
        "This text appears in the UDP trap body."
    ::= { wtWebioEA12x6RelAlarmEntry 14 }
    
wtWebioEA12x6RelAlarmTcpIpAddr OBJECT-TYPE
    SYNTAX OCTET STRING
    ACCESS read-write
    STATUS mandatory
    DESCRIPTION
        "IP address of the TCP listener to which the Webio device should send TCP traps."
    ::= { wtWebioEA12x6RelAlarmEntry 15 }    

wtWebioEA12x6RelAlarmTcpPort OBJECT-TYPE
    SYNTAX INTEGER (1..65535) 
    ACCESS read-write
    STATUS mandatory
    DESCRIPTION
        "Port number of the TCP listener to which the Webio device should send TCP traps."
    ::= { wtWebioEA12x6RelAlarmEntry 16 }    

wtWebioEA12x6RelAlarmTcpText OBJECT-TYPE
    SYNTAX OCTET STRING 
    ACCESS read-write
    STATUS mandatory
    DESCRIPTION
        "This text appears in the TCP trap body."
    ::= { wtWebioEA12x6RelAlarmEntry 17 }

wtWebioEA12x6RelAlarmSyslogIpAddr OBJECT-TYPE
    SYNTAX OCTET STRING 
    ACCESS read-write
    STATUS mandatory
    DESCRIPTION
        "IP address of the syslog server to which the Webio device should send syslog messages."
    ::= { wtWebioEA12x6RelAlarmEntry 18 }    

wtWebioEA12x6RelAlarmSyslogPort OBJECT-TYPE
    SYNTAX INTEGER (1..65535) 
    ACCESS read-write
    STATUS mandatory
    DESCRIPTION
        "Port number of the syslog server to which the Webio device should send syslog messages."
    ::= { wtWebioEA12x6RelAlarmEntry 19 }    

wtWebioEA12x6RelAlarmSyslogText OBJECT-TYPE
    SYNTAX OCTET STRING 
    ACCESS read-write
    STATUS mandatory
    DESCRIPTION
        "Every message starts with the priority key, a time stamp and the host ip address, according RFC3164.
        This text appears in the following syslog message body."
    ::= { wtWebioEA12x6RelAlarmEntry 20 }    
    
wtWebioEA12x6RelAlarmFtpDataPort OBJECT-TYPE
    SYNTAX OCTET STRING 
    ACCESS read-write
    STATUS mandatory
    DESCRIPTION
        "Local data port: 1..65535 or AUTO: the next free port will be assigned."
    ::= { wtWebioEA12x6RelAlarmEntry 21 }
    
wtWebioEA12x6RelAlarmFtpFileName OBJECT-TYPE
    SYNTAX OCTET STRING 
    ACCESS read-write
    STATUS mandatory
    DESCRIPTION
        "Name of the file including path informations."
    ::= { wtWebioEA12x6RelAlarmEntry 22 }
    
wtWebioEA12x6RelAlarmFtpText OBJECT-TYPE
    SYNTAX OCTET STRING 
    ACCESS read-write
    STATUS mandatory
    DESCRIPTION
        "Message text to store on the FTP server."
    ::= { wtWebioEA12x6RelAlarmEntry 23 }

wtWebioEA12x6RelAlarmFtpOption OBJECT-TYPE
    SYNTAX OCTET STRING (SIZE(4))
    ACCESS read-write
    STATUS mandatory
    DESCRIPTION
        "Binary coded options, select only one option at the same time:
        STORE  = replace file
        APPEND = append message at the end of the file
        
        Octet 1: unused
        Octet 2: unused
        Octet 3: unused
        Octet 4:
		Bit 0  :	STORE
		Bit 1  :	APPEND
        	Bit 2-7:	unused"
    ::= { wtWebioEA12x6RelAlarmEntry 24 }      
    
wtWebioEA12x6RelAlarmTimerCron OBJECT-TYPE
    SYNTAX OCTET STRING
    ACCESS read-write
    STATUS mandatory
    DESCRIPTION
        "This entry contains 5 space or tab seperated text fields for time trigger definition.
        Each field must match with the actual time to trigger a message, weekday and day of month
        are interpreted separatley.
        1: Minutes	Range 0-59
        2. Hours	Range 0-23, 0 is midnight
        3: Day of month	Range 1-31
        4: Month	Range 1-12
        5: Weekday	Range 0-6, 0 is sunday
        
        Syntax for every field:
         - an asterix (*) enables every possible setting of a field
         - single numbers seperated by commas
         - a partition within the allowed range (1-5)
         - step size within an partition of the allowed range (0-59/2: every second minute)."
    ::= { wtWebioEA12x6RelAlarmEntry 25 }      


wtWebioEA12x6RelAlarmMailReleaseSubject OBJECT-TYPE
    SYNTAX OCTET STRING 
    ACCESS read-write
    STATUS mandatory
    DESCRIPTION
       "Subject line for alarm mail."
    ::= { wtWebioEA12x6RelAlarmEntry 26 }

wtWebioEA12x6RelAlarmMailReleaseText OBJECT-TYPE
    SYNTAX OCTET STRING 
    ACCESS read-write
    STATUS mandatory
    DESCRIPTION
        "Release Alarm mail text: 
        States of the Webio device can be included by using special tags.
        Please refer to the respective Webio manual"
    ::= { wtWebioEA12x6RelAlarmEntry 27 }    

wtWebioEA12x6RelAlarmSnmpTrapReleaseText OBJECT-TYPE
    SYNTAX OCTET STRING 
    ACCESS read-write
    STATUS mandatory
    DESCRIPTION
        "This text appears in the trap body."
    ::= { wtWebioEA12x6RelAlarmEntry 28 }

wtWebioEA12x6RelAlarmUdpReleaseText OBJECT-TYPE
    SYNTAX OCTET STRING 
    ACCESS read-write
    STATUS mandatory
    DESCRIPTION
        "This text appears in the UDP trap body."
    ::= { wtWebioEA12x6RelAlarmEntry 29 }

wtWebioEA12x6RelAlarmTcpReleaseText OBJECT-TYPE
    SYNTAX OCTET STRING 
    ACCESS read-write
    STATUS mandatory
    DESCRIPTION
        "This text appears in the TCP trap body."
    ::= { wtWebioEA12x6RelAlarmEntry 30 }

wtWebioEA12x6RelAlarmSyslogReleaseText OBJECT-TYPE
    SYNTAX OCTET STRING 
    ACCESS read-write
    STATUS mandatory
    DESCRIPTION
        "Every message starts with the priority key, a time stamp and the host ip address, according RFC3164.
        This text appears in the following syslog message body."
    ::= { wtWebioEA12x6RelAlarmEntry 31 }

wtWebioEA12x6RelAlarmFtpReleaseText OBJECT-TYPE
    SYNTAX OCTET STRING 
    ACCESS read-write
    STATUS mandatory
    DESCRIPTION
        "Message text to store on the FTP server."
    ::= { wtWebioEA12x6RelAlarmEntry 32 }

-- wtWebioEA12x6RelPorts Group
----------------------------

-- Input Port Table

wtWebioEA12x6RelInputPortTable OBJECT-TYPE
    SYNTAX SEQUENCE OF WtWebioEA12x6RelInputPortEntry
    ACCESS not-accessible
    STATUS mandatory
    DESCRIPTION
        "List of settings depending on the input number."
    ::= { wtWebioEA12x6RelPorts 1 }

wtWebioEA12x6RelInputPortEntry OBJECT-TYPE
    SYNTAX WtWebioEA12x6RelInputPortEntry
    ACCESS not-accessible
    STATUS mandatory
    DESCRIPTION
        "Input parameter for the individual inputs."
    INDEX  { wtWebioEA12x6RelInputNo }
    ::= { wtWebioEA12x6RelInputPortTable 1 }

WtWebioEA12x6RelInputPortEntry ::= SEQUENCE {
    wtWebioEA12x6RelPortInputName				OCTET STRING,
    wtWebioEA12x6RelPortInputText				OCTET STRING,
    wtWebioEA12x6RelPortInputMode				OCTET STRING,
    wtWebioEA12x6RelPortInputFilter				INTEGER,
    wtWebioEA12x6RelPortInputBicountPulsePolarity		OCTET STRING,
    wtWebioEA12x6RelPortInputBicountInactivTimeout		INTEGER
}

wtWebioEA12x6RelPortInputName OBJECT-TYPE
    SYNTAX OCTET STRING 
    ACCESS read-write
    STATUS mandatory
    DESCRIPTION
        "Name of the input."
    ::= { wtWebioEA12x6RelInputPortEntry 1 }

wtWebioEA12x6RelPortInputText OBJECT-TYPE
    SYNTAX OCTET STRING 
    ACCESS read-write
    STATUS mandatory
    DESCRIPTION
        "Description of the input."
    ::= { wtWebioEA12x6RelInputPortEntry 2 }

wtWebioEA12x6RelPortInputMode OBJECT-TYPE
    SYNTAX OCTET STRING (SIZE(4))
    ACCESS read-write
    STATUS mandatory
    DESCRIPTION
        "Binary coded modes:
        Selecting short pulse detection enable by setting the corresponding bit to 1 enables 
        interrupt support for counting. Only positive edges are accepted as trigger 
        source. The maximum counting frequenz equals 2000 Hz.
        This mode is available for inputs 0-3 only.
        Selecting counter clear on read by setting the corresponding bit to 1 enables
        the corresponding counter to be cleared automatically every time it is read,
        except HTTP reading with user rights.
        The OCTETS are interpreted bit-by-bit, with each bit corresponding to an input. 
        Bit 0 corresponds to the LSB.
        Selection for input 0-3:
        OCTET 1: unused
        OCTET 2: unused
        OCTET 3: unused
        OCTET 4, Bit 3-7: unused
        	 Bit 2  : Counter clear on read
        	 Bit 1  : Change detection enable (default)
        	 Bit 0  : Short Pulse detection enable
        	 
	Selection for inputs 4-11:
	OCTET 1: unused
	OCTET 2: unused
	OCTET 3: unused
	OCTET 4, Bit 2-7: unused
		 Bit 1  : Counter clear on read
		 Bit 0  : Change detection enable (default)"
    ::= { wtWebioEA12x6RelInputPortEntry 3 }    
    
wtWebioEA12x6RelPortInputFilter OBJECT-TYPE
    SYNTAX INTEGER 
    ACCESS read-write
    STATUS mandatory
    DESCRIPTION
        "Pulses with a duration shorter than here specified (duration in 1/1000 sec),
	are ignored."
    ::= { wtWebioEA12x6RelInputPortEntry 4 }
    
wtWebioEA12x6RelPortInputBicountPulsePolarity OBJECT-TYPE
    SYNTAX OCTET STRING (SIZE (4))
    ACCESS read-write
    STATUS mandatory
    DESCRIPTION
        "This value defines the polarity of the input pulse.
        OCTET 1: unused
        OCTET 2: unused
        OCTET 3: unused
        	OCTET 4: 
        	 Bit 0   : negative polarity
        	 Bit 1   : positive polarity
        	 Bit 2-7 : unused"
    ::= { wtWebioEA12x6RelInputPortEntry 5 }

wtWebioEA12x6RelPortInputBicountInactivTimeout OBJECT-TYPE
    SYNTAX INTEGER 
    ACCESS read-write
    STATUS mandatory
    DESCRIPTION
        "Pulse chains with a duration shorter than here specified (in 1/10 sek),
	are ignored."
    ::= { wtWebioEA12x6RelInputPortEntry 6 }
    
-- Output Port Table

wtWebioEA12x6RelOutputPortTable OBJECT-TYPE
    SYNTAX SEQUENCE OF WtWebioEA12x6RelOutputPortEntry
    ACCESS not-accessible
    STATUS mandatory
    DESCRIPTION
        "List of settings depending on the output number."
    ::= { wtWebioEA12x6RelPorts 2 }

wtWebioEA12x6RelOutputPortEntry OBJECT-TYPE
    SYNTAX WtWebioEA12x6RelOutputPortEntry
    ACCESS not-accessible
    STATUS mandatory
    DESCRIPTION
        "Output parameters of the individual outputs."
    INDEX  { wtWebioEA12x6RelOutputNo }
    ::= { wtWebioEA12x6RelOutputPortTable 1 }

WtWebioEA12x6RelOutputPortEntry ::= SEQUENCE {
    wtWebioEA12x6RelPortOutputName		OCTET STRING,
    wtWebioEA12x6RelPortOutputText		OCTET STRING,
    wtWebioEA12x6RelPortOutputGroupMode		OCTET STRING,
    wtWebioEA12x6RelPortOutputSafetyState	OCTET STRING,
    wtWebioEA12x6RelPortLogicInputMask		OCTET STRING,
    wtWebioEA12x6RelPortLogicInputInverter	OCTET STRING,
    wtWebioEA12x6RelPortLogicFunction		OCTET STRING,
    wtWebioEA12x6RelPortLogicOutputInverter	OCTET STRING,
    wtWebioEA12x6RelPortPulseDuration		INTEGER,
    wtWebioEA12x6RelPortPulsePolarity		OCTET STRING
    
}

wtWebioEA12x6RelPortOutputName OBJECT-TYPE
    SYNTAX OCTET STRING 
    ACCESS read-write
    STATUS mandatory
    DESCRIPTION
        "Name of the output."
    ::= { wtWebioEA12x6RelOutputPortEntry 1 }

wtWebioEA12x6RelPortOutputText OBJECT-TYPE
    SYNTAX OCTET STRING 
    ACCESS read-write
    STATUS mandatory
    DESCRIPTION
        "Description of the output."
    ::= { wtWebioEA12x6RelOutputPortEntry 2 }

wtWebioEA12x6RelPortOutputGroupMode OBJECT-TYPE
    SYNTAX OCTET STRING 
    ACCESS read-write
    STATUS mandatory
    DESCRIPTION
        "Unused in this device 57634"
    ::= { wtWebioEA12x6RelOutputPortEntry 3 }

wtWebioEA12x6RelPortOutputSafetyState OBJECT-TYPE
    SYNTAX OCTET STRING 
    ACCESS read-write
    STATUS mandatory
    DESCRIPTION
        "This variable allows setting of individual digital outputs. The OCTETS are 
        interpreted bit-by-bit, with each bit corresponding to an output. Bit 0 corresponds 
        to the LSB.
        The first four OCTETS contain the mask which determines which of the outputs are to 
        be set (corresponding bit = 1) and which outputs are to remain unchanged 
        (corresponding bit = 0):
        OCTET 1		: unused
        OCTET 2		: unused
        OCTET 3		: unused
        OCTET 4, Bit 1-7: unused
        	 Bit 0	: Mask for digital output
        OCTETS 5-8 contain the level (1=HIGH=Relais closed, 0=LOW Relais open) which the outputs to be changed 
        should assume:
        OCTET 5		: unused
        OCTET 6		: unused
        OCTET 7		: unused
        OCTET 8, Bit 1-7: unused
        	 Bit 0  : Level of digital output"
    ::= { wtWebioEA12x6RelOutputPortEntry 4 }

wtWebioEA12x6RelPortLogicInputMask OBJECT-TYPE
    SYNTAX OCTET STRING (SIZE (4))
    ACCESS read-write
    STATUS mandatory
    DESCRIPTION
        "Selecting one of these inputs by setting the corresponding bit to 1 
        enables the logic function for the output identified by the index within 
        this table. The calculation take place in 4 steps:
        1. Selecting inputs				(wtWebioEA12x6RelPortLogicInputMask)
        2. Inverting inputs if necessary	(wtWebioEA12x6RelPortLogicInputInverter)
        3. Logical combination				(wtWebioEA12x6RelPortLogicFunction)
        4. Inverting the result if necessary	(wtWebioEA12x6RelPortLogicOutputInverter)
        OCTET 1: unused
        OCTET 2: unused
        OCTET 3: Bit 0-3 : inputs 8-11
        	 Bit 4-7 : unused
        OCTET 4: 
        	 Bit 0-7 : inputs 0-7"
    ::= { wtWebioEA12x6RelOutputPortEntry 5 }

wtWebioEA12x6RelPortLogicInputInverter OBJECT-TYPE
    SYNTAX OCTET STRING (SIZE (4))
    ACCESS read-write
    STATUS mandatory
    DESCRIPTION
        "Every input bit selected here will be inverted.
        OCTET 1: unused
        OCTET 2: unused
        OCTET 3: Bit 0-3 : inputs 8-11
        	 Bit 4-7 : unused
        OCTET 4: 
        	 Bit 0-7 : inputs 0-7"
    ::= { wtWebioEA12x6RelOutputPortEntry 6 }

wtWebioEA12x6RelPortLogicFunction OBJECT-TYPE
    SYNTAX OCTET STRING (SIZE (4))
    ACCESS read-write
    STATUS mandatory
    DESCRIPTION
        "This determines the logic function. No more than one function
        may be selected.
        OCTET 1: unused
        OCTET 2: unused
        OCTET 3: unused
        OCTET 4: 
        	 Bit 0   : logic function OR (default)
        	 Bit 1   : logic function AND
        	 Bit 2-7 : unused"
    ::= { wtWebioEA12x6RelOutputPortEntry 7 }

wtWebioEA12x6RelPortLogicOutputInverter OBJECT-TYPE
    SYNTAX OCTET STRING (SIZE (4))
    ACCESS read-write
    STATUS mandatory
    DESCRIPTION
        "The logical operation result could be inverteted by setting the corresponding
        bit to 1.
        OCTET 1: unused
        OCTET 2: unused
        OCTET 3: unused
        	OCTET 4: 
        	 Bit 0   : Output Inverter enable
        	 Bit 1-7 : unused"
    ::= { wtWebioEA12x6RelOutputPortEntry 8 }

wtWebioEA12x6RelPortPulseDuration OBJECT-TYPE
    SYNTAX INTEGER
    ACCESS read-write
    STATUS mandatory
    DESCRIPTION
        "Pulse length in 1/1000 sec. Setting this value to zero, disables the pulse output."
    ::= { wtWebioEA12x6RelOutputPortEntry 9 }

wtWebioEA12x6RelPortPulsePolarity OBJECT-TYPE
    SYNTAX OCTET STRING (SIZE (4))
    ACCESS read-write
    STATUS mandatory
    DESCRIPTION
        "This value defines the polarity of the output pulse, if wtWebioEA12x6RelPortPulseDuration is not set to zero.
        After the pulse is finished, the output switches back to the opposite state.
        OCTET 1: unused
        OCTET 2: unused
        OCTET 3: unused
        	OCTET 4: 
        	 Bit 0   : negative polarity
        	 Bit 1   : positive polarity
        	 Bit 2-7 : unused"
    ::= { wtWebioEA12x6RelOutputPortEntry 10 }

-- wtWebioEA12x6RelManufact Group
----------------------------

wtWebioEA12x6RelMfName OBJECT-TYPE
    SYNTAX OCTET STRING 
    ACCESS read-write
    STATUS mandatory
    DESCRIPTION
        "Manufacturer company name"
    ::= { wtWebioEA12x6RelManufact 1 }

wtWebioEA12x6RelMfAddr OBJECT-TYPE
    SYNTAX OCTET STRING 
    ACCESS read-write
    STATUS mandatory
    DESCRIPTION
        "Manufacturer address."
    ::= { wtWebioEA12x6RelManufact 2 }

wtWebioEA12x6RelMfHotline OBJECT-TYPE
    SYNTAX OCTET STRING 
    ACCESS read-write
    STATUS mandatory
    DESCRIPTION
        "Manufacturer hotline."
    ::= { wtWebioEA12x6RelManufact 3 }

wtWebioEA12x6RelMfInternet OBJECT-TYPE
    SYNTAX OCTET STRING 
    ACCESS read-write
    STATUS mandatory
    DESCRIPTION
        "Manufacturer Internet address."
    ::= { wtWebioEA12x6RelManufact 4 }

wtWebioEA12x6RelMfDeviceTyp OBJECT-TYPE
    SYNTAX OCTET STRING 
    ACCESS read-write
    STATUS mandatory
    DESCRIPTION
        "Manufacturer device name (model number)."
    ::= { wtWebioEA12x6RelManufact 5 }

wtWebioEA12x6RelMfOrderNo OBJECT-TYPE
    SYNTAX OCTET STRING 
    ACCESS read-write
    STATUS mandatory
    DESCRIPTION
        "Manufacturer part number."
    ::= { wtWebioEA12x6RelManufact 6 }

-- wtWebioEA12x6RelDiag Group
----------------------------

wtWebioEA12x6RelDiagErrorCount OBJECT-TYPE
    SYNTAX INTEGER
    ACCESS read-only
    STATUS mandatory
    DESCRIPTION
        "Number of entries in the error memory."
    ::= { wtWebioEA12x6RelDiag 1 }

wtWebioEA12x6RelDiagBinaryError OBJECT-TYPE
    SYNTAX OCTET STRING 
    ACCESS read-only
    STATUS mandatory
    DESCRIPTION
        "Error causes coded bit-by-bit."
    ::= { wtWebioEA12x6RelDiag 2 }

wtWebioEA12x6RelDiagErrorIndex OBJECT-TYPE
    SYNTAX INTEGER
    ACCESS read-write
    STATUS mandatory
    DESCRIPTION
        "The value of this variable is used as an index to read 
        an error massege from wtWebioEA12x6RelDiagErrorMessage.
        Errors are numbered from 1 to wtWebioEA12x6RelDiagErrorCount.
        Writing a valid value into this variable, making the appropriate 
        message readable from wtWebioEA12x6RelDiagErrorMessage."
    ::= { wtWebioEA12x6RelDiag 3 }

wtWebioEA12x6RelDiagErrorMessage OBJECT-TYPE
    SYNTAX OCTET STRING 
    ACCESS read-only
    STATUS mandatory
    DESCRIPTION
        "Using wtWebioEA12x6RelDiagErrorIndex as an index, the appropriate message is available."
    ::= { wtWebioEA12x6RelDiag 4 }
    
wtWebioEA12x6RelDiagErrorClear OBJECT-TYPE
    SYNTAX INTEGER
    ACCESS write-only
    STATUS mandatory
    DESCRIPTION
        "Writing 1 into this variable clears all diagnosis messages."
    ::= { wtWebioEA12x6RelDiag 5 }


-- TRAP DEFINITIONS

-- Diese SNMP-Traps werden gesendet, wenn die Alarmtriggerbedingungen zutreffen 

wtWebioEA12x6RelAlert1 TRAP-TYPE
    ENTERPRISE  wtWebioEA12x6Rel
    VARIABLES   { wtWebioEA12x6RelAlarmSnmpTrapText }
    DESCRIPTION
        "This SNMP trap is generated when Alarm 1 was triggered,
        SNMP trap enable is set and
        SNMP is enabled."
    -- NMS trap annotation
    --#TYPE "Webio Digital Alarm 1"
    --#SUMMARY "Alarm 1: %s"
    --#ARGUMENTS {0}
    --#SEVERITY INFORMATIONAL
    --#TIMEINDEX 99
    --#STATE OPERATIONAL    
    ::= 41

wtWebioEA12x6RelAlert2 TRAP-TYPE
    ENTERPRISE  wtWebioEA12x6Rel
    VARIABLES   { wtWebioEA12x6RelAlarmSnmpTrapText }
    DESCRIPTION
        "This SNMP trap is generated when Alarm 2 was triggered,
        SNMP trap enable is set and
        SNMP is enabled."
    -- NMS trap annotation
    --#TYPE "Webio Digital Alarm 2"
    --#SUMMARY "Alarm 2: %s"
    --#ARGUMENTS {0}
    --#SEVERITY INFORMATIONAL
    --#TIMEINDEX 99
    --#STATE OPERATIONAL    
    ::= 42

wtWebioEA12x6RelAlert3 TRAP-TYPE
    ENTERPRISE  wtWebioEA12x6Rel
    VARIABLES   { wtWebioEA12x6RelAlarmSnmpTrapText }
    DESCRIPTION
        "This SNMP trap is generated when Alarm 3 was triggered,
        SNMP trap enable is set and
        SNMP is enabled."
    -- NMS trap annotation
    --#TYPE "Webio Digital Alarm 3"
    --#SUMMARY "Alarm 3: %s"
    --#ARGUMENTS {0}
    --#SEVERITY INFORMATIONAL
    --#TIMEINDEX 99
    --#STATE OPERATIONAL    
    ::= 43

wtWebioEA12x6RelAlert4 TRAP-TYPE
    ENTERPRISE  wtWebioEA12x6Rel
    VARIABLES   { wtWebioEA12x6RelAlarmSnmpTrapText }
    DESCRIPTION
        "This SNMP trap is generated when Alarm 4 was triggered,
        SNMP trap enable is set and
        SNMP is enabled."
    -- NMS trap annotation
    --#TYPE "Webio Digital Alarm 4"
    --#SUMMARY "Alarm 4: %s"
    --#ARGUMENTS {0}
    --#SEVERITY INFORMATIONAL
    --#TIMEINDEX 99
    --#STATE OPERATIONAL    
    ::= 44

wtWebioEA12x6RelAlert5 TRAP-TYPE
    ENTERPRISE  wtWebioEA12x6Rel
    VARIABLES   { wtWebioEA12x6RelAlarmSnmpTrapText }
    DESCRIPTION
        "This SNMP trap is generated when Alarm 5 was triggered,
        SNMP trap enable is set and
        SNMP is enabled."
    -- NMS trap annotation
    --#TYPE "Webio Digital Alarm 5"
    --#SUMMARY "Alarm 5: %s"
    --#ARGUMENTS {0}
    --#SEVERITY INFORMATIONAL
    --#TIMEINDEX 99
    --#STATE OPERATIONAL    
    ::= 45

wtWebioEA12x6RelAlert6 TRAP-TYPE
    ENTERPRISE  wtWebioEA12x6Rel
    VARIABLES   { wtWebioEA12x6RelAlarmSnmpTrapText }
    DESCRIPTION
        "This SNMP trap is generated when Alarm 6 was triggered,
        SNMP trap enable is set and
        SNMP is enabled."
    -- NMS trap annotation
    --#TYPE "Webio Digital Alarm 6"
    --#SUMMARY "Alarm 6: %s"
    --#ARGUMENTS {0}
    --#SEVERITY INFORMATIONAL
    --#TIMEINDEX 99
    --#STATE OPERATIONAL    
    ::= 46

wtWebioEA12x6RelAlert7 TRAP-TYPE
    ENTERPRISE  wtWebioEA12x6Rel
    VARIABLES   { wtWebioEA12x6RelAlarmSnmpTrapText }
    DESCRIPTION
        "This SNMP trap is generated when Alarm 7 was triggered,
        SNMP trap enable is set and
        SNMP is enabled."
    -- NMS trap annotation
    --#TYPE "Webio Digital Alarm 7"
    --#SUMMARY "Alarm 7: %s"
    --#ARGUMENTS {0}
    --#SEVERITY INFORMATIONAL
    --#TIMEINDEX 99
    --#STATE OPERATIONAL    
    ::= 47

wtWebioEA12x6RelAlert8 TRAP-TYPE
    ENTERPRISE  wtWebioEA12x6Rel
    VARIABLES   { wtWebioEA12x6RelAlarmSnmpTrapText }
    DESCRIPTION
        "This SNMP trap is generated when Alarm 8 was triggered,
        SNMP trap enable is set and
        SNMP is enabled."
    -- NMS trap annotation
    --#TYPE "Webio Digital Alarm 8"
    --#SUMMARY "Alarm 8: %s"
    --#ARGUMENTS {0}
    --#SEVERITY INFORMATIONAL
    --#TIMEINDEX 99
    --#STATE OPERATIONAL    
    ::= 48

wtWebioEA12x6RelAlert9 TRAP-TYPE
    ENTERPRISE  wtWebioEA12x6Rel
    VARIABLES   { wtWebioEA12x6RelAlarmSnmpTrapText }
    DESCRIPTION
        "This SNMP trap is generated when Alarm 9 was triggered,
        SNMP trap enable is set and
        SNMP is enabled."
    -- NMS trap annotation
    --#TYPE "Webio Digital Alarm 9"
    --#SUMMARY "Alarm 9: %s"
    --#ARGUMENTS {0}
    --#SEVERITY INFORMATIONAL
    --#TIMEINDEX 99
    --#STATE OPERATIONAL    
    ::= 49

wtWebioEA12x6RelAlert10 TRAP-TYPE
    ENTERPRISE  wtWebioEA12x6Rel
    VARIABLES   { wtWebioEA12x6RelAlarmSnmpTrapText }
    DESCRIPTION
        "This SNMP trap is generated when Alarm 10 was triggered,
        SNMP trap enable is set and
        SNMP is enabled."
    -- NMS trap annotation
    --#TYPE "Webio Digital Alarm 10"
    --#SUMMARY "Alarm 10: %s"
    --#ARGUMENTS {0}
    --#SEVERITY INFORMATIONAL
    --#TIMEINDEX 99
    --#STATE OPERATIONAL    
    ::= 50

wtWebioEA12x6RelAlert11 TRAP-TYPE
    ENTERPRISE  wtWebioEA12x6Rel
    VARIABLES   { wtWebioEA12x6RelAlarmSnmpTrapText }
    DESCRIPTION
        "This SNMP trap is generated when Alarm 11 was triggered,
        SNMP trap enable is set and
        SNMP is enabled."
    -- NMS trap annotation
    --#TYPE "Webio Digital Alarm 11"
    --#SUMMARY "Alarm 11: %s"
    --#ARGUMENTS {0}
    --#SEVERITY INFORMATIONAL
    --#TIMEINDEX 99
    --#STATE OPERATIONAL    
    ::= 51

wtWebioEA12x6RelAlert12 TRAP-TYPE
    ENTERPRISE  wtWebioEA12x6Rel
    VARIABLES   { wtWebioEA12x6RelAlarmSnmpTrapText }
    DESCRIPTION
        "This SNMP trap is generated when Alarm 12 was triggered,
        SNMP trap enable is set and
        SNMP is enabled."
    -- NMS trap annotation
    --#TYPE "Webio Digital Alarm 12"
    --#SUMMARY "Alarm 12: %s"
    --#ARGUMENTS {0}
    --#SEVERITY INFORMATIONAL
    --#TIMEINDEX 99
    --#STATE OPERATIONAL    
    ::= 52

wtWebioEA12x6RelAlert13 TRAP-TYPE
    ENTERPRISE  wtWebioEA12x6Rel
    VARIABLES   { wtWebioEA12x6RelAlarmSnmpTrapReleaseText }
    DESCRIPTION
        "This SNMP trap is generated when Alarm 1 was released,
        SNMP trap enable is set and
        SNMP is enabled."
    -- NMS trap annotation
    --#TYPE "Webio Digital Release Alarm 1"
    --#SUMMARY "Release Alarm 1: %s"
    --#ARGUMENTS {0}
    --#SEVERITY INFORMATIONAL
    --#TIMEINDEX 99
    --#STATE OPERATIONAL    
    ::= 71

wtWebioEA12x6RelAlert14 TRAP-TYPE
    ENTERPRISE  wtWebioEA12x6Rel
    VARIABLES   { wtWebioEA12x6RelAlarmSnmpTrapReleaseText }
    DESCRIPTION
        "This SNMP trap is generated when Alarm 2 was released,
        SNMP trap enable is set and
        SNMP is enabled."
    -- NMS trap annotation
    --#TYPE "Webio Digital Release Alarm 2"
    --#SUMMARY "Release Alarm 2: %s"
    --#ARGUMENTS {0}
    --#SEVERITY INFORMATIONAL
    --#TIMEINDEX 99
    --#STATE OPERATIONAL    
    ::= 72

wtWebioEA12x6RelAlert15 TRAP-TYPE
    ENTERPRISE  wtWebioEA12x6Rel
    VARIABLES   { wtWebioEA12x6RelAlarmSnmpTrapReleaseText }
    DESCRIPTION
        "This SNMP trap is generated when Alarm 3 was released,
        SNMP trap enable is set and
        SNMP is enabled."
    -- NMS trap annotation
    --#TYPE "Webio Digital Release Alarm 3"
    --#SUMMARY "Release Alarm 3: %s"
    --#ARGUMENTS {0}
    --#SEVERITY INFORMATIONAL
    --#TIMEINDEX 99
    --#STATE OPERATIONAL    
    ::= 73

wtWebioEA12x6RelAlert16 TRAP-TYPE
    ENTERPRISE  wtWebioEA12x6Rel
    VARIABLES   { wtWebioEA12x6RelAlarmSnmpTrapReleaseText }
    DESCRIPTION
        "This SNMP trap is generated when Alarm 4 was released,
        SNMP trap enable is set and
        SNMP is enabled."
    -- NMS trap annotation
    --#TYPE "Webio Digital Release Alarm 4"
    --#SUMMARY "Release Alarm 4: %s"
    --#ARGUMENTS {0}
    --#SEVERITY INFORMATIONAL
    --#TIMEINDEX 99
    --#STATE OPERATIONAL    
    ::= 74

wtWebioEA12x6RelAlert17 TRAP-TYPE
    ENTERPRISE  wtWebioEA12x6Rel
    VARIABLES   { wtWebioEA12x6RelAlarmSnmpTrapReleaseText }
    DESCRIPTION
        "This SNMP trap is generated when Alarm 5 was released,
        SNMP trap enable is set and
        SNMP is enabled."
    -- NMS trap annotation
    --#TYPE "Webio Digital Release Alarm 5"
    --#SUMMARY "Release Alarm 5: %s"
    --#ARGUMENTS {0}
    --#SEVERITY INFORMATIONAL
    --#TIMEINDEX 99
    --#STATE OPERATIONAL    
    ::= 75

wtWebioEA12x6RelAlert18 TRAP-TYPE
    ENTERPRISE  wtWebioEA12x6Rel
    VARIABLES   { wtWebioEA12x6RelAlarmSnmpTrapReleaseText }
    DESCRIPTION
        "This SNMP trap is generated when Alarm 6 was released,
        SNMP trap enable is set and
        SNMP is enabled."
    -- NMS trap annotation
    --#TYPE "Webio Digital Release Alarm 6"
    --#SUMMARY "Release Alarm 6: %s"
    --#ARGUMENTS {0}
    --#SEVERITY INFORMATIONAL
    --#TIMEINDEX 99
    --#STATE OPERATIONAL    
    ::= 76

wtWebioEA12x6RelAlert19 TRAP-TYPE
    ENTERPRISE  wtWebioEA12x6Rel
    VARIABLES   { wtWebioEA12x6RelAlarmSnmpTrapReleaseText }
    DESCRIPTION
        "This SNMP trap is generated when Alarm 7 was released,
        SNMP trap enable is set and
        SNMP is enabled."
    -- NMS trap annotation
    --#TYPE "Webio Digital Release Alarm 7"
    --#SUMMARY "Release Alarm 7: %s"
    --#ARGUMENTS {0}
    --#SEVERITY INFORMATIONAL
    --#TIMEINDEX 99
    --#STATE OPERATIONAL    
    ::= 77

wtWebioEA12x6RelAlert20 TRAP-TYPE
    ENTERPRISE  wtWebioEA12x6Rel
    VARIABLES   { wtWebioEA12x6RelAlarmSnmpTrapReleaseText }
    DESCRIPTION
        "This SNMP trap is generated when Alarm 8 was released,
        SNMP trap enable is set and
        SNMP is enabled."
    -- NMS trap annotation
    --#TYPE "Webio Digital Release Alarm 8"
    --#SUMMARY "Release Alarm 8: %s"
    --#ARGUMENTS {0}
    --#SEVERITY INFORMATIONAL
    --#TIMEINDEX 99
    --#STATE OPERATIONAL    
    ::= 78

wtWebioEA12x6RelAlert21 TRAP-TYPE
    ENTERPRISE  wtWebioEA12x6Rel
    VARIABLES   { wtWebioEA12x6RelAlarmSnmpTrapReleaseText }
    DESCRIPTION
        "This SNMP trap is generated when Alarm 9 was released,
        SNMP trap enable is set and
        SNMP is enabled."
    -- NMS trap annotation
    --#TYPE "Webio Digital Release Alarm 9"
    --#SUMMARY "Release Alarm 9: %s"
    --#ARGUMENTS {0}
    --#SEVERITY INFORMATIONAL
    --#TIMEINDEX 99
    --#STATE OPERATIONAL    
    ::= 79

wtWebioEA12x6RelAlert22 TRAP-TYPE
    ENTERPRISE  wtWebioEA12x6Rel
    VARIABLES   { wtWebioEA12x6RelAlarmSnmpTrapReleaseText }
    DESCRIPTION
        "This SNMP trap is generated when Alarm 10 was released,
        SNMP trap enable is set and
        SNMP is enabled."
    -- NMS trap annotation
    --#TYPE "Webio Digital Release Alarm 10"
    --#SUMMARY "Release Alarm 10: %s"
    --#ARGUMENTS {0}
    --#SEVERITY INFORMATIONAL
    --#TIMEINDEX 99
    --#STATE OPERATIONAL    
    ::= 80

wtWebioEA12x6RelAlert23 TRAP-TYPE
    ENTERPRISE  wtWebioEA12x6Rel
    VARIABLES   { wtWebioEA12x6RelAlarmSnmpTrapReleaseText }
    DESCRIPTION
        "This SNMP trap is generated when Alarm 11 was released,
        SNMP trap enable is set and
        SNMP is enabled."
    -- NMS trap annotation
    --#TYPE "Webio Digital Release Alarm 11"
    --#SUMMARY "Release Alarm 11: %s"
    --#ARGUMENTS {0}
    --#SEVERITY INFORMATIONAL
    --#TIMEINDEX 99
    --#STATE OPERATIONAL    
    ::= 81

wtWebioEA12x6RelAlert24 TRAP-TYPE
    ENTERPRISE  wtWebioEA12x6Rel
    VARIABLES   { wtWebioEA12x6RelAlarmSnmpTrapReleaseText }
    DESCRIPTION
        "This SNMP trap is generated when Alarm 12 was released,
        SNMP trap enable is set and
        SNMP is enabled."
    -- NMS trap annotation
    --#TYPE "Webio Digital Release Alarm 12"
    --#SUMMARY "Release Alarm 12: %s"
    --#ARGUMENTS {0}
    --#SEVERITY INFORMATIONAL
    --#TIMEINDEX 99
    --#STATE OPERATIONAL    
    ::= 82

wtWebioEA12x6RelAlertDiag TRAP-TYPE
    ENTERPRISE  wtWebioEA12x6Rel
    VARIABLES   { 	
    		wtWebioEA12x6RelDiagErrorIndex,
    	  	wtWebioEA12x6RelDiagErrorMessage
    		}
    DESCRIPTION
        "This SNMP trap is generated when a diagnosis/error message was triggered,
        SNMP trap enable is set and
        SNMP is enabled."
    -- NMS trap annotation
    --#TYPE "Webio Digital Diagnose Error"
    --#SUMMARY "Diagnose error index: %d, Message: %s."
    --#ARGUMENTS {0,1}
    --#SEVERITY MAJOR
    --#TIMEINDEX 99
    --#STATE DEGRADED    
    ::= 110

--------------------------------------------------------------------------------
--------------------------------------------------------------------------------
--------------------------------------------------------------------------------

-- wtWebAlarm6x6InOut Group
------------------------

wtWebAlarm6x6Inputs OBJECT-TYPE
    SYNTAX INTEGER (1..6)
    ACCESS read-only
    STATUS mandatory
    DESCRIPTION
        "Number of idependent inputs."
    ::= { wtWebAlarm6x6InOut 1 }

wtWebAlarm6x6Outputs OBJECT-TYPE
    SYNTAX INTEGER (1..6)
    ACCESS read-only
    STATUS mandatory
    DESCRIPTION
        "Number of independent outputs."
    ::= { wtWebAlarm6x6InOut 2 }

-- Input Interface Table

wtWebAlarm6x6InputTable OBJECT-TYPE
    SYNTAX SEQUENCE OF WtWebAlarm6x6InputEntry
    ACCESS not-accessible
    STATUS mandatory
    DESCRIPTION
        "List of input indices."
    ::= { wtWebAlarm6x6InOut 3 }

wtWebAlarm6x6InputEntry OBJECT-TYPE
    SYNTAX WtWebAlarm6x6InputEntry
    ACCESS not-accessible
    STATUS mandatory
    DESCRIPTION
        "Number of the inputs."
    INDEX  { wtWebAlarm6x6InputNo }
    ::= { wtWebAlarm6x6InputTable 1 }

WtWebAlarm6x6InputEntry ::= SEQUENCE {
    wtWebAlarm6x6InputNo INTEGER,
    wtWebAlarm6x6InputCounter INTEGER,
    wtWebAlarm6x6InputCounterClear INTEGER,
    wtWebAlarm6x6InputState INTEGER
}

wtWebAlarm6x6InputNo OBJECT-TYPE
    SYNTAX INTEGER (1)
    ACCESS read-only
    STATUS mandatory
    DESCRIPTION
        "Index numbers of the inputs."
    ::= { wtWebAlarm6x6InputEntry 1 }

wtWebAlarm6x6InputCounter OBJECT-TYPE
    SYNTAX INTEGER (1)
    ACCESS read-only
    STATUS mandatory
    DESCRIPTION
        "Value of the input counter."
    ::= { wtWebAlarm6x6InputEntry 2 }
    
wtWebAlarm6x6InputCounterClear OBJECT-TYPE
    SYNTAX INTEGER
    ACCESS read-only
    STATUS mandatory
    DESCRIPTION
        "Clears the input counter after returning its value."
    ::= { wtWebAlarm6x6InputEntry 3 }
    
wtWebAlarm6x6InputState OBJECT-TYPE
    SYNTAX INTEGER{
    wtWebAlarm6x6InputState-OFF(0),
    wtWebAlarm6x6InputState-ON(1)
    }
    ACCESS read-only
    STATUS mandatory
    DESCRIPTION
        "States of the inputs."
    ::= { wtWebAlarm6x6InputEntry 4 }
    
    
wtWebAlarm6x6InputValue OBJECT-TYPE
    SYNTAX INTEGER 
    ACCESS read-only
    STATUS mandatory
    DESCRIPTION
        "This variable is used to read the inputs of the digital I/O port.
        The OCTETS are interpreted bit-by-bit, with each bit corresponding to an input.
        Bit 0 corresponds to the LSB.
        OCTET 1: unused
        OCTET 2: unused
        OCTET 3: unused
        OCTET 4, Bit 0-5: Digital inputs 0-5
        	 Bit 6-7: unused"
    ::= { wtWebAlarm6x6InOut 4 }
    

-- Output Interface Table

wtWebAlarm6x6OutputTable OBJECT-TYPE
    SYNTAX SEQUENCE OF WtWebAlarm6x6OutputEntry
    ACCESS not-accessible
    STATUS mandatory
    DESCRIPTION
        "List of output indices."
    ::= { wtWebAlarm6x6InOut 5 }

wtWebAlarm6x6OutputEntry OBJECT-TYPE
    SYNTAX WtWebAlarm6x6OutputEntry
    ACCESS not-accessible
    STATUS mandatory
    DESCRIPTION
        "Number of the outputs."
    INDEX  { wtWebAlarm6x6OutputNo }
    ::= { wtWebAlarm6x6OutputTable 1 }

WtWebAlarm6x6OutputEntry ::= SEQUENCE {
    wtWebAlarm6x6OutputNo INTEGER,
    wtWebAlarm6x6OutputState INTEGER    
}

wtWebAlarm6x6OutputNo OBJECT-TYPE
    SYNTAX INTEGER (1)
    ACCESS read-only
    STATUS mandatory
    DESCRIPTION
        "Output number."
    ::= { wtWebAlarm6x6OutputEntry 1 }

wtWebAlarm6x6OutputState OBJECT-TYPE
    SYNTAX INTEGER{
    wtWebAlarm6x6OutputState-OFF(0),
    wtWebAlarm6x6OutputState-ON(1)
    }
    ACCESS read-write
    STATUS mandatory
    DESCRIPTION
        "States of the outputs."
    ::= { wtWebAlarm6x6OutputEntry 2 }

wtWebAlarm6x6OutputValue OBJECT-TYPE
    SYNTAX INTEGER
    ACCESS read-only
    STATUS mandatory
    DESCRIPTION
        "This variable is used to read the outputs of the digital I/O port. 
        The OCTETS are interpreted bit-by-bit, with each bit corresponding to an output. 
        Bit 0 corresponds to the LSB.
        OCTET 1: unused
        OCTET 2: unused
        OCTET 3: unused
        OCTET 4: Bit 0-5: Digital outputs 0-5"
    ::= { wtWebAlarm6x6InOut 6 }

-- Alarm Output Interface Table

wtWebAlarm6x6AlarmOutputTable OBJECT-TYPE
    SYNTAX SEQUENCE OF WtWebAlarm6x6AlarmOutputEntry
    ACCESS not-accessible
    STATUS mandatory
    DESCRIPTION
        "List of alarm indices.."
    ::= { wtWebAlarm6x6InOut 8 }

wtWebAlarm6x6AlarmOutputEntry OBJECT-TYPE
    SYNTAX WtWebAlarm6x6AlarmOutputEntry
    ACCESS not-accessible
    STATUS mandatory
    DESCRIPTION
        "Index reference."
    INDEX  { wtWebAlarm6x6AlarmNo }
    ::= { wtWebAlarm6x6AlarmOutputTable 1 }

WtWebAlarm6x6AlarmOutputEntry ::= SEQUENCE {
    wtWebAlarm6x6AlarmOutputState	INTEGER,
    wtWebAlarm6x6AlarmTriggerState	INTEGER
}

wtWebAlarm6x6AlarmOutputState OBJECT-TYPE
    SYNTAX INTEGER{
    wtWebAlarm6x6AlarmOutputState-OFF(0),
    wtWebAlarm6x6AlarmOutputState-ON(1)
    }
    ACCESS read-write
    STATUS mandatory
    DESCRIPTION
        "State of the alarm."
    ::= { wtWebAlarm6x6AlarmOutputEntry 1 }

wtWebAlarm6x6AlarmTriggerState OBJECT-TYPE
    SYNTAX INTEGER{
    wtWebAlarm6x6AlarmTriggerState-OFF(0),
    wtWebAlarm6x6AlarmTriggerState-ON(1)
    }
    ACCESS read-only
    STATUS mandatory
    DESCRIPTION
        "State of the trigger condition."
    ::= { wtWebAlarm6x6AlarmOutputEntry 2 }    
    
-- wtWebAlarm6x6SessCntrl Group
--------------------------------

wtWebAlarm6x6SessCntrlPassword OBJECT-TYPE
    SYNTAX OCTET STRING 
    ACCESS read-write
    STATUS mandatory
    DESCRIPTION
        "Entering this password opens a session which is ended by writing a 1 to 
        wtWebAlarm6x6SessCntrlLogout. When read this variable provides a string of
        length zero."
    ::= { wtWebAlarm6x6SessCntrl 1 }

wtWebAlarm6x6SessCntrlConfigMode OBJECT-TYPE
    SYNTAX INTEGER {
    wtWebAlarm6x6SessCntrl-NoSession(0),
    wtWebAlarm6x6SessCntrl-Session(1)
    }
    ACCESS read-only
    STATUS mandatory
    DESCRIPTION
        "When the device is in SNMP configuration mode, the value 1 is
        returned, otherwise 0. If the read value is 0 even though the password
        was written, the device is already in config mode and the variables
        can only be read."
    ::= { wtWebAlarm6x6SessCntrl 2 }

wtWebAlarm6x6SessCntrlLogout OBJECT-TYPE
    SYNTAX INTEGER 
    ACCESS read-write
    STATUS mandatory
    DESCRIPTION
        "If the device is in configuration mode and the session was opened by
        this SNMP Manager, writing a 1 to this variable will end the session 
        and all parameters are stored.
        Writing a 2 discards all entries again. When read this variable
        provides the value 0."
    ::= { wtWebAlarm6x6SessCntrl 3 }

wtWebAlarm6x6SessCntrlAdminPassword OBJECT-TYPE
    SYNTAX OCTET STRING 
    ACCESS read-write
    STATUS mandatory
    DESCRIPTION
        "This password protects access to the variables with administrator rights.
        It can only be changed by the administrator. If no password was assigned,
        the valid password is public."
    ::= { wtWebAlarm6x6SessCntrl 4 }

wtWebAlarm6x6SessCntrlConfigPassword OBJECT-TYPE
    SYNTAX OCTET STRING 
    ACCESS read-write
    STATUS mandatory
    DESCRIPTION
        "This password protects access to the variables with configurator rights. It can
        be changed by the administrator and by the configurator. If no password was assigned, 
        the valid password is public. When read this variable provides a null-pointer."
    ::= { wtWebAlarm6x6SessCntrl 5 }
    
-- wtWebAlarm6x6Text Group
------------------------

wtWebAlarm6x6DeviceName OBJECT-TYPE
    SYNTAX OCTET STRING 
    ACCESS read-write
    STATUS mandatory
    DESCRIPTION
        "Name of the Webio, which is user definable."
    ::= { wtWebAlarm6x6Text 1 }

wtWebAlarm6x6DeviceText OBJECT-TYPE
    SYNTAX OCTET STRING 
    ACCESS read-write
    STATUS mandatory
    DESCRIPTION
        "Description of the Webio, which is user definable."
    ::= { wtWebAlarm6x6Text 2 }
    
wtWebAlarm6x6DeviceLocation OBJECT-TYPE
    SYNTAX OCTET STRING 
    ACCESS read-write
    STATUS mandatory
    DESCRIPTION
        "Description of the location of the Webio, which is user definable."
    ::= { wtWebAlarm6x6Text 3 }

wtWebAlarm6x6DeviceContact OBJECT-TYPE
    SYNTAX OCTET STRING 
    ACCESS read-write
    STATUS mandatory
    DESCRIPTION
        "Contact address of the system operator of the Webio, which is user definable."
    ::= { wtWebAlarm6x6Text 4 }    

-- wtWebAlarm6x6TimeZone Group
----------------------------

wtWebAlarm6x6TzOffsetHrs OBJECT-TYPE
    SYNTAX INTEGER 
    ACCESS read-write
    STATUS mandatory
    DESCRIPTION
        "Offset hours for the time zone (winter time) with respect to UTC."
    ::= { wtWebAlarm6x6TimeZone 1 }

wtWebAlarm6x6TzOffsetMin OBJECT-TYPE
    SYNTAX INTEGER 
    ACCESS read-write
    STATUS mandatory
    DESCRIPTION
        "Offset minutes for the time zone (winter time) with respect to UTC."
    ::= { wtWebAlarm6x6TimeZone 2 }

wtWebAlarm6x6TzEnable OBJECT-TYPE
    SYNTAX OCTET STRING (SIZE(4))
    ACCESS read-write
    STATUS mandatory
    DESCRIPTION
        "Binary coded conditions:
        Octet 1: unused
        Octet 2: unused
        Octet 3: unused
        Octet 4:
        	Bit 1-7: unused
	        Bit 0  : Apply Timezone"
    ::= { wtWebAlarm6x6TimeZone 3 }

wtWebAlarm6x6StTzOffsetHrs OBJECT-TYPE
    SYNTAX INTEGER 
    ACCESS read-write
    STATUS mandatory
    DESCRIPTION
        "Offset hours of the time zone (summer time) with respect to UTC."
    ::= { wtWebAlarm6x6TimeZone 4 }

wtWebAlarm6x6StTzOffsetMin OBJECT-TYPE
    SYNTAX INTEGER 
    ACCESS read-write
    STATUS mandatory
    DESCRIPTION
        "Offset minutes of the time zone (summer time) with respect to UTC."
    ::= { wtWebAlarm6x6TimeZone 5 }

wtWebAlarm6x6StTzEnable OBJECT-TYPE
    SYNTAX OCTET STRING (SIZE(4))
    ACCESS read-write
    STATUS mandatory
    DESCRIPTION
        "Binary coded conditions:
        Octet 1: unused
        Octet 2: unused
        Octet 3: unused
        Octet 4:
        	Bit 1-7: unused
	        Bit 0  : Apply Summertime"
    ::= { wtWebAlarm6x6TimeZone 6 }

wtWebAlarm6x6StTzStartMonth OBJECT-TYPE
    SYNTAX INTEGER {
    	wtWebAlarm6x6StartMonth-January(1),
    	wtWebAlarm6x6StartMonth-February(2),
    	wtWebAlarm6x6StartMonth-March(3),
    	wtWebAlarm6x6StartMonth-April(4),
    	wtWebAlarm6x6StartMonth-May(5),
    	wtWebAlarm6x6StartMonth-June(6),
    	wtWebAlarm6x6StartMonth-July(7),
    	wtWebAlarm6x6StartMonth-August(8),
    	wtWebAlarm6x6StartMonth-September(9),
    	wtWebAlarm6x6StartMonth-October(10),
    	wtWebAlarm6x6StartMonth-November(11),
    	wtWebAlarm6x6StartMonth-December(12)
    	}
    	
    ACCESS read-write
    STATUS mandatory
    DESCRIPTION
        "Month in which the change is made from winter time to summer time."
    ::= { wtWebAlarm6x6TimeZone 7 }

wtWebAlarm6x6StTzStartMode OBJECT-TYPE
    SYNTAX INTEGER {
    	wtWebAlarm6x6StartMode-first(1),
    	wtWebAlarm6x6StartMode-second(2),
    	wtWebAlarm6x6StartMode-third(3),
    	wtWebAlarm6x6StartMode-fourth(4),
    	wtWebAlarm6x6StartMode-last(5)
    	}
    	
    ACCESS read-write
    STATUS mandatory
    DESCRIPTION
        "Mode of the day of the week for which the change is made from winter time to summer time."
    ::= { wtWebAlarm6x6TimeZone 8 }

wtWebAlarm6x6StTzStartWday OBJECT-TYPE
    SYNTAX INTEGER {
    	wtWebAlarm6x6StartWday-Sunday(1),
    	wtWebAlarm6x6StartWday-Monday(2),
    	wtWebAlarm6x6StartWday-Tuesday(3),
    	wtWebAlarm6x6StartWday-Thursday(4),
    	wtWebAlarm6x6StartWday-Wednesday(5),
    	wtWebAlarm6x6StartWday-Friday(6),
    	wtWebAlarm6x6StartWday-Saturday(7)
    	}
    	
    ACCESS read-write
    STATUS mandatory
    DESCRIPTION
        "Day of the week on which the change is made from winter time to summer time"
    ::= { wtWebAlarm6x6TimeZone 9 }
    
wtWebAlarm6x6StTzStartHrs OBJECT-TYPE
    SYNTAX INTEGER 
    ACCESS read-write
    STATUS mandatory
    DESCRIPTION
        "Hour in which the time zone is changed from winter to summer time with
        respect to UTC."
    ::= { wtWebAlarm6x6TimeZone 10 }

wtWebAlarm6x6StTzStartMin OBJECT-TYPE
    SYNTAX INTEGER 
    ACCESS read-write
    STATUS mandatory
    DESCRIPTION
        "Minute in which the time zone is changed from winter to summer time with
        respect to UTC."
    ::= { wtWebAlarm6x6TimeZone 11 }
 
wtWebAlarm6x6StTzStopMonth OBJECT-TYPE
    SYNTAX INTEGER {
    	wtWebAlarm6x6StopMonth-January(1),
    	wtWebAlarm6x6StopMonth-February(2),
    	wtWebAlarm6x6StopMonth-March(3),
    	wtWebAlarm6x6StopMonth-April(4),
    	wtWebAlarm6x6StopMonth-May(5),
    	wtWebAlarm6x6StopMonth-June(6),
    	wtWebAlarm6x6StopMonth-July(7),
    	wtWebAlarm6x6StopMonth-August(8),
    	wtWebAlarm6x6StopMonth-September(9),
    	wtWebAlarm6x6StopMonth-October(10),
    	wtWebAlarm6x6StopMonth-November(11),
    	wtWebAlarm6x6StopMonth-December(12)
    	}
    ACCESS read-write
    STATUS mandatory
    DESCRIPTION
        "Month in which the change is made from summer time to winter time."
   ::= { wtWebAlarm6x6TimeZone 12 }

wtWebAlarm6x6StTzStopMode OBJECT-TYPE
    SYNTAX INTEGER {
    	wtWebAlarm6x6StopMode-first(1),
    	wtWebAlarm6x6StopMode-second(2),
    	wtWebAlarm6x6StopMode-third(3),
    	wtWebAlarm6x6StopMode-fourth(4),
    	wtWebAlarm6x6StopMode-last(5)
    	}
    ACCESS read-write
    STATUS mandatory
    DESCRIPTION
        "Mode of the week day on which the change is made from summer time to winter time."
    ::= { wtWebAlarm6x6TimeZone 13 }

wtWebAlarm6x6StTzStopWday OBJECT-TYPE
    SYNTAX INTEGER {
    	wtWebAlarm6x6StopWday-Sunday(1),
    	wtWebAlarm6x6StopWday-Monday(2),
    	wtWebAlarm6x6StopWday-Tuesday(3),
    	wtWebAlarm6x6StopWday-Thursday(4),
    	wtWebAlarm6x6StopWday-Wednesday(5),
    	wtWebAlarm6x6StopWday-Friday(6),
    	wtWebAlarm6x6StopWday-Saturday(7)
    	}
    ACCESS read-write
    STATUS mandatory
    DESCRIPTION
        "Day of the week on which the change is made from summer time to winter time."
    ::= { wtWebAlarm6x6TimeZone 14 }
    
wtWebAlarm6x6StTzStopHrs OBJECT-TYPE
    SYNTAX INTEGER 
    ACCESS read-write
    STATUS mandatory
    DESCRIPTION
        "Hour at which the time zone is changed from summer to winter time with
        respect to UTC."
    ::= { wtWebAlarm6x6TimeZone 15 }

wtWebAlarm6x6StTzStopMin OBJECT-TYPE
    SYNTAX INTEGER 
    ACCESS read-write
    STATUS mandatory
    DESCRIPTION
        "Minute at which the time zone is changed from summer to winter time with
        respect to UTC."
    ::= { wtWebAlarm6x6TimeZone 16 }

-- wtWebAlarm6x6TimeServer Group
----------------------------

wtWebAlarm6x6TimeServer1 OBJECT-TYPE
    SYNTAX OCTET STRING 
    ACCESS read-write
    STATUS mandatory
    DESCRIPTION
        "IP address or name of the 1st time server in ASCII"
    ::= { wtWebAlarm6x6TimeServer 1 }

wtWebAlarm6x6TimeServer2 OBJECT-TYPE
    SYNTAX OCTET STRING 
    ACCESS read-write
    STATUS mandatory
    DESCRIPTION
        "IP address or name of the 2nd time server in ASCII"
    ::= { wtWebAlarm6x6TimeServer 2 }

wtWebAlarm6x6TsEnable OBJECT-TYPE
    SYNTAX OCTET STRING (SIZE(4))
    ACCESS read-write
    STATUS mandatory
    DESCRIPTION
        "Binary coded conditions:
        Octet 1: unused
        Octet 2: unused
        Octet 3: unused
        Octet 4:
        	Bit 1-7: unused
	        Bit 0  : Apply Time Server"
    ::= { wtWebAlarm6x6TimeServer 3 }

wtWebAlarm6x6TsSyncTime OBJECT-TYPE
    SYNTAX INTEGER 
    ACCESS read-write
    STATUS mandatory
    DESCRIPTION
        "Daily synchronisation time with the time server (hour: 0-23)."
    ::= { wtWebAlarm6x6TimeServer 4 }
      
    
-- wtWebAlarm6x6DeviceClock Group
----------------------------

wtWebAlarm6x6ClockHrs OBJECT-TYPE
    SYNTAX INTEGER (0..23)
    ACCESS read-write
    STATUS mandatory
    DESCRIPTION
        "Clock hours taking into account the time zone settings."
    ::= { wtWebAlarm6x6DeviceClock 1 }

wtWebAlarm6x6ClockMin OBJECT-TYPE
    SYNTAX INTEGER (0..59)
    ACCESS read-write
    STATUS mandatory
    DESCRIPTION
        "Clock minutes taking into account the time zone settings."
    ::= { wtWebAlarm6x6DeviceClock 2 }

wtWebAlarm6x6ClockDay OBJECT-TYPE
    SYNTAX INTEGER (1..31)
    ACCESS read-write
    STATUS mandatory
    DESCRIPTION
        "Date: Day of the month, taking into account the time zone settings."
    ::= { wtWebAlarm6x6DeviceClock 3 }

wtWebAlarm6x6ClockMonth OBJECT-TYPE
   SYNTAX INTEGER {
    	wtWebAlarm6x6ClockMonth-January(1),
    	wtWebAlarm6x6ClockMonth-February(2),
    	wtWebAlarm6x6ClockMonth-March(3),
    	wtWebAlarm6x6ClockMonth-April(4),
    	wtWebAlarm6x6ClockMonth-May(5),
    	wtWebAlarm6x6ClockMonth-June(6),
    	wtWebAlarm6x6ClockMonth-July(7),
    	wtWebAlarm6x6ClockMonth-August(8),
    	wtWebAlarm6x6ClockMonth-September(9),
    	wtWebAlarm6x6ClockMonth-October(10),
    	wtWebAlarm6x6ClockMonth-November(11),
    	wtWebAlarm6x6ClockMonth-December(12)
    	}
    ACCESS read-write
    STATUS mandatory
    DESCRIPTION
        "Date: Month, taking into account the time zone settings."
    ::= { wtWebAlarm6x6DeviceClock 4 }

wtWebAlarm6x6ClockYear OBJECT-TYPE
    SYNTAX INTEGER (0..65535)
    ACCESS read-write
    STATUS mandatory
    DESCRIPTION
        "Date: Year, taking into account the time zone settings."
    ::= { wtWebAlarm6x6DeviceClock 5 }

-- wtWebAlarm6x6Network Group
------------------------

wtWebAlarm6x6IpAddress OBJECT-TYPE
    SYNTAX IpAddress
    ACCESS read-write
    STATUS mandatory
    DESCRIPTION
        "IP address of the Webio"
    ::= { wtWebAlarm6x6Network 1 }

wtWebAlarm6x6SubnetMask OBJECT-TYPE
    SYNTAX IpAddress
    ACCESS read-write
    STATUS mandatory
    DESCRIPTION
        "Subnet mask of the Webio"
    ::= { wtWebAlarm6x6Network 2 }

wtWebAlarm6x6Gateway OBJECT-TYPE
    SYNTAX IpAddress
    ACCESS read-write
    STATUS mandatory
    DESCRIPTION
        "Gateway of the Webio"
    ::= { wtWebAlarm6x6Network 3 }

wtWebAlarm6x6DnsServer1 OBJECT-TYPE
    SYNTAX OCTET STRING 
    ACCESS read-write
    STATUS mandatory
    DESCRIPTION
        "IP address of the 1st DNS server in ASCII"
    ::= { wtWebAlarm6x6Network 4 }

wtWebAlarm6x6DnsServer2 OBJECT-TYPE
    SYNTAX OCTET STRING 
    ACCESS read-write
    STATUS mandatory
    DESCRIPTION
        "IP address of the 2nd DNS server in ASCII"
    ::= { wtWebAlarm6x6Network 5 }

wtWebAlarm6x6AddConfig OBJECT-TYPE
    SYNTAX OCTET STRING 
    ACCESS read-write
    STATUS mandatory
    DESCRIPTION
        "Additional configuration (1=ON):
        Octet 1: unused
        Octet 2: unused
        Octet 3: unused
        Octet 4:
	        Bit 1: DHCP  enable
	        Bit 0: BOOTP enable"
    ::= { wtWebAlarm6x6Network 6 }

--  wtWebAlarm6x6HTTP Group
--------------------------------

wtWebAlarm6x6HttpPort OBJECT-TYPE
    SYNTAX INTEGER (1..65534)
    ACCESS read-write
    STATUS mandatory
    DESCRIPTION
       "Definition of the standard HTML port (Default: 80)."
    ::= { wtWebAlarm6x6HTTP 4 }        
    
    
-- wtWebAlarm6x6Mail Group
--------------------------------

wtWebAlarm6x6MailAdName OBJECT-TYPE
    SYNTAX OCTET STRING 
    ACCESS read-write
    STATUS mandatory
    DESCRIPTION
        "Device name for mail administration."
    ::= { wtWebAlarm6x6Mail 1 }
    
wtWebAlarm6x6MailReply OBJECT-TYPE
    SYNTAX OCTET STRING 
    ACCESS read-write
    STATUS mandatory
    DESCRIPTION
        "Reply address for the mail server."
    ::= { wtWebAlarm6x6Mail 2 }
    
wtWebAlarm6x6MailServer OBJECT-TYPE
    SYNTAX OCTET STRING 
    ACCESS read-write
    STATUS mandatory
    DESCRIPTION
        "Name or IP address of the mail server."
    ::= { wtWebAlarm6x6Mail 3 }
    
wtWebAlarm6x6MailEnable OBJECT-TYPE
    SYNTAX OCTET STRING 
    ACCESS read-write
    STATUS mandatory
    DESCRIPTION
        "Set this bit to enable the sending of mails:
        Octet 1: unused
        Octet 2: unused
        Octet 3: unused
        Octet 4:
        	Bit 1-7: unused
                Bit 0  : Mail enable"
    ::= { wtWebAlarm6x6Mail 4 }

wtWebAlarm6x6MailAuthentication OBJECT-TYPE
    SYNTAX OCTET STRING (SIZE (4))
    ACCESS read-write
    STATUS mandatory
    DESCRIPTION
        "Selection of the authentication modi:
        The OCTETS are interpreted bit-by-bit, 
        Bit 0 corresponds to the LSB.
        OCTET 1: unused
        OCTET 2: unused
        OCTET 3: unused
        OCTET 4: Bit 3-7: unused
        	 Bit 2  : POP3 before SMTP
        	 Bit 1  : ESMTP, authentication
        	 Bit 0  : SMTP, no authentication"
    ::= { wtWebAlarm6x6Mail 5 }
    
wtWebAlarm6x6MailAuthUser OBJECT-TYPE
    SYNTAX OCTET STRING 
    ACCESS read-write
    STATUS mandatory
    DESCRIPTION
        "Name of the user to be authenticated."
    ::= { wtWebAlarm6x6Mail 6 }    
    
wtWebAlarm6x6MailAuthPassword OBJECT-TYPE
    SYNTAX OCTET STRING 
    ACCESS read-write
    STATUS mandatory
    DESCRIPTION
        "Authentication password."
    ::= { wtWebAlarm6x6Mail 7 }    
    
wtWebAlarm6x6MailPop3Server OBJECT-TYPE
    SYNTAX OCTET STRING 
    ACCESS read-write
    STATUS mandatory
    DESCRIPTION
        "Name or Ip-address of the POP3 Servers."
    ::= { wtWebAlarm6x6Mail 8 }        
    

--  wtWebAlarm6x6Snmp Group
--------------------------------

wtWebAlarm6x6SnmpEnable OBJECT-TYPE
    SYNTAX OCTET STRING 
    ACCESS read-write
    STATUS mandatory
    DESCRIPTION
        "Set bit 0 to enable SNMP.
        If disabled, the device did not respond to any SNMP requests.
        Bit 1 decided wether the community string of read operations 
        is compared with the system password or not:
        Octet 1: unused
        Octet 2: unused
        Octet 3: unused
        Octet 4:
        	Bit 1-7: unused
        	Bit 0  : SNMP enable"
    ::= { wtWebAlarm6x6SNMP 1 }
    
wtWebAlarm6x6SnmpCommunityStringRead OBJECT-TYPE
    SYNTAX OCTET STRING
    ACCESS read-write
    STATUS mandatory
    DESCRIPTION
        "Community string read only"
    ::= { wtWebAlarm6x6SNMP 2 }

wtWebAlarm6x6SnmpCommunityStringReadWrite OBJECT-TYPE
    SYNTAX OCTET STRING
    ACCESS read-write
    STATUS mandatory
    DESCRIPTION
        "Community string read / write"
    ::= { wtWebAlarm6x6SNMP 3 }

wtWebAlarm6x6SnmpSystemTrapManagerIP OBJECT-TYPE
    SYNTAX OCTET STRING 
    ACCESS read-write
    STATUS mandatory
    DESCRIPTION
        "Name or IP address of the TCP server which accepts the system trap."
    ::= { wtWebAlarm6x6SNMP 4 }
    
wtWebAlarm6x6SnmpSystemTrapEnable OBJECT-TYPE
    SYNTAX OCTET STRING (SIZE(4))
    ACCESS read-write
    STATUS mandatory
    DESCRIPTION
        "Binary coded trigger conditions:
        Octet 1: unused
        Octet 2: unused
        Octet 3: unused
        Octet 4:
	        Bit 0:   ColdStart
	        Bit 1:   WarmStart
	        Bit 2:   Diag messages
	        Bit 3-7: unused"
    ::= { wtWebAlarm6x6SNMP 5 }    

-- wtWebAlarm6x6Udp Group
--------------------------------   

wtWebAlarm6x6UdpAdminPort OBJECT-TYPE
    SYNTAX INTEGER
    ACCESS read-write
    STATUS mandatory
    DESCRIPTION
        "Udp port to which the Udp queries ( short form GET requests) can be sent. This
        port number must be unique within the device."
    ::= { wtWebAlarm6x6UDP 1 }

wtWebAlarm6x6UdpEnable OBJECT-TYPE
    SYNTAX OCTET STRING 
    ACCESS read-write
    STATUS mandatory
    DESCRIPTION
        "Set this bit to enable UDP support:
        Octet 1: unused
        Octet 2: unused
        Octet 3: unused
        Octet 4:
        	Bit 1-7: unused
                Bit 0  : UDP enable"
    ::= { wtWebAlarm6x6UDP 2 }

wtWebAlarm6x6UdpRemotePort OBJECT-TYPE
    SYNTAX INTEGER
    ACCESS read-write
    STATUS mandatory
    DESCRIPTION
        "Udp remote port setting.
        If this value is set to zero, the source port read from a request will be used 
        as destination port for the answer.
        A non zero value forced the destination port to this value."
    ::= { wtWebAlarm6x6UDP 3 }
    
--  wtWebAlarm6x6Syslog Group
--------------------------------
    
wtWebAlarm6x6SyslogServerIP OBJECT-TYPE
    SYNTAX OCTET STRING 
    ACCESS read-write
    STATUS mandatory
    DESCRIPTION
        "Name or IP address of the Syslog server, which accepts the Syslog messgaes."
    ::= { wtWebAlarm6x6Syslog 1 }
    
wtWebAlarm6x6SyslogServerPort OBJECT-TYPE
    SYNTAX INTEGER
    ACCESS read-write
    STATUS mandatory
    DESCRIPTION
        "Portnumber of the Syslog servers, default 514."
    ::= { wtWebAlarm6x6Syslog 2 }

wtWebAlarm6x6SyslogSystemMessagesEnable OBJECT-TYPE
    SYNTAX OCTET STRING (SIZE(4))
    ACCESS read-write
    STATUS mandatory
    DESCRIPTION
        "Binary coded trigger conditions:
        Octet 1: unused
        Octet 2: unused
        Octet 3: unused
        Octet 4:
	        Bit 0:   ColdStart
	        Bit 1:   WarmStart
	        Bit 2:   Diag Messages
	        Bit 3-7: unused"
    ::= { wtWebAlarm6x6Syslog 3 }    

wtWebAlarm6x6SyslogEnable OBJECT-TYPE
    SYNTAX OCTET STRING 
    ACCESS read-write
    STATUS mandatory
    DESCRIPTION
        "Set bit 0to enable Syslog:
        Octet 1: unused
        Octet 2: unused
        Octet 3: unused
        Octet 4:
        	Bit 1-7: unused
                Bit 0  : Syslog enable"
    ::= { wtWebAlarm6x6Syslog 4 }

--  wtWebAlarm6x6FTP Group
--------------------------------

wtWebAlarm6x6FTPServerIP OBJECT-TYPE
    SYNTAX OCTET STRING 
    ACCESS read-write
    STATUS mandatory
    DESCRIPTION
        "Name or IP address of the FTP server, which accepts the FTP messages."
    ::= { wtWebAlarm6x6FTP 1 }
    
wtWebAlarm6x6FTPServerControlPort OBJECT-TYPE
    SYNTAX INTEGER
    ACCESS read-write
    STATUS mandatory
    DESCRIPTION
        "Portnumber of the control port of the FTP server, default 21."
    ::= { wtWebAlarm6x6FTP 2 }
    
wtWebAlarm6x6FTPUserName OBJECT-TYPE
    SYNTAX OCTET STRING 
    ACCESS read-write
    STATUS mandatory
    DESCRIPTION
        "FTP Loggin: user name."
    ::= { wtWebAlarm6x6FTP 3 }
    
wtWebAlarm6x6FTPPassword OBJECT-TYPE
    SYNTAX OCTET STRING 
    ACCESS read-write
    STATUS mandatory
    DESCRIPTION
        "FTP Loggin: user password."
    ::= { wtWebAlarm6x6FTP 4 }

wtWebAlarm6x6FTPAccount OBJECT-TYPE
    SYNTAX OCTET STRING 
    ACCESS read-write
    STATUS mandatory
    DESCRIPTION
        "FTP Loggin: name of account."
    ::= { wtWebAlarm6x6FTP 5 }

wtWebAlarm6x6FTPOption OBJECT-TYPE
    SYNTAX OCTET STRING 
    ACCESS read-write
    STATUS mandatory
    DESCRIPTION
        "Bit 0 switches the FTP Server in Passiv-Mode,
        the Client controls the data connection on its own:
        Octet 1: unused
        Octet 2: unused
        Octet 3: unused
        Octet 4:
        	Bit 1-7: unused
                Bit 0  : PASV enable"
    ::= { wtWebAlarm6x6FTP 6 }
    
wtWebAlarm6x6FTPEnable OBJECT-TYPE
    SYNTAX OCTET STRING 
    ACCESS read-write
    STATUS mandatory
    DESCRIPTION
        "Set Bit 0 to enable FTP:
        Octet 1: unused
        Octet 2: unused
        Octet 3: unused
        Octet 4:
        	Bit 1-7: unused
                Bit 0  : FTP enable"
    ::= { wtWebAlarm6x6FTP 7 }  

-- wtWebAlarm6x6Alarm Group
----------------------------

wtWebAlarm6x6AlarmCount OBJECT-TYPE
    SYNTAX INTEGER (1..12)
    ACCESS read-only
    STATUS mandatory
    DESCRIPTION
        "Number of independent alarms."
    ::= { wtWebAlarm6x6Alarm 1 }
    
-- Alarm Interface Table

wtWebAlarm6x6AlarmIfTable OBJECT-TYPE
    SYNTAX SEQUENCE OF WtWebAlarm6x6AlarmIfEntry
    ACCESS not-accessible
    STATUS mandatory
    DESCRIPTION
        "List of alarm indices."
    ::= { wtWebAlarm6x6Alarm 2 }

wtWebAlarm6x6AlarmIfEntry OBJECT-TYPE
    SYNTAX WtWebAlarm6x6AlarmIfEntry
    ACCESS not-accessible
    STATUS mandatory
    DESCRIPTION
        "Numbers of the alarms."
    INDEX  { wtWebAlarm6x6AlarmNo }
    ::= { wtWebAlarm6x6AlarmIfTable 1 }

WtWebAlarm6x6AlarmIfEntry ::= SEQUENCE {
    wtWebAlarm6x6AlarmNo INTEGER
}

wtWebAlarm6x6AlarmNo OBJECT-TYPE
    SYNTAX INTEGER (1..12)
    ACCESS read-only
    STATUS mandatory
    DESCRIPTION
        "Numbers of the alarms."
    ::= { wtWebAlarm6x6AlarmIfEntry 1 }

-- Alarm Table

wtWebAlarm6x6AlarmTable OBJECT-TYPE
    SYNTAX SEQUENCE OF WtWebAlarm6x6AlarmEntry
    ACCESS not-accessible
    STATUS mandatory
    DESCRIPTION
        "List of settings depending on the alarm number."
    ::= { wtWebAlarm6x6Alarm 3 }

wtWebAlarm6x6AlarmEntry OBJECT-TYPE
    SYNTAX WtWebAlarm6x6AlarmEntry
    ACCESS not-accessible
    STATUS mandatory
    DESCRIPTION
        "Alarm parameters of the individual alarms."
    INDEX  { wtWebAlarm6x6AlarmNo }
    ::= { wtWebAlarm6x6AlarmTable 1 }

WtWebAlarm6x6AlarmEntry ::= SEQUENCE {
    wtWebAlarm6x6AlarmInputTrigger		OCTET STRING,
    wtWebAlarm6x6AlarmMaxCounterValue		OCTET STRING,
    wtWebAlarm6x6AlarmInterval			OCTET STRING,
    wtWebAlarm6x6AlarmEnable			OCTET STRING,
    wtWebAlarm6x6AlarmMailAddr			OCTET STRING,
    wtWebAlarm6x6AlarmMailSubject		OCTET STRING,
    wtWebAlarm6x6AlarmMailText			OCTET STRING,
    wtWebAlarm6x6AlarmSnmpManagerIP		OCTET STRING,
    wtWebAlarm6x6AlarmSnmpTrapText		OCTET STRING,
    wtWebAlarm6x6AlarmUdpIpAddr			OCTET STRING,
    wtWebAlarm6x6AlarmUdpPort			INTEGER,
    wtWebAlarm6x6AlarmUdpText			OCTET STRING,
    wtWebAlarm6x6AlarmTcpIpAddr			OCTET STRING,
    wtWebAlarm6x6AlarmTcpPort			INTEGER,
    wtWebAlarm6x6AlarmTcpText			OCTET STRING,    
    wtWebAlarm6x6AlarmSyslogIpAddr		OCTET STRING,
    wtWebAlarm6x6AlarmSyslogPort		INTEGER,
    wtWebAlarm6x6AlarmSyslogText		OCTET STRING,
    wtWebAlarm6x6AlarmFtpDataPort		OCTET STRING,
    wtWebAlarm6x6AlarmFtpFileName		OCTET STRING,
    wtWebAlarm6x6AlarmFtpText			OCTET STRING,
    wtWebAlarm6x6AlarmFtpOption			OCTET STRING,
    
    wtWebAlarm6x6AlarmMailReleaseSubject	OCTET STRING,
    wtWebAlarm6x6AlarmMailReleaseText		OCTET STRING,
    wtWebAlarm6x6AlarmSnmpTrapReleaseText	OCTET STRING,
    wtWebAlarm6x6AlarmUdpReleaseText		OCTET STRING,
    wtWebAlarm6x6AlarmTcpReleaseText		OCTET STRING,    
    wtWebAlarm6x6AlarmSyslogReleaseText		OCTET STRING,
    wtWebAlarm6x6AlarmFtpReleaseText		OCTET STRING,        
    
    wtWebAlarm6x6AlarmName			OCTET STRING,
    wtWebAlarm6x6AlarmGlobalEnable		OCTET STRING,
    wtWebAlarm6x6AlarmCounterClear		OCTET STRING,
    wtWebAlarm6x6AlarmAckEnable			OCTET STRING,
    wtWebAlarm6x6AlarmAckPort			INTEGER,
    wtWebAlarm6x6AlarmSetPort			INTEGER,
    
    wtWebAlarm6x6AlarmMailTrgClearSubject	OCTET STRING,
    wtWebAlarm6x6AlarmMailTrgClearText		OCTET STRING,
    wtWebAlarm6x6AlarmSnmpTrapTrgClearText	OCTET STRING,
    wtWebAlarm6x6AlarmUdpTrgClearText		OCTET STRING,
    wtWebAlarm6x6AlarmTcpTrgClearText		OCTET STRING,    
    wtWebAlarm6x6AlarmSyslogTrgClearText	OCTET STRING,
    wtWebAlarm6x6AlarmFtpTrgClearText		OCTET STRING,
    
    wtWebAlarm6x6AlarmMailTrapTxEnable		OCTET STRING,
    wtWebAlarm6x6AlarmSnmpTrapTrapTxEnable	OCTET STRING,
    wtWebAlarm6x6AlarmUdpTrapTxEnable		OCTET STRING,
    wtWebAlarm6x6AlarmTcpTrapTxEnable		OCTET STRING,    
    wtWebAlarm6x6AlarmSyslogTrapTxEnable	OCTET STRING,
    wtWebAlarm6x6AlarmFtpTrapTxEnable		OCTET STRING        

}

wtWebAlarm6x6AlarmInputTrigger OBJECT-TYPE
    SYNTAX OCTET STRING (SIZE(12))
    ACCESS read-write
    STATUS mandatory
    DESCRIPTION
        "This variable allows setting of individual input trigger conditions. 
        The OCTETS are interpreted bit-by-bit, with each bit corresponding to an input. 
        Bit 0 corresponds to the LSB.
	The first four OCTETS contain the mask which determines which of the inputs are to 
	be considered (corresponding bit = 1) and which inputs are to ignore 
	(corresponding bit = 0):
	OCTET 1 : unused
	OCTET 2 : unused
	OCTET 3:  unused
	OCTET 4, Bit 0-5: Mask for digital inputs 0-5
		 Bit 6-7: unused
	
	OCTETS 5-8 contain the level (1=HIGH, 0=LOW) which the inputs 
	should assume:
	OCTET 5 : unused
	OCTET 6 : unused
	OCTET 7 : unused
        OCTET 8, Bit 0-5: Level of digital inputs 0-5
        	 Bit 6-7: unused
        
	OCTETS 9-12 contain the counter bit (1=ON, 0=OFF). Inputs masked with the counter bit trigger an alarm 
	when the corresponding counter reaching the wtWebAlarm6x6AlarmMaxCounterValue. Settings in OCTET 5-9 are then unused:
	OCTET 9 : unused
	OCTET 10: unused
	OCTET 11: unused
	OCTET 12, Bit 0-5: Counter bits of digital inputs 0-5
		  Bit 6-7: unused."
        
    ::= { wtWebAlarm6x6AlarmEntry 1 }

wtWebAlarm6x6AlarmMaxCounterValue OBJECT-TYPE
    SYNTAX OCTET STRING 
    ACCESS read-write
    STATUS mandatory
    DESCRIPTION
        "This variable configures a max. counter value. If an input counter value
        exceeds this max. value, the corresponding alarm is triggered. Input counters with
        its mask bit unset in wtWebAlarm6x6AlarmInputTrigger are not considered."
    ::= { wtWebAlarm6x6AlarmEntry 4 }

wtWebAlarm6x6AlarmInterval OBJECT-TYPE
    SYNTAX OCTET STRING 
    ACCESS read-write
    STATUS mandatory
    DESCRIPTION
        "Send interval for alarm messages."
    ::= { wtWebAlarm6x6AlarmEntry 5 }

wtWebAlarm6x6AlarmEnable OBJECT-TYPE
    SYNTAX OCTET STRING (SIZE(4))
    ACCESS read-write
    STATUS mandatory
    DESCRIPTION
        "Binary coded alarm enable:
        Octet 1: unused
        Octet 2: unused
        Octet 3: unused
        Octet 4:
        	Bit 0:  Output Switch Enable
		Bit 1:	Mail Enable
        	Bit 2:	SNMP Trap enable
        	Bit 3:  UDP enable
        	Bit 4:  unused
        	Bit 5:  TCP Client enable
        	Bit 6:	Syslog Messages enable
        	Bit 7:  FTP Client enable"
    ::= { wtWebAlarm6x6AlarmEntry 6 }

wtWebAlarm6x6AlarmMailAddr OBJECT-TYPE
    SYNTAX OCTET STRING 
    ACCESS read-write
    STATUS mandatory
    DESCRIPTION
        "E-Mail address for sending the alarm mail to."
    ::= { wtWebAlarm6x6AlarmEntry 7 }

wtWebAlarm6x6AlarmMailSubject OBJECT-TYPE
    SYNTAX OCTET STRING 
    ACCESS read-write
    STATUS mandatory
    DESCRIPTION
        "Subject line for alarm mail."
    ::= { wtWebAlarm6x6AlarmEntry 8 }

wtWebAlarm6x6AlarmMailText OBJECT-TYPE
    SYNTAX OCTET STRING 
    ACCESS read-write
    STATUS mandatory
    DESCRIPTION
        "Alarm mail text: 
        States of the Webio device can be included by using special tags.
        Please refer to the respective Webio manual"
    ::= { wtWebAlarm6x6AlarmEntry 9 }

wtWebAlarm6x6AlarmSnmpManagerIP OBJECT-TYPE
    SYNTAX OCTET STRING 
    ACCESS read-write
    STATUS mandatory
    DESCRIPTION
        "IP address of the SNMP Manager to which the Webio device should send SNMP traps."
    ::= { wtWebAlarm6x6AlarmEntry 10 }

wtWebAlarm6x6AlarmSnmpTrapText OBJECT-TYPE
    SYNTAX OCTET STRING 
    ACCESS read-write
    STATUS mandatory
    DESCRIPTION
        "This text appears in the trap body."
    ::= { wtWebAlarm6x6AlarmEntry 11 }
    
wtWebAlarm6x6AlarmUdpIpAddr OBJECT-TYPE
    SYNTAX OCTET STRING 
    ACCESS read-write
    STATUS mandatory
    DESCRIPTION
        "IP address of the UDP listener to which the Webio device should send UDP traps."
    ::= { wtWebAlarm6x6AlarmEntry 12 }    

wtWebAlarm6x6AlarmUdpPort OBJECT-TYPE
    SYNTAX INTEGER (1..65535) 
    ACCESS read-write
    STATUS mandatory
    DESCRIPTION
        "Port number of the UDP listener to which the Webio device should send UDP traps."
    ::= { wtWebAlarm6x6AlarmEntry 13 }    

wtWebAlarm6x6AlarmUdpText OBJECT-TYPE
    SYNTAX OCTET STRING 
    ACCESS read-write
    STATUS mandatory
    DESCRIPTION
        "This text appears in the UDP trap body."
    ::= { wtWebAlarm6x6AlarmEntry 14 }
    
wtWebAlarm6x6AlarmTcpIpAddr OBJECT-TYPE
    SYNTAX OCTET STRING
    ACCESS read-write
    STATUS mandatory
    DESCRIPTION
        "IP address of the TCP listener to which the Webio device should send TCP traps."
    ::= { wtWebAlarm6x6AlarmEntry 15 }    

wtWebAlarm6x6AlarmTcpPort OBJECT-TYPE
    SYNTAX INTEGER (1..65535) 
    ACCESS read-write
    STATUS mandatory
    DESCRIPTION
        "Port number of the TCP listener to which the Webio device should send TCP traps."
    ::= { wtWebAlarm6x6AlarmEntry 16 }    

wtWebAlarm6x6AlarmTcpText OBJECT-TYPE
    SYNTAX OCTET STRING 
    ACCESS read-write
    STATUS mandatory
    DESCRIPTION
        "This text appears in the TCP trap body."
    ::= { wtWebAlarm6x6AlarmEntry 17 }

wtWebAlarm6x6AlarmSyslogIpAddr OBJECT-TYPE
    SYNTAX OCTET STRING 
    ACCESS read-write
    STATUS mandatory
    DESCRIPTION
        "IP address of the syslog server to which the Webio device should send syslog messages."
    ::= { wtWebAlarm6x6AlarmEntry 18 }    

wtWebAlarm6x6AlarmSyslogPort OBJECT-TYPE
    SYNTAX INTEGER (1..65535) 
    ACCESS read-write
    STATUS mandatory
    DESCRIPTION
        "Port number of the syslog server to which the Webio device should send syslog messages."
    ::= { wtWebAlarm6x6AlarmEntry 19 }    

wtWebAlarm6x6AlarmSyslogText OBJECT-TYPE
    SYNTAX OCTET STRING 
    ACCESS read-write
    STATUS mandatory
    DESCRIPTION
        "Every message starts with the priority key, a time stamp and the host ip address, according RFC3164.
        This text appears in the following syslog message body."
    ::= { wtWebAlarm6x6AlarmEntry 20 }    
    
wtWebAlarm6x6AlarmFtpDataPort OBJECT-TYPE
    SYNTAX OCTET STRING 
    ACCESS read-write
    STATUS mandatory
    DESCRIPTION
        "Local data port: 1..65535 or AUTO: the next free port will be assigned."
    ::= { wtWebAlarm6x6AlarmEntry 21 }
    
wtWebAlarm6x6AlarmFtpFileName OBJECT-TYPE
    SYNTAX OCTET STRING 
    ACCESS read-write
    STATUS mandatory
    DESCRIPTION
        "Name of the file including path informations."
    ::= { wtWebAlarm6x6AlarmEntry 22 }
    
wtWebAlarm6x6AlarmFtpText OBJECT-TYPE
    SYNTAX OCTET STRING 
    ACCESS read-write
    STATUS mandatory
    DESCRIPTION
        "Message text to store on the FTP server."
    ::= { wtWebAlarm6x6AlarmEntry 23 }

wtWebAlarm6x6AlarmFtpOption OBJECT-TYPE
    SYNTAX OCTET STRING (SIZE(4))
    ACCESS read-write
    STATUS mandatory
    DESCRIPTION
        "Binary coded options, select only one option at the same time:
        STORE  = replace file
        APPEND = append message at the end of the file
        
        Octet 1: unused
        Octet 2: unused
        Octet 3: unused
        Octet 4:
		Bit 0  :	STORE
		Bit 1  :	APPEND
        	Bit 2-7:	unused"
    ::= { wtWebAlarm6x6AlarmEntry 24 }      
    
wtWebAlarm6x6AlarmMailReleaseSubject OBJECT-TYPE
    SYNTAX OCTET STRING 
    ACCESS read-write
    STATUS mandatory
    DESCRIPTION
        "Subject line for alarm mail."
    ::= { wtWebAlarm6x6AlarmEntry 26 }

wtWebAlarm6x6AlarmMailReleaseText OBJECT-TYPE
    SYNTAX OCTET STRING 
    ACCESS read-write
    STATUS mandatory
    DESCRIPTION
        "Alarm mail text: 
        States of the Webio device can be included by using special tags.
        Please refer to the respective Webio manual"
    ::= { wtWebAlarm6x6AlarmEntry 27 }    

wtWebAlarm6x6AlarmSnmpTrapReleaseText OBJECT-TYPE
    SYNTAX OCTET STRING 
    ACCESS read-write
    STATUS mandatory
    DESCRIPTION
        "This text appears in the trap body."
    ::= { wtWebAlarm6x6AlarmEntry 28 }

wtWebAlarm6x6AlarmUdpReleaseText OBJECT-TYPE
    SYNTAX OCTET STRING 
    ACCESS read-write
    STATUS mandatory
    DESCRIPTION
        "This text appears in the UDP trap body."
    ::= { wtWebAlarm6x6AlarmEntry 29 }

wtWebAlarm6x6AlarmTcpReleaseText OBJECT-TYPE
    SYNTAX OCTET STRING 
    ACCESS read-write
    STATUS mandatory
    DESCRIPTION
      "This text appears in the TCP trap body."
    ::= { wtWebAlarm6x6AlarmEntry 30 }

wtWebAlarm6x6AlarmSyslogReleaseText OBJECT-TYPE
    SYNTAX OCTET STRING 
    ACCESS read-write
    STATUS mandatory
    DESCRIPTION
        "Every message starts with the priority key, a time stamp and the host ip address, according RFC3164.
        This text appears in the following syslog message body."
    ::= { wtWebAlarm6x6AlarmEntry 31 }

wtWebAlarm6x6AlarmFtpReleaseText OBJECT-TYPE
    SYNTAX OCTET STRING 
    ACCESS read-write
    STATUS mandatory
    DESCRIPTION
        "Message text to store on the FTP server."
    ::= { wtWebAlarm6x6AlarmEntry 32 } 

wtWebAlarm6x6AlarmName OBJECT-TYPE
    SYNTAX OCTET STRING 
    ACCESS read-write
    STATUS mandatory
    DESCRIPTION
        "Name of the alarm."
    ::= { wtWebAlarm6x6AlarmEntry 33 }    

wtWebAlarm6x6AlarmGlobalEnable OBJECT-TYPE
    SYNTAX OCTET STRING 
    ACCESS read-write
    STATUS mandatory
    DESCRIPTION
        "Binary coded alarm activation:
        Die OCTETS werden bitweise interpretiert.
        Bit 0 entspricht dem LSB.
        OCTET 1: unused
        OCTET 2: unused
        OCTET 3: unused
        OCTET 4, Bit 1-7: unused
        	 Bit 0  : Alarm enable"
    ::= { wtWebAlarm6x6AlarmEntry 34 }    

wtWebAlarm6x6AlarmCounterClear OBJECT-TYPE
    SYNTAX OCTET STRING 
    ACCESS read-write
    STATUS mandatory
    DESCRIPTION
        "Binary coded options:
        The OCTETS are interpreted bit-by-bit. 
        Bit 0 corresponds to the LSB.
        OCTET 1: unused
        OCTET 2: unused
        OCTET 3: unused
        OCTET 4, Bit 2-7: unused
        	 Bit 1  : Counter clear on Alarm acknowledge 
        	 Bit 0  : Counter clear on Alarm send"
    ::= { wtWebAlarm6x6AlarmEntry 35 }


    wtWebAlarm6x6AlarmAckEnable OBJECT-TYPE
    SYNTAX OCTET STRING 
    ACCESS read-write
    STATUS mandatory
    DESCRIPTION
        "Binary coded options:
        The OCTETS are interpreted bit-by-bit. 
        Bit 0 corresponds to the LSB.
        OCTET 1: unused
        OCTET 2: unused
        OCTET 3: unused
        OCTET 4, Bit 2-7: unused
        	 Bit 1  : Software acknowledge enable
        	 Bit 0  : Hardware acknowledge enable"
    ::= { wtWebAlarm6x6AlarmEntry 36 }


    wtWebAlarm6x6AlarmAckPort OBJECT-TYPE
    SYNTAX INTEGER 
    ACCESS read-write
    STATUS mandatory
    DESCRIPTION
        "Number of the input, which clears the alarm (1-6)."
    ::= { wtWebAlarm6x6AlarmEntry 37 }

    wtWebAlarm6x6AlarmSetPort OBJECT-TYPE
    SYNTAX INTEGER 
    ACCESS read-write
    STATUS mandatory
    DESCRIPTION
        "Number of the output, which will be set by this alarm (1-6).
        The configuration of pulse mode and polarity defined in the port output section is used."
    ::= { wtWebAlarm6x6AlarmEntry 38 }
    
wtWebAlarm6x6AlarmMailTrgClearSubject OBJECT-TYPE
    SYNTAX OCTET STRING 
    ACCESS read-write
    STATUS mandatory
    DESCRIPTION
        "Subject line for alarm mail."
    ::= { wtWebAlarm6x6AlarmEntry 39 }

wtWebAlarm6x6AlarmMailTrgClearText OBJECT-TYPE
    SYNTAX OCTET STRING 
    ACCESS read-write
    STATUS mandatory
    DESCRIPTION
        "Alarm mail text: 
        States of the Webio device can be included by using special tags.
        Please refer to the respective Webio manual"
    ::= { wtWebAlarm6x6AlarmEntry 40 }    

wtWebAlarm6x6AlarmSnmpTrapTrgClearText OBJECT-TYPE
    SYNTAX OCTET STRING 
    ACCESS read-write
    STATUS mandatory
    DESCRIPTION
        "This text appears in the trap body."
    ::= { wtWebAlarm6x6AlarmEntry 41 }

wtWebAlarm6x6AlarmUdpTrgClearText OBJECT-TYPE
    SYNTAX OCTET STRING 
    ACCESS read-write
    STATUS mandatory
    DESCRIPTION
        "This text appears in the UDP trap body."
    ::= { wtWebAlarm6x6AlarmEntry 42 }

wtWebAlarm6x6AlarmTcpTrgClearText OBJECT-TYPE
    SYNTAX OCTET STRING 
    ACCESS read-write
    STATUS mandatory
    DESCRIPTION
      "This text appears in the TCP trap body."
    ::= { wtWebAlarm6x6AlarmEntry 43 }

wtWebAlarm6x6AlarmSyslogTrgClearText OBJECT-TYPE
    SYNTAX OCTET STRING 
    ACCESS read-write
    STATUS mandatory
    DESCRIPTION
        "Every message starts with the priority key, a time stamp and the host ip address, according RFC3164.
        This text appears in the following syslog message body."
    ::= { wtWebAlarm6x6AlarmEntry 44 }

wtWebAlarm6x6AlarmFtpTrgClearText OBJECT-TYPE
    SYNTAX OCTET STRING 
    ACCESS read-write
    STATUS mandatory
    DESCRIPTION
        "Message text to store on the FTP server."
    ::= { wtWebAlarm6x6AlarmEntry 45 }     

    wtWebAlarm6x6AlarmMailTrapTxEnable OBJECT-TYPE
    SYNTAX OCTET STRING 
    ACCESS read-write
    STATUS mandatory
    DESCRIPTION
        "Binary coded options:
        The OCTETS are interpreted bit-by-bit. 
        Bit 0 corresponds to the LSB.
        OCTET 1: unused
        OCTET 2: unused
        OCTET 3: unused
        OCTET 4, Bit 4-7: unused
        	 Bit 3  : Alarm OFF message enable
        	 Bit 2  : Trigger OFF message enable
        	 Bit 1  : Re-Trigger message enable
        	 Bit 0  : Alarm ON message enable"
    ::= { wtWebAlarm6x6AlarmEntry 46 }

    wtWebAlarm6x6AlarmSnmpTrapTrapTxEnable OBJECT-TYPE
    SYNTAX OCTET STRING 
    ACCESS read-write
    STATUS mandatory
    DESCRIPTION
        "Binary coded options:
        The OCTETS are interpreted bit-by-bit. 
        Bit 0 corresponds to the LSB.
        OCTET 1: unused
        OCTET 2: unused
        OCTET 3: unused
        OCTET 4, Bit 4-7: unused
        	 Bit 3  : Alarm OFF message enable
        	 Bit 2  : Trigger OFF message enable
        	 Bit 1  : Re-Trigger message enable
        	 Bit 0  : Alarm ON message enable"
    ::= { wtWebAlarm6x6AlarmEntry 47 }

    wtWebAlarm6x6AlarmUdpTrapTxEnable OBJECT-TYPE
    SYNTAX OCTET STRING 
    ACCESS read-write
    STATUS mandatory
    DESCRIPTION
        "Binary coded options:
        The OCTETS are interpreted bit-by-bit. 
        Bit 0 corresponds to the LSB.
        OCTET 1: unused
        OCTET 2: unused
        OCTET 3: unused
        OCTET 4, Bit 4-7: unused
        	 Bit 3  : Alarm OFF message enable
        	 Bit 2  : Trigger OFF message enable
        	 Bit 1  : Re-Trigger message enable
        	 Bit 0  : Alarm ON message enable"
    ::= { wtWebAlarm6x6AlarmEntry 48 }

    wtWebAlarm6x6AlarmTcpTrapTxEnable OBJECT-TYPE
    SYNTAX OCTET STRING 
    ACCESS read-write
    STATUS mandatory
    DESCRIPTION
        "Binary coded options:
        The OCTETS are interpreted bit-by-bit. 
        Bit 0 corresponds to the LSB.
        OCTET 1: unused
        OCTET 2: unused
        OCTET 3: unused
        OCTET 4, Bit 4-7: unused
        	 Bit 3  : Alarm OFF message enable
        	 Bit 2  : Trigger OFF message enable
        	 Bit 1  : Re-Trigger message enable
        	 Bit 0  : Alarm ON message enable"
    ::= { wtWebAlarm6x6AlarmEntry 49 }

    wtWebAlarm6x6AlarmSyslogTrapTxEnable OBJECT-TYPE
    SYNTAX OCTET STRING 
    ACCESS read-write
    STATUS mandatory
    DESCRIPTION
        "Binary coded options:
        The OCTETS are interpreted bit-by-bit. 
        Bit 0 corresponds to the LSB.
        OCTET 1: unused
        OCTET 2: unused
        OCTET 3: unused
        OCTET 4, Bit 4-7: unused
        	 Bit 3  : Alarm OFF message enable
        	 Bit 2  : Trigger OFF message enable
        	 Bit 1  : Re-Trigger message enable
        	 Bit 0  : Alarm ON message enable"
    ::= { wtWebAlarm6x6AlarmEntry 50 }

    wtWebAlarm6x6AlarmFtpTrapTxEnable OBJECT-TYPE
    SYNTAX OCTET STRING 
    ACCESS read-write
    STATUS mandatory
    DESCRIPTION
        "Binary coded options:
        The OCTETS are interpreted bit-by-bit. 
        Bit 0 corresponds to the LSB.
        OCTET 1: unused
        OCTET 2: unused
        OCTET 3: unused
        OCTET 4, Bit 4-7: unused
        	 Bit 3  : Alarm OFF message enable
        	 Bit 2  : Trigger OFF message enable
        	 Bit 1  : Re-Trigger message enable
        	 Bit 0  : Alarm ON message enable"
    ::= { wtWebAlarm6x6AlarmEntry 51 }

    
-- wtWebAlarm6x6Ports Group
----------------------------

-- Input Port Table

wtWebAlarm6x6InputPortTable OBJECT-TYPE
    SYNTAX SEQUENCE OF WtWebAlarm6x6InputPortEntry
    ACCESS not-accessible
    STATUS mandatory
    DESCRIPTION
        "List of settings depending on the input number."
    ::= { wtWebAlarm6x6Ports 1 }

wtWebAlarm6x6InputPortEntry OBJECT-TYPE
    SYNTAX WtWebAlarm6x6InputPortEntry
    ACCESS not-accessible
    STATUS mandatory
    DESCRIPTION
        "Input parameter for the individual inputs."
    INDEX  { wtWebAlarm6x6InputNo }
    ::= { wtWebAlarm6x6InputPortTable 1 }

WtWebAlarm6x6InputPortEntry ::= SEQUENCE {
    wtWebAlarm6x6PortInputName				OCTET STRING,
    wtWebAlarm6x6PortInputText				OCTET STRING,
    wtWebAlarm6x6PortInputFilter			INTEGER,
    wtWebAlarm6x6PortInputPulsePolarity			OCTET STRING,
    wtWebAlarm6x6PortInputCounterSet			INTEGER
   
}

wtWebAlarm6x6PortInputName OBJECT-TYPE
    SYNTAX OCTET STRING 
    ACCESS read-write
    STATUS mandatory
    DESCRIPTION
        "Name of the input."
    ::= { wtWebAlarm6x6InputPortEntry 1 }

wtWebAlarm6x6PortInputText OBJECT-TYPE
    SYNTAX OCTET STRING 
    ACCESS read-write
    STATUS mandatory
    DESCRIPTION
        "Description of the input."
    ::= { wtWebAlarm6x6InputPortEntry 2 }

    
wtWebAlarm6x6PortInputFilter OBJECT-TYPE
    SYNTAX INTEGER 
    ACCESS read-write
    STATUS mandatory
    DESCRIPTION
        "Pulses with a duration shorter than here specified (duration in 1/1000 sec),
	are ignored."
    ::= { wtWebAlarm6x6InputPortEntry 4 }
    
wtWebAlarm6x6PortInputPulsePolarity OBJECT-TYPE
    SYNTAX OCTET STRING (SIZE (4))
    ACCESS read-write
    STATUS mandatory
    DESCRIPTION
        "This value defines the polarity of the input pulse.
        OCTET 1: unused
        OCTET 2: unused
        OCTET 3: unused
        	OCTET 4: 
        	 Bit 0   : negative polarity
        	 Bit 1   : positive polarity
        	 Bit 2-7 : unused"
    ::= { wtWebAlarm6x6InputPortEntry 5 }
    
wtWebAlarm6x6PortInputCounterSet OBJECT-TYPE
    SYNTAX INTEGER 
    ACCESS read-write
    STATUS mandatory
    DESCRIPTION
        "Writing to this variable presets the counter, while reading returns the actual value."
    ::= { wtWebAlarm6x6InputPortEntry 7 }
   
-- Output Port Table

wtWebAlarm6x6OutputPortTable OBJECT-TYPE
    SYNTAX SEQUENCE OF WtWebAlarm6x6OutputPortEntry
    ACCESS not-accessible
    STATUS mandatory
    DESCRIPTION
        "List of settings depending on the output number."
    ::= { wtWebAlarm6x6Ports 2 }

wtWebAlarm6x6OutputPortEntry OBJECT-TYPE
    SYNTAX WtWebAlarm6x6OutputPortEntry
    ACCESS not-accessible
    STATUS mandatory
    DESCRIPTION
        "Output parameters of the individual outputs."
    INDEX  { wtWebAlarm6x6OutputNo }
    ::= { wtWebAlarm6x6OutputPortTable 1 }

WtWebAlarm6x6OutputPortEntry ::= SEQUENCE {
    wtWebAlarm6x6PortOutputName			OCTET STRING,
    wtWebAlarm6x6PortOutputText			OCTET STRING,
    wtWebAlarm6x6PortPulseDuration		INTEGER,
    wtWebAlarm6x6PortPulsePolarity		OCTET STRING
    
}

wtWebAlarm6x6PortOutputName OBJECT-TYPE
    SYNTAX OCTET STRING 
    ACCESS read-write
    STATUS mandatory
    DESCRIPTION
        "Name of the output."
    ::= { wtWebAlarm6x6OutputPortEntry 1 }

wtWebAlarm6x6PortOutputText OBJECT-TYPE
    SYNTAX OCTET STRING 
    ACCESS read-write
    STATUS mandatory
    DESCRIPTION
        "Description of the output."
    ::= { wtWebAlarm6x6OutputPortEntry 2 }

wtWebAlarm6x6PortPulseDuration OBJECT-TYPE
    SYNTAX INTEGER
    ACCESS read-write
    STATUS mandatory
    DESCRIPTION
        "Pulse length in 1/100 sec. Setting this value to zero, disables the pulse output."
    ::= { wtWebAlarm6x6OutputPortEntry 9 }

wtWebAlarm6x6PortPulsePolarity OBJECT-TYPE
    SYNTAX OCTET STRING (SIZE (4))
    ACCESS read-write
    STATUS mandatory
    DESCRIPTION
        "This value defines the polarity of the output pulse, if wtWebAlarm6x6PortPulseDuration is not set to zero.
        After the pulse is finished, the output switches back to the opposite state.
        OCTET 1: unused
        OCTET 2: unused
        OCTET 3: unused
        	OCTET 4: 
        	 Bit 0   : negative polarity
        	 Bit 1   : positive polarity
        	 Bit 2-7 : unused"
    ::= { wtWebAlarm6x6OutputPortEntry 10 }

-- wtWebAlarm6x6Manufact Group
----------------------------

wtWebAlarm6x6MfName OBJECT-TYPE
    SYNTAX OCTET STRING 
    ACCESS read-write
    STATUS mandatory
    DESCRIPTION
        "Manufacturer company name"
    ::= { wtWebAlarm6x6Manufact 1 }

wtWebAlarm6x6MfAddr OBJECT-TYPE
    SYNTAX OCTET STRING 
    ACCESS read-write
    STATUS mandatory
    DESCRIPTION
        "Manufacturer address."
    ::= { wtWebAlarm6x6Manufact 2 }

wtWebAlarm6x6MfHotline OBJECT-TYPE
    SYNTAX OCTET STRING 
    ACCESS read-write
    STATUS mandatory
    DESCRIPTION
        "Manufacturer hotline."
    ::= { wtWebAlarm6x6Manufact 3 }

wtWebAlarm6x6MfInternet OBJECT-TYPE
    SYNTAX OCTET STRING 
    ACCESS read-write
    STATUS mandatory
    DESCRIPTION
        "Manufacturer Internet address."
    ::= { wtWebAlarm6x6Manufact 4 }

wtWebAlarm6x6MfDeviceTyp OBJECT-TYPE
    SYNTAX OCTET STRING 
    ACCESS read-write
    STATUS mandatory
    DESCRIPTION
        "Manufacturer device name (model number)."
    ::= { wtWebAlarm6x6Manufact 5 }

wtWebAlarm6x6MfOrderNo OBJECT-TYPE
    SYNTAX OCTET STRING 
    ACCESS read-write
    STATUS mandatory
    DESCRIPTION
        "Manufacturer part number."
    ::= { wtWebAlarm6x6Manufact 6 }

-- wtWebAlarm6x6Diag Group
----------------------------

wtWebAlarm6x6DiagErrorCount OBJECT-TYPE
    SYNTAX INTEGER
    ACCESS read-only
    STATUS mandatory
    DESCRIPTION
        "Number of entries in the error memory."
    ::= { wtWebAlarm6x6Diag 1 }

wtWebAlarm6x6DiagBinaryError OBJECT-TYPE
    SYNTAX OCTET STRING 
    ACCESS read-only
    STATUS mandatory
    DESCRIPTION
        "Error causes coded bit-by-bit."
    ::= { wtWebAlarm6x6Diag 2 }

wtWebAlarm6x6DiagErrorIndex OBJECT-TYPE
    SYNTAX INTEGER
    ACCESS read-write
    STATUS mandatory
    DESCRIPTION
        "The value of this variable is used as an index to read 
        an error massege from wtWebAlarm6x6DiagErrorMessage.
        Errors are numbered from 1 to wtWebAlarm6x6DiagErrorCount.
        Writing a valid value into this variable, making the appropriate 
        message readable from wtWebAlarm6x6DiagErrorMessage."
    ::= { wtWebAlarm6x6Diag 3 }

wtWebAlarm6x6DiagErrorMessage OBJECT-TYPE
    SYNTAX OCTET STRING 
    ACCESS read-only
    STATUS mandatory
    DESCRIPTION
        "Using wtWebAlarm6x6DiagErrorIndex as an index, the appropriate message is available."
    ::= { wtWebAlarm6x6Diag 4 }
    
wtWebAlarm6x6DiagErrorClear OBJECT-TYPE
    SYNTAX INTEGER
    ACCESS write-only
    STATUS mandatory
    DESCRIPTION
        "Writing 1 into this variable clears all diagnosis messages."
    ::= { wtWebAlarm6x6Diag 5 }


-- TRAP DEFINITIONS

-- Diese SNMP-Traps werden gesendet, wenn die Alarmtriggerbedingungen zutreffen 

wtWebAlarm6x6Alert1 TRAP-TYPE
    ENTERPRISE  wtWebAlarm6x6
    VARIABLES   { wtWebAlarm6x6AlarmSnmpTrapText }
    DESCRIPTION
        "This SNMP trap is generated when Alarm 1 was triggered,
        SNMP trap enable is set and
        SNMP is enabled."
    -- NMS trap annotation
    --#TYPE "WebAlarm Alarm 1"
    --#SUMMARY "Alarm 1: %s"
    --#ARGUMENTS {0}
    --#SEVERITY INFORMATIONAL
    --#TIMEINDEX 99
    --#STATE OPERATIONAL    
    ::= 41

wtWebAlarm6x6Alert2 TRAP-TYPE
    ENTERPRISE  wtWebAlarm6x6
    VARIABLES   { wtWebAlarm6x6AlarmSnmpTrapText }
    DESCRIPTION
        "This SNMP trap is generated when Alarm 2 was triggered,
        SNMP trap enable is set and
        SNMP is enabled."
    -- NMS trap annotation
    --#TYPE "WebAlarm Alarm 2"
    --#SUMMARY "Alarm 2: %s"
    --#ARGUMENTS {0}
    --#SEVERITY INFORMATIONAL
    --#TIMEINDEX 99
    --#STATE OPERATIONAL    
    ::= 42

wtWebAlarm6x6Alert3 TRAP-TYPE
    ENTERPRISE  wtWebAlarm6x6
    VARIABLES   { wtWebAlarm6x6AlarmSnmpTrapText }
    DESCRIPTION
        "This SNMP trap is generated when Alarm 3 was triggered,
        SNMP trap enable is set and
        SNMP is enabled."
    -- NMS trap annotation
    --#TYPE "WebAlarm Alarm 3"
    --#SUMMARY "Alarm 3: %s"
    --#ARGUMENTS {0}
    --#SEVERITY INFORMATIONAL
    --#TIMEINDEX 99
    --#STATE OPERATIONAL    
    ::= 43

wtWebAlarm6x6Alert4 TRAP-TYPE
    ENTERPRISE  wtWebAlarm6x6
    VARIABLES   { wtWebAlarm6x6AlarmSnmpTrapText }
    DESCRIPTION
        "This SNMP trap is generated when Alarm 4 was triggered,
        SNMP trap enable is set and
        SNMP is enabled."
    -- NMS trap annotation
    --#TYPE "WebAlarm Alarm 4"
    --#SUMMARY "Alarm 4: %s"
    --#ARGUMENTS {0}
    --#SEVERITY INFORMATIONAL
    --#TIMEINDEX 99
    --#STATE OPERATIONAL    
    ::= 44

wtWebAlarm6x6Alert5 TRAP-TYPE
    ENTERPRISE  wtWebAlarm6x6
    VARIABLES   { wtWebAlarm6x6AlarmSnmpTrapText }
    DESCRIPTION
        "This SNMP trap is generated when Alarm 5 was triggered,
        SNMP trap enable is set and
        SNMP is enabled."
    -- NMS trap annotation
    --#TYPE "WebAlarm Alarm 5"
    --#SUMMARY "Alarm 5: %s"
    --#ARGUMENTS {0}
    --#SEVERITY INFORMATIONAL
    --#TIMEINDEX 99
    --#STATE OPERATIONAL    
    ::= 45

wtWebAlarm6x6Alert6 TRAP-TYPE
    ENTERPRISE  wtWebAlarm6x6
    VARIABLES   { wtWebAlarm6x6AlarmSnmpTrapText }
    DESCRIPTION
        "This SNMP trap is generated when Alarm 6 was triggered,
        SNMP trap enable is set and
        SNMP is enabled."
    -- NMS trap annotation
    --#TYPE "WebAlarm Alarm 6"
    --#SUMMARY "Alarm 6: %s"
    --#ARGUMENTS {0}
    --#SEVERITY INFORMATIONAL
    --#TIMEINDEX 99
    --#STATE OPERATIONAL    
    ::= 46

wtWebAlarm6x6Alert7 TRAP-TYPE
    ENTERPRISE  wtWebAlarm6x6
    VARIABLES   { wtWebAlarm6x6AlarmSnmpTrapText }
    DESCRIPTION
        "This SNMP trap is generated when Alarm 7 was triggered,
        SNMP trap enable is set and
        SNMP is enabled."
    -- NMS trap annotation
    --#TYPE "WebAlarm Alarm 7"
    --#SUMMARY "Alarm 7: %s"
    --#ARGUMENTS {0}
    --#SEVERITY INFORMATIONAL
    --#TIMEINDEX 99
    --#STATE OPERATIONAL    
    ::= 47

wtWebAlarm6x6Alert8 TRAP-TYPE
    ENTERPRISE  wtWebAlarm6x6
    VARIABLES   { wtWebAlarm6x6AlarmSnmpTrapText }
    DESCRIPTION
        "This SNMP trap is generated when Alarm 8 was triggered,
        SNMP trap enable is set and
        SNMP is enabled."
    -- NMS trap annotation
    --#TYPE "WebAlarm Alarm 8"
    --#SUMMARY "Alarm 8: %s"
    --#ARGUMENTS {0}
    --#SEVERITY INFORMATIONAL
    --#TIMEINDEX 99
    --#STATE OPERATIONAL    
    ::= 48

wtWebAlarm6x6Alert9 TRAP-TYPE
    ENTERPRISE  wtWebAlarm6x6
    VARIABLES   { wtWebAlarm6x6AlarmSnmpTrapText }
    DESCRIPTION
        "This SNMP trap is generated when Alarm 9 was triggered,
        SNMP trap enable is set and
        SNMP is enabled."
    -- NMS trap annotation
    --#TYPE "WebAlarm Alarm 9"
    --#SUMMARY "Alarm 9: %s"
    --#ARGUMENTS {0}
    --#SEVERITY INFORMATIONAL
    --#TIMEINDEX 99
    --#STATE OPERATIONAL    
    ::= 49

wtWebAlarm6x6Alert10 TRAP-TYPE
    ENTERPRISE  wtWebAlarm6x6
    VARIABLES   { wtWebAlarm6x6AlarmSnmpTrapText }
    DESCRIPTION
        "This SNMP trap is generated when Alarm 10 was triggered,
        SNMP trap enable is set and
        SNMP is enabled."
    -- NMS trap annotation
    --#TYPE "WebAlarm Alarm 10"
    --#SUMMARY "Alarm 10: %s"
    --#ARGUMENTS {0}
    --#SEVERITY INFORMATIONAL
    --#TIMEINDEX 99
    --#STATE OPERATIONAL    
    ::= 50

wtWebAlarm6x6Alert11 TRAP-TYPE
    ENTERPRISE  wtWebAlarm6x6
    VARIABLES   { wtWebAlarm6x6AlarmSnmpTrapText }
    DESCRIPTION
        "This SNMP trap is generated when Alarm 11 was triggered,
        SNMP trap enable is set and
        SNMP is enabled."
    -- NMS trap annotation
    --#TYPE "WebAlarm Alarm 11"
    --#SUMMARY "Alarm 11: %s"
    --#ARGUMENTS {0}
    --#SEVERITY INFORMATIONAL
    --#TIMEINDEX 99
    --#STATE OPERATIONAL    
    ::= 51

wtWebAlarm6x6Alert12 TRAP-TYPE
    ENTERPRISE  wtWebAlarm6x6
    VARIABLES   { wtWebAlarm6x6AlarmSnmpTrapText }
    DESCRIPTION
        "This SNMP trap is generated when Alarm 12 was triggered,
        SNMP trap enable is set and
        SNMP is enabled."
    -- NMS trap annotation
    --#TYPE "WebAlarm Alarm 12"
    --#SUMMARY "Alarm 12: %s"
    --#ARGUMENTS {0}
    --#SEVERITY INFORMATIONAL
    --#TIMEINDEX 99
    --#STATE OPERATIONAL    
    ::= 52

wtWebAlarm6x6Alert13 TRAP-TYPE
    ENTERPRISE  wtWebAlarm6x6
    VARIABLES   { wtWebAlarm6x6AlarmSnmpTrapReleaseText }
    DESCRIPTION
        "This SNMP trap is generated when Alarm 1 was released,
        SNMP trap enable is set and
        SNMP is enabled."
    -- NMS trap annotation
    --#TYPE "WebAlarm Release Alarm 1"
    --#SUMMARY "Alarm 1: %s"
    --#ARGUMENTS {0}
    --#SEVERITY INFORMATIONAL
    --#TIMEINDEX 99
    --#STATE OPERATIONAL    
    ::= 71

wtWebAlarm6x6Alert14 TRAP-TYPE
    ENTERPRISE  wtWebAlarm6x6
    VARIABLES   { wtWebAlarm6x6AlarmSnmpTrapReleaseText }
    DESCRIPTION
        "This SNMP trap is generated when Alarm 2 was released,
        SNMP trap enable is set and
        SNMP is enabled."
    -- NMS trap annotation
    --#TYPE "WebAlarm Release Alarm 2"
    --#SUMMARY "Release Alarm 2: %s"
    --#ARGUMENTS {0}
    --#SEVERITY INFORMATIONAL
    --#TIMEINDEX 99
    --#STATE OPERATIONAL    
    ::= 72

wtWebAlarm6x6Alert15 TRAP-TYPE
    ENTERPRISE  wtWebAlarm6x6
    VARIABLES   { wtWebAlarm6x6AlarmSnmpTrapReleaseText }
    DESCRIPTION
        "This SNMP trap is generated when Alarm 3 was released,
        SNMP trap enable is set and
        SNMP is enabled."
    -- NMS trap annotation
    --#TYPE "WebAlarm Release Alarm 3"
    --#SUMMARY "Release Alarm 3: %s"
    --#ARGUMENTS {0}
    --#SEVERITY INFORMATIONAL
    --#TIMEINDEX 99
    --#STATE OPERATIONAL    
    ::= 73

wtWebAlarm6x6Alert16 TRAP-TYPE
    ENTERPRISE  wtWebAlarm6x6
    VARIABLES   { wtWebAlarm6x6AlarmSnmpTrapReleaseText }
    DESCRIPTION
        "This SNMP trap is generated when Alarm 4 was released,
        SNMP trap enable is set and
        SNMP is enabled."
    -- NMS trap annotation
    --#TYPE "WebAlarm Release Alarm 4"
    --#SUMMARY "Release Alarm 4: %s"
    --#ARGUMENTS {0}
    --#SEVERITY INFORMATIONAL
    --#TIMEINDEX 99
    --#STATE OPERATIONAL    
    ::= 74

wtWebAlarm6x6Alert17 TRAP-TYPE
    ENTERPRISE  wtWebAlarm6x6
    VARIABLES   { wtWebAlarm6x6AlarmSnmpTrapReleaseText }
    DESCRIPTION
        "This SNMP trap is generated when Alarm 5 was released,
        SNMP trap enable is set and
        SNMP is enabled."
    -- NMS trap annotation
    --#TYPE "WebAlarm Release Alarm 5"
    --#SUMMARY "Release Alarm 5: %s"
    --#ARGUMENTS {0}
    --#SEVERITY INFORMATIONAL
    --#TIMEINDEX 99
    --#STATE OPERATIONAL    
    ::= 75

wtWebAlarm6x6Alert18 TRAP-TYPE
    ENTERPRISE  wtWebAlarm6x6
    VARIABLES   { wtWebAlarm6x6AlarmSnmpTrapReleaseText }
    DESCRIPTION
        "This SNMP trap is generated when Alarm 6 was released,
        SNMP trap enable is set and
        SNMP is enabled."
    -- NMS trap annotation
    --#TYPE "WebAlarm Release Alarm 6"
    --#SUMMARY "Release Alarm 6: %s"
    --#ARGUMENTS {0}
    --#SEVERITY INFORMATIONAL
    --#TIMEINDEX 99
    --#STATE OPERATIONAL    
    ::= 76

wtWebAlarm6x6Alert19 TRAP-TYPE
    ENTERPRISE  wtWebAlarm6x6
    VARIABLES   { wtWebAlarm6x6AlarmSnmpTrapReleaseText }
    DESCRIPTION
        "This SNMP trap is generated when Alarm 7 was released,
        SNMP trap enable is set and
        SNMP is enabled."
    -- NMS trap annotation
    --#TYPE "WebAlarm Release Alarm 7"
    --#SUMMARY "Release Alarm 7: %s"
    --#ARGUMENTS {0}
    --#SEVERITY INFORMATIONAL
    --#TIMEINDEX 99
    --#STATE OPERATIONAL    
    ::= 77

wtWebAlarm6x6Alert20 TRAP-TYPE
    ENTERPRISE  wtWebAlarm6x6
    VARIABLES   { wtWebAlarm6x6AlarmSnmpTrapReleaseText }
    DESCRIPTION
        "This SNMP trap is generated when Alarm 8 was released,
        SNMP trap enable is set and
        SNMP is enabled."
    -- NMS trap annotation
    --#TYPE "WebAlarm Release Alarm 8"
    --#SUMMARY "Release Alarm 8: %s"
    --#ARGUMENTS {0}
    --#SEVERITY INFORMATIONAL
    --#TIMEINDEX 99
    --#STATE OPERATIONAL    
    ::= 78

wtWebAlarm6x6Alert21 TRAP-TYPE
    ENTERPRISE  wtWebAlarm6x6
    VARIABLES   { wtWebAlarm6x6AlarmSnmpTrapReleaseText }
    DESCRIPTION
        "This SNMP trap is generated when Alarm 9 was released,
        SNMP trap enable is set and
        SNMP is enabled."
    -- NMS trap annotation
    --#TYPE "WebAlarm Release Alarm 9"
    --#SUMMARY "Release Alarm 9: %s"
    --#ARGUMENTS {0}
    --#SEVERITY INFORMATIONAL
    --#TIMEINDEX 99
    --#STATE OPERATIONAL    
    ::= 79

wtWebAlarm6x6Alert22 TRAP-TYPE
    ENTERPRISE  wtWebAlarm6x6
    VARIABLES   { wtWebAlarm6x6AlarmSnmpTrapReleaseText }
    DESCRIPTION
        "This SNMP trap is generated when Alarm 10 was released,
        SNMP trap enable is set and
        SNMP is enabled."
    -- NMS trap annotation
    --#TYPE "WebAlarm Release Alarm 10"
    --#SUMMARY "Release Alarm 10: %s"
    --#ARGUMENTS {0}
    --#SEVERITY INFORMATIONAL
    --#TIMEINDEX 99
    --#STATE OPERATIONAL    
    ::= 80

wtWebAlarm6x6Alert23 TRAP-TYPE
    ENTERPRISE  wtWebAlarm6x6
    VARIABLES   { wtWebAlarm6x6AlarmSnmpTrapReleaseText }
    DESCRIPTION
        "This SNMP trap is generated when Alarm 11 was released,
        SNMP trap enable is set and
        SNMP is enabled."
    -- NMS trap annotation
    --#TYPE "WebAlarm Release Alarm 11"
    --#SUMMARY "Release Alarm 11: %s"
    --#ARGUMENTS {0}
    --#SEVERITY INFORMATIONAL
    --#TIMEINDEX 99
    --#STATE OPERATIONAL    
    ::= 81

wtWebAlarm6x6Alert24 TRAP-TYPE
    ENTERPRISE  wtWebAlarm6x6
    VARIABLES   { wtWebAlarm6x6AlarmSnmpTrapReleaseText }
    DESCRIPTION
        "This SNMP trap is generated when Alarm 12 was released,
        SNMP trap enable is set and
        SNMP is enabled."
    -- NMS trap annotation
    --#TYPE "WebAlarm Release Alarm 12"
    --#SUMMARY "Release Alarm 12: %s"
    --#ARGUMENTS {0}
    --#SEVERITY INFORMATIONAL
    --#TIMEINDEX 99
    --#STATE OPERATIONAL    
    ::= 82

wtWebAlarm6x6Alert25 TRAP-TYPE
    ENTERPRISE  wtWebAlarm6x6
    VARIABLES   { wtWebAlarm6x6AlarmSnmpTrapTrgClearText }
    DESCRIPTION
        "This SNMP trap is generated when the trigger of the Alarm 1 was released,
        SNMP trap enable is set and
        SNMP is enabled."
    -- NMS trap annotation
    --#TYPE "WebAlarm Release Alarm 1"
    --#SUMMARY "Alarm 1: %s"
    --#ARGUMENTS {0}
    --#SEVERITY INFORMATIONAL
    --#TIMEINDEX 99
    --#STATE OPERATIONAL    
    ::= 91

wtWebAlarm6x6Alert26 TRAP-TYPE
    ENTERPRISE  wtWebAlarm6x6
    VARIABLES   { wtWebAlarm6x6AlarmSnmpTrapTrgClearText }
    DESCRIPTION
        "This SNMP trap is generated when the trigger of the Alarm 2 was released,
        SNMP trap enable is set and
        SNMP is enabled."
    -- NMS trap annotation
    --#TYPE "WebAlarm Release Alarm 2"
    --#SUMMARY "Release Alarm 2: %s"
    --#ARGUMENTS {0}
    --#SEVERITY INFORMATIONAL
    --#TIMEINDEX 99
    --#STATE OPERATIONAL    
    ::= 92

wtWebAlarm6x6Alert27 TRAP-TYPE
    ENTERPRISE  wtWebAlarm6x6
    VARIABLES   { wtWebAlarm6x6AlarmSnmpTrapTrgClearText }
    DESCRIPTION
        "This SNMP trap is generated when the trigger of the Alarm 3 was released,
        SNMP trap enable is set and
        SNMP is enabled."
    -- NMS trap annotation
    --#TYPE "WebAlarm Release Alarm 3"
    --#SUMMARY "Release Alarm 3: %s"
    --#ARGUMENTS {0}
    --#SEVERITY INFORMATIONAL
    --#TIMEINDEX 99
    --#STATE OPERATIONAL    
    ::= 93

wtWebAlarm6x6Alert28 TRAP-TYPE
    ENTERPRISE  wtWebAlarm6x6
    VARIABLES   { wtWebAlarm6x6AlarmSnmpTrapTrgClearText }
    DESCRIPTION
        "This SNMP trap is generated when the trigger of the Alarm 4 was released,
        SNMP trap enable is set and
        SNMP is enabled."
    -- NMS trap annotation
    --#TYPE "WebAlarm Release Alarm 4"
    --#SUMMARY "Release Alarm 4: %s"
    --#ARGUMENTS {0}
    --#SEVERITY INFORMATIONAL
    --#TIMEINDEX 99
    --#STATE OPERATIONAL    
    ::= 94

wtWebAlarm6x6Alert29 TRAP-TYPE
    ENTERPRISE  wtWebAlarm6x6
    VARIABLES   { wtWebAlarm6x6AlarmSnmpTrapTrgClearText }
    DESCRIPTION
        "This SNMP trap is generated when the trigger of the Alarm 5 was released,
        SNMP trap enable is set and
        SNMP is enabled."
    -- NMS trap annotation
    --#TYPE "WebAlarm Release Alarm 5"
    --#SUMMARY "Release Alarm 5: %s"
    --#ARGUMENTS {0}
    --#SEVERITY INFORMATIONAL
    --#TIMEINDEX 99
    --#STATE OPERATIONAL    
    ::= 95

wtWebAlarm6x6Alert30 TRAP-TYPE
    ENTERPRISE  wtWebAlarm6x6
    VARIABLES   { wtWebAlarm6x6AlarmSnmpTrapTrgClearText }
    DESCRIPTION
        "This SNMP trap is generated when the trigger of the Alarm 6 was released,
        SNMP trap enable is set and
        SNMP is enabled."
    -- NMS trap annotation
    --#TYPE "WebAlarm Release Alarm 6"
    --#SUMMARY "Release Alarm 6: %s"
    --#ARGUMENTS {0}
    --#SEVERITY INFORMATIONAL
    --#TIMEINDEX 99
    --#STATE OPERATIONAL    
    ::= 96

wtWebAlarm6x6Alert31 TRAP-TYPE
    ENTERPRISE  wtWebAlarm6x6
    VARIABLES   { wtWebAlarm6x6AlarmSnmpTrapTrgClearText }
    DESCRIPTION
        "This SNMP trap is generated when the trigger of the Alarm 7 was released,
        SNMP trap enable is set and
        SNMP is enabled."
    -- NMS trap annotation
    --#TYPE "WebAlarm Release Alarm 7"
    --#SUMMARY "Release Alarm 7: %s"
    --#ARGUMENTS {0}
    --#SEVERITY INFORMATIONAL
    --#TIMEINDEX 99
    --#STATE OPERATIONAL    
    ::= 97

wtWebAlarm6x6Alert32 TRAP-TYPE
    ENTERPRISE  wtWebAlarm6x6
    VARIABLES   { wtWebAlarm6x6AlarmSnmpTrapTrgClearText }
    DESCRIPTION
        "This SNMP trap is generated when the trigger of the Alarm 8 was released,
        SNMP trap enable is set and
        SNMP is enabled."
    -- NMS trap annotation
    --#TYPE "WebAlarm Release Alarm 8"
    --#SUMMARY "Release Alarm 8: %s"
    --#ARGUMENTS {0}
    --#SEVERITY INFORMATIONAL
    --#TIMEINDEX 99
    --#STATE OPERATIONAL    
    ::= 98

wtWebAlarm6x6Alert33 TRAP-TYPE
    ENTERPRISE  wtWebAlarm6x6
    VARIABLES   { wtWebAlarm6x6AlarmSnmpTrapTrgClearText }
    DESCRIPTION
        "This SNMP trap is generated when the trigger of the Alarm 9 was released,
        SNMP trap enable is set and
        SNMP is enabled."
    -- NMS trap annotation
    --#TYPE "WebAlarm Release Alarm 9"
    --#SUMMARY "Release Alarm 9: %s"
    --#ARGUMENTS {0}
    --#SEVERITY INFORMATIONAL
    --#TIMEINDEX 99
    --#STATE OPERATIONAL    
    ::= 99

wtWebAlarm6x6Alert34 TRAP-TYPE
    ENTERPRISE  wtWebAlarm6x6
    VARIABLES   { wtWebAlarm6x6AlarmSnmpTrapTrgClearText }
    DESCRIPTION
        "This SNMP trap is generated when the trigger of the Alarm 10 was released,
        SNMP trap enable is set and
        SNMP is enabled."
    -- NMS trap annotation
    --#TYPE "WebAlarm Release Alarm 10"
    --#SUMMARY "Release Alarm 10: %s"
    --#ARGUMENTS {0}
    --#SEVERITY INFORMATIONAL
    --#TIMEINDEX 99
    --#STATE OPERATIONAL    
    ::= 100

wtWebAlarm6x6Alert35 TRAP-TYPE
    ENTERPRISE  wtWebAlarm6x6
    VARIABLES   { wtWebAlarm6x6AlarmSnmpTrapTrgClearText }
    DESCRIPTION
        "This SNMP trap is generated when the trigger of the Alarm 11 was released,
        SNMP trap enable is set and
        SNMP is enabled."
    -- NMS trap annotation
    --#TYPE "WebAlarm Release Alarm 11"
    --#SUMMARY "Release Alarm 11: %s"
    --#ARGUMENTS {0}
    --#SEVERITY INFORMATIONAL
    --#TIMEINDEX 99
    --#STATE OPERATIONAL    
    ::= 101

wtWebAlarm6x6Alert36 TRAP-TYPE
    ENTERPRISE  wtWebAlarm6x6
    VARIABLES   { wtWebAlarm6x6AlarmSnmpTrapTrgClearText }
    DESCRIPTION
        "This SNMP trap is generated when the trigger of the Alarm 12 was released,
        SNMP trap enable is set and
        SNMP is enabled."
    -- NMS trap annotation
    --#TYPE "WebAlarm Release Alarm 12"
    --#SUMMARY "Release Alarm 12: %s"
    --#ARGUMENTS {0}
    --#SEVERITY INFORMATIONAL
    --#TIMEINDEX 99
    --#STATE OPERATIONAL    
    ::= 102
    
wtWebAlarm6x6AlertDiag TRAP-TYPE
    ENTERPRISE  wtWebAlarm6x6
    VARIABLES   { 	
    		wtWebAlarm6x6DiagErrorIndex,
    	  	wtWebAlarm6x6DiagErrorMessage
    		}
    DESCRIPTION
        "This SNMP trap is generated when a diagnosis/error message was triggered,
        SNMP trap enable is set and
        SNMP is enabled."
    -- NMS trap annotation
    --#TYPE "WebAlarm Diagnose Error"
    --#SUMMARY "Diagnose error index: %d, Message: %s."
    --#ARGUMENTS {0,1}
    --#SEVERITY MAJOR
    --#TIMEINDEX 99
    --#STATE DEGRADED    
    ::= 110

--------------------------------------------------------------------------------
--------------------------------------------------------------------------------
--------------------------------------------------------------------------------

-- wtWebCount6InOut Group
------------------------

wtWebCount6Inputs OBJECT-TYPE
    SYNTAX INTEGER (1..6)
    ACCESS read-only
    STATUS mandatory
    DESCRIPTION
        "Number of idependent inputs."
    ::= { wtWebCount6InOut 1 }

wtWebCount6Outputs OBJECT-TYPE
    SYNTAX INTEGER (1..6)
    ACCESS read-only
    STATUS mandatory
    DESCRIPTION
        "Number of independent outputs."
    ::= { wtWebCount6InOut 2 }

-- Input Interface Table

wtWebCount6InputTable OBJECT-TYPE
    SYNTAX SEQUENCE OF WtWebCount6InputEntry
    ACCESS not-accessible
    STATUS mandatory
    DESCRIPTION
        "List of input indices."
    ::= { wtWebCount6InOut 3 }

wtWebCount6InputEntry OBJECT-TYPE
    SYNTAX WtWebCount6InputEntry
    ACCESS not-accessible
    STATUS mandatory
    DESCRIPTION
        "Number of the inputs."
    INDEX  { wtWebCount6InputNo }
    ::= { wtWebCount6InputTable 1 }

WtWebCount6InputEntry ::= SEQUENCE {
    wtWebCount6InputNo INTEGER,
    wtWebCount6InputCounter INTEGER,
    wtWebCount6InputCounterClear INTEGER,
    wtWebCount6InputState INTEGER
}

wtWebCount6InputNo OBJECT-TYPE
    SYNTAX INTEGER (1)
    ACCESS read-only
    STATUS mandatory
    DESCRIPTION
        "Index numbers of the inputs."
    ::= { wtWebCount6InputEntry 1 }

wtWebCount6InputCounter OBJECT-TYPE
    SYNTAX INTEGER (1)
    ACCESS read-only
    STATUS mandatory
    DESCRIPTION
        "Value of the input counter."
    ::= { wtWebCount6InputEntry 2 }
    
wtWebCount6InputCounterClear OBJECT-TYPE
    SYNTAX INTEGER
    ACCESS read-only
    STATUS mandatory
    DESCRIPTION
        "Clears the input counter after returning its value."
    ::= { wtWebCount6InputEntry 3 }
    
wtWebCount6InputState OBJECT-TYPE
    SYNTAX INTEGER{
    wtWebCount6InputState-OFF(0),
    wtWebCount6InputState-ON(1)
    }
    ACCESS read-only
    STATUS mandatory
    DESCRIPTION
        "Tates of the inputs."
    ::= { wtWebCount6InputEntry 4 }
    
wtWebCount6InputValue OBJECT-TYPE
    SYNTAX INTEGER 
    ACCESS read-only
    STATUS mandatory
    DESCRIPTION
        "This variable is used to read the inputs of the digital I/O port.
        The OCTETS are interpreted bit-by-bit, with each bit corresponding to an input.
        Bit 0 corresponds to the LSB.
        OCTET 1: unused
        OCTET 2: unused
        OCTET 3: unused
        OCTET 4, Bit 0-5: Digital inputs 0-5
        	 Bit 6-7: unused"
    ::= { wtWebCount6InOut 4 }
    
-- Report Output Interface Table

wtWebCount6ReportOutputTable OBJECT-TYPE
    SYNTAX SEQUENCE OF WtWebCount6ReportOutputEntry
    ACCESS not-accessible
    STATUS mandatory
    DESCRIPTION
        "List of Report indices.."
    ::= { wtWebCount6InOut 8 }

wtWebCount6ReportOutputEntry OBJECT-TYPE
    SYNTAX WtWebCount6ReportOutputEntry
    ACCESS not-accessible
    STATUS mandatory
    DESCRIPTION
        "Index reference."
    INDEX  { wtWebCount6ReportNo }
    ::= { wtWebCount6ReportOutputTable 1 }

WtWebCount6ReportOutputEntry ::= SEQUENCE {
    wtWebCount6ReportOutputState	INTEGER,
    wtWebCount6ReportTriggerState	INTEGER
}

wtWebCount6ReportOutputState OBJECT-TYPE
    SYNTAX INTEGER{
    wtWebCount6ReportOutputState-OFF(0),
    wtWebCount6ReportOutputState-ON(1)
    }
    ACCESS read-write
    STATUS mandatory
    DESCRIPTION
        "State of the Report."
    ::= { wtWebCount6ReportOutputEntry 1 }

wtWebCount6ReportTriggerState OBJECT-TYPE
    SYNTAX INTEGER{
    wtWebCount6ReportTriggerState-OFF(0),
    wtWebCount6ReportTriggerState-ON(1)
    }
    ACCESS read-only
    STATUS mandatory
    DESCRIPTION
        "State of the trigger condition."
    ::= { wtWebCount6ReportOutputEntry 2 }    
    
-- wtWebCount6SessCntrl Group
--------------------------------

wtWebCount6SessCntrlPassword OBJECT-TYPE
    SYNTAX OCTET STRING 
    ACCESS read-write
    STATUS mandatory
    DESCRIPTION
        "Entering this password opens a session which is ended by writing a 1 to 
        wtWebCount6SessCntrlLogout. When read this variable provides a string of
        length zero."
    ::= { wtWebCount6SessCntrl 1 }

wtWebCount6SessCntrlConfigMode OBJECT-TYPE
    SYNTAX INTEGER {
    wtWebCount6SessCntrl-NoSession(0),
    wtWebCount6SessCntrl-Session(1)
    }
    ACCESS read-only
    STATUS mandatory
    DESCRIPTION
        "When the device is in SNMP configuration mode, the value 1 is
        returned, otherwise 0. If the read value is 0 even though the password
        was written, the device is already in config mode and the variables
        can only be read."
    ::= { wtWebCount6SessCntrl 2 }

wtWebCount6SessCntrlLogout OBJECT-TYPE
    SYNTAX INTEGER 
    ACCESS read-write
    STATUS mandatory
    DESCRIPTION
        "If the device is in configuration mode and the session was opened by
        this SNMP Manager, writing a 1 to this variable will end the session 
        and all parameters are stored.
        Writing a 2 discards all entries again. When read this variable
        provides the value 0."
    ::= { wtWebCount6SessCntrl 3 }

wtWebCount6SessCntrlAdminPassword OBJECT-TYPE
    SYNTAX OCTET STRING 
    ACCESS read-write
    STATUS mandatory
    DESCRIPTION
        "This password protects access to the variables with administrator rights.
        It can only be changed by the administrator. If no password was assigned,
        the valid password is public."
    ::= { wtWebCount6SessCntrl 4 }

wtWebCount6SessCntrlConfigPassword OBJECT-TYPE
    SYNTAX OCTET STRING 
    ACCESS read-write
    STATUS mandatory
    DESCRIPTION
        "This password protects access to the variables with configurator rights. It can
        be changed by the administrator and by the configurator. If no password was assigned, 
        the valid password is public. When read this variable provides a null-pointer."
    ::= { wtWebCount6SessCntrl 5 }
    
-- wtWebCount6Text Group
------------------------

wtWebCount6DeviceName OBJECT-TYPE
    SYNTAX OCTET STRING 
    ACCESS read-write
    STATUS mandatory
    DESCRIPTION
        "Name of the Webio, which is user definable."
    ::= { wtWebCount6Text 1 }

wtWebCount6DeviceText OBJECT-TYPE
    SYNTAX OCTET STRING 
    ACCESS read-write
    STATUS mandatory
    DESCRIPTION
        "Description of the Webio, which is user definable."
    ::= { wtWebCount6Text 2 }
    
wtWebCount6DeviceLocation OBJECT-TYPE
    SYNTAX OCTET STRING 
    ACCESS read-write
    STATUS mandatory
    DESCRIPTION
        "Description of the location of the Webio, which is user definable."
    ::= { wtWebCount6Text 3 }

wtWebCount6DeviceContact OBJECT-TYPE
    SYNTAX OCTET STRING 
    ACCESS read-write
    STATUS mandatory
    DESCRIPTION
        "Contact address of the system operator of the Webio, which is user definable."
    ::= { wtWebCount6Text 4 }    

-- wtWebCount6TimeZone Group
----------------------------

wtWebCount6TzOffsetHrs OBJECT-TYPE
    SYNTAX INTEGER 
    ACCESS read-write
    STATUS mandatory
    DESCRIPTION
        "Offset hours for the time zone (winter time) with respect to UTC."
    ::= { wtWebCount6TimeZone 1 }

wtWebCount6TzOffsetMin OBJECT-TYPE
    SYNTAX INTEGER 
    ACCESS read-write
    STATUS mandatory
    DESCRIPTION
        "Offset minutes for the time zone (winter time) with respect to UTC."
    ::= { wtWebCount6TimeZone 2 }

wtWebCount6TzEnable OBJECT-TYPE
    SYNTAX OCTET STRING (SIZE(4))
    ACCESS read-write
    STATUS mandatory
    DESCRIPTION
        "Binary coded conditions:
        Octet 1: unused
        Octet 2: unused
        Octet 3: unused
        Octet 4:
        	Bit 1-7: unused
	        Bit 0  : Apply Timezone"
    ::= { wtWebCount6TimeZone 3 }

wtWebCount6StTzOffsetHrs OBJECT-TYPE
    SYNTAX INTEGER 
    ACCESS read-write
    STATUS mandatory
    DESCRIPTION
        "Offset hours of the time zone (summer time) with respect to UTC."
    ::= { wtWebCount6TimeZone 4 }

wtWebCount6StTzOffsetMin OBJECT-TYPE
    SYNTAX INTEGER 
    ACCESS read-write
    STATUS mandatory
    DESCRIPTION
        "Offset minutes of the time zone (summer time) with respect to UTC."
    ::= { wtWebCount6TimeZone 5 }

wtWebCount6StTzEnable OBJECT-TYPE
    SYNTAX OCTET STRING (SIZE(4))
    ACCESS read-write
    STATUS mandatory
    DESCRIPTION
        "Binary coded conditions:
        Octet 1: unused
        Octet 2: unused
        Octet 3: unused
        Octet 4:
        	Bit 1-7: unused
	        Bit 0  : Apply Summertime"
    ::= { wtWebCount6TimeZone 6 }

wtWebCount6StTzStartMonth OBJECT-TYPE
    SYNTAX INTEGER {
    	wtWebCount6StartMonth-January(1),
    	wtWebCount6StartMonth-February(2),
    	wtWebCount6StartMonth-March(3),
    	wtWebCount6StartMonth-April(4),
    	wtWebCount6StartMonth-May(5),
    	wtWebCount6StartMonth-June(6),
    	wtWebCount6StartMonth-July(7),
    	wtWebCount6StartMonth-August(8),
    	wtWebCount6StartMonth-September(9),
    	wtWebCount6StartMonth-October(10),
    	wtWebCount6StartMonth-November(11),
    	wtWebCount6StartMonth-December(12)
    	}
    	
    ACCESS read-write
    STATUS mandatory
    DESCRIPTION
        "Month in which the change is made from winter time to summer time."
    ::= { wtWebCount6TimeZone 7 }

wtWebCount6StTzStartMode OBJECT-TYPE
    SYNTAX INTEGER {
    	wtWebCount6StartMode-first(1),
    	wtWebCount6StartMode-second(2),
    	wtWebCount6StartMode-third(3),
    	wtWebCount6StartMode-fourth(4),
    	wtWebCount6StartMode-last(5)
    	}
    	
    ACCESS read-write
    STATUS mandatory
    DESCRIPTION
        "Mode of the day of the week for which the change is made from winter time to summer time."
    ::= { wtWebCount6TimeZone 8 }

wtWebCount6StTzStartWday OBJECT-TYPE
    SYNTAX INTEGER {
    	wtWebCount6StartWday-Sunday(1),
    	wtWebCount6StartWday-Monday(2),
    	wtWebCount6StartWday-Tuesday(3),
    	wtWebCount6StartWday-Thursday(4),
    	wtWebCount6StartWday-Wednesday(5),
    	wtWebCount6StartWday-Friday(6),
    	wtWebCount6StartWday-Saturday(7)
    	}
    	
    ACCESS read-write
    STATUS mandatory
    DESCRIPTION
        "Day of the week on which the change is made from winter time to summer time"
    ::= { wtWebCount6TimeZone 9 }
    
wtWebCount6StTzStartHrs OBJECT-TYPE
    SYNTAX INTEGER 
    ACCESS read-write
    STATUS mandatory
    DESCRIPTION
        "Hour in which the time zone is changed from winter to summer time with
        respect to UTC."
    ::= { wtWebCount6TimeZone 10 }

wtWebCount6StTzStartMin OBJECT-TYPE
    SYNTAX INTEGER 
    ACCESS read-write
    STATUS mandatory
    DESCRIPTION
        "Minute in which the time zone is changed from winter to summer time with
        respect to UTC."
    ::= { wtWebCount6TimeZone 11 }
 
wtWebCount6StTzStopMonth OBJECT-TYPE
    SYNTAX INTEGER {
    	wtWebCount6StopMonth-January(1),
    	wtWebCount6StopMonth-February(2),
    	wtWebCount6StopMonth-March(3),
    	wtWebCount6StopMonth-April(4),
    	wtWebCount6StopMonth-May(5),
    	wtWebCount6StopMonth-June(6),
    	wtWebCount6StopMonth-July(7),
    	wtWebCount6StopMonth-August(8),
    	wtWebCount6StopMonth-September(9),
    	wtWebCount6StopMonth-October(10),
    	wtWebCount6StopMonth-November(11),
    	wtWebCount6StopMonth-December(12)
    	}
    ACCESS read-write
    STATUS mandatory
    DESCRIPTION
        "Month in which the change is made from summer time to winter time."
   ::= { wtWebCount6TimeZone 12 }

wtWebCount6StTzStopMode OBJECT-TYPE
    SYNTAX INTEGER {
    	wtWebCount6StopMode-first(1),
    	wtWebCount6StopMode-second(2),
    	wtWebCount6StopMode-third(3),
    	wtWebCount6StopMode-fourth(4),
    	wtWebCount6StopMode-last(5)
    	}
    ACCESS read-write
    STATUS mandatory
    DESCRIPTION
        "Mode of the week day on which the change is made from summer time to winter time."
    ::= { wtWebCount6TimeZone 13 }

wtWebCount6StTzStopWday OBJECT-TYPE
    SYNTAX INTEGER {
    	wtWebCount6StopWday-Sunday(1),
    	wtWebCount6StopWday-Monday(2),
    	wtWebCount6StopWday-Tuesday(3),
    	wtWebCount6StopWday-Thursday(4),
    	wtWebCount6StopWday-Wednesday(5),
    	wtWebCount6StopWday-Friday(6),
    	wtWebCount6StopWday-Saturday(7)
    	}
    ACCESS read-write
    STATUS mandatory
    DESCRIPTION
        "Day of the week on which the change is made from summer time to winter time."
    ::= { wtWebCount6TimeZone 14 }
    
wtWebCount6StTzStopHrs OBJECT-TYPE
    SYNTAX INTEGER 
    ACCESS read-write
    STATUS mandatory
    DESCRIPTION
        "Hour at which the time zone is changed from summer to winter time with
        respect to UTC."
    ::= { wtWebCount6TimeZone 15 }

wtWebCount6StTzStopMin OBJECT-TYPE
    SYNTAX INTEGER 
    ACCESS read-write
    STATUS mandatory
    DESCRIPTION
        "Minute at which the time zone is changed from summer to winter time with
        respect to UTC."
    ::= { wtWebCount6TimeZone 16 }

-- wtWebCount6TimeServer Group
----------------------------

wtWebCount6TimeServer1 OBJECT-TYPE
    SYNTAX OCTET STRING 
    ACCESS read-write
    STATUS mandatory
    DESCRIPTION
        "IP address or name of the 1st time server in ASCII"
    ::= { wtWebCount6TimeServer 1 }

wtWebCount6TimeServer2 OBJECT-TYPE
    SYNTAX OCTET STRING 
    ACCESS read-write
    STATUS mandatory
    DESCRIPTION
        "IP address or name of the 2nd time server in ASCII"
    ::= { wtWebCount6TimeServer 2 }

wtWebCount6TsEnable OBJECT-TYPE
    SYNTAX OCTET STRING (SIZE(4))
    ACCESS read-write
    STATUS mandatory
    DESCRIPTION
        "Binary coded conditions:
        Octet 1: unused
        Octet 2: unused
        Octet 3: unused
        Octet 4:
        	Bit 1-7: unused
	        Bit 0  : Apply Time Server"
    ::= { wtWebCount6TimeServer 3 }

wtWebCount6TsSyncTime OBJECT-TYPE
    SYNTAX INTEGER 
    ACCESS read-write
    STATUS mandatory
    DESCRIPTION
        "Daily synchronisation time with the time server (hour: 0-23)."
    ::= { wtWebCount6TimeServer 4 }
      
    
-- wtWebCount6DeviceClock Group
----------------------------

wtWebCount6ClockHrs OBJECT-TYPE
    SYNTAX INTEGER (0..23)
    ACCESS read-write
    STATUS mandatory
    DESCRIPTION
        "Clock hours taking into account the time zone settings."
    ::= { wtWebCount6DeviceClock 1 }

wtWebCount6ClockMin OBJECT-TYPE
    SYNTAX INTEGER (0..59)
    ACCESS read-write
    STATUS mandatory
    DESCRIPTION
        "Clock minutes taking into account the time zone settings."
    ::= { wtWebCount6DeviceClock 2 }

wtWebCount6ClockDay OBJECT-TYPE
    SYNTAX INTEGER (1..31)
    ACCESS read-write
    STATUS mandatory
    DESCRIPTION
        "Date: Day of the month, taking into account the time zone settings."
    ::= { wtWebCount6DeviceClock 3 }

wtWebCount6ClockMonth OBJECT-TYPE
   SYNTAX INTEGER {
    	wtWebCount6ClockMonth-January(1),
    	wtWebCount6ClockMonth-February(2),
    	wtWebCount6ClockMonth-March(3),
    	wtWebCount6ClockMonth-April(4),
    	wtWebCount6ClockMonth-May(5),
    	wtWebCount6ClockMonth-June(6),
    	wtWebCount6ClockMonth-July(7),
    	wtWebCount6ClockMonth-August(8),
    	wtWebCount6ClockMonth-September(9),
    	wtWebCount6ClockMonth-October(10),
    	wtWebCount6ClockMonth-November(11),
    	wtWebCount6ClockMonth-December(12)
    	}
    ACCESS read-write
    STATUS mandatory
    DESCRIPTION
        "Date: Month, taking into account the time zone settings."
    ::= { wtWebCount6DeviceClock 4 }

wtWebCount6ClockYear OBJECT-TYPE
    SYNTAX INTEGER (0..65535)
    ACCESS read-write
    STATUS mandatory
    DESCRIPTION
        "Date: Year, taking into account the time zone settings."
    ::= { wtWebCount6DeviceClock 5 }

-- wtWebCount6Network Group
------------------------

wtWebCount6IpAddress OBJECT-TYPE
    SYNTAX IpAddress
    ACCESS read-write
    STATUS mandatory
    DESCRIPTION
        "IP address of the Webio"
    ::= { wtWebCount6Network 1 }

wtWebCount6SubnetMask OBJECT-TYPE
    SYNTAX IpAddress
    ACCESS read-write
    STATUS mandatory
    DESCRIPTION
        "Subnet mask of the Webio"
    ::= { wtWebCount6Network 2 }

wtWebCount6Gateway OBJECT-TYPE
    SYNTAX IpAddress
    ACCESS read-write
    STATUS mandatory
    DESCRIPTION
        "Gateway of the Webio"
    ::= { wtWebCount6Network 3 }

wtWebCount6DnsServer1 OBJECT-TYPE
    SYNTAX OCTET STRING 
    ACCESS read-write
    STATUS mandatory
    DESCRIPTION
        "IP address of the 1st DNS server in ASCII"
    ::= { wtWebCount6Network 4 }

wtWebCount6DnsServer2 OBJECT-TYPE
    SYNTAX OCTET STRING 
    ACCESS read-write
    STATUS mandatory
    DESCRIPTION
        "IP address of the 2nd DNS server in ASCII"
    ::= { wtWebCount6Network 5 }

wtWebCount6AddConfig OBJECT-TYPE
    SYNTAX OCTET STRING 
    ACCESS read-write
    STATUS mandatory
    DESCRIPTION
        "Additional configuration (1=ON):
        Octet 1: unused
        Octet 2: unused
        Octet 3: unused
        Octet 4:
	        Bit 1: DHCP  enable
	        Bit 0: BOOTP enable"
    ::= { wtWebCount6Network 6 }

--  wtWebCount6HTTP Group
--------------------------------

wtWebCount6HttpPort OBJECT-TYPE
    SYNTAX INTEGER (1..65534)
    ACCESS read-write
    STATUS mandatory
    DESCRIPTION
       "Definition of the standard HTML port (Default: 80)."
    ::= { wtWebCount6HTTP 4 }        
    
    
-- wtWebCount6Mail Group
--------------------------------

wtWebCount6MailAdName OBJECT-TYPE
    SYNTAX OCTET STRING 
    ACCESS read-write
    STATUS mandatory
    DESCRIPTION
        "Device name for mail administration."
    ::= { wtWebCount6Mail 1 }
    
wtWebCount6MailReply OBJECT-TYPE
    SYNTAX OCTET STRING 
    ACCESS read-write
    STATUS mandatory
    DESCRIPTION
        "Reply address for the mail server."
    ::= { wtWebCount6Mail 2 }
    
wtWebCount6MailServer OBJECT-TYPE
    SYNTAX OCTET STRING 
    ACCESS read-write
    STATUS mandatory
    DESCRIPTION
        "Name or IP address of the mail server."
    ::= { wtWebCount6Mail 3 }
    
wtWebCount6MailEnable OBJECT-TYPE
    SYNTAX OCTET STRING 
    ACCESS read-write
    STATUS mandatory
    DESCRIPTION
        "Set this bit to enable the sending of mails:
        Octet 1: unused
        Octet 2: unused
        Octet 3: unused
        Octet 4:
        	Bit 1-7: unused
                Bit 0  : Mail enable"
    ::= { wtWebCount6Mail 4 }

wtWebCount6MailAuthentication OBJECT-TYPE
    SYNTAX OCTET STRING (SIZE (4))
    ACCESS read-write
    STATUS mandatory
    DESCRIPTION
        "Selection of the authentication modi:
        The OCTETS are interpreted bit-by-bit, 
        Bit 0 corresponds to the LSB.
        OCTET 1: unused
        OCTET 2: unused
        OCTET 3: unused
        OCTET 4: Bit 3-7: unused
        	 Bit 2  : POP3 before SMTP
        	 Bit 1  : ESMTP, authentication
        	 Bit 0  : SMTP, no authentication"
    ::= { wtWebCount6Mail 5 }
    
wtWebCount6MailAuthUser OBJECT-TYPE
    SYNTAX OCTET STRING 
    ACCESS read-write
    STATUS mandatory
    DESCRIPTION
        "Name of the user to be authenticated."
    ::= { wtWebCount6Mail 6 }    
    
wtWebCount6MailAuthPassword OBJECT-TYPE
    SYNTAX OCTET STRING 
    ACCESS read-write
    STATUS mandatory
    DESCRIPTION
        "Authentication password."
    ::= { wtWebCount6Mail 7 }    
    
wtWebCount6MailPop3Server OBJECT-TYPE
    SYNTAX OCTET STRING 
    ACCESS read-write
    STATUS mandatory
    DESCRIPTION
        "Name or Ip-address of the POP3 Servers."
    ::= { wtWebCount6Mail 8 }        
    

--  wtWebCount6Snmp Group
--------------------------------

wtWebCount6SnmpEnable OBJECT-TYPE
    SYNTAX OCTET STRING 
    ACCESS read-write
    STATUS mandatory
    DESCRIPTION
        "Set bit 0 to enable SNMP.
        If disabled, the device did not respond to any SNMP requests.
        Bit 1 decided wether the community string of read operations 
        is compared with the system password or not:
        Octet 1: unused
        Octet 2: unused
        Octet 3: unused
        Octet 4:
        	Bit 1-7: unused
        	Bit 0  : SNMP enable"
    ::= { wtWebCount6SNMP 1 }
    
wtWebCount6SnmpCommunityStringRead OBJECT-TYPE
    SYNTAX OCTET STRING
    ACCESS read-write
    STATUS mandatory
    DESCRIPTION
        "Community string read only"
    ::= { wtWebCount6SNMP 2 }

wtWebCount6SnmpCommunityStringReadWrite OBJECT-TYPE
    SYNTAX OCTET STRING
    ACCESS read-write
    STATUS mandatory
    DESCRIPTION
        "Community string read / write"
    ::= { wtWebCount6SNMP 3 }

wtWebCount6SnmpSystemTrapManagerIP OBJECT-TYPE
    SYNTAX OCTET STRING 
    ACCESS read-write
    STATUS mandatory
    DESCRIPTION
        "Name or IP address of the TCP server which accepts the system trap."
    ::= { wtWebCount6SNMP 4 }
    
wtWebCount6SnmpSystemTrapEnable OBJECT-TYPE
    SYNTAX OCTET STRING (SIZE(4))
    ACCESS read-write
    STATUS mandatory
    DESCRIPTION
        "Binary coded trigger conditions:
        Octet 1: unused
        Octet 2: unused
        Octet 3: unused
        Octet 4:
	        Bit 0:   ColdStart
	        Bit 1:   WarmStart
	        Bit 2:   Diag messages
	        Bit 3-7: unused"
    ::= { wtWebCount6SNMP 5 }    

-- wtWebCount6Udp Group
--------------------------------   

wtWebCount6UdpAdminPort OBJECT-TYPE
    SYNTAX INTEGER
    ACCESS read-write
    STATUS mandatory
    DESCRIPTION
        "Udp port to which the Udp queries ( short form GET requests) can be sent. This
        port number must be unique within the device."
    ::= { wtWebCount6UDP 1 }

wtWebCount6UdpEnable OBJECT-TYPE
    SYNTAX OCTET STRING 
    ACCESS read-write
    STATUS mandatory
    DESCRIPTION
        "Set this bit to enable UDP support:
        Octet 1: unused
        Octet 2: unused
        Octet 3: unused
        Octet 4:
        	Bit 1-7: unused
                Bit 0  : UDP enable"
    ::= { wtWebCount6UDP 2 }

wtWebCount6UdpRemotePort OBJECT-TYPE
    SYNTAX INTEGER
    ACCESS read-write
    STATUS mandatory
    DESCRIPTION
        "Udp remote port setting.
        If this value is set to zero, the source port read from a request will be used 
        as destination port for the answer.
        A non zero value forced the destination port to this value."
    ::= { wtWebCount6UDP 3 }
    
--  wtWebCount6Syslog Group
--------------------------------
    
wtWebCount6SyslogServerIP OBJECT-TYPE
    SYNTAX OCTET STRING 
    ACCESS read-write
    STATUS mandatory
    DESCRIPTION
        "Name or IP address of the Syslog server, which accepts the Syslog messgaes."
    ::= { wtWebCount6Syslog 1 }
    
wtWebCount6SyslogServerPort OBJECT-TYPE
    SYNTAX INTEGER
    ACCESS read-write
    STATUS mandatory
    DESCRIPTION
        "Portnumber of the Syslog servers, default 514."
    ::= { wtWebCount6Syslog 2 }

wtWebCount6SyslogSystemMessagesEnable OBJECT-TYPE
    SYNTAX OCTET STRING (SIZE(4))
    ACCESS read-write
    STATUS mandatory
    DESCRIPTION
        "Binary coded trigger conditions:
        Octet 1: unused
        Octet 2: unused
        Octet 3: unused
        Octet 4:
	        Bit 0:   ColdStart
	        Bit 1:   WarmStart
	        Bit 2:   Diag Messages
	        Bit 3-7: unused"
    ::= { wtWebCount6Syslog 3 }    

wtWebCount6SyslogEnable OBJECT-TYPE
    SYNTAX OCTET STRING 
    ACCESS read-write
    STATUS mandatory
    DESCRIPTION
        "Set bit 0to enable Syslog:
        Octet 1: unused
        Octet 2: unused
        Octet 3: unused
        Octet 4:
        	Bit 1-7: unused
                Bit 0  : Syslog enable"
    ::= { wtWebCount6Syslog 4 }

--  wtWebCount6FTP Group
--------------------------------

wtWebCount6FTPServerIP OBJECT-TYPE
    SYNTAX OCTET STRING 
    ACCESS read-write
    STATUS mandatory
    DESCRIPTION
        "Name or IP address of the FTP server, which accepts the FTP messages."
    ::= { wtWebCount6FTP 1 }
    
wtWebCount6FTPServerControlPort OBJECT-TYPE
    SYNTAX INTEGER
    ACCESS read-write
    STATUS mandatory
    DESCRIPTION
        "Portnumber of the control port of the FTP server, default 21."
    ::= { wtWebCount6FTP 2 }
    
wtWebCount6FTPUserName OBJECT-TYPE
    SYNTAX OCTET STRING 
    ACCESS read-write
    STATUS mandatory
    DESCRIPTION
        "FTP Loggin: user name."
    ::= { wtWebCount6FTP 3 }
    
wtWebCount6FTPPassword OBJECT-TYPE
    SYNTAX OCTET STRING 
    ACCESS read-write
    STATUS mandatory
    DESCRIPTION
        "FTP Loggin: user password."
    ::= { wtWebCount6FTP 4 }

wtWebCount6FTPAccount OBJECT-TYPE
    SYNTAX OCTET STRING 
    ACCESS read-write
    STATUS mandatory
    DESCRIPTION
        "FTP Loggin: name of account."
    ::= { wtWebCount6FTP 5 }

wtWebCount6FTPOption OBJECT-TYPE
    SYNTAX OCTET STRING 
    ACCESS read-write
    STATUS mandatory
    DESCRIPTION
        "Bit 0 switches the FTP Server in Passiv-Mode,
        the Client controls the data connection on its own:
        Octet 1: unused
        Octet 2: unused
        Octet 3: unused
        Octet 4:
        	Bit 1-7: unused
                Bit 0  : PASV enable"
    ::= { wtWebCount6FTP 6 }
    
wtWebCount6FTPEnable OBJECT-TYPE
    SYNTAX OCTET STRING 
    ACCESS read-write
    STATUS mandatory
    DESCRIPTION
        "Set Bit 0 to enable FTP:
        Octet 1: unused
        Octet 2: unused
        Octet 3: unused
        Octet 4:
        	Bit 1-7: unused
                Bit 0  : FTP enable"
    ::= { wtWebCount6FTP 7 }  

-- wtWebCount6Report Group
----------------------------

wtWebCount6ReportCount OBJECT-TYPE
    SYNTAX INTEGER (1..12)
    ACCESS read-only
    STATUS mandatory
    DESCRIPTION
        "Number of independent Reports."
    ::= { wtWebCount6Report 1 }
    
-- Report Interface Table

wtWebCount6ReportIfTable OBJECT-TYPE
    SYNTAX SEQUENCE OF WtWebCount6ReportIfEntry
    ACCESS not-accessible
    STATUS mandatory
    DESCRIPTION
        "List of Report indices."
    ::= { wtWebCount6Report 2 }

wtWebCount6ReportIfEntry OBJECT-TYPE
    SYNTAX WtWebCount6ReportIfEntry
    ACCESS not-accessible
    STATUS mandatory
    DESCRIPTION
        "Numbers of the Reports."
    INDEX  { wtWebCount6ReportNo }
    ::= { wtWebCount6ReportIfTable 1 }

WtWebCount6ReportIfEntry ::= SEQUENCE {
    wtWebCount6ReportNo INTEGER
}

wtWebCount6ReportNo OBJECT-TYPE
    SYNTAX INTEGER (1..12)
    ACCESS read-only
    STATUS mandatory
    DESCRIPTION
        "Numbers of the Reports."
    ::= { wtWebCount6ReportIfEntry 1 }

-- Report Table

wtWebCount6ReportTable OBJECT-TYPE
    SYNTAX SEQUENCE OF WtWebCount6ReportEntry
    ACCESS not-accessible
    STATUS mandatory
    DESCRIPTION
        "List of settings depending on the Report number."
    ::= { wtWebCount6Report 3 }

wtWebCount6ReportEntry OBJECT-TYPE
    SYNTAX WtWebCount6ReportEntry
    ACCESS not-accessible
    STATUS mandatory
    DESCRIPTION
        "Report parameters of the individual Reports."
    INDEX  { wtWebCount6ReportNo }
    ::= { wtWebCount6ReportTable 1 }

WtWebCount6ReportEntry ::= SEQUENCE {
    wtWebCount6ReportInputTrigger		OCTET STRING,
    wtWebCount6ReportSystemTrigger		OCTET STRING,
    wtWebCount6ReportMaxCounterValue		OCTET STRING,
    wtWebCount6ReportInterval			OCTET STRING,
    wtWebCount6ReportEnable			OCTET STRING,
    wtWebCount6ReportMailAddr			OCTET STRING,
    wtWebCount6ReportMailSubject		OCTET STRING,
    wtWebCount6ReportMailText			OCTET STRING,
    wtWebCount6ReportSnmpManagerIP		OCTET STRING,
    wtWebCount6ReportSnmpTrapText		OCTET STRING,
    wtWebCount6ReportUdpIpAddr			OCTET STRING,
    wtWebCount6ReportUdpPort			INTEGER,
    wtWebCount6ReportUdpText			OCTET STRING,
    wtWebCount6ReportTcpIpAddr			OCTET STRING,
    wtWebCount6ReportTcpPort			INTEGER,
    wtWebCount6ReportTcpText			OCTET STRING,    
    wtWebCount6ReportSyslogIpAddr		OCTET STRING,
    wtWebCount6ReportSyslogPort			INTEGER,
    wtWebCount6ReportSyslogText			OCTET STRING,
    wtWebCount6ReportFtpDataPort		OCTET STRING,
    wtWebCount6ReportFtpFileName		OCTET STRING,
    wtWebCount6ReportFtpText			OCTET STRING,
    wtWebCount6ReportFtpOption			OCTET STRING,
    wtWebCount6ReportTimerCron			OCTET STRING,
    
    wtWebCount6ReportName			OCTET STRING,
    wtWebCount6ReportGlobalEnable		OCTET STRING,
    wtWebCount6ReportCounterClear		OCTET STRING,
    wtWebCount6ReportRateOfChange		OCTET STRING,
    wtWebCount6ReportRateOfChangeWindow		OCTET STRING,
    wtWebCount6ReportRateOfChange		OCTET STRING,
    wtWebCount6ReportRateOfChangeMode		OCTET STRING
    
}

wtWebCount6ReportInputTrigger OBJECT-TYPE
    SYNTAX OCTET STRING (SIZE(12))
    ACCESS read-write
    STATUS mandatory
    DESCRIPTION
        "This variable allows setting of individual input trigger conditions. 
        The OCTETS are interpreted bit-by-bit, with each bit corresponding to an input. 
        Bit 0 corresponds to the LSB.
	The first four OCTETS contain the mask which determines which of the inputs are to 
	be considered (corresponding bit = 1) and which inputs are to ignore 
	(corresponding bit = 0):
	OCTET 1 : unused
	OCTET 2 : unused
	OCTET 3:  unused
	OCTET 4, Bit 0-5: Mask for digital inputs 0-5
		 Bit 6-7: unused
	
	OCTETS 5-8 contain the level (1=HIGH, 0=LOW) which the inputs 
	should assume:
	OCTET 5 : unused
	OCTET 6 : unused
	OCTET 7 : unused
        OCTET 8, Bit 0-5: Level of digital inputs 0-5
        	 Bit 6-7: unused
        
	OCTETS 9-12 contain the counter bit (1=ON, 0=OFF). Inputs masked with the counter bit trigger an Report 
	when the corresponding counter reaching the wtWebCount6ReportMaxCounterValue. Settings in OCTET 5-9 are then unused:
	OCTET 9 : unused
	OCTET 10: unused
	OCTET 11: unused
	OCTET 12, Bit 0-5: Counter bits of digital inputs 0-5
		  Bit 6-7: unused."
        
    ::= { wtWebCount6ReportEntry 1 }

wtWebCount6ReportSystemTrigger OBJECT-TYPE
    SYNTAX OCTET STRING
    ACCESS read-write
    STATUS mandatory
    DESCRIPTION
        "Binary coded trigger conditions:
        The OCTETS are interpreted bit-by-bit.
        Bit 0 corresponds to the LSB.
        OCTET 1: unused
        OCTET 2: unused
        OCTET 3: unused
        OCTET 4, 
        
        	 Bit 7	: Timer OFF
        	 Bit 6	: Time Window
        	 Bit 5	: unused
        	 Bit 4	: unused
        	 Bit 3  : unused
        	 Bit 2  : unused
        	 Bit 1  : Timer
        	 Bit 0  : unused"
    ::= { wtWebCount6ReportEntry 3 }
    
    
wtWebCount6ReportMaxCounterValue OBJECT-TYPE
    SYNTAX OCTET STRING 
    ACCESS read-write
    STATUS mandatory
    DESCRIPTION
        "This variable configures a max. counter value. If an input counter value
        exceeds this max. value, the corresponding Report is triggered. Input counters with
        its mask bit unset in wtWebCount6ReportInputTrigger are not considered."
    ::= { wtWebCount6ReportEntry 4 }

wtWebCount6ReportInterval OBJECT-TYPE
    SYNTAX OCTET STRING 
    ACCESS read-write
    STATUS mandatory
    DESCRIPTION
        "Send interval for Report messages."
    ::= { wtWebCount6ReportEntry 5 }

wtWebCount6ReportEnable OBJECT-TYPE
    SYNTAX OCTET STRING (SIZE(4))
    ACCESS read-write
    STATUS mandatory
    DESCRIPTION
        "Binary coded Report enable:
        Octet 1: unused
        Octet 2: unused
        Octet 3: unused
        Octet 4:
        	Bit 0:  Output Switch Enable
		Bit 1:	Mail Enable
        	Bit 2:	SNMP Trap enable
        	Bit 3:  UDP enable
        	Bit 4:  unused
        	Bit 5:  TCP Client enable
        	Bit 6:	Syslog Messages enable
        	Bit 7:  FTP Client enable"
    ::= { wtWebCount6ReportEntry 6 }

wtWebCount6ReportMailAddr OBJECT-TYPE
    SYNTAX OCTET STRING 
    ACCESS read-write
    STATUS mandatory
    DESCRIPTION
        "E-Mail address for sending the Report mail to."
    ::= { wtWebCount6ReportEntry 7 }

wtWebCount6ReportMailSubject OBJECT-TYPE
    SYNTAX OCTET STRING 
    ACCESS read-write
    STATUS mandatory
    DESCRIPTION
        "Subject line for Report mail."
    ::= { wtWebCount6ReportEntry 8 }

wtWebCount6ReportMailText OBJECT-TYPE
    SYNTAX OCTET STRING 
    ACCESS read-write
    STATUS mandatory
    DESCRIPTION
        "Report mail text: 
        States of the Webio device can be included by using special tags.
        Please refer to the respective Webio manual"
    ::= { wtWebCount6ReportEntry 9 }

wtWebCount6ReportSnmpManagerIP OBJECT-TYPE
    SYNTAX OCTET STRING 
    ACCESS read-write
    STATUS mandatory
    DESCRIPTION
        "IP address of the SNMP Manager to which the Webio device should send SNMP traps."
    ::= { wtWebCount6ReportEntry 10 }

wtWebCount6ReportSnmpTrapText OBJECT-TYPE
    SYNTAX OCTET STRING 
    ACCESS read-write
    STATUS mandatory
    DESCRIPTION
        "This text appears in the trap body."
    ::= { wtWebCount6ReportEntry 11 }
    
wtWebCount6ReportUdpIpAddr OBJECT-TYPE
    SYNTAX OCTET STRING 
    ACCESS read-write
    STATUS mandatory
    DESCRIPTION
        "IP address of the UDP listener to which the Webio device should send UDP traps."
    ::= { wtWebCount6ReportEntry 12 }    

wtWebCount6ReportUdpPort OBJECT-TYPE
    SYNTAX INTEGER (1..65535) 
    ACCESS read-write
    STATUS mandatory
    DESCRIPTION
        "Port number of the UDP listener to which the Webio device should send UDP traps."
    ::= { wtWebCount6ReportEntry 13 }    

wtWebCount6ReportUdpText OBJECT-TYPE
    SYNTAX OCTET STRING 
    ACCESS read-write
    STATUS mandatory
    DESCRIPTION
        "This text appears in the UDP trap body."
    ::= { wtWebCount6ReportEntry 14 }
    
wtWebCount6ReportTcpIpAddr OBJECT-TYPE
    SYNTAX OCTET STRING
    ACCESS read-write
    STATUS mandatory
    DESCRIPTION
        "IP address of the TCP listener to which the Webio device should send TCP traps."
    ::= { wtWebCount6ReportEntry 15 }    

wtWebCount6ReportTcpPort OBJECT-TYPE
    SYNTAX INTEGER (1..65535) 
    ACCESS read-write
    STATUS mandatory
    DESCRIPTION
        "Port number of the TCP listener to which the Webio device should send TCP traps."
    ::= { wtWebCount6ReportEntry 16 }    

wtWebCount6ReportTcpText OBJECT-TYPE
    SYNTAX OCTET STRING 
    ACCESS read-write
    STATUS mandatory
    DESCRIPTION
        "This text appears in the TCP trap body."
    ::= { wtWebCount6ReportEntry 17 }

wtWebCount6ReportSyslogIpAddr OBJECT-TYPE
    SYNTAX OCTET STRING 
    ACCESS read-write
    STATUS mandatory
    DESCRIPTION
        "IP address of the syslog server to which the Webio device should send syslog messages."
    ::= { wtWebCount6ReportEntry 18 }    

wtWebCount6ReportSyslogPort OBJECT-TYPE
    SYNTAX INTEGER (1..65535) 
    ACCESS read-write
    STATUS mandatory
    DESCRIPTION
        "Port number of the syslog server to which the Webio device should send syslog messages."
    ::= { wtWebCount6ReportEntry 19 }    

wtWebCount6ReportSyslogText OBJECT-TYPE
    SYNTAX OCTET STRING 
    ACCESS read-write
    STATUS mandatory
    DESCRIPTION
        "Every message starts with the priority key, a time stamp and the host ip address, according RFC3164.
        This text appears in the following syslog message body."
    ::= { wtWebCount6ReportEntry 20 }    
    
wtWebCount6ReportFtpDataPort OBJECT-TYPE
    SYNTAX OCTET STRING 
    ACCESS read-write
    STATUS mandatory
    DESCRIPTION
        "Local data port: 1..65535 or AUTO: the next free port will be assigned."
    ::= { wtWebCount6ReportEntry 21 }
    
wtWebCount6ReportFtpFileName OBJECT-TYPE
    SYNTAX OCTET STRING 
    ACCESS read-write
    STATUS mandatory
    DESCRIPTION
        "Name of the file including path informations."
    ::= { wtWebCount6ReportEntry 22 }
    
wtWebCount6ReportFtpText OBJECT-TYPE
    SYNTAX OCTET STRING 
    ACCESS read-write
    STATUS mandatory
    DESCRIPTION
        "Message text to store on the FTP server."
    ::= { wtWebCount6ReportEntry 23 }

wtWebCount6ReportFtpOption OBJECT-TYPE
    SYNTAX OCTET STRING (SIZE(4))
    ACCESS read-write
    STATUS mandatory
    DESCRIPTION
        "Binary coded options, select only one option at the same time:
        STORE  = replace file
        APPEND = append message at the end of the file
        
        Octet 1: unused
        Octet 2: unused
        Octet 3: unused
        Octet 4:
		Bit 0  :	STORE
		Bit 1  :	APPEND
        	Bit 2-7:	unused"
    ::= { wtWebCount6ReportEntry 24 }      
    
wtWebCount6ReportTimerCron OBJECT-TYPE
    SYNTAX OCTET STRING
    ACCESS read-write
    STATUS mandatory
    DESCRIPTION
        "This entry contains 5 space or tab seperated text fields for time trigger definition.
        Each field must match with the actual time to trigger a report, weekday and day of month
        are interpreted separatley.
        1: Minutes	Range 0-59
        2. Hours	Range 0-23, 0 is midnight
        3: Day of month	Range 1-31
        4: Month	Range 1-12
        5: Weekday	Range 0-6, 0 is sunday
        
        Syntax for every field:
         - an asterix (*) enables every possible setting of a field
         - single numbers seperated by commas
         - a partition within the allowed range (1-5)
         - step size within an partition of the allowed range (0-59/2: every second minute)."
    ::= { wtWebCount6ReportEntry 25 }      

wtWebCount6ReportName OBJECT-TYPE
    SYNTAX OCTET STRING 
    ACCESS read-write
    STATUS mandatory
    DESCRIPTION
        "Name of the Report."
    ::= { wtWebCount6ReportEntry 33 }    

wtWebCount6ReportGlobalEnable OBJECT-TYPE
    SYNTAX OCTET STRING 
    ACCESS read-write
    STATUS mandatory
    DESCRIPTION
        "Binary coded Report activation:
        Die OCTETS werden bitweise interpretiert.
        Bit 0 entspricht dem LSB.
        OCTET 1: unused
        OCTET 2: unused
        OCTET 3: unused
        OCTET 4, Bit 1-7: unused
        	 Bit 0  : Report enable"
    ::= { wtWebCount6ReportEntry 34 }    

wtWebCount6ReportCounterClear OBJECT-TYPE
    SYNTAX OCTET STRING 
    ACCESS read-write
    STATUS mandatory
    DESCRIPTION
        "Binary coded options:
        The OCTETS are interpreted bit-by-bit. 
        Bit 0 corresponds to the LSB.
        OCTET 1: unused
        OCTET 2: unused
        OCTET 3: unused
        OCTET 4, Bit 1-7: unused
        	 Bit 0  : Counter clear on Report send"
    ::= { wtWebCount6ReportEntry 35 }

wtWebCount6ReportRateOfChange OBJECT-TYPE
    SYNTAX OCTET STRING 
    ACCESS read-write
    STATUS mandatory
    DESCRIPTION
	"This variable configures a max. counter value within a time slot. If an input counter value
        exceeds this max. value, the corresponding Report is triggered. Input counters with
        its mask bit unset in wtWebCount6ReportInputTrigger are not considered. A value of Zero
        disable the tracing of rate of change."
    ::= { wtWebCount6ReportEntry 52 }
    
wtWebCount6ReportRateOfChangeWindow OBJECT-TYPE
    SYNTAX OCTET STRING 
    ACCESS read-write
    STATUS mandatory
    DESCRIPTION
	"This variable configures the time slot of wtWebCount6ReportRateOfChange. Input counters with
        its mask bit unset in wtWebCount6ReportInputTrigger are not considered. A value of Zero
        disable the tracing of rate of change."
    ::= { wtWebCount6ReportEntry 53 }
    
wtWebCount6ReportRateOfChangeMode OBJECT-TYPE
    SYNTAX OCTET STRING 
    ACCESS read-write
    STATUS mandatory
    DESCRIPTION
        "Binary coded options:
        Minimum mode: a report will be send if the count of pulses is lower than
        the given pulse count in wtWebCount6ReportRateOfChange.
        Maximum mode: a report will be send if the count of pulses is greater than 
        the pulse count given in wtWebCount6ReportRateOfChange.
        The OCTETS are interpreted bit-by-bit, use only one bit at a time. 
        Bit 0 corresponds to the LSB.
        OCTET 1: unused
        OCTET 2: unused
        OCTET 3: unused
        OCTET 4, Bit 1-7: unused
        	 Bit 2  : Maximum Mode
        	 Bit 1  : Minimum Mode
        	 Bit 0  : Rate of Change OFF"
    ::= { wtWebCount6ReportEntry 54 }    

-- wtWebCount6Ports Group
----------------------------

-- Input Port Table

wtWebCount6InputPortTable OBJECT-TYPE
    SYNTAX SEQUENCE OF WtWebCount6InputPortEntry
    ACCESS not-accessible
    STATUS mandatory
    DESCRIPTION
        "List of settings depending on the input number."
    ::= { wtWebCount6Ports 1 }

wtWebCount6InputPortEntry OBJECT-TYPE
    SYNTAX WtWebCount6InputPortEntry
    ACCESS not-accessible
    STATUS mandatory
    DESCRIPTION
        "Input parameter for the individual inputs."
    INDEX  { wtWebCount6InputNo }
    ::= { wtWebCount6InputPortTable 1 }

WtWebCount6InputPortEntry ::= SEQUENCE {
    wtWebCount6PortInputName			OCTET STRING,
    wtWebCount6PortInputText			OCTET STRING,
    wtWebCount6PortInputMode			OCTET STRING,
    wtWebCount6PortInputFilter			INTEGER,
    wtWebCount6PortInputPulsePolarity		OCTET STRING,
    wtWebCount6PortInputBicountInactivTimeout	INTEGER,
    wtWebCount6PortInputCounterSet		INTEGER,
    wtWebCount6PortInputCounterScale		OCTET STRING,
    wtWebCount6PortInputCounterUnit		OCTET STRING    
    }

wtWebCount6PortInputName OBJECT-TYPE
    SYNTAX OCTET STRING 
    ACCESS read-write
    STATUS mandatory
    DESCRIPTION
        "Name of the input."
    ::= { wtWebCount6InputPortEntry 1 }

wtWebCount6PortInputText OBJECT-TYPE
    SYNTAX OCTET STRING 
    ACCESS read-write
    STATUS mandatory
    DESCRIPTION
        "Description of the input."
    ::= { wtWebCount6InputPortEntry 2 }

wtWebCount6PortInputMode OBJECT-TYPE
    SYNTAX OCTET STRING (SIZE(4))
    ACCESS read-write
    STATUS mandatory
    DESCRIPTION
        "Binary coded modes:
        The OCTETS are interpreted bit-by-bit,
        Bit 0 corresponds to the LSB.
        Selection for input 0-1:
        OCTET 1: unused
        OCTET 2: unused
        OCTET 3: unused
        OCTET 4, Bit 4-7: unused
		 Bit 3	: Bidirectional counter enable
        	 Bit 2  : unused
        	 Bit 1  : Change detection enable
        	 Bit 0  : unused"
    ::= { wtWebCount6InputPortEntry 3 }    
    
wtWebCount6PortInputFilter OBJECT-TYPE
    SYNTAX INTEGER 
    ACCESS read-write
    STATUS mandatory
    DESCRIPTION
        "Pulses with a duration shorter than here specified (duration in 1/1000 sec),
	are ignored."
    ::= { wtWebCount6InputPortEntry 4 }
    
wtWebCount6PortInputPulsePolarity OBJECT-TYPE
    SYNTAX OCTET STRING (SIZE (4))
    ACCESS read-write
    STATUS mandatory
    DESCRIPTION
        "This value defines the polarity of the input pulse.
        OCTET 1: unused
        OCTET 2: unused
        OCTET 3: unused
        	OCTET 4: 
        	 Bit 0   : negative polarity
        	 Bit 1   : positive polarity
        	 Bit 2-7 : unused"
    ::= { wtWebCount6InputPortEntry 5 }
    
wtWebCount6PortInputBicountInactivTimeout OBJECT-TYPE
    SYNTAX INTEGER 
    ACCESS read-write
    STATUS mandatory
    DESCRIPTION
        "Pulse chains with a duration shorter than here specified (in 1/10 sek),
	are ignored."
    ::= { wtWebCount6InputPortEntry 6 }    
    
wtWebCount6PortInputCounterSet OBJECT-TYPE
    SYNTAX INTEGER 
    ACCESS read-write
    STATUS mandatory
    DESCRIPTION
        "Writing to this variable presets the counter, while reading returns the actual value."
    ::= { wtWebCount6InputPortEntry 7 }

wtWebCount6PortInputCounterScale OBJECT-TYPE
    SYNTAX OCTET STRING 
    ACCESS read-write
    STATUS mandatory
    DESCRIPTION
        "Conversion factor for this counter."
    ::= { wtWebCount6InputPortEntry 8 }  

wtWebCount6PortInputCounterUnit OBJECT-TYPE
    SYNTAX OCTET STRING 
    ACCESS read-write
    STATUS mandatory
    DESCRIPTION
        "Unit for this counter."
    ::= { wtWebCount6InputPortEntry 9 }  


-- wtWebCount6Manufact Group
----------------------------

wtWebCount6MfName OBJECT-TYPE
    SYNTAX OCTET STRING 
    ACCESS read-write
    STATUS mandatory
    DESCRIPTION
        "Manufacturer company name"
    ::= { wtWebCount6Manufact 1 }

wtWebCount6MfAddr OBJECT-TYPE
    SYNTAX OCTET STRING 
    ACCESS read-write
    STATUS mandatory
    DESCRIPTION
        "Manufacturer address."
    ::= { wtWebCount6Manufact 2 }

wtWebCount6MfHotline OBJECT-TYPE
    SYNTAX OCTET STRING 
    ACCESS read-write
    STATUS mandatory
    DESCRIPTION
        "Manufacturer hotline."
    ::= { wtWebCount6Manufact 3 }

wtWebCount6MfInternet OBJECT-TYPE
    SYNTAX OCTET STRING 
    ACCESS read-write
    STATUS mandatory
    DESCRIPTION
        "Manufacturer Internet address."
    ::= { wtWebCount6Manufact 4 }

wtWebCount6MfDeviceTyp OBJECT-TYPE
    SYNTAX OCTET STRING 
    ACCESS read-write
    STATUS mandatory
    DESCRIPTION
        "Manufacturer device name (model number)."
    ::= { wtWebCount6Manufact 5 }

wtWebCount6MfOrderNo OBJECT-TYPE
    SYNTAX OCTET STRING 
    ACCESS read-write
    STATUS mandatory
    DESCRIPTION
        "Manufacturer part number."
    ::= { wtWebCount6Manufact 6 }

-- wtWebCount6Diag Group
----------------------------

wtWebCount6DiagErrorCount OBJECT-TYPE
    SYNTAX INTEGER
    ACCESS read-only
    STATUS mandatory
    DESCRIPTION
        "Number of entries in the error memory."
    ::= { wtWebCount6Diag 1 }

wtWebCount6DiagBinaryError OBJECT-TYPE
    SYNTAX OCTET STRING 
    ACCESS read-only
    STATUS mandatory
    DESCRIPTION
        "Error causes coded bit-by-bit."
    ::= { wtWebCount6Diag 2 }

wtWebCount6DiagErrorIndex OBJECT-TYPE
    SYNTAX INTEGER
    ACCESS read-write
    STATUS mandatory
    DESCRIPTION
        "The value of this variable is used as an index to read 
        an error massege from wtWebCount6DiagErrorMessage.
        Errors are numbered from 1 to wtWebCount6DiagErrorCount.
        Writing a valid value into this variable, making the appropriate 
        message readable from wtWebCount6DiagErrorMessage."
    ::= { wtWebCount6Diag 3 }

wtWebCount6DiagErrorMessage OBJECT-TYPE
    SYNTAX OCTET STRING 
    ACCESS read-only
    STATUS mandatory
    DESCRIPTION
        "Using wtWebCount6DiagErrorIndex as an index, the appropriate message is available."
    ::= { wtWebCount6Diag 4 }
    
wtWebCount6DiagErrorClear OBJECT-TYPE
    SYNTAX INTEGER
    ACCESS write-only
    STATUS mandatory
    DESCRIPTION
        "Writing 1 into this variable clears all diagnosis messages."
    ::= { wtWebCount6Diag 5 }


-- TRAP DEFINITIONS

-- Diese SNMP-Traps werden gesendet, wenn die Reporttriggerbedingungen zutreffen 

wtWebCount6Alert1 TRAP-TYPE
    ENTERPRISE  wtWebCount6
    VARIABLES   { wtWebCount6ReportSnmpTrapText }
    DESCRIPTION
        "This SNMP trap is generated when Report 1 was triggered,
        SNMP trap enable is set and
        SNMP is enabled."
    -- NMS trap annotation
    --#TYPE "WebCount Report 1"
    --#SUMMARY "Report 1: %s"
    --#ARGUMENTS {0}
    --#SEVERITY INFORMATIONAL
    --#TIMEINDEX 99
    --#STATE OPERATIONAL    
    ::= 41

wtWebCount6Alert2 TRAP-TYPE
    ENTERPRISE  wtWebCount6
    VARIABLES   { wtWebCount6ReportSnmpTrapText }
    DESCRIPTION
        "This SNMP trap is generated when Report 2 was triggered,
        SNMP trap enable is set and
        SNMP is enabled."
    -- NMS trap annotation
    --#TYPE "WebCount Report 2"
    --#SUMMARY "Report 2: %s"
    --#ARGUMENTS {0}
    --#SEVERITY INFORMATIONAL
    --#TIMEINDEX 99
    --#STATE OPERATIONAL    
    ::= 42

wtWebCount6Alert3 TRAP-TYPE
    ENTERPRISE  wtWebCount6
    VARIABLES   { wtWebCount6ReportSnmpTrapText }
    DESCRIPTION
        "This SNMP trap is generated when Report 3 was triggered,
        SNMP trap enable is set and
        SNMP is enabled."
    -- NMS trap annotation
    --#TYPE "WebCount Report 3"
    --#SUMMARY "Report 3: %s"
    --#ARGUMENTS {0}
    --#SEVERITY INFORMATIONAL
    --#TIMEINDEX 99
    --#STATE OPERATIONAL    
    ::= 43

wtWebCount6Alert4 TRAP-TYPE
    ENTERPRISE  wtWebCount6
    VARIABLES   { wtWebCount6ReportSnmpTrapText }
    DESCRIPTION
        "This SNMP trap is generated when Report 4 was triggered,
        SNMP trap enable is set and
        SNMP is enabled."
    -- NMS trap annotation
    --#TYPE "WebCount Report 4"
    --#SUMMARY "Report 4: %s"
    --#ARGUMENTS {0}
    --#SEVERITY INFORMATIONAL
    --#TIMEINDEX 99
    --#STATE OPERATIONAL    
    ::= 44

wtWebCount6Alert5 TRAP-TYPE
    ENTERPRISE  wtWebCount6
    VARIABLES   { wtWebCount6ReportSnmpTrapText }
    DESCRIPTION
        "This SNMP trap is generated when Report 5 was triggered,
        SNMP trap enable is set and
        SNMP is enabled."
    -- NMS trap annotation
    --#TYPE "WebCount Report 5"
    --#SUMMARY "Report 5: %s"
    --#ARGUMENTS {0}
    --#SEVERITY INFORMATIONAL
    --#TIMEINDEX 99
    --#STATE OPERATIONAL    
    ::= 45

wtWebCount6Alert6 TRAP-TYPE
    ENTERPRISE  wtWebCount6
    VARIABLES   { wtWebCount6ReportSnmpTrapText }
    DESCRIPTION
        "This SNMP trap is generated when Report 6 was triggered,
        SNMP trap enable is set and
        SNMP is enabled."
    -- NMS trap annotation
    --#TYPE "WebCount Report 6"
    --#SUMMARY "Report 6: %s"
    --#ARGUMENTS {0}
    --#SEVERITY INFORMATIONAL
    --#TIMEINDEX 99
    --#STATE OPERATIONAL    
    ::= 46

wtWebCount6Alert7 TRAP-TYPE
    ENTERPRISE  wtWebCount6
    VARIABLES   { wtWebCount6ReportSnmpTrapText }
    DESCRIPTION
        "This SNMP trap is generated when Report 7 was triggered,
        SNMP trap enable is set and
        SNMP is enabled."
    -- NMS trap annotation
    --#TYPE "WebCount Report 7"
    --#SUMMARY "Report 7: %s"
    --#ARGUMENTS {0}
    --#SEVERITY INFORMATIONAL
    --#TIMEINDEX 99
    --#STATE OPERATIONAL    
    ::= 47

wtWebCount6Alert8 TRAP-TYPE
    ENTERPRISE  wtWebCount6
    VARIABLES   { wtWebCount6ReportSnmpTrapText }
    DESCRIPTION
        "This SNMP trap is generated when Report 8 was triggered,
        SNMP trap enable is set and
        SNMP is enabled."
    -- NMS trap annotation
    --#TYPE "WebCount Report 8"
    --#SUMMARY "Report 8: %s"
    --#ARGUMENTS {0}
    --#SEVERITY INFORMATIONAL
    --#TIMEINDEX 99
    --#STATE OPERATIONAL    
    ::= 48

wtWebCount6Alert9 TRAP-TYPE
    ENTERPRISE  wtWebCount6
    VARIABLES   { wtWebCount6ReportSnmpTrapText }
    DESCRIPTION
        "This SNMP trap is generated when Report 9 was triggered,
        SNMP trap enable is set and
        SNMP is enabled."
    -- NMS trap annotation
    --#TYPE "WebCount Report 9"
    --#SUMMARY "Report 9: %s"
    --#ARGUMENTS {0}
    --#SEVERITY INFORMATIONAL
    --#TIMEINDEX 99
    --#STATE OPERATIONAL    
    ::= 49

wtWebCount6Alert10 TRAP-TYPE
    ENTERPRISE  wtWebCount6
    VARIABLES   { wtWebCount6ReportSnmpTrapText }
    DESCRIPTION
        "This SNMP trap is generated when Report 10 was triggered,
        SNMP trap enable is set and
        SNMP is enabled."
    -- NMS trap annotation
    --#TYPE "WebCount Report 10"
    --#SUMMARY "Report 10: %s"
    --#ARGUMENTS {0}
    --#SEVERITY INFORMATIONAL
    --#TIMEINDEX 99
    --#STATE OPERATIONAL    
    ::= 50

wtWebCount6Alert11 TRAP-TYPE
    ENTERPRISE  wtWebCount6
    VARIABLES   { wtWebCount6ReportSnmpTrapText }
    DESCRIPTION
        "This SNMP trap is generated when Report 11 was triggered,
        SNMP trap enable is set and
        SNMP is enabled."
    -- NMS trap annotation
    --#TYPE "WebCount Report 11"
    --#SUMMARY "Report 11: %s"
    --#ARGUMENTS {0}
    --#SEVERITY INFORMATIONAL
    --#TIMEINDEX 99
    --#STATE OPERATIONAL    
    ::= 51

wtWebCount6Alert12 TRAP-TYPE
    ENTERPRISE  wtWebCount6
    VARIABLES   { wtWebCount6ReportSnmpTrapText }
    DESCRIPTION
        "This SNMP trap is generated when Report 12 was triggered,
        SNMP trap enable is set and
        SNMP is enabled."
    -- NMS trap annotation
    --#TYPE "WebCount Report 12"
    --#SUMMARY "Report 12: %s"
    --#ARGUMENTS {0}
    --#SEVERITY INFORMATIONAL
    --#TIMEINDEX 99
    --#STATE OPERATIONAL    
    ::= 52

wtWebCount6AlertDiag TRAP-TYPE
    ENTERPRISE  wtWebCount6
    VARIABLES   { 	
    		wtWebCount6DiagErrorIndex,
    	  	wtWebCount6DiagErrorMessage
    		}
    DESCRIPTION
        "This SNMP trap is generated when a diagnosis/error message was triggered,
        SNMP trap enable is set and
        SNMP is enabled."
    -- NMS trap annotation
    --#TYPE "WebCount Diagnose Error"
    --#SUMMARY "Diagnose error index: %d, Message: %s."
    --#ARGUMENTS {0,1}
    --#SEVERITY MAJOR
    --#TIMEINDEX 99
    --#STATE DEGRADED    
    ::= 110


--------------------------------------------------------------------------------
--------------------------------------------------------------------------------
--------------------------------------------------------------------------------

-- wtWebioEA6x6InOut Group
------------------------

wtWebioEA6x6Inputs OBJECT-TYPE
    SYNTAX INTEGER (1..6)
    ACCESS read-only
    STATUS mandatory
    DESCRIPTION
        "Number of idependent inputs."
    ::= { wtWebioEA6x6InOut 1 }

wtWebioEA6x6Outputs OBJECT-TYPE
    SYNTAX INTEGER (1..6)
    ACCESS read-only
    STATUS mandatory
    DESCRIPTION
        "Number of idependent outputs."
    ::= { wtWebioEA6x6InOut 2 }

-- Input Interface Table

wtWebioEA6x6InputTable OBJECT-TYPE
    SYNTAX SEQUENCE OF WtWebioEA6x6InputEntry
    ACCESS not-accessible
    STATUS mandatory
    DESCRIPTION
        "List of input indices."
    ::= { wtWebioEA6x6InOut 3 }

wtWebioEA6x6InputEntry OBJECT-TYPE
    SYNTAX WtWebioEA6x6InputEntry
    ACCESS not-accessible
    STATUS mandatory
    DESCRIPTION
        "Number of the inputs."
    INDEX  { wtWebioEA6x6InputNo }
    ::= { wtWebioEA6x6InputTable 1 }

WtWebioEA6x6InputEntry ::= SEQUENCE {
    wtWebioEA6x6InputNo INTEGER,
    wtWebioEA6x6InputCounter INTEGER,
    wtWebioEA6x6InputCounterClear INTEGER,
    wtWebioEA6x6InputState INTEGER
}

wtWebioEA6x6InputNo OBJECT-TYPE
    SYNTAX INTEGER (1)
    ACCESS read-only
    STATUS mandatory
    DESCRIPTION
        "Index numbers of the inputs."
    ::= { wtWebioEA6x6InputEntry 1 }

wtWebioEA6x6InputCounter OBJECT-TYPE
    SYNTAX INTEGER (1)
    ACCESS read-only
    STATUS mandatory
    DESCRIPTION
        "Value of the input counter."
    ::= { wtWebioEA6x6InputEntry 2 }
    
wtWebioEA6x6InputCounterClear OBJECT-TYPE
    SYNTAX INTEGER
    ACCESS read-only
    STATUS mandatory
    DESCRIPTION
        "Clears the input counter after returning its value."
    ::= { wtWebioEA6x6InputEntry 3 }

wtWebioEA6x6InputState OBJECT-TYPE
    SYNTAX INTEGER{
    wtWebioEA6x6InputState-OFF(0),
    wtWebioEA6x6InputState-ON(1)
    }
    ACCESS read-only
    STATUS mandatory
    DESCRIPTION
        "Value of a single input bit."
    ::= { wtWebioEA6x6InputEntry 4 }    
    
wtWebioEA6x6InputValue OBJECT-TYPE
    SYNTAX INTEGER 
    ACCESS read-only
    STATUS mandatory
    DESCRIPTION
        "This variable is used to read the inputs of the digital I/O port.
        The OCTETS are interpreted bit-by-bit, with each bit corresponding to an output.
        Bit 0 corresponds to the LSB.
        OCTET 1: unused
        OCTET 2: unused
        OCTET 3, unused
        OCTET 4, Bit 0-5: Digital outputs 0-5
        	 Bit 6-7: unused"
    ::= { wtWebioEA6x6InOut 4 }
    

-- Output Interface Table

wtWebioEA6x6OutputTable OBJECT-TYPE
    SYNTAX SEQUENCE OF WtWebioEA6x6OutputEntry
    ACCESS not-accessible
    STATUS mandatory
    DESCRIPTION
        "List of output indices."
    ::= { wtWebioEA6x6InOut 5 }

wtWebioEA6x6OutputEntry OBJECT-TYPE
    SYNTAX WtWebioEA6x6OutputEntry
    ACCESS not-accessible
    STATUS mandatory
    DESCRIPTION
        "Number of the outputs."
    INDEX  { wtWebioEA6x6OutputNo }
    ::= { wtWebioEA6x6OutputTable 1 }

WtWebioEA6x6OutputEntry ::= SEQUENCE {
    wtWebioEA6x6OutputNo INTEGER,
    wtWebioEA6x6OutputState INTEGER
}

wtWebioEA6x6OutputNo OBJECT-TYPE
    SYNTAX INTEGER (1)
    ACCESS read-only
    STATUS mandatory
    DESCRIPTION
        "Output number."
    ::= { wtWebioEA6x6OutputEntry 1 }
    
wtWebioEA6x6OutputState OBJECT-TYPE
    SYNTAX INTEGER{
    wtWebioEA6x6OutputState-OFF(0),
    wtWebioEA6x6OutputState-ON(1)
    }
    ACCESS read-write
    STATUS mandatory
    DESCRIPTION
        "Value of a single output bit."
    ::= { wtWebioEA6x6OutputEntry 2 }    

wtWebioEA6x6OutputValue OBJECT-TYPE
    SYNTAX INTEGER
    ACCESS read-write
    STATUS mandatory
    DESCRIPTION
        "This variable is used to read and write the outputs of the digital I/O port. 
        The OCTETS are interpreted bit-by-bit, with each bit corresponding to an output. 
        Bit 0 corresponds to the LSB.
        OCTET 1: unused
        OCTET 2: unused
        OCTET 3, unused
        OCTET 4, Bit 0-5: Digital outputs 0-5
        	 Bit 6-7: unused"
    ::= { wtWebioEA6x6InOut 6 }
    
wtWebioEA6x6SetOutput OBJECT-TYPE
    SYNTAX OCTET STRING (SIZE (8))
    ACCESS read-write			-- write-only
    STATUS mandatory
    DESCRIPTION
        "This variable allows setting of individual digital outputs. The OCTETS are 
        interpreted bit-by-bit, with each bit corresponding to an output. Bit 0 corresponds 
        to the LSB.
        The first two OCTETS contain the mask which determines which of the outputs are to 
        be set (corresponding bit = 1) and which outputs are to remain unchanged 
        (corresponding bit = 0):
	OCTET 1 : unused
	OCTET 2 : unused
	OCTET 3 : unused
	OCTET 4 : Bit 0-5: Mask for digital outputs 0-5
		  Bit 6-7: unused
	
	OCTETS 5-8 contain the level (1=HIGH, 0=LOW) which the inputs 
	should assume:
	OCTET 5 : unused
	OCTET 6 : unused
	OCTET 7 : unused
        OCTET 8 : Bit 0-5: Level of digital outputs 0-5
        	  Bit 6-7: unused"
    ::= { wtWebioEA6x6InOut 7 }
    
-- wtWebioEA6x6SessCntrl Group
--------------------------------

wtWebioEA6x6SessCntrlPassword OBJECT-TYPE
    SYNTAX OCTET STRING 
    ACCESS read-write
    STATUS mandatory
    DESCRIPTION
        "Entering this password opens a session which is ended by writing a 1 to 
        wtWebioEA6x6SessCntrlLogout. When read this variable provides a string of
        length zero."
    ::= { wtWebioEA6x6SessCntrl 1 }

wtWebioEA6x6SessCntrlConfigMode OBJECT-TYPE
    SYNTAX INTEGER {
    wtWebioEA6x6SessCntrl-NoSession(0),
    wtWebioEA6x6SessCntrl-Session(1)
    }
    ACCESS read-only
    STATUS mandatory
    DESCRIPTION
        "When the device is in SNMP configuration mode, the value 1 is
        returned, otherwise 0. If the read value is 0 even though the password
        was written, the device is already in config mode and the variables
        can only be read."
    ::= { wtWebioEA6x6SessCntrl 2 }

wtWebioEA6x6SessCntrlLogout OBJECT-TYPE
    SYNTAX INTEGER 
    ACCESS read-write
    STATUS mandatory
    DESCRIPTION
        "If the device is in configuration mode and the session was opened by
        this SNMP Manager, writing a 1 to this variable will end the session 
        and all parameters are stored.
        Writing a 2 discards all entries again. When read this variable
        provides the value 0."
    ::= { wtWebioEA6x6SessCntrl 3 }

wtWebioEA6x6SessCntrlAdminPassword OBJECT-TYPE
    SYNTAX OCTET STRING 
    ACCESS read-write
    STATUS mandatory
    DESCRIPTION
        "This password protects access to the variables with administrator rights.
        It can only be changed by the administrator. If no password was assigned,
        the valid password is public."
    ::= { wtWebioEA6x6SessCntrl 4 }

wtWebioEA6x6SessCntrlConfigPassword OBJECT-TYPE
    SYNTAX OCTET STRING 
    ACCESS read-write
    STATUS mandatory
    DESCRIPTION
        "This password protects access to the variables with configurator rights. It can
        be changed by the administrator and by the configurator. If no password was assigned, 
        the valid password is public. When read this variable provides a null-pointer."
    ::= { wtWebioEA6x6SessCntrl 5 }
    
-- wtWebioEA6x6Text Group
------------------------

wtWebioEA6x6DeviceName OBJECT-TYPE
    SYNTAX OCTET STRING 
    ACCESS read-write
    STATUS mandatory
    DESCRIPTION
        "Name of the Webio, which is user definable."
    ::= { wtWebioEA6x6Text 1 }

wtWebioEA6x6DeviceText OBJECT-TYPE
    SYNTAX OCTET STRING 
    ACCESS read-write
    STATUS mandatory
    DESCRIPTION
        "Description of the Webio, which is user definable."
    ::= { wtWebioEA6x6Text 2 }
    
wtWebioEA6x6DeviceLocation OBJECT-TYPE
    SYNTAX OCTET STRING 
    ACCESS read-write
    STATUS mandatory
    DESCRIPTION
        "Description of the location of the Webio, which is user definable."
    ::= { wtWebioEA6x6Text 3 }

wtWebioEA6x6DeviceContact OBJECT-TYPE
    SYNTAX OCTET STRING 
    ACCESS read-write
    STATUS mandatory
    DESCRIPTION
        "Contact address of the system operator of the Webio, which is user definable."
    ::= { wtWebioEA6x6Text 4 }    

-- wtWebioEA6x6TimeZone Group
----------------------------

wtWebioEA6x6TzOffsetHrs OBJECT-TYPE
    SYNTAX INTEGER 
    ACCESS read-write
    STATUS mandatory
    DESCRIPTION
        "Offset hours for the time zone (winter time) with respect to UTC."
    ::= { wtWebioEA6x6TimeZone 1 }

wtWebioEA6x6TzOffsetMin OBJECT-TYPE
    SYNTAX INTEGER 
    ACCESS read-write
    STATUS mandatory
    DESCRIPTION
        "Offset minutes for the time zone (winter time) with respect to UTC."
    ::= { wtWebioEA6x6TimeZone 2 }

wtWebioEA6x6TzEnable OBJECT-TYPE
    SYNTAX OCTET STRING (SIZE(4))
    ACCESS read-write
    STATUS mandatory
    DESCRIPTION
        "Binary coded conditions:
        Octet 1: unused
        Octet 2: unused
        Octet 3: unused
        Octet 4:
        	Bit 1-7: unused
	        Bit 0  : Apply Timezone"
    ::= { wtWebioEA6x6TimeZone 3 }

wtWebioEA6x6StTzOffsetHrs OBJECT-TYPE
    SYNTAX INTEGER 
    ACCESS read-write
    STATUS mandatory
    DESCRIPTION
        "Offset hours of the time zone (summer time) with respect to UTC."
    ::= { wtWebioEA6x6TimeZone 4 }

wtWebioEA6x6StTzOffsetMin OBJECT-TYPE
    SYNTAX INTEGER 
    ACCESS read-write
    STATUS mandatory
    DESCRIPTION
        "Offset minutes of the time zone (summer time) with respect to UTC."
    ::= { wtWebioEA6x6TimeZone 5 }

wtWebioEA6x6StTzEnable OBJECT-TYPE
    SYNTAX OCTET STRING (SIZE(4))
    ACCESS read-write
    STATUS mandatory
    DESCRIPTION
        "Binary coded conditions:
        Octet 1: unused
        Octet 2: unused
        Octet 3: unused
        Octet 4:
        	Bit 1-7: unused
	        Bit 0  : Apply Summertime"
    ::= { wtWebioEA6x6TimeZone 6 }

wtWebioEA6x6StTzStartMonth OBJECT-TYPE
    SYNTAX INTEGER {
    	wtWebioEA6x6StartMonth-January(1),
    	wtWebioEA6x6StartMonth-February(2),
    	wtWebioEA6x6StartMonth-March(3),
    	wtWebioEA6x6StartMonth-April(4),
    	wtWebioEA6x6StartMonth-May(5),
    	wtWebioEA6x6StartMonth-June(6),
    	wtWebioEA6x6StartMonth-July(7),
    	wtWebioEA6x6StartMonth-August(8),
    	wtWebioEA6x6StartMonth-September(9),
    	wtWebioEA6x6StartMonth-October(10),
    	wtWebioEA6x6StartMonth-November(11),
    	wtWebioEA6x6StartMonth-December(12)
    	}
    	
    ACCESS read-write
    STATUS mandatory
    DESCRIPTION
        "Month in which the change is made from winter time to summer time."
    ::= { wtWebioEA6x6TimeZone 7 }

wtWebioEA6x6StTzStartMode OBJECT-TYPE
    SYNTAX INTEGER {
    	wtWebioEA6x6StartMode-first(1),
    	wtWebioEA6x6StartMode-second(2),
    	wtWebioEA6x6StartMode-third(3),
    	wtWebioEA6x6StartMode-fourth(4),
    	wtWebioEA6x6StartMode-last(5)
    	}
    	
    ACCESS read-write
    STATUS mandatory
    DESCRIPTION
        "Mode of the day of the week for which the change is made from winter time to summer time."
    ::= { wtWebioEA6x6TimeZone 8 }

wtWebioEA6x6StTzStartWday OBJECT-TYPE
    SYNTAX INTEGER {
    	wtWebioEA6x6StartWday-Sunday(1),
    	wtWebioEA6x6StartWday-Monday(2),
    	wtWebioEA6x6StartWday-Tuesday(3),
    	wtWebioEA6x6StartWday-Thursday(4),
    	wtWebioEA6x6StartWday-Wednesday(5),
    	wtWebioEA6x6StartWday-Friday(6),
    	wtWebioEA6x6StartWday-Saturday(7)
    	}
    	
    ACCESS read-write
    STATUS mandatory
    DESCRIPTION
        "Day of the week on which the change is made from winter time to summer time"
    ::= { wtWebioEA6x6TimeZone 9 }
    
wtWebioEA6x6StTzStartHrs OBJECT-TYPE
    SYNTAX INTEGER 
    ACCESS read-write
    STATUS mandatory
    DESCRIPTION
        "Hour in which the time zone is changed from winter to summer time with
        respect to UTC."
    ::= { wtWebioEA6x6TimeZone 10 }

wtWebioEA6x6StTzStartMin OBJECT-TYPE
    SYNTAX INTEGER 
    ACCESS read-write
    STATUS mandatory
    DESCRIPTION
        "Minute in which the time zone is changed from winter to summer time with
        respect to UTC."
    ::= { wtWebioEA6x6TimeZone 11 }
 
wtWebioEA6x6StTzStopMonth OBJECT-TYPE
    SYNTAX INTEGER {
    	wtWebioEA6x6StopMonth-January(1),
    	wtWebioEA6x6StopMonth-February(2),
    	wtWebioEA6x6StopMonth-March(3),
    	wtWebioEA6x6StopMonth-April(4),
    	wtWebioEA6x6StopMonth-May(5),
    	wtWebioEA6x6StopMonth-June(6),
    	wtWebioEA6x6StopMonth-July(7),
    	wtWebioEA6x6StopMonth-August(8),
    	wtWebioEA6x6StopMonth-September(9),
    	wtWebioEA6x6StopMonth-October(10),
    	wtWebioEA6x6StopMonth-November(11),
    	wtWebioEA6x6StopMonth-December(12)
    	}
    ACCESS read-write
    STATUS mandatory
    DESCRIPTION
        "Month in which the change is made from summer time to winter time."
   ::= { wtWebioEA6x6TimeZone 12 }

wtWebioEA6x6StTzStopMode OBJECT-TYPE
    SYNTAX INTEGER {
    	wtWebioEA6x6StopMode-first(1),
    	wtWebioEA6x6StopMode-second(2),
    	wtWebioEA6x6StopMode-third(3),
    	wtWebioEA6x6StopMode-fourth(4),
    	wtWebioEA6x6StopMode-last(5)
    	}
    ACCESS read-write
    STATUS mandatory
    DESCRIPTION
        "Mode of the week day on which the change is made from summer time to winter time."
    ::= { wtWebioEA6x6TimeZone 13 }

wtWebioEA6x6StTzStopWday OBJECT-TYPE
    SYNTAX INTEGER {
    	wtWebioEA6x6StopWday-Sunday(1),
    	wtWebioEA6x6StopWday-Monday(2),
    	wtWebioEA6x6StopWday-Tuesday(3),
    	wtWebioEA6x6StopWday-Thursday(4),
    	wtWebioEA6x6StopWday-Wednesday(5),
    	wtWebioEA6x6StopWday-Friday(6),
    	wtWebioEA6x6StopWday-Saturday(7)
    	}
    ACCESS read-write
    STATUS mandatory
    DESCRIPTION
        "Day of the week on which the change is made from summer time to winter time."
    ::= { wtWebioEA6x6TimeZone 14 }
    
wtWebioEA6x6StTzStopHrs OBJECT-TYPE
    SYNTAX INTEGER 
    ACCESS read-write
    STATUS mandatory
    DESCRIPTION
        "Hour at which the time zone is changed from summer to winter time with
        respect to UTC."
    ::= { wtWebioEA6x6TimeZone 15 }

wtWebioEA6x6StTzStopMin OBJECT-TYPE
    SYNTAX INTEGER 
    ACCESS read-write
    STATUS mandatory
    DESCRIPTION
        "Minute at which the time zone is changed from summer to winter time with
        respect to UTC."
    ::= { wtWebioEA6x6TimeZone 16 }

-- wtWebioEA6x6TimeServer Group
----------------------------

wtWebioEA6x6TimeServer1 OBJECT-TYPE
    SYNTAX OCTET STRING 
    ACCESS read-write
    STATUS mandatory
    DESCRIPTION
        "IP address or name of the 1st time server in ASCII"
    ::= { wtWebioEA6x6TimeServer 1 }

wtWebioEA6x6TimeServer2 OBJECT-TYPE
    SYNTAX OCTET STRING 
    ACCESS read-write
    STATUS mandatory
    DESCRIPTION
        "IP address or name of the 2nd time server in ASCII"
    ::= { wtWebioEA6x6TimeServer 2 }

wtWebioEA6x6TsEnable OBJECT-TYPE
    SYNTAX OCTET STRING (SIZE(4))
    ACCESS read-write
    STATUS mandatory
    DESCRIPTION
        "Binary coded conditions:
        Octet 1: unused
        Octet 2: unused
        Octet 3: unused
        Octet 4:
        	Bit 1-7: unused
	        Bit 0  : Apply Time Server"
    ::= { wtWebioEA6x6TimeServer 3 }

wtWebioEA6x6TsSyncTime OBJECT-TYPE
    SYNTAX INTEGER 
    ACCESS read-write
    STATUS mandatory
    DESCRIPTION
        "Daily synchronisation time with the time server (hour: 0-23)."
    ::= { wtWebioEA6x6TimeServer 4 }
      
    
-- wtWebioEA6x6DeviceClock Group
----------------------------

wtWebioEA6x6ClockHrs OBJECT-TYPE
    SYNTAX INTEGER (0..23)
    ACCESS read-write
    STATUS mandatory
    DESCRIPTION
        "Clock hours taking into account the time zone settings."
    ::= { wtWebioEA6x6DeviceClock 1 }

wtWebioEA6x6ClockMin OBJECT-TYPE
    SYNTAX INTEGER (0..59)
    ACCESS read-write
    STATUS mandatory
    DESCRIPTION
        "Clock minutes taking into account the time zone settings."
    ::= { wtWebioEA6x6DeviceClock 2 }

wtWebioEA6x6ClockDay OBJECT-TYPE
    SYNTAX INTEGER (1..31)
    ACCESS read-write
    STATUS mandatory
    DESCRIPTION
        "Date: Day of the month, taking into account the time zone settings."
    ::= { wtWebioEA6x6DeviceClock 3 }

wtWebioEA6x6ClockMonth OBJECT-TYPE
   SYNTAX INTEGER {
    	wtWebioEA6x6ClockMonth-January(1),
    	wtWebioEA6x6ClockMonth-February(2),
    	wtWebioEA6x6ClockMonth-March(3),
    	wtWebioEA6x6ClockMonth-April(4),
    	wtWebioEA6x6ClockMonth-May(5),
    	wtWebioEA6x6ClockMonth-June(6),
    	wtWebioEA6x6ClockMonth-July(7),
    	wtWebioEA6x6ClockMonth-August(8),
    	wtWebioEA6x6ClockMonth-September(9),
    	wtWebioEA6x6ClockMonth-October(10),
    	wtWebioEA6x6ClockMonth-November(11),
    	wtWebioEA6x6ClockMonth-December(12)
    	}
    ACCESS read-write
    STATUS mandatory
    DESCRIPTION
        "Date: Month, taking into account the time zone settings."
    ::= { wtWebioEA6x6DeviceClock 4 }

wtWebioEA6x6ClockYear OBJECT-TYPE
    SYNTAX INTEGER (0..65535)
    ACCESS read-write
    STATUS mandatory
    DESCRIPTION
        "Date: Year, taking into account the time zone settings."
    ::= { wtWebioEA6x6DeviceClock 5 }

-- wtWebioEA6x6Network Group
------------------------

wtWebioEA6x6IpAddress OBJECT-TYPE
    SYNTAX IpAddress
    ACCESS read-write
    STATUS mandatory
    DESCRIPTION
        "IP address of the Webio"
    ::= { wtWebioEA6x6Network 1 }

wtWebioEA6x6SubnetMask OBJECT-TYPE
    SYNTAX IpAddress
    ACCESS read-write
    STATUS mandatory
    DESCRIPTION
        "Subnet mask of the Webio"
    ::= { wtWebioEA6x6Network 2 }

wtWebioEA6x6Gateway OBJECT-TYPE
    SYNTAX IpAddress
    ACCESS read-write
    STATUS mandatory
    DESCRIPTION
        "Gateway of the Webio"
    ::= { wtWebioEA6x6Network 3 }

wtWebioEA6x6DnsServer1 OBJECT-TYPE
    SYNTAX OCTET STRING 
    ACCESS read-write
    STATUS mandatory
    DESCRIPTION
        "IP address of the 1st DNS server in ASCII"
    ::= { wtWebioEA6x6Network 4 }

wtWebioEA6x6DnsServer2 OBJECT-TYPE
    SYNTAX OCTET STRING 
    ACCESS read-write
    STATUS mandatory
    DESCRIPTION
        "IP address of the 2nd DNS server in ASCII"
    ::= { wtWebioEA6x6Network 5 }

wtWebioEA6x6AddConfig OBJECT-TYPE
    SYNTAX OCTET STRING 
    ACCESS read-write
    STATUS mandatory
    DESCRIPTION
        "Additional configuration (1=ON):
        Octet 1: unused
        Octet 2: unused
        Octet 3: unused
        Octet 4:
	        Bit 1: DHCP  enable
	        Bit 0: BOOTP enable"
    ::= { wtWebioEA6x6Network 6 }

--  wtWebioEA6x6HTTP Group
--------------------------------

wtWebioEA6x6Startup OBJECT-TYPE
    SYNTAX OCTET STRING 
    ACCESS read-write
    STATUS mandatory
    DESCRIPTION
        "Binary coded start page, more than one page must not be selected:
        Octet 1: unused
        Octet 2: unused
        Octet 3: unused
        Octet 4:
        	Bit 2: user.htm
        	Bit 1: home.htm
	        Bit 0: index.htm"
    ::= { wtWebioEA6x6HTTP 1 }

wtWebioEA6x6GetHeaderEnable OBJECT-TYPE
    SYNTAX OCTET STRING 
    ACCESS read-write
    STATUS mandatory
    DESCRIPTION
        "If bits are set, every answer of a short form GET question will be lead
        by the IP-address and name of the device (Header) or a HTTP header (HTTP):
        Octet 1: unused
        Octet 2: unused
        Octet 3: unused
        Octet 4:
        	Bit 2-7: unused
        	Bit 1  : GET HTTP enable
                Bit 0  : GET Header enable"
    ::= { wtWebioEA6x6HTTP 2 }

wtWebioEA6x6HttpInputTrigger OBJECT-TYPE
    SYNTAX OCTET STRING (SIZE (4))
    ACCESS read-write
    STATUS mandatory
    DESCRIPTION
        "Every change on the inputs causes their state to be transmitted to the 
        remote device. To minimize data traffic, individual inputs may be exempted 
        from this rule. Nevertheless every transmission will contain all input bits.
        If a bit is set (1), a change of state on the corresponding input 
        triggers a transmission. If the bit is not set (0), no transmission 
        takes place.
        The OCTETS are interpreted bit-by-bit, with each bit corresponding to an output. 
        Bit 0 corresponds to the LSB.
        OCTET 1: unused
        OCTET 2: unused
        OCTET 3: unused
        OCTET 4, Bit 0-5: Digital inputs 0-5
        	 Bit 6-7: unused"
    ::= { wtWebioEA6x6HTTP 3 }

wtWebioEA6x6HttpPort OBJECT-TYPE
    SYNTAX INTEGER (1..65534)
    ACCESS read-write
    STATUS mandatory
    DESCRIPTION
       "Definition of the standard HTML port (Default: 80)."
    ::= { wtWebioEA6x6HTTP 4 }        
    
    
-- wtWebioEA6x6Mail Group
--------------------------------

wtWebioEA6x6MailAdName OBJECT-TYPE
    SYNTAX OCTET STRING 
    ACCESS read-write
    STATUS mandatory
    DESCRIPTION
        "Device name for mail administration."
    ::= { wtWebioEA6x6Mail 1 }
    
wtWebioEA6x6MailReply OBJECT-TYPE
    SYNTAX OCTET STRING 
    ACCESS read-write
    STATUS mandatory
    DESCRIPTION
        "Reply address for the mail server."
    ::= { wtWebioEA6x6Mail 2 }
    
wtWebioEA6x6MailServer OBJECT-TYPE
    SYNTAX OCTET STRING 
    ACCESS read-write
    STATUS mandatory
    DESCRIPTION
        "Name or IP address of the mail server."
    ::= { wtWebioEA6x6Mail 3 }
    
wtWebioEA6x6MailEnable OBJECT-TYPE
    SYNTAX OCTET STRING 
    ACCESS read-write
    STATUS mandatory
    DESCRIPTION
        "Set this bit to enable the sending of mails:
        Octet 1: unused
        Octet 2: unused
        Octet 3: unused
        Octet 4:
        	Bit 1-7: unused
                Bit 0  : Mail enable"
    ::= { wtWebioEA6x6Mail 4 }

wtWebioEA6x6MailAuthentication OBJECT-TYPE
    SYNTAX OCTET STRING (SIZE (4))
    ACCESS read-write
    STATUS mandatory
    DESCRIPTION
        "Selection of the authentication modi:
        The OCTETS are interpreted bit-by-bit,
        Bit 0 corresponds to the LSB.
        OCTET 1: unused
        OCTET 2: unused
        OCTET 3: unused
        OCTET 4: Bit 3-7: unused
        	 Bit 2  : POP3 before SMTP
        	 Bit 1  : ESMTP, authentication
        	 Bit 0  : SMTP, no authentication"
    ::= { wtWebioEA6x6Mail 5 }
    
wtWebioEA6x6MailAuthUser OBJECT-TYPE
    SYNTAX OCTET STRING 
    ACCESS read-write
    STATUS mandatory
    DESCRIPTION
        "Name of the user to be authenticated."
    ::= { wtWebioEA6x6Mail 6 }    
    
wtWebioEA6x6MailAuthPassword OBJECT-TYPE
    SYNTAX OCTET STRING 
    ACCESS read-write
    STATUS mandatory
    DESCRIPTION
        "Authentication password."
    ::= { wtWebioEA6x6Mail 7 }    
    
wtWebioEA6x6MailPop3Server OBJECT-TYPE
    SYNTAX OCTET STRING 
    ACCESS read-write
    STATUS mandatory
    DESCRIPTION
        "Name or Ip-address of the POP3 Servers."
    ::= { wtWebioEA6x6Mail 8 }        
    

--  wtWebioEA6x6Snmp Group
--------------------------------

wtWebioEA6x6SnmpEnable OBJECT-TYPE
    SYNTAX OCTET STRING 
    ACCESS read-write
    STATUS mandatory
    DESCRIPTION
        "Set bit 0 to enable SNMP.
        If disabled, the device did not respond to any SNMP requests.
        Bit 1 decided wether the community string of read operations 
        is compared with the system password or not:
        Octet 1: unused
        Octet 2: unused
        Octet 3: unused
        Octet 4:
        	Bit 1-7: unused
        	Bit 0  : SNMP enable"
    ::= { wtWebioEA6x6SNMP 1 }
    
wtWebioEA6x6SnmpCommunityStringRead OBJECT-TYPE
    SYNTAX OCTET STRING
    ACCESS read-write
    STATUS mandatory
    DESCRIPTION
        "Community string read only"
    ::= { wtWebioEA6x6SNMP 2 }

wtWebioEA6x6SnmpCommunityStringReadWrite OBJECT-TYPE
    SYNTAX OCTET STRING
    ACCESS read-write
    STATUS mandatory
    DESCRIPTION
        "Community string read / write"
    ::= { wtWebioEA6x6SNMP 3 }

wtWebioEA6x6SnmpSystemTrapManagerIP OBJECT-TYPE
    SYNTAX OCTET STRING 
    ACCESS read-write
    STATUS mandatory
    DESCRIPTION
        "Name or IP address of the TCP server which accepts the system trap."
    ::= { wtWebioEA6x6SNMP 4 }
    
wtWebioEA6x6SnmpSystemTrapEnable OBJECT-TYPE
    SYNTAX OCTET STRING (SIZE(4))
    ACCESS read-write
    STATUS mandatory
    DESCRIPTION
        "Binary coded trigger conditions:
        Octet 1: unused
        Octet 2: unused
        Octet 3: unused
        Octet 4:
	        Bit 0:   ColdStart
	        Bit 1:   WarmStart
	        Bit 2:   Diag messages
	        Bit 3-7: unused"
    ::= { wtWebioEA6x6SNMP 5 }    

-- wtWebioEA6x6Udp Group
--------------------------------   

wtWebioEA6x6UdpAdminPort OBJECT-TYPE
    SYNTAX INTEGER
    ACCESS read-write
    STATUS mandatory
    DESCRIPTION
        "Udp port to which the Udp queries ( short form GET requests) can be sent. This
        port number must be unique within the device."
    ::= { wtWebioEA6x6UDP 1 }

wtWebioEA6x6UdpEnable OBJECT-TYPE
    SYNTAX OCTET STRING 
    ACCESS read-write
    STATUS mandatory
    DESCRIPTION
        "Set this bit to enable UDP support:
        Octet 1: unused
        Octet 2: unused
        Octet 3: unused
        Octet 4:
        	Bit 1-7: unused
                Bit 0  : UDP enable"
    ::= { wtWebioEA6x6UDP 2 }

wtWebioEA6x6UdpRemotePort OBJECT-TYPE
    SYNTAX INTEGER
    ACCESS read-write
    STATUS mandatory
    DESCRIPTION
        "Udp remote port setting.
        If this value is set to zero, the source port read from a request will be used 
        as destination port for the answer.
        A non zero value forced the destination port to this value."
    ::= { wtWebioEA6x6UDP 3 }
    
--  wtWebioEA6x6Binary Group
--------------------------------

wtWebioEA6x6BinaryModeCount OBJECT-TYPE
    SYNTAX INTEGER (1..2)
    ACCESS read-only
    STATUS mandatory
    DESCRIPTION
        "Number of independent binary channels."
    ::= { wtWebioEA6x6Binary 1 }
    
-- Binary Interface Table

wtWebioEA6x6BinaryIfTable OBJECT-TYPE
    SYNTAX SEQUENCE OF WtWebioEA6x6BinaryIfEntry
    ACCESS not-accessible
    STATUS mandatory
    DESCRIPTION
        "Table of indices."
    ::= { wtWebioEA6x6Binary 2 }

wtWebioEA6x6BinaryIfEntry OBJECT-TYPE
    SYNTAX WtWebioEA6x6BinaryIfEntry
    ACCESS not-accessible
    STATUS mandatory
    DESCRIPTION
        "Indices of the binary channels."
    INDEX  { wtWebioEA6x6BinaryModeNo }
    ::= { wtWebioEA6x6BinaryIfTable 1 }

WtWebioEA6x6BinaryIfEntry ::= SEQUENCE {
    wtWebioEA6x6BinaryModeNo INTEGER
}

wtWebioEA6x6BinaryModeNo OBJECT-TYPE
    SYNTAX INTEGER (1..2)
    ACCESS read-only
    STATUS mandatory
    DESCRIPTION
        "Number of the binary channel."
    ::= { wtWebioEA6x6BinaryIfEntry 1 }

-- Binary Table
--------------------------------

wtWebioEA6x6BinaryTable OBJECT-TYPE
    SYNTAX SEQUENCE OF WtWebioEA6x6BinaryEntry
    ACCESS not-accessible
    STATUS mandatory
    DESCRIPTION
        "Table of properties of the binary mode."
    ::= { wtWebioEA6x6Binary 3 }

wtWebioEA6x6BinaryEntry OBJECT-TYPE
    SYNTAX WtWebioEA6x6BinaryEntry
    ACCESS not-accessible
    STATUS mandatory
    DESCRIPTION
        "Binary properties."
    INDEX  { wtWebioEA6x6BinaryModeNo }
    ::= { wtWebioEA6x6BinaryTable 1 }

WtWebioEA6x6BinaryEntry ::= SEQUENCE {
    wtWebioEA6x6BinaryOperationMode			OCTET STRING,
    wtWebioEA6x6BinaryTcpServerLocalPort		INTEGER,
    wtWebioEA6x6BinaryTcpServerInputTrigger		OCTET STRING,
    wtWebioEA6x6BinaryTcpServerApplicationMode		OCTET STRING,
    wtWebioEA6x6BinaryTcpClientLocalPort		INTEGER,
    wtWebioEA6x6BinaryTcpClientServerPort		INTEGER,
    wtWebioEA6x6BinaryTcpClientServerIpAddr		OCTET STRING,
    wtWebioEA6x6BinaryTcpClientServerPassword		OCTET STRING,
    wtWebioEA6x6BinaryTcpClientInactivity		INTEGER,
    wtWebioEA6x6BinaryTcpClientInputTrigger		OCTET STRING,
    wtWebioEA6x6BinaryTcpClientInterval			INTEGER,
    wtWebioEA6x6BinaryTcpClientApplicationMode		OCTET STRING,
    wtWebioEA6x6BinaryUdpPeerLocalPort			INTEGER,
    wtWebioEA6x6BinaryUdpPeerRemotePort			INTEGER,
    wtWebioEA6x6BinaryUdpPeerRemoteIpAddr		OCTET STRING,
    wtWebioEA6x6BinaryUdpPeerInputTrigger		OCTET STRING,
    wtWebioEA6x6BinaryUdpPeerInterval			INTEGER,
    wtWebioEA6x6BinaryUdpPeerApplicationMode		OCTET STRING,
    wtWebioEA6x6BinaryConnectedPort			INTEGER,
    wtWebioEA6x6BinaryConnectedIpAddr			IpAddress,
    wtWebioEA6x6BinaryTcpServerClientHttpPort		INTEGER,
    wtWebioEA6x6BinaryTcpClientServerHttpPort		INTEGER
    
}

wtWebioEA6x6BinaryOperationMode OBJECT-TYPE
    SYNTAX OCTET STRING (SIZE (4))
    ACCESS read-write
    STATUS mandatory
    DESCRIPTION
        "Selection of the operation mode:
        The OCTETS are interpreted bit-by-bit,
        Bit 0 corresponds to the LSB.
        OCTET 1: unused
        OCTET 2: unused
        OCTET 3: unused
        OCTET 4: Bit 3-7: unused
        	 Bit 2  : UDP Peer
        	 Bit 1  : TCP Client
        	 Bit 0  : TCP Server"
    ::= { wtWebioEA6x6BinaryEntry 1 }

wtWebioEA6x6BinaryTcpServerLocalPort OBJECT-TYPE
    SYNTAX INTEGER (1..65535)
    ACCESS read-write
    STATUS mandatory
    DESCRIPTION
        "Local TCP port for data exchange in this server mode.
        This port number must be unique within the device.
	Reserved port number must not be used (refere to the manual)."
    ::= { wtWebioEA6x6BinaryEntry 2 }

wtWebioEA6x6BinaryTcpServerInputTrigger OBJECT-TYPE
    SYNTAX OCTET STRING (SIZE (4))
    ACCESS read-write
    STATUS mandatory
    DESCRIPTION
        "Every change on the inputs causes their state to be transmitted to the 
        remote device. To minimize data traffic, individual inputs may be exempted 
        from this rule. Nevertheless every transmission will contain all input bits.
        If a bit is set (1), a change of state on the corresponding input 
        triggers a transmission. If the bit is not set (0), no transmission 
        takes place.
        The OCTETS are interpreted bit-by-bit, with each bit corresponding to an input. 
        Bit 0 corresponds to the LSB.
        OCTET 1: unused
        OCTET 2: unused
        OCTET 3: unused
        OCTET 4, Bit 0-5: Digital inputs 0-5
        	 Bit 6-7: unused"
    ::= { wtWebioEA6x6BinaryEntry 3 }

wtWebioEA6x6BinaryTcpServerApplicationMode OBJECT-TYPE
    SYNTAX OCTET STRING (SIZE (4))
    ACCESS read-write
    STATUS mandatory
    DESCRIPTION
        "Selection of the application mode:
        The OCTETS are interpreted bit-by-bit,
        Bit 0 corresponds to the LSB.
        OCTET 1: unused
        OCTET 2: unused
        OCTET 3: unused
        OCTET 4: Bit 4-7: unused
        	 Bit 3  : OPC Device
        	 Bit 2  : Box2Box Slave
        	 Bit 1  : Compatible 50xxx
        	 Bit 0  : Default"
    ::= { wtWebioEA6x6BinaryEntry 4 }
    
wtWebioEA6x6BinaryTcpClientLocalPort OBJECT-TYPE
    SYNTAX INTEGER (1..65535)
    ACCESS read-write
    STATUS mandatory
    DESCRIPTION
        "Local TCP port for data exchange in this client mode.
        This port number must be unique within the device.
	Reserved port number must not be used (refere to the manual)."
    ::= { wtWebioEA6x6BinaryEntry 5 }

wtWebioEA6x6BinaryTcpClientServerPort OBJECT-TYPE
    SYNTAX INTEGER (1..65535)
    ACCESS read-write
    STATUS mandatory
    DESCRIPTION
        "Port number of the server. A complete set of port number, IP address
        and a valid input/output mask starts this mode.
        No data exchange take place when setting the server port to zero."
    ::= { wtWebioEA6x6BinaryEntry 6 }

wtWebioEA6x6BinaryTcpClientServerIpAddr OBJECT-TYPE
    SYNTAX OCTET STRING
    ACCESS read-write
    STATUS mandatory
    DESCRIPTION
        "Ip address of the server. A complete set of port number, IP address
        and a valid input/output mask starts this mode.
        No data exchange take place when setting the server IP address to 0.0.0.0."
    ::= { wtWebioEA6x6BinaryEntry 7 }

wtWebioEA6x6BinaryTcpClientServerPassword OBJECT-TYPE
    SYNTAX OCTET STRING
    ACCESS read-write
    STATUS mandatory
    DESCRIPTION
        "Building a connection may be protected by the 
        administrator password of the server. Enter the server password
        to establish the connection, if a server administrator password
        exists."
    ::= { wtWebioEA6x6BinaryEntry 8 }

wtWebioEA6x6BinaryTcpClientInactivity OBJECT-TYPE
    SYNTAX INTEGER 
    ACCESS read-write
    STATUS mandatory
    DESCRIPTION
        "Connection timeout in 100ms. If no data are exchanged within the specified  
        time, the device closes the connection to the server.
        The value 0 deactivates the timer. Using the Box2Box mode this function is
        disabled."
    ::= { wtWebioEA6x6BinaryEntry 9 }
    
wtWebioEA6x6BinaryTcpClientInputTrigger OBJECT-TYPE
    SYNTAX OCTET STRING (SIZE (4))
    ACCESS read-write
    STATUS mandatory
    DESCRIPTION
        "Every change on the inputs causes their state to be transmitted to the 
        remote device. To minimize data traffic, individual inputs may be exempted 
        from this rule. Nevertheless every transmission will contain all input bits.
        If a bit is set (1), a change of state on the corresponding input 
        triggers a transmission. If the bit is not set (0), no transmission 
        takes place.
        The OCTETS are interpreted bit-by-bit, with each bit corresponding to an input. 
        Bit 0 corresponds to the LSB.
        OCTET 1: unused
        OCTET 2: unused
        OCTET 3: unused
        OCTET 4, Bit 0-5: Digital inputs 0-5
        	 Bit 6-7: unused"
    ::= { wtWebioEA6x6BinaryEntry 10 }
 
wtWebioEA6x6BinaryTcpClientInterval OBJECT-TYPE
    SYNTAX INTEGER (0..65535)
    ACCESS read-write
    STATUS mandatory
    DESCRIPTION
        "Configurable interval with a 100ms base, in which the Webio device sends
        data to the configured application. A interval of zero stopps the 
        periodical sending."
    ::= { wtWebioEA6x6BinaryEntry 11 }

wtWebioEA6x6BinaryTcpClientApplicationMode OBJECT-TYPE
    SYNTAX OCTET STRING (SIZE (4))
    ACCESS read-write
    STATUS mandatory
    DESCRIPTION
        "Selection of the application mode:
        The OCTETS are interpreted bit-by-bit,
        Bit 0 corresponds to the LSB.
        OCTET 1: unused
        OCTET 2: unused
        OCTET 3: unused
        OCTET 4: Bit 3-7: unused
        	 Bit 2  : Box2Box Slave
        	 Bit 1  : Compatible 50xxx
        	 Bit 0  : Default"
    ::= { wtWebioEA6x6BinaryEntry 12 }

wtWebioEA6x6BinaryUdpPeerLocalPort OBJECT-TYPE
    SYNTAX INTEGER (1..65535)
    ACCESS read-write
    STATUS mandatory
    DESCRIPTION
        "Local UDP port for data exchange in this peer to peer mode.
        This port number must be unique within the device.
	Reserved port number must not be used (refere to the manual)."
    ::= { wtWebioEA6x6BinaryEntry 13 }

wtWebioEA6x6BinaryUdpPeerRemotePort OBJECT-TYPE
    SYNTAX INTEGER (1..65535)
    ACCESS read-write
    STATUS mandatory
    DESCRIPTION
        "Port number of the remote device. A complete set of port number, IP address
        and a valid input/output mask starts this mode.
        No data exchange take place when setting the remote port to zero."
    ::= { wtWebioEA6x6BinaryEntry 14 }

wtWebioEA6x6BinaryUdpPeerRemoteIpAddr OBJECT-TYPE
    SYNTAX OCTET STRING
    ACCESS read-write
    STATUS mandatory
    DESCRIPTION
        "Ip address of the remote device. A complete set of port number, IP address
        and a valid input/output mask starts this mode.
        No data exchange take place when setting the remote device IP address to 0.0.0.0."
    ::= { wtWebioEA6x6BinaryEntry 15 }

wtWebioEA6x6BinaryUdpPeerInputTrigger OBJECT-TYPE
    SYNTAX OCTET STRING (SIZE (4))
    ACCESS read-write
    STATUS mandatory
    DESCRIPTION
        "Every change on the inputs causes their state to be transmitted to the 
        remote device. To minimize data traffic, individual inputs may be exempted 
        from this rule. Nevertheless every transmission will contain all input bits.
        If a bit is set (1), a change of state on the corresponding input 
        triggers a transmission. If the bit is not set (0), no transmission 
        takes place.
        The OCTETS are interpreted bit-by-bit, with each bit corresponding to an input. 
        Bit 0 corresponds to the LSB.
        OCTET 1: unused
        OCTET 2: unused
        OCTET 3: unused
        OCTET 4, Bit 0-5: Digital inputs 0-5
        	 Bit 6-7: unused"
    ::= { wtWebioEA6x6BinaryEntry 16 }

wtWebioEA6x6BinaryUdpPeerInterval OBJECT-TYPE
    SYNTAX INTEGER (0..65535)
    ACCESS read-write
    STATUS mandatory
    DESCRIPTION
        "Configurable interval with a 100ms base, in which the Webio device sends
        data to the configured remote device. A interval of zero stopps the 
        periodical sending."
    ::= { wtWebioEA6x6BinaryEntry 17 }

wtWebioEA6x6BinaryUdpPeerApplicationMode OBJECT-TYPE
    SYNTAX OCTET STRING (SIZE (4))
    ACCESS read-write
    STATUS mandatory
    DESCRIPTION
        "Selection of the application mode:
        The OCTETS are interpreted bit-by-bit,
        Bit 0 corresponds to the LSB.
        OCTET 1: unused
        OCTET 2: unused
        OCTET 3: unused
        OCTET 4: Bit 3-7: unused
        	 Bit 2  : Box2Box Slave
        	 Bit 1  : Compatible 50xxx
        	 Bit 0  : Default"
    ::= { wtWebioEA6x6BinaryEntry 18 }

wtWebioEA6x6BinaryConnectedPort OBJECT-TYPE
    SYNTAX INTEGER (1..65535)
    ACCESS read-only
    STATUS mandatory
    DESCRIPTION
        "Port number of the remote device, after connection has been established.
        In case of no connection or missing port informations a zero will be read."
    ::= { wtWebioEA6x6BinaryEntry 19 }

wtWebioEA6x6BinaryConnectedIpAddr OBJECT-TYPE
    SYNTAX IpAddress
    ACCESS read-only
    STATUS mandatory
    DESCRIPTION
        "IP address of the remote device, after connection has been established.
        In case of no connection or missing port informations 0.0.0.0 will be read."
    ::= { wtWebioEA6x6BinaryEntry 20 } 

wtWebioEA6x6BinaryTcpServerClientHttpPort OBJECT-TYPE
    SYNTAX INTEGER (1..65535)
    ACCESS read-write
    STATUS mandatory
    DESCRIPTION
        "HTTP port number of the remote device at TCP Server Mode. If an mailfunction occurs 
        status informations will be send to this port. 
        Not used at mode Compatible 50xxx."
    ::= { wtWebioEA6x6BinaryEntry 21 }
    
wtWebioEA6x6BinaryTcpClientServerHttpPort OBJECT-TYPE
    SYNTAX INTEGER (1..65535)
    ACCESS read-write
    STATUS mandatory
    DESCRIPTION
        "HTTP port number of the remote device at TCP Client Mode. In the operating mode
        Box2Box connection status informations will be exchanged through this port."
    ::= { wtWebioEA6x6BinaryEntry 22 }            
    
--  wtWebioEA6x6Syslog Group
--------------------------------
    
wtWebioEA6x6SyslogServerIP OBJECT-TYPE
    SYNTAX OCTET STRING 
    ACCESS read-write
    STATUS mandatory
    DESCRIPTION
        "Name or IP address of the Syslog server, which accepts the Syslog messgaes."
    ::= { wtWebioEA6x6Syslog 1 }
    
wtWebioEA6x6SyslogServerPort OBJECT-TYPE
    SYNTAX INTEGER
    ACCESS read-write
    STATUS mandatory
    DESCRIPTION
        "Portnumber of the Syslog servers, default 514."
    ::= { wtWebioEA6x6Syslog 2 }

wtWebioEA6x6SyslogSystemMessagesEnable OBJECT-TYPE
    SYNTAX OCTET STRING (SIZE(4))
    ACCESS read-write
    STATUS mandatory
    DESCRIPTION
        "Binary coded trigger conditions:
        Octet 1: unused
        Octet 2: unused
        Octet 3: unused
        Octet 4:
	        Bit 0:   ColdStart
	        Bit 1:   WarmStart
	        Bit 2:   Diag Messages
	        Bit 3-7: unused"
    ::= { wtWebioEA6x6Syslog 3 }    

wtWebioEA6x6SyslogEnable OBJECT-TYPE
    SYNTAX OCTET STRING 
    ACCESS read-write
    STATUS mandatory
    DESCRIPTION
        "Set bit 0to enable Syslog:
        Octet 1: unused
        Octet 2: unused
        Octet 3: unused
        Octet 4:
        	Bit 1-7: unused
                Bit 0  : Syslog enable"
    ::= { wtWebioEA6x6Syslog 4 }

--  wtWebioEA6x6FTP Group
--------------------------------

wtWebioEA6x6FTPServerIP OBJECT-TYPE
    SYNTAX OCTET STRING 
    ACCESS read-write
    STATUS mandatory
    DESCRIPTION
        "Name or IP address of the FTP server, which accepts the FTP messages."
    ::= { wtWebioEA6x6FTP 1 }
    
wtWebioEA6x6FTPServerControlPort OBJECT-TYPE
    SYNTAX INTEGER
    ACCESS read-write
    STATUS mandatory
    DESCRIPTION
        "Portnumber of the control port of the FTP server, default 21."
    ::= { wtWebioEA6x6FTP 2 }
    
wtWebioEA6x6FTPUserName OBJECT-TYPE
    SYNTAX OCTET STRING 
    ACCESS read-write
    STATUS mandatory
    DESCRIPTION
        "FTP Loggin: user name."
    ::= { wtWebioEA6x6FTP 3 }
    
wtWebioEA6x6FTPPassword OBJECT-TYPE
    SYNTAX OCTET STRING 
    ACCESS read-write
    STATUS mandatory
    DESCRIPTION
        "FTP Loggin: user password."
    ::= { wtWebioEA6x6FTP 4 }

wtWebioEA6x6FTPAccount OBJECT-TYPE
    SYNTAX OCTET STRING 
    ACCESS read-write
    STATUS mandatory
    DESCRIPTION
        "FTP Loggin: name of account."
    ::= { wtWebioEA6x6FTP 5 }

wtWebioEA6x6FTPOption OBJECT-TYPE
    SYNTAX OCTET STRING 
    ACCESS read-write
    STATUS mandatory
    DESCRIPTION
        "Bit 0 switches the FTP Server in Passiv-Mode,
        the Client controls the data connection on its own:
        Octet 1: unused
        Octet 2: unused
        Octet 3: unused
        Octet 4:
        	Bit 1-7: unused
                Bit 0  : PASV enable"
    ::= { wtWebioEA6x6FTP 6 }
    
wtWebioEA6x6FTPEnable OBJECT-TYPE
    SYNTAX OCTET STRING 
    ACCESS read-write
    STATUS mandatory
    DESCRIPTION
        "Set Bit 0 to enable FTP:
        Octet 1: unused
        Octet 2: unused
        Octet 3: unused
        Octet 4:
        	Bit 1-7: unused
                Bit 0  : FTP enable"
    ::= { wtWebioEA6x6FTP 7 }  
    
--  wtWebioEA6x6OutputMode Group
--------------------------------

-- OutputMode Table

wtWebioEA6x6OutputModeTable OBJECT-TYPE
    SYNTAX SEQUENCE OF WtWebioEA6x6OutputModeEntry
    ACCESS not-accessible
    STATUS mandatory
    DESCRIPTION
        "Table of output mode configurations dependent on the output indices."
    ::= { wtWebioEA6x6OutputMode 1 }

wtWebioEA6x6OutputModeEntry OBJECT-TYPE
    SYNTAX WtWebioEA6x6OutputModeEntry
    ACCESS not-accessible
    STATUS mandatory
    DESCRIPTION
        "Output mode configurations of the individual outputs."
    INDEX  { wtWebioEA6x6OutputNo }
    ::= { wtWebioEA6x6OutputModeTable 1 }

WtWebioEA6x6OutputModeEntry ::= SEQUENCE {
    wtWebioEA6x6OutputModeBit	OCTET STRING
}

wtWebioEA6x6OutputModeBit OBJECT-TYPE
    SYNTAX OCTET STRING (SIZE (4))
    ACCESS read-write
    STATUS mandatory
    DESCRIPTION
        "This binary coded output mode defines the individual operation mode for any
        output. More than one mode must not be selected.
        The OCTETS are interpreted bit-by-bit, 
        Bit 0 corresponds to the LSB.
        OCTET 1: unused
        OCTET 2: unused
        OCTET 3: unused
        OCTET 4: Bit 6-7: unused
        	 Bit 5  : Logic
        	 Bit 4  : Binary 2
        	 Bit 3  : Binary 1
        	 Bit 2  : SNMP
        	 Bit 1  : UDP ASCII
        	 Bit 0  : HTTP"
    ::= { wtWebioEA6x6OutputModeEntry 1 }
    
wtWebioEA6x6SafetyTimeout OBJECT-TYPE
    SYNTAX INTEGER (0..65535)
    ACCESS read-write
    STATUS mandatory
    DESCRIPTION
        "After this period of time (multiple of 100ms) without receiving data
        outputs switch to their Safety States. For each output a independend safety state
        could be defined."
    ::= { wtWebioEA6x6OutputMode 2 }
 
  
-- wtWebioEA6x6Alarm Group
----------------------------

wtWebioEA6x6AlarmCount OBJECT-TYPE
    SYNTAX INTEGER (1..12)
    ACCESS read-only
    STATUS mandatory
    DESCRIPTION
        "Number of independent alarms."
    ::= { wtWebioEA6x6Alarm 1 }
    
-- Alarm Interface Table

wtWebioEA6x6AlarmIfTable OBJECT-TYPE
    SYNTAX SEQUENCE OF WtWebioEA6x6AlarmIfEntry
    ACCESS not-accessible
    STATUS mandatory
    DESCRIPTION
        "List of alarm indices."
    ::= { wtWebioEA6x6Alarm 2 }

wtWebioEA6x6AlarmIfEntry OBJECT-TYPE
    SYNTAX WtWebioEA6x6AlarmIfEntry
    ACCESS not-accessible
    STATUS mandatory
    DESCRIPTION
        "Numbers of the alarms."
    INDEX  { wtWebioEA6x6AlarmNo }
    ::= { wtWebioEA6x6AlarmIfTable 1 }

WtWebioEA6x6AlarmIfEntry ::= SEQUENCE {
    wtWebioEA6x6AlarmNo INTEGER
}

wtWebioEA6x6AlarmNo OBJECT-TYPE
    SYNTAX INTEGER (1..12)
    ACCESS read-only
    STATUS mandatory
    DESCRIPTION
        "Numbers of the alarms."
    ::= { wtWebioEA6x6AlarmIfEntry 1 }

-- Alarm Table

wtWebioEA6x6AlarmTable OBJECT-TYPE
    SYNTAX SEQUENCE OF WtWebioEA6x6AlarmEntry
    ACCESS not-accessible
    STATUS mandatory
    DESCRIPTION
        "List of settings depending on the alarm number."
    ::= { wtWebioEA6x6Alarm 3 }

wtWebioEA6x6AlarmEntry OBJECT-TYPE
    SYNTAX WtWebioEA6x6AlarmEntry
    ACCESS not-accessible
    STATUS mandatory
    DESCRIPTION
        "Alarm parameters of the individual alarms."
    INDEX  { wtWebioEA6x6AlarmNo }
    ::= { wtWebioEA6x6AlarmTable 1 }

WtWebioEA6x6AlarmEntry ::= SEQUENCE {
    wtWebioEA6x6AlarmInputTrigger		OCTET STRING,
    wtWebioEA6x6AlarmOutputTrigger		OCTET STRING,
    wtWebioEA6x6AlarmSystemTrigger		OCTET STRING,
    wtWebioEA6x6AlarmMaxCounterValue		OCTET STRING,
    wtWebioEA6x6AlarmInterval			OCTET STRING,
    wtWebioEA6x6AlarmEnable			OCTET STRING,
    wtWebioEA6x6AlarmMailAddr			OCTET STRING,
    wtWebioEA6x6AlarmMailSubject		OCTET STRING,
    wtWebioEA6x6AlarmMailText			OCTET STRING,
    wtWebioEA6x6AlarmSnmpManagerIP		OCTET STRING,
    wtWebioEA6x6AlarmSnmpTrapText		OCTET STRING,
    wtWebioEA6x6AlarmUdpIpAddr			OCTET STRING,
    wtWebioEA6x6AlarmUdpPort			INTEGER,
    wtWebioEA6x6AlarmUdpText			OCTET STRING,
    wtWebioEA6x6AlarmTcpIpAddr			OCTET STRING,
    wtWebioEA6x6AlarmTcpPort			INTEGER,
    wtWebioEA6x6AlarmTcpText			OCTET STRING,    
    wtWebioEA6x6AlarmSyslogIpAddr		OCTET STRING,
    wtWebioEA6x6AlarmSyslogPort			INTEGER,
    wtWebioEA6x6AlarmSyslogText			OCTET STRING,
    wtWebioEA6x6AlarmFtpDataPort		OCTET STRING,
    wtWebioEA6x6AlarmFtpFileName		OCTET STRING,
    wtWebioEA6x6AlarmFtpText			OCTET STRING,
    wtWebioEA6x6AlarmFtpOption			OCTET STRING,
    wtWebioEA6x6AlarmTimerCron			OCTET STRING,
    
    wtWebioEA6x6AlarmMailReleaseSubject		OCTET STRING,
    wtWebioEA6x6AlarmMailReleaseText		OCTET STRING,
    wtWebioEA6x6AlarmSnmpTrapReleaseText	OCTET STRING,
    wtWebioEA6x6AlarmUdpReleaseText		OCTET STRING,
    wtWebioEA6x6AlarmTcpReleaseText		OCTET STRING,    
    wtWebioEA6x6AlarmSyslogReleaseText		OCTET STRING,
    wtWebioEA6x6AlarmFtpReleaseText		OCTET STRING    
    
}

wtWebioEA6x6AlarmInputTrigger OBJECT-TYPE
    SYNTAX OCTET STRING (SIZE(12))
    ACCESS read-write
    STATUS mandatory
    DESCRIPTION
        "This variable allows setting of individual input trigger conditions. 
        The OCTETS are interpreted bit-by-bit, with each bit corresponding to an input. 
        Bit 0 corresponds to the LSB.
	The first four OCTETS contain the mask which determines which of the inputs are to 
	be considered (corresponding bit = 1) and which inputs are to ignore 
	(corresponding bit = 0):
	OCTET 1 : unused
	OCTET 2 : unused
	OCTET 3 : unused
	OCTET 4, Bit 0-5: Mask for digital inputs 0-5
		 Bit 6-7: unused
	
	OCTETS 5-8 contain the level (1=HIGH, 0=LOW) which the inputs 
	should assume:
	OCTET 5 : unused
	OCTET 6 : unused
	OCTET 7 : unused
        OCTET 8, Bit 0-5: Level of digital inputs 0-5
        	 Bit 6-7: unused
        
	OCTETS 9-12 contain the ANY bit (1=ON, 0=OFF). Inputs masked with the any bit trigger with any change 
	of the corresponding input bit. Settings in OCTET 5-9 are then unused:
	OCTET 9 : unused
	OCTET 10: unused
	OCTET 11: unused
	OCTET 12, Bit 0-5: ANY bits of digital inputs 0-5
		  Bit 6-7: unused"
        
    ::= { wtWebioEA6x6AlarmEntry 1 }

wtWebioEA6x6AlarmOutputTrigger OBJECT-TYPE
    SYNTAX OCTET STRING (SIZE(12))
    ACCESS read-write
    STATUS mandatory
    DESCRIPTION
        "This variable allows setting of individual output trigger conditions. 
        The OCTETS are interpreted bit-by-bit, with each bit corresponding to an output. 
        Bit 0 corresponds to the LSB.
	The first four OCTETS contain the mask which determines which of the outputs are to 
	be considered (corresponding bit = 1) and which outputs are to ignore 
	(corresponding bit = 0):
	OCTET 1 : unused
	OCTET 2 : unused
	OCTET 3 : unused
	OCTET 4, Bit 0-5: Mask for digital outputs 0-5
		 Bit 6-7: unused
	
	OCTETS 5-8 contain the level (1=HIGH, 0=LOW) which the outputs 
	should assume:
	OCTET 5 : unused
	OCTET 6 : unused
	OCTET 7 : unused
        OCTET 8, Bit 0-5: Level of digital outputs 0-5
        	 Bit 6-7: unused

	OCTETS 9-12 contain the ANY bit (1=ON, 0=OFF). Outputs masked with the any bit trigger with any change 
	of the corresponding output bit. Settings in OCTET 5-9 are then unused:
	OCTET 9 : unused
	OCTET 10: unused
	OCTET 11: unused
	OCTET 12, Bit 0-5: ANY bits of digital outputs 0-5
		  Bit 6-7: unused"
        
    ::= { wtWebioEA6x6AlarmEntry 2 }
    
wtWebioEA6x6AlarmSystemTrigger OBJECT-TYPE
    SYNTAX OCTET STRING (SIZE(4))
    ACCESS read-write
    STATUS mandatory
    DESCRIPTION
        "Binary coded trigger conditions:
        The OCTETS are interpreted bit-by-bit.
        Bit 0 corresponds to the LSB.
        OCTET 1: unused
        OCTET 2: unused
        OCTET 3: unused
        OCTET 4, 
        	 Bit 4-7: unused
        	 Bit 3  : Warm Start
        	 Bit 2  : Cold Start
        	 Bit 1  : Timer
        	 Bit 0  : Load Control"
    ::= { wtWebioEA6x6AlarmEntry 3 }

wtWebioEA6x6AlarmMaxCounterValue OBJECT-TYPE
    SYNTAX OCTET STRING 
    ACCESS read-write
    STATUS mandatory
    DESCRIPTION
        "This variable configures a max. counter value. If an input counter value
        exceeds this max. value, the corresponding alarm is triggered. Input counters with
        its mask bit unset in wtWebioEA6x6AlarmInputTrigger are not considered."
    ::= { wtWebioEA6x6AlarmEntry 4 }

wtWebioEA6x6AlarmInterval OBJECT-TYPE
    SYNTAX OCTET STRING 
    ACCESS read-write
    STATUS mandatory
    DESCRIPTION
        "Send interval for alarm messages."
    ::= { wtWebioEA6x6AlarmEntry 5 }

wtWebioEA6x6AlarmEnable OBJECT-TYPE
    SYNTAX OCTET STRING (SIZE(4))
    ACCESS read-write
    STATUS mandatory
    DESCRIPTION
        "Binary coded alarm enable:
        Octet 1: unused
        Octet 2: unused
        Octet 3: unused
        Octet 4:
		Bit 0:	Mail Enable
        	Bit 1:	SNMP Trap enable
        	Bit 2:  UDP enable
        	Bit 3:  Send inputs to pending TCP connections
        	Bit 4:  TCP Client enable
        	Bit 5:	Syslog Messages enable
        	Bit 6-7: unused"
    ::= { wtWebioEA6x6AlarmEntry 6 }

wtWebioEA6x6AlarmMailAddr OBJECT-TYPE
    SYNTAX OCTET STRING 
    ACCESS read-write
    STATUS mandatory
    DESCRIPTION
        "E-Mail address for sending the alarm mail to."
    ::= { wtWebioEA6x6AlarmEntry 7 }

wtWebioEA6x6AlarmMailSubject OBJECT-TYPE
    SYNTAX OCTET STRING 
    ACCESS read-write
    STATUS mandatory
    DESCRIPTION
        "Subject line for alarm mail."
    ::= { wtWebioEA6x6AlarmEntry 8 }

wtWebioEA6x6AlarmMailText OBJECT-TYPE
    SYNTAX OCTET STRING 
    ACCESS read-write
    STATUS mandatory
    DESCRIPTION
        "Alarm mail text: 
        States of the Webio device can be included by using special tags.
        Please refer to the respective Webio manual"
    ::= { wtWebioEA6x6AlarmEntry 9 }

wtWebioEA6x6AlarmSnmpManagerIP OBJECT-TYPE
    SYNTAX OCTET STRING 
    ACCESS read-write
    STATUS mandatory
    DESCRIPTION
        "IP address of the SNMP Manager to which the Webio device should send SNMP traps."
    ::= { wtWebioEA6x6AlarmEntry 10 }

wtWebioEA6x6AlarmSnmpTrapText OBJECT-TYPE
    SYNTAX OCTET STRING 
    ACCESS read-write
    STATUS mandatory
    DESCRIPTION
        "This text appears in the trap body."
    ::= { wtWebioEA6x6AlarmEntry 11 }
    
wtWebioEA6x6AlarmUdpIpAddr OBJECT-TYPE
    SYNTAX OCTET STRING 
    ACCESS read-write
    STATUS mandatory
    DESCRIPTION
        "IP address of the UDP listener to which the Webio device should send UDP traps."
    ::= { wtWebioEA6x6AlarmEntry 12 }    

wtWebioEA6x6AlarmUdpPort OBJECT-TYPE
    SYNTAX INTEGER (1..65535) 
    ACCESS read-write
    STATUS mandatory
    DESCRIPTION
        "Port number of the UDP listener to which the Webio device should send UDP traps."
    ::= { wtWebioEA6x6AlarmEntry 13 }    

wtWebioEA6x6AlarmUdpText OBJECT-TYPE
    SYNTAX OCTET STRING 
    ACCESS read-write
    STATUS mandatory
    DESCRIPTION
        "This text appears in the UDP trap body."
    ::= { wtWebioEA6x6AlarmEntry 14 }
    
wtWebioEA6x6AlarmTcpIpAddr OBJECT-TYPE
    SYNTAX OCTET STRING
    ACCESS read-write
    STATUS mandatory
    DESCRIPTION
        "IP address of the TCP listener to which the Webio device should send TCP traps."
    ::= { wtWebioEA6x6AlarmEntry 15 }    

wtWebioEA6x6AlarmTcpPort OBJECT-TYPE
    SYNTAX INTEGER (1..65535) 
    ACCESS read-write
    STATUS mandatory
    DESCRIPTION
        "Port number of the TCP listener to which the Webio device should send TCP traps."
    ::= { wtWebioEA6x6AlarmEntry 16 }    

wtWebioEA6x6AlarmTcpText OBJECT-TYPE
    SYNTAX OCTET STRING 
    ACCESS read-write
    STATUS mandatory
    DESCRIPTION
        "This text appears in the TCP trap body."
    ::= { wtWebioEA6x6AlarmEntry 17 }

wtWebioEA6x6AlarmSyslogIpAddr OBJECT-TYPE
    SYNTAX OCTET STRING 
    ACCESS read-write
    STATUS mandatory
    DESCRIPTION
        "IP address of the syslog server to which the Webio device should send syslog messages."
    ::= { wtWebioEA6x6AlarmEntry 18 }    

wtWebioEA6x6AlarmSyslogPort OBJECT-TYPE
    SYNTAX INTEGER (1..65535) 
    ACCESS read-write
    STATUS mandatory
    DESCRIPTION
        "Port number of the syslog server to which the Webio device should send syslog messages."
    ::= { wtWebioEA6x6AlarmEntry 19 }    

wtWebioEA6x6AlarmSyslogText OBJECT-TYPE
    SYNTAX OCTET STRING 
    ACCESS read-write
    STATUS mandatory
    DESCRIPTION
        "Every message starts with the priority key, a time stamp and the host ip address, according RFC3164.
        This text appears in the following syslog message body."
    ::= { wtWebioEA6x6AlarmEntry 20 }    
    
wtWebioEA6x6AlarmFtpDataPort OBJECT-TYPE
    SYNTAX OCTET STRING 
    ACCESS read-write
    STATUS mandatory
    DESCRIPTION
        "Local data port: 1..65535 or AUTO: the next free port will be assigned."
    ::= { wtWebioEA6x6AlarmEntry 21 }
    
wtWebioEA6x6AlarmFtpFileName OBJECT-TYPE
    SYNTAX OCTET STRING 
    ACCESS read-write
    STATUS mandatory
    DESCRIPTION
        "Name of the file including path informations."
    ::= { wtWebioEA6x6AlarmEntry 22 }
    
wtWebioEA6x6AlarmFtpText OBJECT-TYPE
    SYNTAX OCTET STRING 
    ACCESS read-write
    STATUS mandatory
    DESCRIPTION
        "Message text to store on the FTP server."
    ::= { wtWebioEA6x6AlarmEntry 23 }

wtWebioEA6x6AlarmFtpOption OBJECT-TYPE
    SYNTAX OCTET STRING (SIZE(4))
    ACCESS read-write
    STATUS mandatory
    DESCRIPTION
        "Binary coded options, select only one option at the same time:
        STORE  = replace file
        APPEND = append message at the end of the file
        
        Octet 1: unused
        Octet 2: unused
        Octet 3: unused
        Octet 4:
		Bit 0  :	STORE
		Bit 1  :	APPEND
        	Bit 2-7:	unused"
    ::= { wtWebioEA6x6AlarmEntry 24 }      
    
wtWebioEA6x6AlarmTimerCron OBJECT-TYPE
    SYNTAX OCTET STRING
    ACCESS read-write
    STATUS mandatory
    DESCRIPTION
        "This entry contains 5 space or tab seperated text fields for time trigger definition.
        Each field must match with the actual time to trigger a message, weekday and day of month
        are interpreted separatley.
        1: Minutes	Range 0-59
        2. Hours	Range 0-23, 0 is midnight
        3: Day of month	Range 1-31
        4: Month	Range 1-12
        5: Weekday	Range 0-6, 0 is sunday
        
        Syntax for every field:
         - an asterix (*) enables every possible setting of a field
         - single numbers seperated by commas
         - a partition within the allowed range (1-5)
         - step size within an partition of the allowed range (0-59/2: every second minute)."
    ::= { wtWebioEA6x6AlarmEntry 25 }      


wtWebioEA6x6AlarmMailReleaseSubject OBJECT-TYPE
    SYNTAX OCTET STRING 
    ACCESS read-write
    STATUS mandatory
    DESCRIPTION
       "Subject line for alarm mail."
    ::= { wtWebioEA6x6AlarmEntry 26 }

wtWebioEA6x6AlarmMailReleaseText OBJECT-TYPE
    SYNTAX OCTET STRING 
    ACCESS read-write
    STATUS mandatory
    DESCRIPTION
        "Release Alarm mail text: 
        States of the Webio device can be included by using special tags.
        Please refer to the respective Webio manual"
    ::= { wtWebioEA6x6AlarmEntry 27 }    

wtWebioEA6x6AlarmSnmpTrapReleaseText OBJECT-TYPE
    SYNTAX OCTET STRING 
    ACCESS read-write
    STATUS mandatory
    DESCRIPTION
        "This text appears in the trap body."
    ::= { wtWebioEA6x6AlarmEntry 28 }

wtWebioEA6x6AlarmUdpReleaseText OBJECT-TYPE
    SYNTAX OCTET STRING 
    ACCESS read-write
    STATUS mandatory
    DESCRIPTION
        "This text appears in the UDP trap body."
    ::= { wtWebioEA6x6AlarmEntry 29 }

wtWebioEA6x6AlarmTcpReleaseText OBJECT-TYPE
    SYNTAX OCTET STRING 
    ACCESS read-write
    STATUS mandatory
    DESCRIPTION
        "This text appears in the TCP trap body."
    ::= { wtWebioEA6x6AlarmEntry 30 }

wtWebioEA6x6AlarmSyslogReleaseText OBJECT-TYPE
    SYNTAX OCTET STRING 
    ACCESS read-write
    STATUS mandatory
    DESCRIPTION
        "Every message starts with the priority key, a time stamp and the host ip address, according RFC3164.
        This text appears in the following syslog message body."
    ::= { wtWebioEA6x6AlarmEntry 31 }

wtWebioEA6x6AlarmFtpReleaseText OBJECT-TYPE
    SYNTAX OCTET STRING 
    ACCESS read-write
    STATUS mandatory
    DESCRIPTION
        "Message text to store on the FTP server."
    ::= { wtWebioEA6x6AlarmEntry 32 }

-- wtWebioEA6x6Ports Group
----------------------------

-- Input Port Table

wtWebioEA6x6InputPortTable OBJECT-TYPE
    SYNTAX SEQUENCE OF WtWebioEA6x6InputPortEntry
    ACCESS not-accessible
    STATUS mandatory
    DESCRIPTION
        "List of settings depending on the input number."
    ::= { wtWebioEA6x6Ports 1 }

wtWebioEA6x6InputPortEntry OBJECT-TYPE
    SYNTAX WtWebioEA6x6InputPortEntry
    ACCESS not-accessible
    STATUS mandatory
    DESCRIPTION
        "Input parameter for the individual inputs."
    INDEX  { wtWebioEA6x6InputNo }
    ::= { wtWebioEA6x6InputPortTable 1 }

WtWebioEA6x6InputPortEntry ::= SEQUENCE {
    wtWebioEA6x6PortInputName				OCTET STRING,
    wtWebioEA6x6PortInputText				OCTET STRING,
    wtWebioEA6x6PortInputMode				OCTET STRING,
    wtWebioEA6x6PortInputFilter				INTEGER,
    wtWebioEA6x6PortInputBicountPulsePolarity		OCTET STRING,
    wtWebioEA6x6PortInputBicountInactivTimeout		INTEGER
}

wtWebioEA6x6PortInputName OBJECT-TYPE
    SYNTAX OCTET STRING 
    ACCESS read-write
    STATUS mandatory
    DESCRIPTION
        "Name of the input."
    ::= { wtWebioEA6x6InputPortEntry 1 }

wtWebioEA6x6PortInputText OBJECT-TYPE
    SYNTAX OCTET STRING 
    ACCESS read-write
    STATUS mandatory
    DESCRIPTION
        "Description of the input."
    ::= { wtWebioEA6x6InputPortEntry 2 }

wtWebioEA6x6PortInputMode OBJECT-TYPE
    SYNTAX OCTET STRING (SIZE(4))
    ACCESS read-write
    STATUS mandatory
    DESCRIPTION
        "Binary coded modes:
        Selecting short pulse detection enable by setting the corresponding bit to 1 enables 
        interrupt support for counting. Only positive edges are accepted as trigger 
        source. The maximum counting frequenz equals 2000 Hz.
        This mode is available for inputs 0-3 only.
        Selecting counter clear on read by setting the corresponding bit to 1 enables
        the corresponding counter to be cleared automatically every time it is read,
        except HTTP reading with user rights.
        The OCTETS are interpreted bit-by-bit, with each set of octets corresponding to an input. 
        Bit 0 corresponds to the LSB.
        Selection for input 0-3:
        OCTET 1: unused
        OCTET 2: unused
        OCTET 3: unused
        OCTET 4, Bit 3-7: unused
        	 Bit 2  : Counter clear on read
        	 Bit 1  : Change detection enable (default)
        	 Bit 0  : Short Pulse detection enable
        	 
	Selection for inputs 4-5:
	OCTET 1: unused
	OCTET 2: unused
	OCTET 3: unused
	OCTET 4, Bit 2-7: unused
		 Bit 1  : Counter clear on read
		 Bit 0  : Change detection enable (default)"
    ::= { wtWebioEA6x6InputPortEntry 3 }    
    
wtWebioEA6x6PortInputFilter OBJECT-TYPE
    SYNTAX INTEGER 
    ACCESS read-write
    STATUS mandatory
    DESCRIPTION
        "Pulses with a duration shorter than here specified (duration in 1/1000 sec),
	are ignored."
    ::= { wtWebioEA6x6InputPortEntry 4 }
    
wtWebioEA6x6PortInputBicountPulsePolarity OBJECT-TYPE
    SYNTAX OCTET STRING (SIZE (4))
    ACCESS read-write
    STATUS mandatory
    DESCRIPTION
        "This value defines the polarity of the input pulse.
        OCTET 1: unused
        OCTET 2: unused
        OCTET 3: unused
        	OCTET 4: 
        	 Bit 0   : negative polarity
        	 Bit 1   : positive polarity
        	 Bit 2-7 : unused"
    ::= { wtWebioEA6x6InputPortEntry 5 }

wtWebioEA6x6PortInputBicountInactivTimeout OBJECT-TYPE
    SYNTAX INTEGER 
    ACCESS read-write
    STATUS mandatory
    DESCRIPTION
        "Pulse chains with a duration shorter than here specified (in 1/10 sek),
	are ignored."
    ::= { wtWebioEA6x6InputPortEntry 6 }
    
-- Output Port Table

wtWebioEA6x6OutputPortTable OBJECT-TYPE
    SYNTAX SEQUENCE OF WtWebioEA6x6OutputPortEntry
    ACCESS not-accessible
    STATUS mandatory
    DESCRIPTION
        "List of settings depending on the output number."
    ::= { wtWebioEA6x6Ports 2 }

wtWebioEA6x6OutputPortEntry OBJECT-TYPE
    SYNTAX WtWebioEA6x6OutputPortEntry
    ACCESS not-accessible
    STATUS mandatory
    DESCRIPTION
        "Output parameters of the individual outputs."
    INDEX  { wtWebioEA6x6OutputNo }
    ::= { wtWebioEA6x6OutputPortTable 1 }

WtWebioEA6x6OutputPortEntry ::= SEQUENCE {
    wtWebioEA6x6PortOutputName			OCTET STRING,
    wtWebioEA6x6PortOutputText			OCTET STRING,
    wtWebioEA6x6PortOutputGroupMode		OCTET STRING,
    wtWebioEA6x6PortOutputSafetyState		OCTET STRING,
    wtWebioEA6x6PortLogicInputMask		OCTET STRING,
    wtWebioEA6x6PortLogicInputInverter		OCTET STRING,
    wtWebioEA6x6PortLogicFunction		OCTET STRING,
    wtWebioEA6x6PortLogicOutputInverter		OCTET STRING,
    wtWebioEA6x6PortPulseDuration		INTEGER,
    wtWebioEA6x6PortPulsePolarity		OCTET STRING
    
}

wtWebioEA6x6PortOutputName OBJECT-TYPE
    SYNTAX OCTET STRING 
    ACCESS read-write
    STATUS mandatory
    DESCRIPTION
        "Name of the output."
    ::= { wtWebioEA6x6OutputPortEntry 1 }

wtWebioEA6x6PortOutputText OBJECT-TYPE
    SYNTAX OCTET STRING 
    ACCESS read-write
    STATUS mandatory
    DESCRIPTION
        "Description of the output."
    ::= { wtWebioEA6x6OutputPortEntry 2 }

wtWebioEA6x6PortOutputGroupMode OBJECT-TYPE
    SYNTAX OCTET STRING 
    ACCESS read-write
    STATUS mandatory
    DESCRIPTION
        "It is possible to connect outputs together to increase the output current.
        This could be done by connecting 2 or 4 outputs in a group together. All bits
        of such a group has to be set all together in the same way. This variable
        configures this group scheme. If one output bit of a group is set, all other 
        output bits of the same group will be set in the same manner.
        More than one configuration must not be selected.
	Selection for outputs 0-3:
        Octet 1: unused
        Octet 2: unused
        Octet 3: unused
        OCTET 4: Bit 0   : outputs 0,1,2,3 disconnected (default)
        	 Bit 1   : outputs 0+1, 2+3 connected
        	 Bit 2   : outputs 0+1+2+3 connected
        	 Bit 3-7 : unused
	Selection for outputs 4-7:
        Octet 1: unused
        Octet 2: unused
        Octet 3: unused
        OCTET 4: Bit 0   : outputs 4, 5 disconnected (default)
        	 Bit 1   : outputs 4+5 connected
        	 Bit 2-7 : unused        	 
	Selection for outputs 8-11:
        Octet 1: unused
        Octet 2: unused
        Octet 3: unused
        OCTET 4: unused"
    ::= { wtWebioEA6x6OutputPortEntry 3 }

wtWebioEA6x6PortOutputSafetyState OBJECT-TYPE
    SYNTAX OCTET STRING 
    ACCESS read-write
    STATUS mandatory
    DESCRIPTION
        "This variable allows setting of individual digital outputs. The OCTETS are 
        interpreted bit-by-bit, with each bit corresponding to an output. Bit 0 corresponds 
        to the LSB.
        The first four OCTETS contain the mask which determines which of the outputs are to 
        be set (corresponding bit = 1) and which outputs are to remain unchanged 
        (corresponding bit = 0):
        OCTET 1		: unused
        OCTET 2		: unused
        OCTET 3		: unused
        OCTET 4, Bit 1-7: unused
        	 Bit 0	: Mask for digital output
        OCTETS 5-8 contain the level (1=HIGH, 0=LOW) which the outputs to be changed 
        should assume:
        OCTET 5		: unused
        OCTET 6		: unused
        OCTET 7		: unused
        OCTET 8, Bit 1-7: unused
        	 Bit 0  : Level of digital output"
    ::= { wtWebioEA6x6OutputPortEntry 4 }

wtWebioEA6x6PortLogicInputMask OBJECT-TYPE
    SYNTAX OCTET STRING (SIZE (4))
    ACCESS read-write
    STATUS mandatory
    DESCRIPTION
        "Selecting one of these inputs by setting the corresponding bit to 1 
        enables the logic function for the output identified by the index within 
        this table. The calculation take place in 4 steps:
        1. Selecting inputs				(wtWebioEA6x6PortLogicInputMask)
        2. Inverting inputs if necessary	(wtWebioEA6x6PortLogicInputInverter)
        3. Logical combination				(wtWebioEA6x6PortLogicFunction)
        4. Inverting the result if necessary	(wtWebioEA6x6PortLogicOutputInverter)
        OCTET 1: unused
        OCTET 2: unused
        OCTET 3: unused
        OCTET 4: 
        	 Bit 0-5 : inputs 0-5
        	 Bit 6-7 : unused"
    ::= { wtWebioEA6x6OutputPortEntry 5 }

wtWebioEA6x6PortLogicInputInverter OBJECT-TYPE
    SYNTAX OCTET STRING (SIZE (4))
    ACCESS read-write
    STATUS mandatory
    DESCRIPTION
        "Every input bit selected here will be inverted.
        OCTET 1: unused
        OCTET 2: unused
        OCTET 3: unused
        OCTET 4: 
        	 Bit 0-5 : inputs 0-5
        	 Bit 6-7 : unused"
    ::= { wtWebioEA6x6OutputPortEntry 6 }

wtWebioEA6x6PortLogicFunction OBJECT-TYPE
    SYNTAX OCTET STRING (SIZE (4))
    ACCESS read-write
    STATUS mandatory
    DESCRIPTION
        "This determines the logic function. No more than one function
        may be selected.
        OCTET 1: unused
        OCTET 2: unused
        OCTET 3: unused
        OCTET 4: 
        	 Bit 0   : logic function OR (default)
        	 Bit 1   : logic function AND
        	 Bit 2-7 : unused"
    ::= { wtWebioEA6x6OutputPortEntry 7 }

wtWebioEA6x6PortLogicOutputInverter OBJECT-TYPE
    SYNTAX OCTET STRING (SIZE (4))
    ACCESS read-write
    STATUS mandatory
    DESCRIPTION
        "The logical operation result could be inverteted by setting the corresponding
        bit to 1.
        OCTET 1: unused
        OCTET 2: unused
        OCTET 3: unused
        	OCTET 4: 
        	 Bit 0   : Output Inverter enable
        	 Bit 1-7 : unused"
    ::= { wtWebioEA6x6OutputPortEntry 8 }

wtWebioEA6x6PortPulseDuration OBJECT-TYPE
    SYNTAX INTEGER
    ACCESS read-write
    STATUS mandatory
    DESCRIPTION
        "Pulse length in 1/1000 sec. Setting this value to zero, disables the pulse output."
    ::= { wtWebioEA6x6OutputPortEntry 9 }

wtWebioEA6x6PortPulsePolarity OBJECT-TYPE
    SYNTAX OCTET STRING (SIZE (4))
    ACCESS read-write
    STATUS mandatory
    DESCRIPTION
        "This value defines the polarity of the output pulse, if wtWebioEA6x6PortPulseDuration is not set to zero.
        After the pulse is finished, the output switches back to the opposite state.
        OCTET 1: unused
        OCTET 2: unused
        OCTET 3: unused
        	OCTET 4: 
        	 Bit 0   : negative polarity
        	 Bit 1   : positive polarity
        	 Bit 2-7 : unused"
    ::= { wtWebioEA6x6OutputPortEntry 10 }

-- wtWebioEA6x6Manufact Group
----------------------------

wtWebioEA6x6MfName OBJECT-TYPE
    SYNTAX OCTET STRING 
    ACCESS read-write
    STATUS mandatory
    DESCRIPTION
        "Manufacturer company name"
    ::= { wtWebioEA6x6Manufact 1 }

wtWebioEA6x6MfAddr OBJECT-TYPE
    SYNTAX OCTET STRING 
    ACCESS read-write
    STATUS mandatory
    DESCRIPTION
        "Manufacturer address."
    ::= { wtWebioEA6x6Manufact 2 }

wtWebioEA6x6MfHotline OBJECT-TYPE
    SYNTAX OCTET STRING 
    ACCESS read-write
    STATUS mandatory
    DESCRIPTION
        "Manufacturer hotline."
    ::= { wtWebioEA6x6Manufact 3 }

wtWebioEA6x6MfInternet OBJECT-TYPE
    SYNTAX OCTET STRING 
    ACCESS read-write
    STATUS mandatory
    DESCRIPTION
        "Manufacturer Internet address."
    ::= { wtWebioEA6x6Manufact 4 }

wtWebioEA6x6MfDeviceTyp OBJECT-TYPE
    SYNTAX OCTET STRING 
    ACCESS read-write
    STATUS mandatory
    DESCRIPTION
        "Manufacturer device name (model number)."
    ::= { wtWebioEA6x6Manufact 5 }

-- wtWebioEA6x6Diag Group
----------------------------

wtWebioEA6x6DiagErrorCount OBJECT-TYPE
    SYNTAX INTEGER
    ACCESS read-only
    STATUS mandatory
    DESCRIPTION
        "Number of entries in the error memory."
    ::= { wtWebioEA6x6Diag 1 }

wtWebioEA6x6DiagBinaryError OBJECT-TYPE
    SYNTAX OCTET STRING 
    ACCESS read-only
    STATUS mandatory
    DESCRIPTION
        "Error causes coded bit-by-bit."
    ::= { wtWebioEA6x6Diag 2 }

wtWebioEA6x6DiagErrorIndex OBJECT-TYPE
    SYNTAX INTEGER
    ACCESS read-write
    STATUS mandatory
    DESCRIPTION
        "The value of this variable is used as an index to read 
        an error massege from wtWebioEA6x6DiagErrorMessage.
        Errors are numbered from 1 to wtWebioEA6x6DiagErrorCount.
        Writing a valid value into this variable, making the appropriate 
        message readable from wtWebioEA6x6DiagErrorMessage."
    ::= { wtWebioEA6x6Diag 3 }

wtWebioEA6x6DiagErrorMessage OBJECT-TYPE
    SYNTAX OCTET STRING 
    ACCESS read-only
    STATUS mandatory
    DESCRIPTION
        "Using wtWebioEA6x6DiagErrorIndex as an index, the appropriate message is available."
    ::= { wtWebioEA6x6Diag 4 }
    
wtWebioEA6x6DiagErrorClear OBJECT-TYPE
    SYNTAX INTEGER
    ACCESS write-only
    STATUS mandatory
    DESCRIPTION
        "Writing 1 into this variable clears all diagnosis messages."
    ::= { wtWebioEA6x6Diag 5 }


-- TRAP DEFINITIONS

-- Diese SNMP-Traps werden gesendet, wenn die Alarmtriggerbedingungen zutreffen 

wtWebioEA6x6Alert1 TRAP-TYPE
    ENTERPRISE  wtWebioEA6x6
    VARIABLES   { wtWebioEA6x6AlarmSnmpTrapText }
    DESCRIPTION
        "This SNMP trap is generated when Alarm 1 was triggered,
        SNMP trap enable is set and
        SNMP is enabled."
    -- NMS trap annotation
    --#TYPE "Webio Digital Alarm 1"
    --#SUMMARY "Alarm 1: %s"
    --#ARGUMENTS {0}
    --#SEVERITY INFORMATIONAL
    --#TIMEINDEX 99
    --#STATE OPERATIONAL    
    ::= 41

wtWebioEA6x6Alert2 TRAP-TYPE
    ENTERPRISE  wtWebioEA6x6
    VARIABLES   { wtWebioEA6x6AlarmSnmpTrapText }
    DESCRIPTION
        "This SNMP trap is generated when Alarm 2 was triggered,
        SNMP trap enable is set and
        SNMP is enabled."
    -- NMS trap annotation
    --#TYPE "Webio Digital Alarm 2"
    --#SUMMARY "Alarm 2: %s"
    --#ARGUMENTS {0}
    --#SEVERITY INFORMATIONAL
    --#TIMEINDEX 99
    --#STATE OPERATIONAL    
    ::= 42

wtWebioEA6x6Alert3 TRAP-TYPE
    ENTERPRISE  wtWebioEA6x6
    VARIABLES   { wtWebioEA6x6AlarmSnmpTrapText }
    DESCRIPTION
        "This SNMP trap is generated when Alarm 3 was triggered,
        SNMP trap enable is set and
        SNMP is enabled."
    -- NMS trap annotation
    --#TYPE "Webio Digital Alarm 3"
    --#SUMMARY "Alarm 3: %s"
    --#ARGUMENTS {0}
    --#SEVERITY INFORMATIONAL
    --#TIMEINDEX 99
    --#STATE OPERATIONAL    
    ::= 43

wtWebioEA6x6Alert4 TRAP-TYPE
    ENTERPRISE  wtWebioEA6x6
    VARIABLES   { wtWebioEA6x6AlarmSnmpTrapText }
    DESCRIPTION
        "This SNMP trap is generated when Alarm 4 was triggered,
        SNMP trap enable is set and
        SNMP is enabled."
    -- NMS trap annotation
    --#TYPE "Webio Digital Alarm 4"
    --#SUMMARY "Alarm 4: %s"
    --#ARGUMENTS {0}
    --#SEVERITY INFORMATIONAL
    --#TIMEINDEX 99
    --#STATE OPERATIONAL    
    ::= 44

wtWebioEA6x6Alert5 TRAP-TYPE
    ENTERPRISE  wtWebioEA6x6
    VARIABLES   { wtWebioEA6x6AlarmSnmpTrapText }
    DESCRIPTION
        "This SNMP trap is generated when Alarm 5 was triggered,
        SNMP trap enable is set and
        SNMP is enabled."
    -- NMS trap annotation
    --#TYPE "Webio Digital Alarm 5"
    --#SUMMARY "Alarm 5: %s"
    --#ARGUMENTS {0}
    --#SEVERITY INFORMATIONAL
    --#TIMEINDEX 99
    --#STATE OPERATIONAL    
    ::= 45

wtWebioEA6x6Alert6 TRAP-TYPE
    ENTERPRISE  wtWebioEA6x6
    VARIABLES   { wtWebioEA6x6AlarmSnmpTrapText }
    DESCRIPTION
        "This SNMP trap is generated when Alarm 6 was triggered,
        SNMP trap enable is set and
        SNMP is enabled."
    -- NMS trap annotation
    --#TYPE "Webio Digital Alarm 6"
    --#SUMMARY "Alarm 6: %s"
    --#ARGUMENTS {0}
    --#SEVERITY INFORMATIONAL
    --#TIMEINDEX 99
    --#STATE OPERATIONAL    
    ::= 46

wtWebioEA6x6Alert7 TRAP-TYPE
    ENTERPRISE  wtWebioEA6x6
    VARIABLES   { wtWebioEA6x6AlarmSnmpTrapText }
    DESCRIPTION
        "This SNMP trap is generated when Alarm 7 was triggered,
        SNMP trap enable is set and
        SNMP is enabled."
    -- NMS trap annotation
    --#TYPE "Webio Digital Alarm 7"
    --#SUMMARY "Alarm 7: %s"
    --#ARGUMENTS {0}
    --#SEVERITY INFORMATIONAL
    --#TIMEINDEX 99
    --#STATE OPERATIONAL    
    ::= 47

wtWebioEA6x6Alert8 TRAP-TYPE
    ENTERPRISE  wtWebioEA6x6
    VARIABLES   { wtWebioEA6x6AlarmSnmpTrapText }
    DESCRIPTION
        "This SNMP trap is generated when Alarm 8 was triggered,
        SNMP trap enable is set and
        SNMP is enabled."
    -- NMS trap annotation
    --#TYPE "Webio Digital Alarm 8"
    --#SUMMARY "Alarm 8: %s"
    --#ARGUMENTS {0}
    --#SEVERITY INFORMATIONAL
    --#TIMEINDEX 99
    --#STATE OPERATIONAL    
    ::= 48

wtWebioEA6x6Alert9 TRAP-TYPE
    ENTERPRISE  wtWebioEA6x6
    VARIABLES   { wtWebioEA6x6AlarmSnmpTrapText }
    DESCRIPTION
        "This SNMP trap is generated when Alarm 9 was triggered,
        SNMP trap enable is set and
        SNMP is enabled."
    -- NMS trap annotation
    --#TYPE "Webio Digital Alarm 9"
    --#SUMMARY "Alarm 9: %s"
    --#ARGUMENTS {0}
    --#SEVERITY INFORMATIONAL
    --#TIMEINDEX 99
    --#STATE OPERATIONAL    
    ::= 49

wtWebioEA6x6Alert10 TRAP-TYPE
    ENTERPRISE  wtWebioEA6x6
    VARIABLES   { wtWebioEA6x6AlarmSnmpTrapText }
    DESCRIPTION
        "This SNMP trap is generated when Alarm 10 was triggered,
        SNMP trap enable is set and
        SNMP is enabled."
    -- NMS trap annotation
    --#TYPE "Webio Digital Alarm 10"
    --#SUMMARY "Alarm 10: %s"
    --#ARGUMENTS {0}
    --#SEVERITY INFORMATIONAL
    --#TIMEINDEX 99
    --#STATE OPERATIONAL    
    ::= 50

wtWebioEA6x6Alert11 TRAP-TYPE
    ENTERPRISE  wtWebioEA6x6
    VARIABLES   { wtWebioEA6x6AlarmSnmpTrapText }
    DESCRIPTION
        "This SNMP trap is generated when Alarm 11 was triggered,
        SNMP trap enable is set and
        SNMP is enabled."
    -- NMS trap annotation
    --#TYPE "Webio Digital Alarm 11"
    --#SUMMARY "Alarm 11: %s"
    --#ARGUMENTS {0}
    --#SEVERITY INFORMATIONAL
    --#TIMEINDEX 99
    --#STATE OPERATIONAL    
    ::= 51

wtWebioEA6x6Alert12 TRAP-TYPE
    ENTERPRISE  wtWebioEA6x6
    VARIABLES   { wtWebioEA6x6AlarmSnmpTrapText }
    DESCRIPTION
        "This SNMP trap is generated when Alarm 12 was triggered,
        SNMP trap enable is set and
        SNMP is enabled."
    -- NMS trap annotation
    --#TYPE "Webio Digital Alarm 12"
    --#SUMMARY "Alarm 12: %s"
    --#ARGUMENTS {0}
    --#SEVERITY INFORMATIONAL
    --#TIMEINDEX 99
    --#STATE OPERATIONAL    
    ::= 52

wtWebioEA6x6Alert13 TRAP-TYPE
    ENTERPRISE  wtWebioEA6x6
    VARIABLES   { wtWebioEA6x6AlarmSnmpTrapReleaseText }
    DESCRIPTION
        "This SNMP trap is generated when Alarm 1 was released,
        SNMP trap enable is set and
        SNMP is enabled."
    -- NMS trap annotation
    --#TYPE "Webio Digital Release Alarm 1"
    --#SUMMARY "Release Alarm 1: %s"
    --#ARGUMENTS {0}
    --#SEVERITY INFORMATIONAL
    --#TIMEINDEX 99
    --#STATE OPERATIONAL    
    ::= 71

wtWebioEA6x6Alert14 TRAP-TYPE
    ENTERPRISE  wtWebioEA6x6
    VARIABLES   { wtWebioEA6x6AlarmSnmpTrapReleaseText }
    DESCRIPTION
        "This SNMP trap is generated when Alarm 2 was released,
        SNMP trap enable is set and
        SNMP is enabled."
    -- NMS trap annotation
    --#TYPE "Webio Digital Release Alarm 2"
    --#SUMMARY "Release Alarm 2: %s"
    --#ARGUMENTS {0}
    --#SEVERITY INFORMATIONAL
    --#TIMEINDEX 99
    --#STATE OPERATIONAL    
    ::= 72

wtWebioEA6x6Alert15 TRAP-TYPE
    ENTERPRISE  wtWebioEA6x6
    VARIABLES   { wtWebioEA6x6AlarmSnmpTrapReleaseText }
    DESCRIPTION
        "This SNMP trap is generated when Alarm 3 was released,
        SNMP trap enable is set and
        SNMP is enabled."
    -- NMS trap annotation
    --#TYPE "Webio Digital Release Alarm 3"
    --#SUMMARY "Release Alarm 3: %s"
    --#ARGUMENTS {0}
    --#SEVERITY INFORMATIONAL
    --#TIMEINDEX 99
    --#STATE OPERATIONAL    
    ::= 73

wtWebioEA6x6Alert16 TRAP-TYPE
    ENTERPRISE  wtWebioEA6x6
    VARIABLES   { wtWebioEA6x6AlarmSnmpTrapReleaseText }
    DESCRIPTION
        "This SNMP trap is generated when Alarm 4 was released,
        SNMP trap enable is set and
        SNMP is enabled."
    -- NMS trap annotation
    --#TYPE "Webio Digital Release Alarm 4"
    --#SUMMARY "Release Alarm 4: %s"
    --#ARGUMENTS {0}
    --#SEVERITY INFORMATIONAL
    --#TIMEINDEX 99
    --#STATE OPERATIONAL    
    ::= 74

wtWebioEA6x6Alert17 TRAP-TYPE
    ENTERPRISE  wtWebioEA6x6
    VARIABLES   { wtWebioEA6x6AlarmSnmpTrapReleaseText }
    DESCRIPTION
        "This SNMP trap is generated when Alarm 5 was released,
        SNMP trap enable is set and
        SNMP is enabled."
    -- NMS trap annotation
    --#TYPE "Webio Digital Release Alarm 5"
    --#SUMMARY "Release Alarm 5: %s"
    --#ARGUMENTS {0}
    --#SEVERITY INFORMATIONAL
    --#TIMEINDEX 99
    --#STATE OPERATIONAL    
    ::= 75

wtWebioEA6x6Alert18 TRAP-TYPE
    ENTERPRISE  wtWebioEA6x6
    VARIABLES   { wtWebioEA6x6AlarmSnmpTrapReleaseText }
    DESCRIPTION
        "This SNMP trap is generated when Alarm 6 was released,
        SNMP trap enable is set and
        SNMP is enabled."
    -- NMS trap annotation
    --#TYPE "Webio Digital Release Alarm 6"
    --#SUMMARY "Release Alarm 6: %s"
    --#ARGUMENTS {0}
    --#SEVERITY INFORMATIONAL
    --#TIMEINDEX 99
    --#STATE OPERATIONAL    
    ::= 76

wtWebioEA6x6Alert19 TRAP-TYPE
    ENTERPRISE  wtWebioEA6x6
    VARIABLES   { wtWebioEA6x6AlarmSnmpTrapReleaseText }
    DESCRIPTION
        "This SNMP trap is generated when Alarm 7 was released,
        SNMP trap enable is set and
        SNMP is enabled."
    -- NMS trap annotation
    --#TYPE "Webio Digital Release Alarm 7"
    --#SUMMARY "Release Alarm 7: %s"
    --#ARGUMENTS {0}
    --#SEVERITY INFORMATIONAL
    --#TIMEINDEX 99
    --#STATE OPERATIONAL    
    ::= 77

wtWebioEA6x6Alert20 TRAP-TYPE
    ENTERPRISE  wtWebioEA6x6
    VARIABLES   { wtWebioEA6x6AlarmSnmpTrapReleaseText }
    DESCRIPTION
        "This SNMP trap is generated when Alarm 8 was released,
        SNMP trap enable is set and
        SNMP is enabled."
    -- NMS trap annotation
    --#TYPE "Webio Digital Release Alarm 8"
    --#SUMMARY "Release Alarm 8: %s"
    --#ARGUMENTS {0}
    --#SEVERITY INFORMATIONAL
    --#TIMEINDEX 99
    --#STATE OPERATIONAL    
    ::= 78

wtWebioEA6x6Alert21 TRAP-TYPE
    ENTERPRISE  wtWebioEA6x6
    VARIABLES   { wtWebioEA6x6AlarmSnmpTrapReleaseText }
    DESCRIPTION
        "This SNMP trap is generated when Alarm 9 was released,
        SNMP trap enable is set and
        SNMP is enabled."
    -- NMS trap annotation
    --#TYPE "Webio Digital Release Alarm 9"
    --#SUMMARY "Release Alarm 9: %s"
    --#ARGUMENTS {0}
    --#SEVERITY INFORMATIONAL
    --#TIMEINDEX 99
    --#STATE OPERATIONAL    
    ::= 79

wtWebioEA6x6Alert22 TRAP-TYPE
    ENTERPRISE  wtWebioEA6x6
    VARIABLES   { wtWebioEA6x6AlarmSnmpTrapReleaseText }
    DESCRIPTION
        "This SNMP trap is generated when Alarm 10 was released,
        SNMP trap enable is set and
        SNMP is enabled."
    -- NMS trap annotation
    --#TYPE "Webio Digital Release Alarm 10"
    --#SUMMARY "Release Alarm 10: %s"
    --#ARGUMENTS {0}
    --#SEVERITY INFORMATIONAL
    --#TIMEINDEX 99
    --#STATE OPERATIONAL    
    ::= 80

wtWebioEA6x6Alert23 TRAP-TYPE
    ENTERPRISE  wtWebioEA6x6
    VARIABLES   { wtWebioEA6x6AlarmSnmpTrapReleaseText }
    DESCRIPTION
        "This SNMP trap is generated when Alarm 11 was released,
        SNMP trap enable is set and
        SNMP is enabled."
    -- NMS trap annotation
    --#TYPE "Webio Digital Release Alarm 11"
    --#SUMMARY "Release Alarm 11: %s"
    --#ARGUMENTS {0}
    --#SEVERITY INFORMATIONAL
    --#TIMEINDEX 99
    --#STATE OPERATIONAL    
    ::= 81

wtWebioEA6x6Alert24 TRAP-TYPE
    ENTERPRISE  wtWebioEA6x6
    VARIABLES   { wtWebioEA6x6AlarmSnmpTrapReleaseText }
    DESCRIPTION
        "This SNMP trap is generated when Alarm 12 was released,
        SNMP trap enable is set and
        SNMP is enabled."
    -- NMS trap annotation
    --#TYPE "Webio Digital Release Alarm 12"
    --#SUMMARY "Release Alarm 12: %s"
    --#ARGUMENTS {0}
    --#SEVERITY INFORMATIONAL
    --#TIMEINDEX 99
    --#STATE OPERATIONAL    
    ::= 82

wtWebioEA6x6AlertDiag TRAP-TYPE
    ENTERPRISE  wtWebioEA6x6
    VARIABLES   { 	
    		wtWebioEA6x6DiagErrorIndex,
    	  	wtWebioEA6x6DiagErrorMessage
    		}
    DESCRIPTION
        "This SNMP trap is generated when a diagnosis/error message was triggered,
        SNMP trap enable is set and
        SNMP is enabled."
    -- NMS trap annotation
    --#TYPE "Webio Digital Diagnose Error"
    --#SUMMARY "Diagnose error index: %d, Message: %s."
    --#ARGUMENTS {0,1}
    --#SEVERITY MAJOR
    --#TIMEINDEX 99
    --#STATE DEGRADED    
    ::= 110

--------------------------------------------------------------------------------
--------------------------------------------------------------------------------
--------------------------------------------------------------------------------

-- wtWebioEA2x2ERPInOut Group
------------------------

wtWebioEA2x2ERPInputs OBJECT-TYPE
    SYNTAX INTEGER (1..2)
    ACCESS read-only
    STATUS mandatory
    DESCRIPTION
        "Number of idependent inputs."
    ::= { wtWebioEA2x2ERPInOut 1 }

wtWebioEA2x2ERPOutputs OBJECT-TYPE
    SYNTAX INTEGER (1..2)
    ACCESS read-only
    STATUS mandatory
    DESCRIPTION
        "Number of idependent outputs."
    ::= { wtWebioEA2x2ERPInOut 2 }

-- Input Interface Table

wtWebioEA2x2ERPInputTable OBJECT-TYPE
    SYNTAX SEQUENCE OF WtWebioEA2x2ERPInputEntry
    ACCESS not-accessible
    STATUS mandatory
    DESCRIPTION
        "List of input indices."
    ::= { wtWebioEA2x2ERPInOut 3 }

wtWebioEA2x2ERPInputEntry OBJECT-TYPE
    SYNTAX WtWebioEA2x2ERPInputEntry
    ACCESS not-accessible
    STATUS mandatory
    DESCRIPTION
        "Number of the inputs."
    INDEX  { wtWebioEA2x2ERPInputNo }
    ::= { wtWebioEA2x2ERPInputTable 1 }

WtWebioEA2x2ERPInputEntry ::= SEQUENCE {
    wtWebioEA2x2ERPInputNo INTEGER,
    wtWebioEA2x2ERPInputCounter INTEGER,
    wtWebioEA2x2ERPInputCounterClear INTEGER,
    wtWebioEA2x2ERPInputState INTEGER
    
}

wtWebioEA2x2ERPInputNo OBJECT-TYPE
    SYNTAX INTEGER (1)
    ACCESS read-only
    STATUS mandatory
    DESCRIPTION
        "Index numbers of the inputs."
    ::= { wtWebioEA2x2ERPInputEntry 1 }

wtWebioEA2x2ERPInputCounter OBJECT-TYPE
    SYNTAX INTEGER (1)
    ACCESS read-only
    STATUS mandatory
    DESCRIPTION
        "Value of the input counter."
    ::= { wtWebioEA2x2ERPInputEntry 2 }
    
wtWebioEA2x2ERPInputCounterClear OBJECT-TYPE
    SYNTAX INTEGER
    ACCESS read-only
    STATUS mandatory
    DESCRIPTION
        "Clears the input counter after returning its value."
    ::= { wtWebioEA2x2ERPInputEntry 3 }
    
wtWebioEA2x2ERPInputState OBJECT-TYPE
    SYNTAX INTEGER{
    wtWebioEA2x2ERPInputState-OFF(0),
    wtWebioEA2x2ERPInputState-ON(1)
    }
    ACCESS read-only
    STATUS mandatory
    DESCRIPTION
        "Value of a single input bit."
    ::= { wtWebioEA2x2ERPInputEntry 4 }    
    
wtWebioEA2x2ERPInputValue OBJECT-TYPE
    SYNTAX INTEGER 
    ACCESS read-only
    STATUS mandatory
    DESCRIPTION
        "This variable is used to read the inputs of the digital I/O port.
        The OCTETS are interpreted bit-by-bit, with each bit corresponding to an output.
        Bit 0 corresponds to the LSB.
        OCTET 1: unused
        OCTET 2: unused
        OCTET 3: unused
        OCTET 4, Bit 0-1: Digital outputs 0-1"
    ::= { wtWebioEA2x2ERPInOut 4 }
    

-- Output Interface Table

wtWebioEA2x2ERPOutputTable OBJECT-TYPE
    SYNTAX SEQUENCE OF WtWebioEA2x2ERPOutputEntry
    ACCESS not-accessible
    STATUS mandatory
    DESCRIPTION
        "List of output indices."
    ::= { wtWebioEA2x2ERPInOut 5 }

wtWebioEA2x2ERPOutputEntry OBJECT-TYPE
    SYNTAX WtWebioEA2x2ERPOutputEntry
    ACCESS not-accessible
    STATUS mandatory
    DESCRIPTION
        "Number of the outputs."
    INDEX  { wtWebioEA2x2ERPOutputNo }
    ::= { wtWebioEA2x2ERPOutputTable 1 }

WtWebioEA2x2ERPOutputEntry ::= SEQUENCE {
    wtWebioEA2x2ERPOutputNo 	INTEGER,
    wtWebioEA2x2ERPOutputState 	INTEGER    
}

wtWebioEA2x2ERPOutputNo OBJECT-TYPE
    SYNTAX INTEGER (1)
    ACCESS read-only
    STATUS mandatory
    DESCRIPTION
        "Output number."
    ::= { wtWebioEA2x2ERPOutputEntry 1 }

wtWebioEA2x2ERPOutputState OBJECT-TYPE
    SYNTAX INTEGER{
    wtWebioEA2x2ERPOutputState-OFF(0),
    wtWebioEA2x2ERPOutputState-ON(1)
    }
    ACCESS read-write
    STATUS mandatory
    DESCRIPTION
        "Value of a single output bit."
    ::= { wtWebioEA2x2ERPOutputEntry 2 }
    

wtWebioEA2x2ERPOutputValue OBJECT-TYPE
    SYNTAX INTEGER
    ACCESS read-write
    STATUS mandatory
    DESCRIPTION
        "This variable is used to read and write the outputs of the digital I/O port. 
        The OCTETS are interpreted bit-by-bit, with each bit corresponding to an output. 
        Bit 0 corresponds to the LSB.
        OCTET 1: unused
        OCTET 2: unused
        OCTET 3: unused
        OCTET 4, Bit 0-1: Digital outputs 0-1
        	 Bit 2-7: ungenutzt"
    ::= { wtWebioEA2x2ERPInOut 6 }
    
wtWebioEA2x2ERPSetOutput OBJECT-TYPE
    SYNTAX OCTET STRING (SIZE (8))
    ACCESS read-write			-- write-only
    STATUS mandatory
    DESCRIPTION
        "This variable allows setting of individual digital outputs. The OCTETS are 
        interpreted bit-by-bit, with each bit corresponding to an output. Bit 0 corresponds 
        to the LSB.
        The first two OCTETS contain the mask which determines which of the outputs are to 
        be set (corresponding bit = 1) and which outputs are to remain unchanged 
        (corresponding bit = 0):
	OCTET 1 : unused
	OCTET 2 : unused
	OCTET 3 : unused
	OCTET 4, Bit 0-1: Mask for digital outputs 0-1
	
	OCTETS 5-8 contain the level (1=HIGH, 0=LOW) which the outputs 
	should assume:
	OCTET 5 : unused
	OCTET 6 : unused
	OCTET 7 : unused
        OCTET 8, Bit 0-1: Level of digital outputs 0-1"
    ::= { wtWebioEA2x2ERPInOut 7 }
    
-- wtWebioEA2x2ERPSessCntrl Group
--------------------------------

wtWebioEA2x2ERPSessCntrlPassword OBJECT-TYPE
    SYNTAX OCTET STRING 
    ACCESS read-write
    STATUS mandatory
    DESCRIPTION
        "Entering this password opens a session which is ended by writing a 1 to 
        wtWebioEA2x2ERPSessCntrlLogout. When read this variable provides a string of
        length zero."
    ::= { wtWebioEA2x2ERPSessCntrl 1 }

wtWebioEA2x2ERPSessCntrlConfigMode OBJECT-TYPE
    SYNTAX INTEGER {
    wtWebioEA2x2ERPSessCntrl-NoSession(0),
    wtWebioEA2x2ERPSessCntrl-Session(1)
    }
    ACCESS read-only
    STATUS mandatory
    DESCRIPTION
        "When the device is in SNMP configuration mode, the value 1 is
        returned, otherwise 0. If the read value is 0 even though the password
        was written, the device is already in config mode and the variables
        can only be read."
    ::= { wtWebioEA2x2ERPSessCntrl 2 }

wtWebioEA2x2ERPSessCntrlLogout OBJECT-TYPE
    SYNTAX INTEGER 
    ACCESS read-write
    STATUS mandatory
    DESCRIPTION
        "If the device is in configuration mode and the session was opened by
        this SNMP Manager, writing a 1 to this variable will end the session 
        and all parameters are stored.
        Writing a 2 discards all entries again. When read this variable
        provides the value 0."
    ::= { wtWebioEA2x2ERPSessCntrl 3 }

wtWebioEA2x2ERPSessCntrlAdminPassword OBJECT-TYPE
    SYNTAX OCTET STRING 
    ACCESS read-write
    STATUS mandatory
    DESCRIPTION
        "This password protects access to the variables with administrator rights.
        It can only be changed by the administrator. If no password was assigned,
        the valid password is public."
    ::= { wtWebioEA2x2ERPSessCntrl 4 }

wtWebioEA2x2ERPSessCntrlConfigPassword OBJECT-TYPE
    SYNTAX OCTET STRING 
    ACCESS read-write
    STATUS mandatory
    DESCRIPTION
        "This password protects access to the variables with configurator rights. It can
        be changed by the administrator and by the configurator. If no password was assigned, 
        the valid password is public. When read this variable provides a null-pointer."
    ::= { wtWebioEA2x2ERPSessCntrl 5 }
    
-- wtWebioEA2x2ERPText Group
------------------------

wtWebioEA2x2ERPDeviceName OBJECT-TYPE
    SYNTAX OCTET STRING 
    ACCESS read-write
    STATUS mandatory
    DESCRIPTION
        "Name of the Webio, which is user definable."
    ::= { wtWebioEA2x2ERPText 1 }

wtWebioEA2x2ERPDeviceText OBJECT-TYPE
    SYNTAX OCTET STRING 
    ACCESS read-write
    STATUS mandatory
    DESCRIPTION
        "Description of the Webio, which is user definable."
    ::= { wtWebioEA2x2ERPText 2 }
    
wtWebioEA2x2ERPDeviceLocation OBJECT-TYPE
    SYNTAX OCTET STRING 
    ACCESS read-write
    STATUS mandatory
    DESCRIPTION
        "Description of the location of the Webio, which is user definable."
    ::= { wtWebioEA2x2ERPText 3 }

wtWebioEA2x2ERPDeviceContact OBJECT-TYPE
    SYNTAX OCTET STRING 
    ACCESS read-write
    STATUS mandatory
    DESCRIPTION
        "Contact address of the system operator of the Webio, which is user definable."
    ::= { wtWebioEA2x2ERPText 4 }    

-- wtWebioEA2x2ERPTimeZone Group
----------------------------

wtWebioEA2x2ERPTzOffsetHrs OBJECT-TYPE
    SYNTAX INTEGER 
    ACCESS read-write
    STATUS mandatory
    DESCRIPTION
        "Offset hours for the time zone (winter time) with respect to UTC."
    ::= { wtWebioEA2x2ERPTimeZone 1 }

wtWebioEA2x2ERPTzOffsetMin OBJECT-TYPE
    SYNTAX INTEGER 
    ACCESS read-write
    STATUS mandatory
    DESCRIPTION
        "Offset minutes for the time zone (winter time) with respect to UTC."
    ::= { wtWebioEA2x2ERPTimeZone 2 }

wtWebioEA2x2ERPTzEnable OBJECT-TYPE
    SYNTAX OCTET STRING (SIZE(4))
    ACCESS read-write
    STATUS mandatory
    DESCRIPTION
        "Binary coded conditions:
        Octet 1: unused
        Octet 2: unused
        Octet 3: unused
        Octet 4:
        	Bit 1-7: unused
	        Bit 0  : Apply Timezone"
    ::= { wtWebioEA2x2ERPTimeZone 3 }

wtWebioEA2x2ERPStTzOffsetHrs OBJECT-TYPE
    SYNTAX INTEGER 
    ACCESS read-write
    STATUS mandatory
    DESCRIPTION
        "Offset hours of the time zone (summer time) with respect to UTC."
    ::= { wtWebioEA2x2ERPTimeZone 4 }

wtWebioEA2x2ERPStTzOffsetMin OBJECT-TYPE
    SYNTAX INTEGER 
    ACCESS read-write
    STATUS mandatory
    DESCRIPTION
        "Offset minutes of the time zone (summer time) with respect to UTC."
    ::= { wtWebioEA2x2ERPTimeZone 5 }

wtWebioEA2x2ERPStTzEnable OBJECT-TYPE
    SYNTAX OCTET STRING (SIZE(4))
    ACCESS read-write
    STATUS mandatory
    DESCRIPTION
        "Binary coded conditions:
        Octet 1: unused
        Octet 2: unused
        Octet 3: unused
        Octet 4:
        	Bit 1-7: unused
	        Bit 0  : Apply Summertime"
    ::= { wtWebioEA2x2ERPTimeZone 6 }

wtWebioEA2x2ERPStTzStartMonth OBJECT-TYPE
    SYNTAX INTEGER {
    	wtWebioEA2x2ERPStartMonth-January(1),
    	wtWebioEA2x2ERPStartMonth-February(2),
    	wtWebioEA2x2ERPStartMonth-March(3),
    	wtWebioEA2x2ERPStartMonth-April(4),
    	wtWebioEA2x2ERPStartMonth-May(5),
    	wtWebioEA2x2ERPStartMonth-June(6),
    	wtWebioEA2x2ERPStartMonth-July(7),
    	wtWebioEA2x2ERPStartMonth-August(8),
    	wtWebioEA2x2ERPStartMonth-September(9),
    	wtWebioEA2x2ERPStartMonth-October(10),
    	wtWebioEA2x2ERPStartMonth-November(11),
    	wtWebioEA2x2ERPStartMonth-December(12)
    	}
    	
    ACCESS read-write
    STATUS mandatory
    DESCRIPTION
        "Month in which the change is made from winter time to summer time."
    ::= { wtWebioEA2x2ERPTimeZone 7 }

wtWebioEA2x2ERPStTzStartMode OBJECT-TYPE
    SYNTAX INTEGER {
    	wtWebioEA2x2ERPStartMode-first(1),
    	wtWebioEA2x2ERPStartMode-second(2),
    	wtWebioEA2x2ERPStartMode-third(3),
    	wtWebioEA2x2ERPStartMode-fourth(4),
    	wtWebioEA2x2ERPStartMode-last(5)
    	}
    	
    ACCESS read-write
    STATUS mandatory
    DESCRIPTION
        "Mode of the day of the week for which the change is made from winter time to summer time."
    ::= { wtWebioEA2x2ERPTimeZone 8 }

wtWebioEA2x2ERPStTzStartWday OBJECT-TYPE
    SYNTAX INTEGER {
    	wtWebioEA2x2ERPStartWday-Sunday(1),
    	wtWebioEA2x2ERPStartWday-Monday(2),
    	wtWebioEA2x2ERPStartWday-Tuesday(3),
    	wtWebioEA2x2ERPStartWday-Thursday(4),
    	wtWebioEA2x2ERPStartWday-Wednesday(5),
    	wtWebioEA2x2ERPStartWday-Friday(6),
    	wtWebioEA2x2ERPStartWday-Saturday(7)
    	}
    	
    ACCESS read-write
    STATUS mandatory
    DESCRIPTION
        "Day of the week on which the change is made from winter time to summer time"
    ::= { wtWebioEA2x2ERPTimeZone 9 }
    
wtWebioEA2x2ERPStTzStartHrs OBJECT-TYPE
    SYNTAX INTEGER 
    ACCESS read-write
    STATUS mandatory
    DESCRIPTION
        "Hour in which the time zone is changed from winter to summer time with
        respect to UTC."
    ::= { wtWebioEA2x2ERPTimeZone 10 }

wtWebioEA2x2ERPStTzStartMin OBJECT-TYPE
    SYNTAX INTEGER 
    ACCESS read-write
    STATUS mandatory
    DESCRIPTION
        "Minute in which the time zone is changed from winter to summer time with
        respect to UTC."
    ::= { wtWebioEA2x2ERPTimeZone 11 }
 
wtWebioEA2x2ERPStTzStopMonth OBJECT-TYPE
    SYNTAX INTEGER {
    	wtWebioEA2x2ERPStopMonth-January(1),
    	wtWebioEA2x2ERPStopMonth-February(2),
    	wtWebioEA2x2ERPStopMonth-March(3),
    	wtWebioEA2x2ERPStopMonth-April(4),
    	wtWebioEA2x2ERPStopMonth-May(5),
    	wtWebioEA2x2ERPStopMonth-June(6),
    	wtWebioEA2x2ERPStopMonth-July(7),
    	wtWebioEA2x2ERPStopMonth-August(8),
    	wtWebioEA2x2ERPStopMonth-September(9),
    	wtWebioEA2x2ERPStopMonth-October(10),
    	wtWebioEA2x2ERPStopMonth-November(11),
    	wtWebioEA2x2ERPStopMonth-December(12)
    	}
    ACCESS read-write
    STATUS mandatory
    DESCRIPTION
        "Month in which the change is made from summer time to winter time."
   ::= { wtWebioEA2x2ERPTimeZone 12 }

wtWebioEA2x2ERPStTzStopMode OBJECT-TYPE
    SYNTAX INTEGER {
    	wtWebioEA2x2ERPStopMode-first(1),
    	wtWebioEA2x2ERPStopMode-second(2),
    	wtWebioEA2x2ERPStopMode-third(3),
    	wtWebioEA2x2ERPStopMode-fourth(4),
    	wtWebioEA2x2ERPStopMode-last(5)
    	}
    ACCESS read-write
    STATUS mandatory
    DESCRIPTION
        "Mode of the week day on which the change is made from summer time to winter time."
    ::= { wtWebioEA2x2ERPTimeZone 13 }

wtWebioEA2x2ERPStTzStopWday OBJECT-TYPE
    SYNTAX INTEGER {
    	wtWebioEA2x2ERPStopWday-Sunday(1),
    	wtWebioEA2x2ERPStopWday-Monday(2),
    	wtWebioEA2x2ERPStopWday-Tuesday(3),
    	wtWebioEA2x2ERPStopWday-Thursday(4),
    	wtWebioEA2x2ERPStopWday-Wednesday(5),
    	wtWebioEA2x2ERPStopWday-Friday(6),
    	wtWebioEA2x2ERPStopWday-Saturday(7)
    	}
    ACCESS read-write
    STATUS mandatory
    DESCRIPTION
        "Day of the week on which the change is made from summer time to winter time."
    ::= { wtWebioEA2x2ERPTimeZone 14 }
    
wtWebioEA2x2ERPStTzStopHrs OBJECT-TYPE
    SYNTAX INTEGER 
    ACCESS read-write
    STATUS mandatory
    DESCRIPTION
        "Hour at which the time zone is changed from summer to winter time with
        respect to UTC."
    ::= { wtWebioEA2x2ERPTimeZone 15 }

wtWebioEA2x2ERPStTzStopMin OBJECT-TYPE
    SYNTAX INTEGER 
    ACCESS read-write
    STATUS mandatory
    DESCRIPTION
        "Minute at which the time zone is changed from summer to winter time with
        respect to UTC."
    ::= { wtWebioEA2x2ERPTimeZone 16 }

-- wtWebioEA2x2ERPTimeServer Group
----------------------------

wtWebioEA2x2ERPTimeServer1 OBJECT-TYPE
    SYNTAX OCTET STRING 
    ACCESS read-write
    STATUS mandatory
    DESCRIPTION
        "IP address or name of the 1st time server in ASCII"
    ::= { wtWebioEA2x2ERPTimeServer 1 }

wtWebioEA2x2ERPTimeServer2 OBJECT-TYPE
    SYNTAX OCTET STRING 
    ACCESS read-write
    STATUS mandatory
    DESCRIPTION
        "IP address or name of the 2nd time server in ASCII"
    ::= { wtWebioEA2x2ERPTimeServer 2 }

wtWebioEA2x2ERPTsEnable OBJECT-TYPE
    SYNTAX OCTET STRING (SIZE(4))
    ACCESS read-write
    STATUS mandatory
    DESCRIPTION
        "Binary coded conditions:
        Octet 1: unused
        Octet 2: unused
        Octet 3: unused
        Octet 4:
        	Bit 1-7: unused
	        Bit 0  : Apply Time Server"
    ::= { wtWebioEA2x2ERPTimeServer 3 }

wtWebioEA2x2ERPTsSyncTime OBJECT-TYPE
    SYNTAX INTEGER 
    ACCESS read-write
    STATUS mandatory
    DESCRIPTION
        "Daily synchronisation time with the time server (hour: 0-23)."
    ::= { wtWebioEA2x2ERPTimeServer 4 }
      
    
-- wtWebioEA2x2ERPDeviceClock Group
----------------------------

wtWebioEA2x2ERPClockHrs OBJECT-TYPE
    SYNTAX INTEGER (0..23)
    ACCESS read-write
    STATUS mandatory
    DESCRIPTION
        "Clock hours taking into account the time zone settings."
    ::= { wtWebioEA2x2ERPDeviceClock 1 }

wtWebioEA2x2ERPClockMin OBJECT-TYPE
    SYNTAX INTEGER (0..59)
    ACCESS read-write
    STATUS mandatory
    DESCRIPTION
        "Clock minutes taking into account the time zone settings."
    ::= { wtWebioEA2x2ERPDeviceClock 2 }

wtWebioEA2x2ERPClockDay OBJECT-TYPE
    SYNTAX INTEGER (1..31)
    ACCESS read-write
    STATUS mandatory
    DESCRIPTION
        "Date: Day of the month, taking into account the time zone settings."
    ::= { wtWebioEA2x2ERPDeviceClock 3 }

wtWebioEA2x2ERPClockMonth OBJECT-TYPE
   SYNTAX INTEGER {
    	wtWebioEA2x2ERPClockMonth-January(1),
    	wtWebioEA2x2ERPClockMonth-February(2),
    	wtWebioEA2x2ERPClockMonth-March(3),
    	wtWebioEA2x2ERPClockMonth-April(4),
    	wtWebioEA2x2ERPClockMonth-May(5),
    	wtWebioEA2x2ERPClockMonth-June(6),
    	wtWebioEA2x2ERPClockMonth-July(7),
    	wtWebioEA2x2ERPClockMonth-August(8),
    	wtWebioEA2x2ERPClockMonth-September(9),
    	wtWebioEA2x2ERPClockMonth-October(10),
    	wtWebioEA2x2ERPClockMonth-November(11),
    	wtWebioEA2x2ERPClockMonth-December(12)
    	}
    ACCESS read-write
    STATUS mandatory
    DESCRIPTION
        "Date: Month, taking into account the time zone settings."
    ::= { wtWebioEA2x2ERPDeviceClock 4 }

wtWebioEA2x2ERPClockYear OBJECT-TYPE
    SYNTAX INTEGER (0..65535)
    ACCESS read-write
    STATUS mandatory
    DESCRIPTION
        "Date: Year, taking into account the time zone settings."
    ::= { wtWebioEA2x2ERPDeviceClock 5 }

-- wtWebioEA2x2ERPNetwork Group
------------------------

wtWebioEA2x2ERPIpAddress OBJECT-TYPE
    SYNTAX IpAddress
    ACCESS read-write
    STATUS mandatory
    DESCRIPTION
        "IP address of the Webio"
    ::= { wtWebioEA2x2ERPNetwork 1 }

wtWebioEA2x2ERPSubnetMask OBJECT-TYPE
    SYNTAX IpAddress
    ACCESS read-write
    STATUS mandatory
    DESCRIPTION
        "Subnet mask of the Webio"
    ::= { wtWebioEA2x2ERPNetwork 2 }

wtWebioEA2x2ERPGateway OBJECT-TYPE
    SYNTAX IpAddress
    ACCESS read-write
    STATUS mandatory
    DESCRIPTION
        "Gateway of the Webio"
    ::= { wtWebioEA2x2ERPNetwork 3 }

wtWebioEA2x2ERPDnsServer1 OBJECT-TYPE
    SYNTAX OCTET STRING 
    ACCESS read-write
    STATUS mandatory
    DESCRIPTION
        "IP address of the 1st DNS server in ASCII"
    ::= { wtWebioEA2x2ERPNetwork 4 }

wtWebioEA2x2ERPDnsServer2 OBJECT-TYPE
    SYNTAX OCTET STRING 
    ACCESS read-write
    STATUS mandatory
    DESCRIPTION
        "IP address of the 2nd DNS server in ASCII"
    ::= { wtWebioEA2x2ERPNetwork 5 }

wtWebioEA2x2ERPAddConfig OBJECT-TYPE
    SYNTAX OCTET STRING 
    ACCESS read-write
    STATUS mandatory
    DESCRIPTION
        "Additional configuration (1=ON):
        Octet 1: unused
        Octet 2: unused
        Octet 3: unused
        Octet 4:
	        Bit 1: DHCP  enable
	        Bit 0: BOOTP enable"
    ::= { wtWebioEA2x2ERPNetwork 6 }

--  wtWebioEA2x2ERPHTTP Group
--------------------------------

wtWebioEA2x2ERPStartup OBJECT-TYPE
    SYNTAX OCTET STRING 
    ACCESS read-write
    STATUS mandatory
    DESCRIPTION
        "Binary coded start page, more than one page must not be selected:
        Octet 1: unused
        Octet 2: unused
        Octet 3: unused
        Octet 4:
        	Bit 2: user.htm
        	Bit 1: home.htm
	        Bit 0: index.htm"
    ::= { wtWebioEA2x2ERPHTTP 1 }

wtWebioEA2x2ERPGetHeaderEnable OBJECT-TYPE
    SYNTAX OCTET STRING 
    ACCESS read-write
    STATUS mandatory
    DESCRIPTION
        "If bits are set, every answer of a short form GET question will be lead
        by the IP-address and name of the device (Header) or a HTTP header (HTTP):
        Octet 1: unused
        Octet 2: unused
        Octet 3: unused
        Octet 4:
        	Bit 2-7: unused
        	Bit 1  : GET HTTP enable
                Bit 0  : GET Header enable"
    ::= { wtWebioEA2x2ERPHTTP 2 }

wtWebioEA2x2ERPHttpInputTrigger OBJECT-TYPE
    SYNTAX OCTET STRING (SIZE (4))
    ACCESS read-write
    STATUS mandatory
    DESCRIPTION
        "Every change on the inputs causes their state to be transmitted to the 
        remote device. To minimize data traffic, individual inputs may be exempted 
        from this rule. Nevertheless every transmission will contain all input bits.
        If a bit is set (1), a change of state on the corresponding input 
        triggers a transmission. If the bit is not set (0), no transmission 
        takes place.
        The OCTETS are interpreted bit-by-bit, with each bit corresponding to an input. 
        Bit 0 corresponds to the LSB.
        OCTET 1: unused
        OCTET 2: unused
        OCTET 3: unused
        OCTET 4, Bit 0-1: Digital inputs 0-1"
    ::= { wtWebioEA2x2ERPHTTP 3 }

wtWebioEA2x2ERPHttpPort OBJECT-TYPE
    SYNTAX INTEGER (1..65534)
    ACCESS read-write
    STATUS mandatory
    DESCRIPTION
       "Definition of the standard HTML port (Default: 80)."
    ::= { wtWebioEA2x2ERPHTTP 4 }        
    
    
-- wtWebioEA2x2ERPMail Group
--------------------------------

wtWebioEA2x2ERPMailAdName OBJECT-TYPE
    SYNTAX OCTET STRING 
    ACCESS read-write
    STATUS mandatory
    DESCRIPTION
        "Device name for mail administration."
    ::= { wtWebioEA2x2ERPMail 1 }
    
wtWebioEA2x2ERPMailReply OBJECT-TYPE
    SYNTAX OCTET STRING 
    ACCESS read-write
    STATUS mandatory
    DESCRIPTION
        "Reply address for the mail server."
    ::= { wtWebioEA2x2ERPMail 2 }
    
wtWebioEA2x2ERPMailServer OBJECT-TYPE
    SYNTAX OCTET STRING 
    ACCESS read-write
    STATUS mandatory
    DESCRIPTION
        "Name or IP address of the mail server."
    ::= { wtWebioEA2x2ERPMail 3 }
    
wtWebioEA2x2ERPMailEnable OBJECT-TYPE
    SYNTAX OCTET STRING 
    ACCESS read-write
    STATUS mandatory
    DESCRIPTION
        "Set this bit to enable the sending of mails:
        Octet 1: unused
        Octet 2: unused
        Octet 3: unused
        Octet 4:
        	Bit 1-7: unused
                Bit 0  : Mail enable"
    ::= { wtWebioEA2x2ERPMail 4 }

wtWebioEA2x2ERPMailAuthentication OBJECT-TYPE
    SYNTAX OCTET STRING (SIZE (4))
    ACCESS read-write
    STATUS mandatory
    DESCRIPTION
        "Selection of the authentication modi:
        The OCTETS are interpreted bit-by-bit,
        Bit 0 corresponds to the LSB.
        OCTET 1: unused
        OCTET 2: unused
        OCTET 3: unused
        OCTET 4: Bit 3-7: unused
        	 Bit 2  : POP3 before SMTP
        	 Bit 1  : ESMTP, authentication
        	 Bit 0  : SMTP, no authentication"
    ::= { wtWebioEA2x2ERPMail 5 }
    
wtWebioEA2x2ERPMailAuthUser OBJECT-TYPE
    SYNTAX OCTET STRING 
    ACCESS read-write
    STATUS mandatory
    DESCRIPTION
        "Name of the user to be authenticated."
    ::= { wtWebioEA2x2ERPMail 6 }    
    
wtWebioEA2x2ERPMailAuthPassword OBJECT-TYPE
    SYNTAX OCTET STRING 
    ACCESS read-write
    STATUS mandatory
    DESCRIPTION
        "Authentication password."
    ::= { wtWebioEA2x2ERPMail 7 }    
    
wtWebioEA2x2ERPMailPop3Server OBJECT-TYPE
    SYNTAX OCTET STRING 
    ACCESS read-write
    STATUS mandatory
    DESCRIPTION
        "Name or Ip-address of the POP3 Servers."
    ::= { wtWebioEA2x2ERPMail 8 }        
    

--  wtWebioEA2x2ERPSnmp Group
--------------------------------

wtWebioEA2x2ERPSnmpEnable OBJECT-TYPE
    SYNTAX OCTET STRING 
    ACCESS read-write
    STATUS mandatory
    DESCRIPTION
        "Set bit 0 to enable SNMP.
        If disabled, the device did not respond to any SNMP requests.
        Bit 1 decided wether the community string of read operations 
        is compared with the system password or not:
        Octet 1: unused
        Octet 2: unused
        Octet 3: unused
        Octet 4:
        	Bit 1-7: unused
        	Bit 0  : SNMP enable"
    ::= { wtWebioEA2x2ERPSNMP 1 }
    
wtWebioEA2x2ERPSnmpCommunityStringRead OBJECT-TYPE
    SYNTAX OCTET STRING
    ACCESS read-write
    STATUS mandatory
    DESCRIPTION
        "Community string read only"
    ::= { wtWebioEA2x2ERPSNMP 2 }

wtWebioEA2x2ERPSnmpCommunityStringReadWrite OBJECT-TYPE
    SYNTAX OCTET STRING
    ACCESS read-write
    STATUS mandatory
    DESCRIPTION
        "Community string read / write"
    ::= { wtWebioEA2x2ERPSNMP 3 }

wtWebioEA2x2ERPSnmpSystemTrapManagerIP OBJECT-TYPE
    SYNTAX OCTET STRING 
    ACCESS read-write
    STATUS mandatory
    DESCRIPTION
        "Name or IP address of the TCP server which accepts the system trap."
    ::= { wtWebioEA2x2ERPSNMP 4 }
    
wtWebioEA2x2ERPSnmpSystemTrapEnable OBJECT-TYPE
    SYNTAX OCTET STRING (SIZE(4))
    ACCESS read-write
    STATUS mandatory
    DESCRIPTION
        "Binary coded trigger conditions:
        Octet 1: unused
        Octet 2: unused
        Octet 3: unused
        Octet 4:
	        Bit 0:   ColdStart
	        Bit 1:   WarmStart
	        Bit 2:   Diag messages
	        Bit 3-7: unused"
    ::= { wtWebioEA2x2ERPSNMP 5 }    

-- wtWebioEA2x2ERPUDP Group
--------------------------------   

wtWebioEA2x2ERPUdpAdminPort OBJECT-TYPE
    SYNTAX INTEGER
    ACCESS read-write
    STATUS mandatory
    DESCRIPTION
        "Udp port to which the Udp queries ( short form GET requests) can be sent. This
        port number must be unique within the device."
    ::= { wtWebioEA2x2ERPUDP 1 }

wtWebioEA2x2ERPUdpEnable OBJECT-TYPE
    SYNTAX OCTET STRING 
    ACCESS read-write
    STATUS mandatory
    DESCRIPTION
        "Set this bit to enable UDP support:
        Octet 1: unused
        Octet 2: unused
        Octet 3: unused
        Octet 4:
        	Bit 1-7: unused
                Bit 0  : UDP enable"
    ::= { wtWebioEA2x2ERPUDP 2 }

wtWebioEA2x2ERPUdpRemotePort OBJECT-TYPE
    SYNTAX INTEGER
    ACCESS read-write
    STATUS mandatory
    DESCRIPTION
        "Udp remote port setting.
        If this value is set to zero, the source port read from a request will be used 
        as destination port for the answer.
        A non zero value forced the destination port to this value."
    ::= { wtWebioEA2x2ERPUDP 3 }
    
--  wtWebioEA2x2ERPBinary Group
--------------------------------

wtWebioEA2x2ERPBinaryModeCount OBJECT-TYPE
    SYNTAX INTEGER (1..2)
    ACCESS read-only
    STATUS mandatory
    DESCRIPTION
        "Number of independent binary channels."
    ::= { wtWebioEA2x2ERPBinary 1 }
    
-- Binary Interface Table

wtWebioEA2x2ERPBinaryIfTable OBJECT-TYPE
    SYNTAX SEQUENCE OF WtWebioEA2x2ERPBinaryIfEntry
    ACCESS not-accessible
    STATUS mandatory
    DESCRIPTION
        "Table of indices."
    ::= { wtWebioEA2x2ERPBinary 2 }

wtWebioEA2x2ERPBinaryIfEntry OBJECT-TYPE
    SYNTAX WtWebioEA2x2ERPBinaryIfEntry
    ACCESS not-accessible
    STATUS mandatory
    DESCRIPTION
        "Indices of the binary channels."
    INDEX  { wtWebioEA2x2ERPBinaryModeNo }
    ::= { wtWebioEA2x2ERPBinaryIfTable 1 }

WtWebioEA2x2ERPBinaryIfEntry ::= SEQUENCE {
    wtWebioEA2x2ERPBinaryModeNo INTEGER
}

wtWebioEA2x2ERPBinaryModeNo OBJECT-TYPE
    SYNTAX INTEGER (1..2)
    ACCESS read-only
    STATUS mandatory
    DESCRIPTION
        "Number of the binary channel."
    ::= { wtWebioEA2x2ERPBinaryIfEntry 1 }

-- Binary Table
--------------------------------

wtWebioEA2x2ERPBinaryTable OBJECT-TYPE
    SYNTAX SEQUENCE OF WtWebioEA2x2ERPBinaryEntry
    ACCESS not-accessible
    STATUS mandatory
    DESCRIPTION
        "Table of properties of the binary mode."
    ::= { wtWebioEA2x2ERPBinary 3 }

wtWebioEA2x2ERPBinaryEntry OBJECT-TYPE
    SYNTAX WtWebioEA2x2ERPBinaryEntry
    ACCESS not-accessible
    STATUS mandatory
    DESCRIPTION
        "Binary properties."
    INDEX  { wtWebioEA2x2ERPBinaryModeNo }
    ::= { wtWebioEA2x2ERPBinaryTable 1 }

WtWebioEA2x2ERPBinaryEntry ::= SEQUENCE {
    wtWebioEA2x2ERPBinaryOperationMode			OCTET STRING,
    wtWebioEA2x2ERPBinaryTcpServerLocalPort		INTEGER,
    wtWebioEA2x2ERPBinaryTcpServerInputTrigger		OCTET STRING,
    wtWebioEA2x2ERPBinaryTcpServerApplicationMode	OCTET STRING,
    wtWebioEA2x2ERPBinaryTcpClientLocalPort		INTEGER,
    wtWebioEA2x2ERPBinaryTcpClientServerPort		INTEGER,
    wtWebioEA2x2ERPBinaryTcpClientServerIpAddr		OCTET STRING,
    wtWebioEA2x2ERPBinaryTcpClientServerPassword	OCTET STRING,
    wtWebioEA2x2ERPBinaryTcpClientInactivity		INTEGER,
    wtWebioEA2x2ERPBinaryTcpClientInputTrigger		OCTET STRING,
    wtWebioEA2x2ERPBinaryTcpClientInterval		INTEGER,
    wtWebioEA2x2ERPBinaryTcpClientApplicationMode	OCTET STRING,
    wtWebioEA2x2ERPBinaryUdpPeerLocalPort		INTEGER,
    wtWebioEA2x2ERPBinaryUdpPeerRemotePort		INTEGER,
    wtWebioEA2x2ERPBinaryUdpPeerRemoteIpAddr		OCTET STRING,
    wtWebioEA2x2ERPBinaryUdpPeerInputTrigger		OCTET STRING,
    wtWebioEA2x2ERPBinaryUdpPeerInterval		INTEGER,
    wtWebioEA2x2ERPBinaryUdpPeerApplicationMode		OCTET STRING,
    wtWebioEA2x2ERPBinaryConnectedPort			INTEGER,
    wtWebioEA2x2ERPBinaryConnectedIpAddr		IpAddress,
    wtWebioEA2x2ERPBinaryTcpServerClientHttpPort	INTEGER,
    wtWebioEA2x2ERPBinaryTcpClientServerHttpPort	INTEGER
    
}

wtWebioEA2x2ERPBinaryOperationMode OBJECT-TYPE
    SYNTAX OCTET STRING (SIZE (4))
    ACCESS read-write
    STATUS mandatory
    DESCRIPTION
        "Selection of the operation mode:
        The OCTETS are interpreted bit-by-bit,
        Bit 0 corresponds to the LSB.
        OCTET 1: unused
        OCTET 2: unused
        OCTET 3: unused
        OCTET 4: Bit 3-7: unused
        	 Bit 2  : UDP Peer
        	 Bit 1  : TCP Client
        	 Bit 0  : TCP Server"
    ::= { wtWebioEA2x2ERPBinaryEntry 1 }

wtWebioEA2x2ERPBinaryTcpServerLocalPort OBJECT-TYPE
    SYNTAX INTEGER (1..65535)
    ACCESS read-write
    STATUS mandatory
    DESCRIPTION
        "Local TCP port for data exchange in this server mode.
        This port number must be unique within the device.
	Reserved port number must not be used (refere to the manual)."
    ::= { wtWebioEA2x2ERPBinaryEntry 2 }

wtWebioEA2x2ERPBinaryTcpServerInputTrigger OBJECT-TYPE
    SYNTAX OCTET STRING (SIZE (4))
    ACCESS read-write
    STATUS mandatory
    DESCRIPTION
        "Every change on the inputs causes their state to be transmitted to the 
        remote device. To minimize data traffic, individual inputs may be exempted 
        from this rule. Nevertheless every transmission will contain all input bits.
        If a bit is set (1), a change of state on the corresponding input 
        triggers a transmission. If the bit is not set (0), no transmission 
        takes place.
        The OCTETS are interpreted bit-by-bit, with each bit corresponding to an input. 
        Bit 0 corresponds to the LSB.
        OCTET 1: unused
        OCTET 2: unused
        OCTET 3: unused
        OCTET 4, Bit 0-1: Digital inputs 0-1"
    ::= { wtWebioEA2x2ERPBinaryEntry 3 }

wtWebioEA2x2ERPBinaryTcpServerApplicationMode OBJECT-TYPE
    SYNTAX OCTET STRING (SIZE (4))
    ACCESS read-write
    STATUS mandatory
    DESCRIPTION
        "Selection of the application mode:
        The OCTETS are interpreted bit-by-bit,
        Bit 0 corresponds to the LSB.
        OCTET 1: unused
        OCTET 2: unused
        OCTET 3: unused
        OCTET 4: Bit 4-7: unused
        	 Bit 3  : OPC Device
        	 Bit 2  : Box2Box Slave
        	 Bit 1  : Compatible 50xxx
        	 Bit 0  : Default"
    ::= { wtWebioEA2x2ERPBinaryEntry 4 }
    
wtWebioEA2x2ERPBinaryTcpClientLocalPort OBJECT-TYPE
    SYNTAX INTEGER (1..65535)
    ACCESS read-write
    STATUS mandatory
    DESCRIPTION
        "Local TCP port for data exchange in this client mode.
        This port number must be unique within the device.
	Reserved port number must not be used (refere to the manual)."
    ::= { wtWebioEA2x2ERPBinaryEntry 5 }

wtWebioEA2x2ERPBinaryTcpClientServerPort OBJECT-TYPE
    SYNTAX INTEGER (1..65535)
    ACCESS read-write
    STATUS mandatory
    DESCRIPTION
        "Port number of the server. A complete set of port number, IP address
        and a valid input/output mask starts this mode.
        No data exchange take place when setting the server port to zero."
    ::= { wtWebioEA2x2ERPBinaryEntry 6 }

wtWebioEA2x2ERPBinaryTcpClientServerIpAddr OBJECT-TYPE
    SYNTAX OCTET STRING
    ACCESS read-write
    STATUS mandatory
    DESCRIPTION
        "Ip address of the server. A complete set of port number, IP address
        and a valid input/output mask starts this mode.
        No data exchange take place when setting the server IP address to 0.0.0.0."
    ::= { wtWebioEA2x2ERPBinaryEntry 7 }

wtWebioEA2x2ERPBinaryTcpClientServerPassword OBJECT-TYPE
    SYNTAX OCTET STRING
    ACCESS read-write
    STATUS mandatory
    DESCRIPTION
        "Building a connection may be protected by the 
        administrator password of the server. Enter the server password
        to establish the connection, if a server administrator password
        exists."
    ::= { wtWebioEA2x2ERPBinaryEntry 8 }

wtWebioEA2x2ERPBinaryTcpClientInactivity OBJECT-TYPE
    SYNTAX INTEGER 
    ACCESS read-write
    STATUS mandatory
    DESCRIPTION
        "Connection timeout in 100ms. If no data are exchanged within the specified  
        time, the device closes the connection to the server.
        The value 0 deactivates the timer. Using the Box2Box mode this function is
        disabled."
    ::= { wtWebioEA2x2ERPBinaryEntry 9 }
    
wtWebioEA2x2ERPBinaryTcpClientInputTrigger OBJECT-TYPE
    SYNTAX OCTET STRING (SIZE (4))
    ACCESS read-write
    STATUS mandatory
    DESCRIPTION
        "Every change on the inputs causes their state to be transmitted to the 
        remote device. To minimize data traffic, individual inputs may be exempted 
        from this rule. Nevertheless every transmission will contain all input bits.
        If a bit is set (1), a change of state on the corresponding input 
        triggers a transmission. If the bit is not set (0), no transmission 
        takes place.
        The OCTETS are interpreted bit-by-bit, with each bit corresponding to an input. 
        Bit 0 corresponds to the LSB.
        OCTET 1: unused
        OCTET 2: unused
        OCTET 3: unused
        OCTET 4, Bit 0-1: Digital inputs 0-1"
    ::= { wtWebioEA2x2ERPBinaryEntry 10 }
 
wtWebioEA2x2ERPBinaryTcpClientInterval OBJECT-TYPE
    SYNTAX INTEGER (0..65535)
    ACCESS read-write
    STATUS mandatory
    DESCRIPTION
        "Configurable interval with a 100ms base, in which the Webio device sends
        data to the configured application. A interval of zero stopps the 
        periodical sending."
    ::= { wtWebioEA2x2ERPBinaryEntry 11 }

wtWebioEA2x2ERPBinaryTcpClientApplicationMode OBJECT-TYPE
    SYNTAX OCTET STRING (SIZE (4))
    ACCESS read-write
    STATUS mandatory
    DESCRIPTION
        "Selection of the application mode:
        The OCTETS are interpreted bit-by-bit,
        Bit 0 corresponds to the LSB.
        OCTET 1: unused
        OCTET 2: unused
        OCTET 3: unused
        OCTET 4: Bit 3-7: unused
        	 Bit 2  : Box2Box Slave
        	 Bit 1  : Compatible 50xxx
        	 Bit 0  : Default"
    ::= { wtWebioEA2x2ERPBinaryEntry 12 }

wtWebioEA2x2ERPBinaryUdpPeerLocalPort OBJECT-TYPE
    SYNTAX INTEGER (1..65535)
    ACCESS read-write
    STATUS mandatory
    DESCRIPTION
        "Local UDP port for data exchange in this peer to peer mode.
        This port number must be unique within the device.
	Reserved port number must not be used (refere to the manual)."
    ::= { wtWebioEA2x2ERPBinaryEntry 13 }

wtWebioEA2x2ERPBinaryUdpPeerRemotePort OBJECT-TYPE
    SYNTAX INTEGER (1..65535)
    ACCESS read-write
    STATUS mandatory
    DESCRIPTION
        "Port number of the remote device. A complete set of port number, IP address
        and a valid input/output mask starts this mode.
        No data exchange take place when setting the remote port to zero."
    ::= { wtWebioEA2x2ERPBinaryEntry 14 }

wtWebioEA2x2ERPBinaryUdpPeerRemoteIpAddr OBJECT-TYPE
    SYNTAX OCTET STRING
    ACCESS read-write
    STATUS mandatory
    DESCRIPTION
        "Ip address of the remote device. A complete set of port number, IP address
        and a valid input/output mask starts this mode.
        No data exchange take place when setting the remote device IP address to 0.0.0.0."
    ::= { wtWebioEA2x2ERPBinaryEntry 15 }

wtWebioEA2x2ERPBinaryUdpPeerInputTrigger OBJECT-TYPE
    SYNTAX OCTET STRING (SIZE (4))
    ACCESS read-write
    STATUS mandatory
    DESCRIPTION
        "Every change on the inputs causes their state to be transmitted to the 
        remote device. To minimize data traffic, individual inputs may be exempted 
        from this rule. Nevertheless every transmission will contain all input bits.
        If a bit is set (1), a change of state on the corresponding input 
        triggers a transmission. If the bit is not set (0), no transmission 
        takes place.
        The OCTETS are interpreted bit-by-bit, with each bit corresponding to an input. 
        Bit 0 corresponds to the LSB.
        OCTET 1: unused
        OCTET 2: unused
        OCTET 3: unused
        OCTET 4, Bit 0-1: Digital inputs 0-1"
    ::= { wtWebioEA2x2ERPBinaryEntry 16 }

wtWebioEA2x2ERPBinaryUdpPeerInterval OBJECT-TYPE
    SYNTAX INTEGER (0..65535)
    ACCESS read-write
    STATUS mandatory
    DESCRIPTION
        "Configurable interval with a 100ms base, in which the Webio device sends
        data to the configured remote device. A interval of zero stopps the 
        periodical sending."
    ::= { wtWebioEA2x2ERPBinaryEntry 17 }

wtWebioEA2x2ERPBinaryUdpPeerApplicationMode OBJECT-TYPE
    SYNTAX OCTET STRING (SIZE (4))
    ACCESS read-write
    STATUS mandatory
    DESCRIPTION
        "Selection of the application mode:
        The OCTETS are interpreted bit-by-bit, with each bit corresponding to an output. 
        Bit 0 corresponds to the LSB.
        OCTET 1: unused
        OCTET 2: unused
        OCTET 3: unused
        OCTET 4: Bit 3-7: unused
        	 Bit 2  : Box2Box Slave
        	 Bit 1  : Compatible 50xxx
        	 Bit 0  : Default"
    ::= { wtWebioEA2x2ERPBinaryEntry 18 }

wtWebioEA2x2ERPBinaryConnectedPort OBJECT-TYPE
    SYNTAX INTEGER (1..65535)
    ACCESS read-only
    STATUS mandatory
    DESCRIPTION
        "Port number of the remote device, after connection has been established.
        In case of no connection or missing port informations a zero will be read."
    ::= { wtWebioEA2x2ERPBinaryEntry 19 }

wtWebioEA2x2ERPBinaryConnectedIpAddr OBJECT-TYPE
    SYNTAX IpAddress
    ACCESS read-only
    STATUS mandatory
    DESCRIPTION
        "IP address of the remote device, after connection has been established.
        In case of no connection or missing port informations 0.0.0.0 will be read."
    ::= { wtWebioEA2x2ERPBinaryEntry 20 } 

wtWebioEA2x2ERPBinaryTcpServerClientHttpPort OBJECT-TYPE
    SYNTAX INTEGER (1..65535)
    ACCESS read-write
    STATUS mandatory
    DESCRIPTION
        "HTTP port number of the remote device at TCP Server Mode. If an mailfunction occurs 
        status informations will be send to this port. 
        Not used at mode Compatible 50xxx."
    ::= { wtWebioEA2x2ERPBinaryEntry 21 }
    
wtWebioEA2x2ERPBinaryTcpClientServerHttpPort OBJECT-TYPE
    SYNTAX INTEGER (1..65535)
    ACCESS read-write
    STATUS mandatory
    DESCRIPTION
        "HTTP port number of the remote device at TCP Client Mode. In the operating mode
        Box2Box connection status informations will be exchanged through this port."
    ::= { wtWebioEA2x2ERPBinaryEntry 22 }            
    
--  wtWebioEA2x2ERPSyslog Group
--------------------------------
    
wtWebioEA2x2ERPSyslogServerIP OBJECT-TYPE
    SYNTAX OCTET STRING 
    ACCESS read-write
    STATUS mandatory
    DESCRIPTION
        "Name or IP address of the Syslog server, which accepts the Syslog messgaes."
    ::= { wtWebioEA2x2ERPSyslog 1 }
    
wtWebioEA2x2ERPSyslogServerPort OBJECT-TYPE
    SYNTAX INTEGER
    ACCESS read-write
    STATUS mandatory
    DESCRIPTION
        "Portnumber of the Syslog servers, default 514."
    ::= { wtWebioEA2x2ERPSyslog 2 }

wtWebioEA2x2ERPSyslogSystemMessagesEnable OBJECT-TYPE
    SYNTAX OCTET STRING (SIZE(4))
    ACCESS read-write
    STATUS mandatory
    DESCRIPTION
        "Binary coded trigger conditions:
        Octet 1: unused
        Octet 2: unused
        Octet 3: unused
        Octet 4:
	        Bit 0:   ColdStart
	        Bit 1:   WarmStart
	        Bit 2:   Diag Messages
	        Bit 3-7: unused"
    ::= { wtWebioEA2x2ERPSyslog 3 }    

wtWebioEA2x2ERPSyslogEnable OBJECT-TYPE
    SYNTAX OCTET STRING 
    ACCESS read-write
    STATUS mandatory
    DESCRIPTION
        "Set bit 0to enable Syslog:
        Octet 1: unused
        Octet 2: unused
        Octet 3: unused
        Octet 4:
        	Bit 1-7: unused
                Bit 0  : Syslog enable"
    ::= { wtWebioEA2x2ERPSyslog 4 }

--  wtWebioEA2x2ERPFTP Group
--------------------------------

wtWebioEA2x2ERPFTPServerIP OBJECT-TYPE
    SYNTAX OCTET STRING 
    ACCESS read-write
    STATUS mandatory
    DESCRIPTION
        "Name or IP address of the FTP server, which accepts the FTP messages."
    ::= { wtWebioEA2x2ERPFTP 1 }
    
wtWebioEA2x2ERPFTPServerControlPort OBJECT-TYPE
    SYNTAX INTEGER
    ACCESS read-write
    STATUS mandatory
    DESCRIPTION
        "Portnumber of the control port of the FTP server, default 21."
    ::= { wtWebioEA2x2ERPFTP 2 }
    
wtWebioEA2x2ERPFTPUserName OBJECT-TYPE
    SYNTAX OCTET STRING 
    ACCESS read-write
    STATUS mandatory
    DESCRIPTION
        "FTP Loggin: user name."
    ::= { wtWebioEA2x2ERPFTP 3 }
    
wtWebioEA2x2ERPFTPPassword OBJECT-TYPE
    SYNTAX OCTET STRING 
    ACCESS read-write
    STATUS mandatory
    DESCRIPTION
        "FTP Loggin: user password."
    ::= { wtWebioEA2x2ERPFTP 4 }

wtWebioEA2x2ERPFTPAccount OBJECT-TYPE
    SYNTAX OCTET STRING 
    ACCESS read-write
    STATUS mandatory
    DESCRIPTION
        "FTP Loggin: name of account."
    ::= { wtWebioEA2x2ERPFTP 5 }

wtWebioEA2x2ERPFTPOption OBJECT-TYPE
    SYNTAX OCTET STRING 
    ACCESS read-write
    STATUS mandatory
    DESCRIPTION
        "Bit 0 switches the FTP Server in Passiv-Mode,
        the Client controls the data connection on its own:
        Octet 1: unused
        Octet 2: unused
        Octet 3: unused
        Octet 4:
        	Bit 1-7: unused
                Bit 0  : PASV enable"
    ::= { wtWebioEA2x2ERPFTP 6 }
    
wtWebioEA2x2ERPFTPEnable OBJECT-TYPE
    SYNTAX OCTET STRING 
    ACCESS read-write
    STATUS mandatory
    DESCRIPTION
        "Set Bit 0 to enable FTP:
        Octet 1: unused
        Octet 2: unused
        Octet 3: unused
        Octet 4:
        	Bit 1-7: unused
                Bit 0  : FTP enable"
    ::= { wtWebioEA2x2ERPFTP 7 }  

--  wtWebioEA2x2ERPWayBack Group
--------------------------------

wtWebioEA2x2ERPWayBackEnable OBJECT-TYPE
    SYNTAX OCTET STRING 
    ACCESS read-write
    STATUS mandatory
    DESCRIPTION
        "Set Bit 0 to enable WayBack:
        Octet 1: unused
        Octet 2: unused
        Octet 3: unused
        Octet 4:
        	Bit 1-7: unused
                Bit 0  : WayBack enable"
    ::= { wtWebioEA2x2ERPWayBack 1 }    

wtWebioEA2x2ERPWayBackServerControlPort OBJECT-TYPE
    SYNTAX INTEGER
    ACCESS read-write
    STATUS mandatory
    DESCRIPTION
        "Portnumber of the control port of the FTP server, default 21."
    ::= { wtWebioEA2x2ERPWayBack 2 }
    
wtWebioEA2x2ERPWayBackFTPPassword OBJECT-TYPE
    SYNTAX OCTET STRING 
    ACCESS read-write
    STATUS mandatory
    DESCRIPTION
        "WayBack FTP Loggin: Password of the user."
    ::= { wtWebioEA2x2ERPWayBack 3 }    
    
wtWebioEA2x2ERPWayBackFTPResponse OBJECT-TYPE
    SYNTAX OCTET STRING 
    ACCESS read-write
    STATUS mandatory
    DESCRIPTION
        "WayBack FTP response: return message after login."
    ::= { wtWebioEA2x2ERPWayBack 4 }
    
wtWebioEA2x2ERPWayBackFTPTimeOut OBJECT-TYPE
    SYNTAX OCTET STRING 
    ACCESS read-write
    STATUS mandatory
    DESCRIPTION
        "WayBack FTP Timeout: a request must be finished within this periode of time."
    ::= { wtWebioEA2x2ERPWayBack 5 }    
    
--  wtWebioEA2x2ERPOutputMode Group
--------------------------------

-- OutputMode Table

wtWebioEA2x2ERPOutputModeTable OBJECT-TYPE
    SYNTAX SEQUENCE OF WtWebioEA2x2ERPOutputModeEntry
    ACCESS not-accessible
    STATUS mandatory
    DESCRIPTION
        "Table of output mode configurations dependent on the output indices."
    ::= { wtWebioEA2x2ERPOutputMode 1 }

wtWebioEA2x2ERPOutputModeEntry OBJECT-TYPE
    SYNTAX WtWebioEA2x2ERPOutputModeEntry
    ACCESS not-accessible
    STATUS mandatory
    DESCRIPTION
        "Output mode configurations of the individual outputs."
    INDEX  { wtWebioEA2x2ERPOutputNo }
    ::= { wtWebioEA2x2ERPOutputModeTable 1 }

WtWebioEA2x2ERPOutputModeEntry ::= SEQUENCE {
    wtWebioEA2x2ERPOutputModeBit	OCTET STRING
}

wtWebioEA2x2ERPOutputModeBit OBJECT-TYPE
    SYNTAX OCTET STRING (SIZE (4))
    ACCESS read-write
    STATUS mandatory
    DESCRIPTION
        "This binary coded output mode defines the individual operation mode for any
        output. More than one mode must not be selected.
        The OCTETS are interpreted bit-by-bit, with each bit corresponding to an output. 
        Bit 0 corresponds to the LSB.
        OCTET 1: unused
        OCTET 2: unused
        OCTET 3: unused
        OCTET 4: Bit 6-7: unused
        	 Bit 5  : Logic
        	 Bit 4  : Binary 2
        	 Bit 3  : Binary 1
        	 Bit 2  : SNMP
        	 Bit 1  : UDP ASCII
        	 Bit 0  : HTTP"
    ::= { wtWebioEA2x2ERPOutputModeEntry 1 }
    
wtWebioEA2x2ERPSafetyTimeout OBJECT-TYPE
    SYNTAX INTEGER (0..65535)
    ACCESS read-write
    STATUS mandatory
    DESCRIPTION
        "After this period of time (multiple of 100ms) without receiving data
        outputs switch to their Safety States. For each output a independend safety state
        could be defined."
    ::= { wtWebioEA2x2ERPOutputMode 2 }
 
 wtWebioEA2x2ERPLoadControlEnable OBJECT-TYPE
    SYNTAX OCTET STRING 
    ACCESS read-write
    STATUS mandatory
    DESCRIPTION
        "Here the function of automatic load control can be enabled. All output were tested in 
        pairs (0-1). If an error occours at one output,
        both output of an pair will be switched of. For a properly function of the load control
        each output of a pair have to has a load. If there is no existing load, a pull down resistor
        can be used.
        Outputs with no load are automaticly detected and not part of the control function.
        The OCTETS are interpreted bit-by-bit, with each bit corresponding to an output. 
        Bit 0 corresponds to the LSB.
        Octet 1: unused
        Octet 2: unused
        Octet 3: unused
        Octet 4:
        	Bit 1-7: unused
                Bit 0  : Load Control enable"
    ::= { wtWebioEA2x2ERPOutputMode 3 }
    
-- wtWebioEA2x2ERPAlarm Group
----------------------------

wtWebioEA2x2ERPAlarmCount OBJECT-TYPE
    SYNTAX INTEGER (1..4)
    ACCESS read-only
    STATUS mandatory
    DESCRIPTION
        "Number of independent alarms."
    ::= { wtWebioEA2x2ERPAlarm 1 }
    
-- Alarm Interface Table

wtWebioEA2x2ERPAlarmIfTable OBJECT-TYPE
    SYNTAX SEQUENCE OF WtWebioEA2x2ERPAlarmIfEntry
    ACCESS not-accessible
    STATUS mandatory
    DESCRIPTION
        "List of alarm indices."
    ::= { wtWebioEA2x2ERPAlarm 2 }

wtWebioEA2x2ERPAlarmIfEntry OBJECT-TYPE
    SYNTAX WtWebioEA2x2ERPAlarmIfEntry
    ACCESS not-accessible
    STATUS mandatory
    DESCRIPTION
        "Numbers of the alarms."
    INDEX  { wtWebioEA2x2ERPAlarmNo }
    ::= { wtWebioEA2x2ERPAlarmIfTable 1 }

WtWebioEA2x2ERPAlarmIfEntry ::= SEQUENCE {
    wtWebioEA2x2ERPAlarmNo INTEGER
}

wtWebioEA2x2ERPAlarmNo OBJECT-TYPE
    SYNTAX INTEGER (1..4)
    ACCESS read-only
    STATUS mandatory
    DESCRIPTION
        "Numbers of the alarms."
    ::= { wtWebioEA2x2ERPAlarmIfEntry 1 }

-- Alarm Table

wtWebioEA2x2ERPAlarmTable OBJECT-TYPE
    SYNTAX SEQUENCE OF WtWebioEA2x2ERPAlarmEntry
    ACCESS not-accessible
    STATUS mandatory
    DESCRIPTION
        "List of settings depending on the alarm number."
    ::= { wtWebioEA2x2ERPAlarm 3 }

wtWebioEA2x2ERPAlarmEntry OBJECT-TYPE
    SYNTAX WtWebioEA2x2ERPAlarmEntry
    ACCESS not-accessible
    STATUS mandatory
    DESCRIPTION
        "Alarm parameters of the individual alarms."
    INDEX  { wtWebioEA2x2ERPAlarmNo }
    ::= { wtWebioEA2x2ERPAlarmTable 1 }

WtWebioEA2x2ERPAlarmEntry ::= SEQUENCE {
    wtWebioEA2x2ERPAlarmInputTrigger		OCTET STRING,
    wtWebioEA2x2ERPAlarmOutputTrigger		OCTET STRING,
    wtWebioEA2x2ERPAlarmSystemTrigger		OCTET STRING,
    wtWebioEA2x2ERPAlarmMaxCounterValue		OCTET STRING,
    wtWebioEA2x2ERPAlarmInterval		OCTET STRING,
    wtWebioEA2x2ERPAlarmEnable			OCTET STRING,
    wtWebioEA2x2ERPAlarmMailAddr		OCTET STRING,
    wtWebioEA2x2ERPAlarmMailSubject		OCTET STRING,
    wtWebioEA2x2ERPAlarmMailText		OCTET STRING,
    wtWebioEA2x2ERPAlarmSnmpManagerIP		OCTET STRING,
    wtWebioEA2x2ERPAlarmSnmpTrapText		OCTET STRING,
    wtWebioEA2x2ERPAlarmUdpIpAddr		OCTET STRING,
    wtWebioEA2x2ERPAlarmUdpPort			INTEGER,
    wtWebioEA2x2ERPAlarmUdpText			OCTET STRING,
    wtWebioEA2x2ERPAlarmTcpIpAddr		OCTET STRING,
    wtWebioEA2x2ERPAlarmTcpPort			INTEGER,
    wtWebioEA2x2ERPAlarmTcpText			OCTET STRING,    
    wtWebioEA2x2ERPAlarmSyslogIpAddr		OCTET STRING,
    wtWebioEA2x2ERPAlarmSyslogPort		INTEGER,
    wtWebioEA2x2ERPAlarmSyslogText		OCTET STRING,
    wtWebioEA2x2ERPAlarmFtpDataPort		OCTET STRING,
    wtWebioEA2x2ERPAlarmFtpFileName		OCTET STRING,
    wtWebioEA2x2ERPAlarmFtpText			OCTET STRING,
    wtWebioEA2x2ERPAlarmFtpOption		OCTET STRING,
    wtWebioEA2x2ERPAlarmTimerCron		OCTET STRING,
    
    wtWebioEA2x2ERPAlarmMailReleaseSubject	OCTET STRING,
    wtWebioEA2x2ERPAlarmMailReleaseText		OCTET STRING,
    wtWebioEA2x2ERPAlarmSnmpTrapReleaseText	OCTET STRING,
    wtWebioEA2x2ERPAlarmUdpReleaseText		OCTET STRING,
    wtWebioEA2x2ERPAlarmTcpReleaseText		OCTET STRING,    
    wtWebioEA2x2ERPAlarmSyslogReleaseText	OCTET STRING,
    wtWebioEA2x2ERPAlarmFtpReleaseText		OCTET STRING    
    
}

wtWebioEA2x2ERPAlarmInputTrigger OBJECT-TYPE
    SYNTAX OCTET STRING (SIZE(12))
    ACCESS read-write
    STATUS mandatory
    DESCRIPTION
        "This variable allows setting of individual input trigger conditions. 
        The OCTETS are interpreted bit-by-bit, with each bit corresponding to an input. 
        Bit 0 corresponds to the LSB.
	The first four OCTETS contain the mask which determines which of the inputs are to 
	be considered (corresponding bit = 1) and which inputs are to ignore 
	(corresponding bit = 0):
	OCTET 1 : unused
	OCTET 2 : unused
	OCTET 3 : unused
	OCTET 4, Bit 0-1: Mask for digital inputs 0-1
	
	OCTETS 5-8 contain the level (1=HIGH, 0=LOW) which the inputs 
	should assume:
	OCTET 5 : unused
	OCTET 6 : unused
	OCTET 7 : unused
        OCTET 8, Bit 0-1: Level of digital inputs 0-1
        
	OCTETS 9-12 contain the ANY bit (1=ON, 0=OFF). Inputs masked with the any bit trigger with any change 
	of the corresponding input bit. Settings in OCTET 5-9 are then unused:
	OCTET 9: unused
	OCTET 10: unused
	OCTET 11: unused
	OCTET 12, Bit 0-1: ANY bits of digital inputs 0-1"
        
    ::= { wtWebioEA2x2ERPAlarmEntry 1 }

wtWebioEA2x2ERPAlarmOutputTrigger OBJECT-TYPE
    SYNTAX OCTET STRING (SIZE(12))
    ACCESS read-write
    STATUS mandatory
    DESCRIPTION
        "This variable allows setting of individual output trigger conditions. 
        The OCTETS are interpreted bit-by-bit, with each bit corresponding to an output. 
        Bit 0 corresponds to the LSB.
	The first four OCTETS contain the mask which determines which of the outputs are to 
	be considered (corresponding bit = 1) and which outputs are to ignore 
	(corresponding bit = 0):
	OCTET 1 : unused
	OCTET 2 : unused
	OCTET 3 : unused
	OCTET 4, Bit 0-1: Mask for digital outputs 0-1
	
	OCTETS 5-8 contain the level (1=HIGH, 0=LOW) which the outputs 
	should assume:
	OCTET 5 : unused
	OCTET 6 : unused
	OCTET 7 : unused
        OCTET 8, Bit 0-1: Level of digital outputs 0-1

	OCTETS 9-12 contain the ANY bit (1=ON, 0=OFF). Outputs masked with the any bit trigger with any change 
	of the corresponding output bit. Settings in OCTET 5-9 are then unused:
	OCTET 9: unused
	OCTET 10: unused
	OCTET 11: unused
	OCTET 12, Bit 0-1: ANY bits of digital outputs 0-1"
        
    ::= { wtWebioEA2x2ERPAlarmEntry 2 }
    
wtWebioEA2x2ERPAlarmSystemTrigger OBJECT-TYPE
    SYNTAX OCTET STRING (SIZE(4))
    ACCESS read-write
    STATUS mandatory
    DESCRIPTION
        "Binary coded trigger conditions:
        The OCTETS are interpreted bit-by-bit.
        Bit 0 corresponds to the LSB.
        OCTET 1: unused
        OCTET 2: unused
        OCTET 3: unused
        OCTET 4, 
        	 Bit 4-7: unused
        	 Bit 3  : Warm Start
        	 Bit 2  : Cold Start
        	 Bit 1  : Timer
        	 Bit 0  : Load Control"
    ::= { wtWebioEA2x2ERPAlarmEntry 3 }

wtWebioEA2x2ERPAlarmMaxCounterValue OBJECT-TYPE
    SYNTAX OCTET STRING 
    ACCESS read-write
    STATUS mandatory
    DESCRIPTION
        "This variable configures a max. counter value. If an input counter value
        exceeds this max. value, the corresponding alarm is triggered. Input counters with
        its mask bit unset in wtWebioEA2x2ERPAlarmInputTrigger are not considered."
    ::= { wtWebioEA2x2ERPAlarmEntry 4 }

wtWebioEA2x2ERPAlarmInterval OBJECT-TYPE
    SYNTAX OCTET STRING 
    ACCESS read-write
    STATUS mandatory
    DESCRIPTION
        "Send interval for alarm messages."
    ::= { wtWebioEA2x2ERPAlarmEntry 5 }

wtWebioEA2x2ERPAlarmEnable OBJECT-TYPE
    SYNTAX OCTET STRING (SIZE(4))
    ACCESS read-write
    STATUS mandatory
    DESCRIPTION
        "Binary coded alarm enable:
        Octet 1: unused
        Octet 2: unused
        Octet 3: unused
        Octet 4:
		Bit 0:	Mail Enable
        	Bit 1:	SNMP Trap enable
        	Bit 2:  UDP enable
        	Bit 3:  Send inputs to pending TCP connections
        	Bit 4:  TCP Client enable
        	Bit 5:	Syslog Messages enable
        	Bit 6-7: unused"
    ::= { wtWebioEA2x2ERPAlarmEntry 6 }

wtWebioEA2x2ERPAlarmMailAddr OBJECT-TYPE
    SYNTAX OCTET STRING 
    ACCESS read-write
    STATUS mandatory
    DESCRIPTION
        "E-Mail address for sending the alarm mail to."
    ::= { wtWebioEA2x2ERPAlarmEntry 7 }

wtWebioEA2x2ERPAlarmMailSubject OBJECT-TYPE
    SYNTAX OCTET STRING 
    ACCESS read-write
    STATUS mandatory
    DESCRIPTION
        "Subject line for alarm mail."
    ::= { wtWebioEA2x2ERPAlarmEntry 8 }

wtWebioEA2x2ERPAlarmMailText OBJECT-TYPE
    SYNTAX OCTET STRING 
    ACCESS read-write
    STATUS mandatory
    DESCRIPTION
        "Alarm mail text: 
        States of the Webio device can be included by using special tags.
        Please refer to the respective Webio manual"
    ::= { wtWebioEA2x2ERPAlarmEntry 9 }

wtWebioEA2x2ERPAlarmSnmpManagerIP OBJECT-TYPE
    SYNTAX OCTET STRING 
    ACCESS read-write
    STATUS mandatory
    DESCRIPTION
        "IP address of the SNMP Manager to which the Webio device should send SNMP traps."
    ::= { wtWebioEA2x2ERPAlarmEntry 10 }

wtWebioEA2x2ERPAlarmSnmpTrapText OBJECT-TYPE
    SYNTAX OCTET STRING 
    ACCESS read-write
    STATUS mandatory
    DESCRIPTION
        "This text appears in the trap body."
    ::= { wtWebioEA2x2ERPAlarmEntry 11 }
    
wtWebioEA2x2ERPAlarmUdpIpAddr OBJECT-TYPE
    SYNTAX OCTET STRING 
    ACCESS read-write
    STATUS mandatory
    DESCRIPTION
        "IP address of the UDP listener to which the Webio device should send UDP traps."
    ::= { wtWebioEA2x2ERPAlarmEntry 12 }    

wtWebioEA2x2ERPAlarmUdpPort OBJECT-TYPE
    SYNTAX INTEGER (1..65535) 
    ACCESS read-write
    STATUS mandatory
    DESCRIPTION
        "Port number of the UDP listener to which the Webio device should send UDP traps."
    ::= { wtWebioEA2x2ERPAlarmEntry 13 }    

wtWebioEA2x2ERPAlarmUdpText OBJECT-TYPE
    SYNTAX OCTET STRING 
    ACCESS read-write
    STATUS mandatory
    DESCRIPTION
        "This text appears in the UDP trap body."
    ::= { wtWebioEA2x2ERPAlarmEntry 14 }
    
wtWebioEA2x2ERPAlarmTcpIpAddr OBJECT-TYPE
    SYNTAX OCTET STRING
    ACCESS read-write
    STATUS mandatory
    DESCRIPTION
        "IP address of the TCP listener to which the Webio device should send TCP traps."
    ::= { wtWebioEA2x2ERPAlarmEntry 15 }    

wtWebioEA2x2ERPAlarmTcpPort OBJECT-TYPE
    SYNTAX INTEGER (1..65535) 
    ACCESS read-write
    STATUS mandatory
    DESCRIPTION
        "Port number of the TCP listener to which the Webio device should send TCP traps."
    ::= { wtWebioEA2x2ERPAlarmEntry 16 }    

wtWebioEA2x2ERPAlarmTcpText OBJECT-TYPE
    SYNTAX OCTET STRING 
    ACCESS read-write
    STATUS mandatory
    DESCRIPTION
        "This text appears in the TCP trap body."
    ::= { wtWebioEA2x2ERPAlarmEntry 17 }

wtWebioEA2x2ERPAlarmSyslogIpAddr OBJECT-TYPE
    SYNTAX OCTET STRING 
    ACCESS read-write
    STATUS mandatory
    DESCRIPTION
        "IP address of the syslog server to which the Webio device should send syslog messages."
    ::= { wtWebioEA2x2ERPAlarmEntry 18 }    

wtWebioEA2x2ERPAlarmSyslogPort OBJECT-TYPE
    SYNTAX INTEGER (1..65535) 
    ACCESS read-write
    STATUS mandatory
    DESCRIPTION
        "Port number of the syslog server to which the Webio device should send syslog messages."
    ::= { wtWebioEA2x2ERPAlarmEntry 19 }    

wtWebioEA2x2ERPAlarmSyslogText OBJECT-TYPE
    SYNTAX OCTET STRING 
    ACCESS read-write
    STATUS mandatory
    DESCRIPTION
        "Every message starts with the priority key, a time stamp and the host ip address, according RFC3164.
        This text appears in the following syslog message body."
    ::= { wtWebioEA2x2ERPAlarmEntry 20 }    
    
wtWebioEA2x2ERPAlarmFtpDataPort OBJECT-TYPE
    SYNTAX OCTET STRING 
    ACCESS read-write
    STATUS mandatory
    DESCRIPTION
        "Local data port: 1..65535 or AUTO: the next free port will be assigned."
    ::= { wtWebioEA2x2ERPAlarmEntry 21 }
    
wtWebioEA2x2ERPAlarmFtpFileName OBJECT-TYPE
    SYNTAX OCTET STRING 
    ACCESS read-write
    STATUS mandatory
    DESCRIPTION
        "Name of the file including path informations."
    ::= { wtWebioEA2x2ERPAlarmEntry 22 }
    
wtWebioEA2x2ERPAlarmFtpText OBJECT-TYPE
    SYNTAX OCTET STRING 
    ACCESS read-write
    STATUS mandatory
    DESCRIPTION
        "Message text to store on the FTP server."
    ::= { wtWebioEA2x2ERPAlarmEntry 23 }

wtWebioEA2x2ERPAlarmFtpOption OBJECT-TYPE
    SYNTAX OCTET STRING (SIZE(4))
    ACCESS read-write
    STATUS mandatory
    DESCRIPTION
        "Binary coded options, select only one option at the same time:
        STORE  = replace file
        APPEND = append message at the end of the file
        
        Octet 1: unused
        Octet 2: unused
        Octet 3: unused
        Octet 4:
		Bit 0  :	STORE
		Bit 1  :	APPEND
        	Bit 2-7:	unused"
    ::= { wtWebioEA2x2ERPAlarmEntry 24 }      
    
wtWebioEA2x2ERPAlarmTimerCron OBJECT-TYPE
    SYNTAX OCTET STRING
    ACCESS read-write
    STATUS mandatory
    DESCRIPTION
        "This entry contains 5 space or tab seperated text fields for time trigger definition.
        Each field must match with the actual time to trigger a message, weekday and day of month
        are interpreted separatley.
        1: Minutes	Range 0-59
        2. Hours	Range 0-23, 0 is midnight
        3: Day of month	Range 1-31
        4: Month	Range 1-12
        5: Weekday	Range 0-6, 0 is sunday
        
        Syntax for every field:
         - an asterix (*) enables every possible setting of a field
         - single numbers seperated by commas
         - a partition within the allowed range (1-5)
         - step size within an partition of the allowed range (0-59/2: every second minute)."
    ::= { wtWebioEA2x2ERPAlarmEntry 25 }      

wtWebioEA2x2ERPAlarmMailReleaseSubject OBJECT-TYPE
    SYNTAX OCTET STRING 
    ACCESS read-write
    STATUS mandatory
    DESCRIPTION
       "Subject line for alarm mail."
    ::= { wtWebioEA2x2ERPAlarmEntry 26 }

wtWebioEA2x2ERPAlarmMailReleaseText OBJECT-TYPE
    SYNTAX OCTET STRING 
    ACCESS read-write
    STATUS mandatory
    DESCRIPTION
        "Release Alarm mail text: 
        States of the Webio device can be included by using special tags.
        Please refer to the respective Webio manual"
    ::= { wtWebioEA2x2ERPAlarmEntry 27 }    

wtWebioEA2x2ERPAlarmSnmpTrapReleaseText OBJECT-TYPE
    SYNTAX OCTET STRING 
    ACCESS read-write
    STATUS mandatory
    DESCRIPTION
        "This text appears in the trap body."
    ::= { wtWebioEA2x2ERPAlarmEntry 28 }

wtWebioEA2x2ERPAlarmUdpReleaseText OBJECT-TYPE
    SYNTAX OCTET STRING 
    ACCESS read-write
    STATUS mandatory
    DESCRIPTION
        "This text appears in the UDP trap body."
    ::= { wtWebioEA2x2ERPAlarmEntry 29 }

wtWebioEA2x2ERPAlarmTcpReleaseText OBJECT-TYPE
    SYNTAX OCTET STRING 
    ACCESS read-write
    STATUS mandatory
    DESCRIPTION
        "This text appears in the TCP trap body."
    ::= { wtWebioEA2x2ERPAlarmEntry 30 }

wtWebioEA2x2ERPAlarmSyslogReleaseText OBJECT-TYPE
    SYNTAX OCTET STRING 
    ACCESS read-write
    STATUS mandatory
    DESCRIPTION
        "Every message starts with the priority key, a time stamp and the host ip address, according RFC3164.
        This text appears in the following syslog message body."
    ::= { wtWebioEA2x2ERPAlarmEntry 31 }

wtWebioEA2x2ERPAlarmFtpReleaseText OBJECT-TYPE
    SYNTAX OCTET STRING 
    ACCESS read-write
    STATUS mandatory
    DESCRIPTION
        "Message text to store on the FTP server."
    ::= { wtWebioEA2x2ERPAlarmEntry 32 }

-- wtWebioEA2x2ERPLoadControl
----------------------------

wtWebioEA2x2ERPLoadControlView OBJECT-TYPE
    SYNTAX OCTET STRING (SIZE(4))
    ACCESS read-only
    STATUS mandatory
    DESCRIPTION
        "Here the result of automatic load control can be read. All output were tested in 
        pairs (0-1). If an error occours at one output,
        both output of an pair will be switched of. For a properly function of the load control
        each output of a pair have to has a load. If there is no existing load, a pull down resistor
        can be used.
        Outputs with no load are automaticly detected and not part of the control function.
        The OCTETS are interpreted bit-by-bit, with each bit corresponding to an output. 
        Bit 0 corresponds to the LSB.
        Octet 1: unused
        Octet 2: unused
        Octet 3: unused
        Octet 4: 
	        Bit 0-1: outputs 0-1."
    ::= { wtWebioEA2x2ERPAlarm 4 }

wtWebioEA2x2ERPLCShutDownView OBJECT-TYPE
    SYNTAX OCTET STRING (SIZE(4))
    ACCESS read-write
    STATUS mandatory
    DESCRIPTION
        "Here the result of the automatic load control shut down can be read. All outputs remain switched of,
        until a zero is written into this variable. But previously all loads should be inspected.
        High current (short circuit), a broken supply line or a defect load (i.e. lamp) may be a shut down reason.
        If no load is detected, the load control unit suspend automaticly the control of the corresponding output pair.
        All controlled output could be identified reading the variable wtWebioEA2x2ERPLoadControlEnable.
        The OCTETS are interpreted bit-by-bit, with each bit corresponding to an ouput.
        Bit 0 corresponds to the LSB.
        
        Octet 1: unused
        Octet 2: unused
        Octet 3: unused
        Octet 4: Bit 0-1: outputs 0-1."
    ::= { wtWebioEA2x2ERPAlarm 5 }

-- wtWebioEA2x2ERPPorts Group
----------------------------

-- Input Port Table

wtWebioEA2x2ERPInputPortTable OBJECT-TYPE
    SYNTAX SEQUENCE OF WtWebioEA2x2ERPInputPortEntry
    ACCESS not-accessible
    STATUS mandatory
    DESCRIPTION
        "List of settings depending on the input number."
    ::= { wtWebioEA2x2ERPPorts 1 }

wtWebioEA2x2ERPInputPortEntry OBJECT-TYPE
    SYNTAX WtWebioEA2x2ERPInputPortEntry
    ACCESS not-accessible
    STATUS mandatory
    DESCRIPTION
        "Input parameter for the individual inputs."
    INDEX  { wtWebioEA2x2ERPInputNo }
    ::= { wtWebioEA2x2ERPInputPortTable 1 }

WtWebioEA2x2ERPInputPortEntry ::= SEQUENCE {
    wtWebioEA2x2ERPPortInputName			OCTET STRING,
    wtWebioEA2x2ERPPortInputText			OCTET STRING,
    wtWebioEA2x2ERPPortInputMode			OCTET STRING,
    wtWebioEA2x2ERPPortInputFilter			INTEGER,
    wtWebioEA2x2ERPPortInputBicountPulsePolarity	OCTET STRING,
    wtWebioEA2x2ERPPortInputBicountInactivTimeout	INTEGER
    
}

wtWebioEA2x2ERPPortInputName OBJECT-TYPE
    SYNTAX OCTET STRING 
    ACCESS read-write
    STATUS mandatory
    DESCRIPTION
        "Name of the input."
    ::= { wtWebioEA2x2ERPInputPortEntry 1 }

wtWebioEA2x2ERPPortInputText OBJECT-TYPE
    SYNTAX OCTET STRING 
    ACCESS read-write
    STATUS mandatory
    DESCRIPTION
        "Description of the input."
    ::= { wtWebioEA2x2ERPInputPortEntry 2 }

wtWebioEA2x2ERPPortInputMode OBJECT-TYPE
    SYNTAX OCTET STRING (SIZE(4))
    ACCESS read-write
    STATUS mandatory
    DESCRIPTION
        "Binary coded modes:
        Selecting short pulse detection enable by setting the corresponding bit to 1 enables 
        interrupt support for counting. Only positive edges are accepted as trigger 
        source. The maximum counting frequenz equals 2000 Hz.
        This mode is available for inputs 0-3 only.
        Selecting counter clear on read by setting the corresponding bit to 1 enables
        the corresponding counter to be cleared automatically every time it is read,
        except HTTP reading with user rights.
        The OCTETS are interpreted bit-by-bit,
        Bit 0 corresponds to the LSB.
        Selection for input 0-1:
        OCTET 1: unused
        OCTET 2: unused
        OCTET 3: unused
        OCTET 4, Bit 4-7: unused
		 Bit 3	: Bidirectional counter enable
        	 Bit 2  : Counter clear on read
        	 Bit 1  : Change detection enable (default)
        	 Bit 0  : Short Pulse detection enable"
    ::= { wtWebioEA2x2ERPInputPortEntry 3 }    
    
wtWebioEA2x2ERPPortInputFilter OBJECT-TYPE
    SYNTAX INTEGER 
    ACCESS read-write
    STATUS mandatory
    DESCRIPTION
        "Pulses with a duration shorter than here specified (duration in 1/1000 sec),
	are ignored."
    ::= { wtWebioEA2x2ERPInputPortEntry 4 }
    
wtWebioEA2x2ERPPortInputBicountPulsePolarity OBJECT-TYPE
    SYNTAX OCTET STRING (SIZE (4))
    ACCESS read-write
    STATUS mandatory
    DESCRIPTION
        "This value defines the polarity of the input pulse.
        OCTET 1: unused
        OCTET 2: unused
        OCTET 3: unused
        	OCTET 4: 
        	 Bit 0   : negative polarity
        	 Bit 1   : positive polarity
        	 Bit 2-7 : unused"
    ::= { wtWebioEA2x2ERPInputPortEntry 5 }

wtWebioEA2x2ERPPortInputBicountInactivTimeout OBJECT-TYPE
    SYNTAX INTEGER 
    ACCESS read-write
    STATUS mandatory
    DESCRIPTION
        "Pulse chains with a duration shorter than here specified (in 1/10 sek),
	are ignored."
    ::= { wtWebioEA2x2ERPInputPortEntry 6 }
        
-- Output Port Table

wtWebioEA2x2ERPOutputPortTable OBJECT-TYPE
    SYNTAX SEQUENCE OF WtWebioEA2x2ERPOutputPortEntry
    ACCESS not-accessible
    STATUS mandatory
    DESCRIPTION
        "List of settings depending on the output number."
    ::= { wtWebioEA2x2ERPPorts 2 }

wtWebioEA2x2ERPOutputPortEntry OBJECT-TYPE
    SYNTAX WtWebioEA2x2ERPOutputPortEntry
    ACCESS not-accessible
    STATUS mandatory
    DESCRIPTION
        "Output parameters of the individual outputs."
    INDEX  { wtWebioEA2x2ERPOutputNo }
    ::= { wtWebioEA2x2ERPOutputPortTable 1 }

WtWebioEA2x2ERPOutputPortEntry ::= SEQUENCE {
    wtWebioEA2x2ERPPortOutputName		OCTET STRING,
    wtWebioEA2x2ERPPortOutputText		OCTET STRING,
    wtWebioEA2x2ERPPortOutputGroupMode		OCTET STRING,
    wtWebioEA2x2ERPPortOutputSafetyState	OCTET STRING,
    wtWebioEA2x2ERPPortLogicInputMask		OCTET STRING,
    wtWebioEA2x2ERPPortLogicInputInverter	OCTET STRING,
    wtWebioEA2x2ERPPortLogicFunction		OCTET STRING,
    wtWebioEA2x2ERPPortLogicOutputInverter	OCTET STRING,
    wtWebioEA2x2ERPPortPulseDuration		INTEGER,
    wtWebioEA2x2ERPPortPulsePolarity		OCTET STRING
    
}

wtWebioEA2x2ERPPortOutputName OBJECT-TYPE
    SYNTAX OCTET STRING 
    ACCESS read-write
    STATUS mandatory
    DESCRIPTION
        "Name of the output."
    ::= { wtWebioEA2x2ERPOutputPortEntry 1 }

wtWebioEA2x2ERPPortOutputText OBJECT-TYPE
    SYNTAX OCTET STRING 
    ACCESS read-write
    STATUS mandatory
    DESCRIPTION
        "Description of the output."
    ::= { wtWebioEA2x2ERPOutputPortEntry 2 }

wtWebioEA2x2ERPPortOutputGroupMode OBJECT-TYPE
    SYNTAX OCTET STRING 
    ACCESS read-write
    STATUS mandatory
    DESCRIPTION
        "It is possible to connect outputs together to increase the output current.
        This could be done by connecting 2 or 4 outputs in a group together. All bits
        of such a group has to be set all together in the same way. This variable
        configures this group scheme. If one ouput bit of a group is set, all other 
        output bits of the same group will be set in the same manner.
        More than one configuration must not be selected.
	Selection for ouputs 0-1:
        Octet 1: unused
        Octet 2: unused
        Octet 3: unused
        OCTET 4: Bit 0   : ouputs 0,1 disconnected (default)
        	 Bit 1   : ouputs 0+1 connected"
    ::= { wtWebioEA2x2ERPOutputPortEntry 3 }

wtWebioEA2x2ERPPortOutputSafetyState OBJECT-TYPE
    SYNTAX OCTET STRING 
    ACCESS read-write
    STATUS mandatory
    DESCRIPTION
        "This variable allows setting of individual digital outputs. The OCTETS are 
        interpreted bit-by-bit, with each bit corresponding to an output. Bit 0 corresponds 
        to the LSB.
        The first four OCTETS contain the mask which determines which of the outputs are to 
        be set (corresponding bit = 1) and which outputs are to remain unchanged 
        (corresponding bit = 0):
        OCTET 1		: unused
        OCTET 2		: unused
        OCTET 3		: unused
        OCTET 4, Bit 1-7: unused
        	 Bit 0	: Mask for digital output
        OCTETS 5-8 contain the level (1=HIGH, 0=LOW) which the outputs to be changed 
        should assume:
        OCTET 5		: unused
        OCTET 6		: unused
        OCTET 7		: unused
        OCTET 8, Bit 1-7: unused
        	 Bit 0  : Level of digital output"
    ::= { wtWebioEA2x2ERPOutputPortEntry 4 }

wtWebioEA2x2ERPPortLogicInputMask OBJECT-TYPE
    SYNTAX OCTET STRING (SIZE (4))
    ACCESS read-write
    STATUS mandatory
    DESCRIPTION
        "Selecting one of these inputs by setting the corresponding bit to 1 
        enables the logic function for the output identified by the index within 
        this table. The calculation take place in 4 steps:
        1. Selecting inputs				(wtWebioEA2x2ERPPortLogicInputMask)
        2. Inverting inputs if necessary	(wtWebioEA2x2ERPPortLogicInputInverter)
        3. Logical combination				(wtWebioEA2x2ERPPortLogicFunction)
        4. Inverting the result if necessary	(wtWebioEA2x2ERPPortLogicOutputInverter)
        OCTET 1: unused
        OCTET 2: unused
        OCTET 3: unused
        OCTET 4: Bit 0-1 : inputs 0-1"
    ::= { wtWebioEA2x2ERPOutputPortEntry 5 }

wtWebioEA2x2ERPPortLogicInputInverter OBJECT-TYPE
    SYNTAX OCTET STRING (SIZE (4))
    ACCESS read-write
    STATUS mandatory
    DESCRIPTION
        "Every input bit selected here will be inverted.
        OCTET 1: unused
        OCTET 2: unused
        OCTET 3: unused
        OCTET 4: Bit 0-1 : inputs 0-1"
    ::= { wtWebioEA2x2ERPOutputPortEntry 6 }

wtWebioEA2x2ERPPortLogicFunction OBJECT-TYPE
    SYNTAX OCTET STRING (SIZE (4))
    ACCESS read-write
    STATUS mandatory
    DESCRIPTION
        "This determines the logic function. No more than one function
        may be selected.
        OCTET 1: unused
        OCTET 2: unused
        OCTET 3: unused
        OCTET 4: 
        	 Bit 0   : logic function OR (default)
        	 Bit 1   : logic function AND
        	 Bit 2-7 : unused"
    ::= { wtWebioEA2x2ERPOutputPortEntry 7 }

wtWebioEA2x2ERPPortLogicOutputInverter OBJECT-TYPE
    SYNTAX OCTET STRING (SIZE (4))
    ACCESS read-write
    STATUS mandatory
    DESCRIPTION
        "The logical operation result could be inverteted by setting the corresponding
        bit to 1.
        OCTET 1: unused
        OCTET 2: unused
        OCTET 3: unused
        	OCTET 4: 
        	 Bit 0   : Output Inverter enable
        	 Bit 1-7 : unused"
    ::= { wtWebioEA2x2ERPOutputPortEntry 8 }

wtWebioEA2x2ERPPortPulseDuration OBJECT-TYPE
    SYNTAX INTEGER
    ACCESS read-write
    STATUS mandatory
    DESCRIPTION
        "Pulse length in 1/1000 sec. Setting this value to zero, disables the pulse output."
    ::= { wtWebioEA2x2ERPOutputPortEntry 9 }

wtWebioEA2x2ERPPortPulsePolarity OBJECT-TYPE
    SYNTAX OCTET STRING (SIZE (4))
    ACCESS read-write
    STATUS mandatory
    DESCRIPTION
        "This value defines the polarity of the output pulse, if wtWebioEA2x2ERPPortPulseDuration is not set to zero.
        After the pulse is finished, the output switches back to the opposite state.
        OCTET 1: unused
        OCTET 2: unused
        OCTET 3: unused
        	OCTET 4: 
        	 Bit 0   : negative polarity
        	 Bit 1   : positive polarity
        	 Bit 2-7 : unused"
    ::= { wtWebioEA2x2ERPOutputPortEntry 10 }

-- wtWebioEA2x2ERPManufact Group
----------------------------

wtWebioEA2x2ERPMfName OBJECT-TYPE
    SYNTAX OCTET STRING 
    ACCESS read-write
    STATUS mandatory
    DESCRIPTION
        "Manufacturer company name"
    ::= { wtWebioEA2x2ERPManufact 1 }

wtWebioEA2x2ERPMfAddr OBJECT-TYPE
    SYNTAX OCTET STRING 
    ACCESS read-write
    STATUS mandatory
    DESCRIPTION
        "Manufacturer address."
    ::= { wtWebioEA2x2ERPManufact 2 }

wtWebioEA2x2ERPMfHotline OBJECT-TYPE
    SYNTAX OCTET STRING 
    ACCESS read-write
    STATUS mandatory
    DESCRIPTION
        "Manufacturer hotline."
    ::= { wtWebioEA2x2ERPManufact 3 }

wtWebioEA2x2ERPMfInternet OBJECT-TYPE
    SYNTAX OCTET STRING 
    ACCESS read-write
    STATUS mandatory
    DESCRIPTION
        "Manufacturer Internet address."
    ::= { wtWebioEA2x2ERPManufact 4 }

wtWebioEA2x2ERPMfDeviceTyp OBJECT-TYPE
    SYNTAX OCTET STRING 
    ACCESS read-write
    STATUS mandatory
    DESCRIPTION
        "Manufacturer device name (model number)."
    ::= { wtWebioEA2x2ERPManufact 5 }

-- wtWebioEA2x2ERPDiag Group
----------------------------

wtWebioEA2x2ERPDiagErrorCount OBJECT-TYPE
    SYNTAX INTEGER
    ACCESS read-only
    STATUS mandatory
    DESCRIPTION
        "Number of entries in the error memory."
    ::= { wtWebioEA2x2ERPDiag 1 }

wtWebioEA2x2ERPDiagBinaryError OBJECT-TYPE
    SYNTAX OCTET STRING 
    ACCESS read-only
    STATUS mandatory
    DESCRIPTION
        "Error causes coded bit-by-bit."
    ::= { wtWebioEA2x2ERPDiag 2 }

wtWebioEA2x2ERPDiagErrorIndex OBJECT-TYPE
    SYNTAX INTEGER
    ACCESS read-write
    STATUS mandatory
    DESCRIPTION
        "The value of this variable is used as an index to read 
        an error massege from wtWebioEA2x2ERPDiagErrorMessage.
        Errors are numbered from 1 to wtWebioEA2x2ERPDiagErrorCount.
        Writing a valid value into this variable, making the appropriate 
        message readable from wtWebioEA2x2ERPDiagErrorMessage."
    ::= { wtWebioEA2x2ERPDiag 3 }

wtWebioEA2x2ERPDiagErrorMessage OBJECT-TYPE
    SYNTAX OCTET STRING 
    ACCESS read-only
    STATUS mandatory
    DESCRIPTION
        "Using wtWebioEA2x2ERPDiagErrorIndex as an index, the appropriate message is available."
    ::= { wtWebioEA2x2ERPDiag 4 }
    
wtWebioEA2x2ERPDiagErrorClear OBJECT-TYPE
    SYNTAX INTEGER
    ACCESS write-only
    STATUS mandatory
    DESCRIPTION
        "Writing 1 into this variable clears all diagnosis messages."
    ::= { wtWebioEA2x2ERPDiag 5 }


-- TRAP DEFINITIONS

-- Diese SNMP-Traps werden gesendet, wenn die Alarmtriggerbedingungen zutreffen 

wtWebioEA2x2ERPAlert1 TRAP-TYPE
    ENTERPRISE  wtWebioEA2x2ERP
    VARIABLES   { wtWebioEA2x2ERPAlarmSnmpTrapText }
    DESCRIPTION
        "This SNMP trap is generated when Alarm 1 was triggered,
        SNMP trap enable is set and
        SNMP is enabled."
    -- NMS trap annotation
    --#TYPE "Webio Digital Alarm 1"
    --#SUMMARY "Alarm 1: %s"
    --#ARGUMENTS {0}
    --#SEVERITY INFORMATIONAL
    --#TIMEINDEX 99
    --#STATE OPERATIONAL    
    ::= 41

wtWebioEA2x2ERPAlert2 TRAP-TYPE
    ENTERPRISE  wtWebioEA2x2ERP
    VARIABLES   { wtWebioEA2x2ERPAlarmSnmpTrapText }
    DESCRIPTION
        "This SNMP trap is generated when Alarm 2 was triggered,
        SNMP trap enable is set and
        SNMP is enabled."
    -- NMS trap annotation
    --#TYPE "Webio Digital Alarm 2"
    --#SUMMARY "Alarm 2: %s"
    --#ARGUMENTS {0}
    --#SEVERITY INFORMATIONAL
    --#TIMEINDEX 99
    --#STATE OPERATIONAL    
    ::= 42

wtWebioEA2x2ERPAlert3 TRAP-TYPE
    ENTERPRISE  wtWebioEA2x2ERP
    VARIABLES   { wtWebioEA2x2ERPAlarmSnmpTrapText }
    DESCRIPTION
        "This SNMP trap is generated when Alarm 3 was triggered,
        SNMP trap enable is set and
        SNMP is enabled."
    -- NMS trap annotation
    --#TYPE "Webio Digital Alarm 3"
    --#SUMMARY "Alarm 3: %s"
    --#ARGUMENTS {0}
    --#SEVERITY INFORMATIONAL
    --#TIMEINDEX 99
    --#STATE OPERATIONAL    
    ::= 43

wtWebioEA2x2ERPAlert4 TRAP-TYPE
    ENTERPRISE  wtWebioEA2x2ERP
    VARIABLES   { wtWebioEA2x2ERPAlarmSnmpTrapText }
    DESCRIPTION
        "This SNMP trap is generated when Alarm 4 was triggered,
        SNMP trap enable is set and
        SNMP is enabled."
    -- NMS trap annotation
    --#TYPE "Webio Digital Alarm 4"
    --#SUMMARY "Alarm 4: %s"
    --#ARGUMENTS {0}
    --#SEVERITY INFORMATIONAL
    --#TIMEINDEX 99
    --#STATE OPERATIONAL    
    ::= 44

wtWebioEA2x2ERPAlert5 TRAP-TYPE
    ENTERPRISE  wtWebioEA2x2ERP
    VARIABLES   { wtWebioEA2x2ERPAlarmSnmpTrapText }
    DESCRIPTION
        "This SNMP trap is generated when Alarm 5 was triggered,
        SNMP trap enable is set and
        SNMP is enabled."
    -- NMS trap annotation
    --#TYPE "Webio Digital Alarm 5"
    --#SUMMARY "Alarm 5: %s"
    --#ARGUMENTS {0}
    --#SEVERITY INFORMATIONAL
    --#TIMEINDEX 99
    --#STATE OPERATIONAL    
    ::= 45

wtWebioEA2x2ERPAlert6 TRAP-TYPE
    ENTERPRISE  wtWebioEA2x2ERP
    VARIABLES   { wtWebioEA2x2ERPAlarmSnmpTrapText }
    DESCRIPTION
        "This SNMP trap is generated when Alarm 6 was triggered,
        SNMP trap enable is set and
        SNMP is enabled."
    -- NMS trap annotation
    --#TYPE "Webio Digital Alarm 6"
    --#SUMMARY "Alarm 6: %s"
    --#ARGUMENTS {0}
    --#SEVERITY INFORMATIONAL
    --#TIMEINDEX 99
    --#STATE OPERATIONAL    
    ::= 46

wtWebioEA2x2ERPAlert7 TRAP-TYPE
    ENTERPRISE  wtWebioEA2x2ERP
    VARIABLES   { wtWebioEA2x2ERPAlarmSnmpTrapText }
    DESCRIPTION
        "This SNMP trap is generated when Alarm 7 was triggered,
        SNMP trap enable is set and
        SNMP is enabled."
    -- NMS trap annotation
    --#TYPE "Webio Digital Alarm 7"
    --#SUMMARY "Alarm 7: %s"
    --#ARGUMENTS {0}
    --#SEVERITY INFORMATIONAL
    --#TIMEINDEX 99
    --#STATE OPERATIONAL    
    ::= 47

wtWebioEA2x2ERPAlert8 TRAP-TYPE
    ENTERPRISE  wtWebioEA2x2ERP
    VARIABLES   { wtWebioEA2x2ERPAlarmSnmpTrapText }
    DESCRIPTION
        "This SNMP trap is generated when Alarm 8 was triggered,
        SNMP trap enable is set and
        SNMP is enabled."
    -- NMS trap annotation
    --#TYPE "Webio Digital Alarm 8"
    --#SUMMARY "Alarm 8: %s"
    --#ARGUMENTS {0}
    --#SEVERITY INFORMATIONAL
    --#TIMEINDEX 99
    --#STATE OPERATIONAL    
    ::= 48

wtWebioEA2x2ERPAlert9 TRAP-TYPE
    ENTERPRISE  wtWebioEA2x2ERP
    VARIABLES   { wtWebioEA2x2ERPAlarmSnmpTrapText }
    DESCRIPTION
        "This SNMP trap is generated when Alarm 9 was triggered,
        SNMP trap enable is set and
        SNMP is enabled."
    -- NMS trap annotation
    --#TYPE "Webio Digital Alarm 9"
    --#SUMMARY "Alarm 9: %s"
    --#ARGUMENTS {0}
    --#SEVERITY INFORMATIONAL
    --#TIMEINDEX 99
    --#STATE OPERATIONAL    
    ::= 49

wtWebioEA2x2ERPAlert10 TRAP-TYPE
    ENTERPRISE  wtWebioEA2x2ERP
    VARIABLES   { wtWebioEA2x2ERPAlarmSnmpTrapText }
    DESCRIPTION
        "This SNMP trap is generated when Alarm 10 was triggered,
        SNMP trap enable is set and
        SNMP is enabled."
    -- NMS trap annotation
    --#TYPE "Webio Digital Alarm 10"
    --#SUMMARY "Alarm 10: %s"
    --#ARGUMENTS {0}
    --#SEVERITY INFORMATIONAL
    --#TIMEINDEX 99
    --#STATE OPERATIONAL    
    ::= 50

wtWebioEA2x2ERPAlert11 TRAP-TYPE
    ENTERPRISE  wtWebioEA2x2ERP
    VARIABLES   { wtWebioEA2x2ERPAlarmSnmpTrapText }
    DESCRIPTION
        "This SNMP trap is generated when Alarm 11 was triggered,
        SNMP trap enable is set and
        SNMP is enabled."
    -- NMS trap annotation
    --#TYPE "Webio Digital Alarm 11"
    --#SUMMARY "Alarm 11: %s"
    --#ARGUMENTS {0}
    --#SEVERITY INFORMATIONAL
    --#TIMEINDEX 99
    --#STATE OPERATIONAL    
    ::= 51

wtWebioEA2x2ERPAlert12 TRAP-TYPE
    ENTERPRISE  wtWebioEA2x2ERP
    VARIABLES   { wtWebioEA2x2ERPAlarmSnmpTrapText }
    DESCRIPTION
        "This SNMP trap is generated when Alarm 12 was triggered,
        SNMP trap enable is set and
        SNMP is enabled."
    -- NMS trap annotation
    --#TYPE "Webio Digital Alarm 12"
    --#SUMMARY "Alarm 12: %s"
    --#ARGUMENTS {0}
    --#SEVERITY INFORMATIONAL
    --#TIMEINDEX 99
    --#STATE OPERATIONAL    
    ::= 52

wtWebioEA2x2ERPAlert13 TRAP-TYPE
    ENTERPRISE  wtWebioEA2x2ERP
    VARIABLES   { wtWebioEA2x2ERPAlarmSnmpTrapReleaseText }
    DESCRIPTION
        "This SNMP trap is generated when Alarm 1 was released,
        SNMP trap enable is set and
        SNMP is enabled."
    -- NMS trap annotation
    --#TYPE "Webio Digital Release Alarm 1"
    --#SUMMARY "Release Alarm 1: %s"
    --#ARGUMENTS {0}
    --#SEVERITY INFORMATIONAL
    --#TIMEINDEX 99
    --#STATE OPERATIONAL    
    ::= 71

wtWebioEA2x2ERPAlert14 TRAP-TYPE
    ENTERPRISE  wtWebioEA2x2ERP
    VARIABLES   { wtWebioEA2x2ERPAlarmSnmpTrapReleaseText }
    DESCRIPTION
        "This SNMP trap is generated when Alarm 2 was released,
        SNMP trap enable is set and
        SNMP is enabled."
    -- NMS trap annotation
    --#TYPE "Webio Digital Release Alarm 2"
    --#SUMMARY "Release Alarm 2: %s"
    --#ARGUMENTS {0}
    --#SEVERITY INFORMATIONAL
    --#TIMEINDEX 99
    --#STATE OPERATIONAL    
    ::= 72

wtWebioEA2x2ERPAlert15 TRAP-TYPE
    ENTERPRISE  wtWebioEA2x2ERP
    VARIABLES   { wtWebioEA2x2ERPAlarmSnmpTrapReleaseText }
    DESCRIPTION
        "This SNMP trap is generated when Alarm 3 was released,
        SNMP trap enable is set and
        SNMP is enabled."
    -- NMS trap annotation
    --#TYPE "Webio Digital Release Alarm 3"
    --#SUMMARY "Release Alarm 3: %s"
    --#ARGUMENTS {0}
    --#SEVERITY INFORMATIONAL
    --#TIMEINDEX 99
    --#STATE OPERATIONAL    
    ::= 73

wtWebioEA2x2ERPAlert16 TRAP-TYPE
    ENTERPRISE  wtWebioEA2x2ERP
    VARIABLES   { wtWebioEA2x2ERPAlarmSnmpTrapReleaseText }
    DESCRIPTION
        "This SNMP trap is generated when Alarm 4 was released,
        SNMP trap enable is set and
        SNMP is enabled."
    -- NMS trap annotation
    --#TYPE "Webio Digital Release Alarm 4"
    --#SUMMARY "Release Alarm 4: %s"
    --#ARGUMENTS {0}
    --#SEVERITY INFORMATIONAL
    --#TIMEINDEX 99
    --#STATE OPERATIONAL    
    ::= 74

wtWebioEA2x2ERPAlert17 TRAP-TYPE
    ENTERPRISE  wtWebioEA2x2ERP
    VARIABLES   { wtWebioEA2x2ERPAlarmSnmpTrapReleaseText }
    DESCRIPTION
        "This SNMP trap is generated when Alarm 5 was released,
        SNMP trap enable is set and
        SNMP is enabled."
    -- NMS trap annotation
    --#TYPE "Webio Digital Release Alarm 5"
    --#SUMMARY "Release Alarm 5: %s"
    --#ARGUMENTS {0}
    --#SEVERITY INFORMATIONAL
    --#TIMEINDEX 99
    --#STATE OPERATIONAL    
    ::= 75

wtWebioEA2x2ERPAlert18 TRAP-TYPE
    ENTERPRISE  wtWebioEA2x2ERP
    VARIABLES   { wtWebioEA2x2ERPAlarmSnmpTrapReleaseText }
    DESCRIPTION
        "This SNMP trap is generated when Alarm 6 was released,
        SNMP trap enable is set and
        SNMP is enabled."
    -- NMS trap annotation
    --#TYPE "Webio Digital Release Alarm 6"
    --#SUMMARY "Release Alarm 6: %s"
    --#ARGUMENTS {0}
    --#SEVERITY INFORMATIONAL
    --#TIMEINDEX 99
    --#STATE OPERATIONAL    
    ::= 76

wtWebioEA2x2ERPAlert19 TRAP-TYPE
    ENTERPRISE  wtWebioEA2x2ERP
    VARIABLES   { wtWebioEA2x2ERPAlarmSnmpTrapReleaseText }
    DESCRIPTION
        "This SNMP trap is generated when Alarm 7 was released,
        SNMP trap enable is set and
        SNMP is enabled."
    -- NMS trap annotation
    --#TYPE "Webio Digital Release Alarm 7"
    --#SUMMARY "Release Alarm 7: %s"
    --#ARGUMENTS {0}
    --#SEVERITY INFORMATIONAL
    --#TIMEINDEX 99
    --#STATE OPERATIONAL    
    ::= 77

wtWebioEA2x2ERPAlert20 TRAP-TYPE
    ENTERPRISE  wtWebioEA2x2ERP
    VARIABLES   { wtWebioEA2x2ERPAlarmSnmpTrapReleaseText }
    DESCRIPTION
        "This SNMP trap is generated when Alarm 8 was released,
        SNMP trap enable is set and
        SNMP is enabled."
    -- NMS trap annotation
    --#TYPE "Webio Digital Release Alarm 8"
    --#SUMMARY "Release Alarm 8: %s"
    --#ARGUMENTS {0}
    --#SEVERITY INFORMATIONAL
    --#TIMEINDEX 99
    --#STATE OPERATIONAL    
    ::= 78

wtWebioEA2x2ERPAlert21 TRAP-TYPE
    ENTERPRISE  wtWebioEA2x2ERP
    VARIABLES   { wtWebioEA2x2ERPAlarmSnmpTrapReleaseText }
    DESCRIPTION
        "This SNMP trap is generated when Alarm 9 was released,
        SNMP trap enable is set and
        SNMP is enabled."
    -- NMS trap annotation
    --#TYPE "Webio Digital Release Alarm 9"
    --#SUMMARY "Release Alarm 9: %s"
    --#ARGUMENTS {0}
    --#SEVERITY INFORMATIONAL
    --#TIMEINDEX 99
    --#STATE OPERATIONAL    
    ::= 79

wtWebioEA2x2ERPAlert22 TRAP-TYPE
    ENTERPRISE  wtWebioEA2x2ERP
    VARIABLES   { wtWebioEA2x2ERPAlarmSnmpTrapReleaseText }
    DESCRIPTION
        "This SNMP trap is generated when Alarm 10 was released,
        SNMP trap enable is set and
        SNMP is enabled."
    -- NMS trap annotation
    --#TYPE "Webio Digital Release Alarm 10"
    --#SUMMARY "Release Alarm 10: %s"
    --#ARGUMENTS {0}
    --#SEVERITY INFORMATIONAL
    --#TIMEINDEX 99
    --#STATE OPERATIONAL    
    ::= 80

wtWebioEA2x2ERPAlert23 TRAP-TYPE
    ENTERPRISE  wtWebioEA2x2ERP
    VARIABLES   { wtWebioEA2x2ERPAlarmSnmpTrapReleaseText }
    DESCRIPTION
        "This SNMP trap is generated when Alarm 11 was released,
        SNMP trap enable is set and
        SNMP is enabled."
    -- NMS trap annotation
    --#TYPE "Webio Digital Release Alarm 11"
    --#SUMMARY "Release Alarm 11: %s"
    --#ARGUMENTS {0}
    --#SEVERITY INFORMATIONAL
    --#TIMEINDEX 99
    --#STATE OPERATIONAL    
    ::= 81

wtWebioEA2x2ERPAlert24 TRAP-TYPE
    ENTERPRISE  wtWebioEA2x2ERP
    VARIABLES   { wtWebioEA2x2ERPAlarmSnmpTrapReleaseText }
    DESCRIPTION
        "This SNMP trap is generated when Alarm 12 was released,
        SNMP trap enable is set and
        SNMP is enabled."
    -- NMS trap annotation
    --#TYPE "Webio Digital Release Alarm 12"
    --#SUMMARY "Release Alarm 12: %s"
    --#ARGUMENTS {0}
    --#SEVERITY INFORMATIONAL
    --#TIMEINDEX 99
    --#STATE OPERATIONAL    
    ::= 82

wtWebioEA2x2ERPAlertDiag TRAP-TYPE
    ENTERPRISE  wtWebioEA2x2ERP
    VARIABLES   { 	
    		wtWebioEA2x2ERPDiagErrorIndex,
    	  	wtWebioEA2x2ERPDiagErrorMessage
    		}
    DESCRIPTION
        "This SNMP trap is generated when a diagnosis/error message was triggered,
        SNMP trap enable is set and
        SNMP is enabled."
    -- NMS trap annotation
    --#TYPE "Webio Digital Diagnose Error"
    --#SUMMARY "Diagnose error index: %d, Message: %s."
    --#ARGUMENTS {0,1}
    --#SEVERITY MAJOR
    --#TIMEINDEX 99
    --#STATE DEGRADED    
    ::= 110

--------------------------------------------------------------------------------
--------------------------------------------------------------------------------
--------------------------------------------------------------------------------

-- wtWebioEA12x6RelERPInOut Group
------------------------

wtWebioEA12x6RelERPInputs OBJECT-TYPE
    SYNTAX INTEGER (1..12)
    ACCESS read-only
    STATUS mandatory
    DESCRIPTION
        "Number of idependent inputs."
    ::= { wtWebioEA12x6RelERPInOut 1 }

wtWebioEA12x6RelERPOutputs OBJECT-TYPE
    SYNTAX INTEGER (1..6)
    ACCESS read-only
    STATUS mandatory
    DESCRIPTION
        "Number of independent outputs."
    ::= { wtWebioEA12x6RelERPInOut 2 }

-- Input Interface Table

wtWebioEA12x6RelERPInputTable OBJECT-TYPE
    SYNTAX SEQUENCE OF WtWebioEA12x6RelERPInputEntry
    ACCESS not-accessible
    STATUS mandatory
    DESCRIPTION
        "List of input indices."
    ::= { wtWebioEA12x6RelERPInOut 3 }

wtWebioEA12x6RelERPInputEntry OBJECT-TYPE
    SYNTAX WtWebioEA12x6RelERPInputEntry
    ACCESS not-accessible
    STATUS mandatory
    DESCRIPTION
        "Number of the inputs."
    INDEX  { wtWebioEA12x6RelERPInputNo }
    ::= { wtWebioEA12x6RelERPInputTable 1 }

WtWebioEA12x6RelERPInputEntry ::= SEQUENCE {
    wtWebioEA12x6RelERPInputNo 			INTEGER,
    wtWebioEA12x6RelERPInputCounter 		INTEGER,
    wtWebioEA12x6RelERPInputCounterClear 	INTEGER
}

wtWebioEA12x6RelERPInputNo OBJECT-TYPE
    SYNTAX INTEGER (1)
    ACCESS read-only
    STATUS mandatory
    DESCRIPTION
        "Index numbers of the inputs."
    ::= { wtWebioEA12x6RelERPInputEntry 1 }

wtWebioEA12x6RelERPInputCounter OBJECT-TYPE
    SYNTAX INTEGER (1)
    ACCESS read-only
    STATUS mandatory
    DESCRIPTION
        "Value of the input counter."
    ::= { wtWebioEA12x6RelERPInputEntry 2 }
    
wtWebioEA12x6RelERPInputCounterClear OBJECT-TYPE
    SYNTAX INTEGER
    ACCESS read-only
    STATUS mandatory
    DESCRIPTION
        "Clears the input counter after returning its value."
    ::= { wtWebioEA12x6RelERPInputEntry 3 }
    
wtWebioEA12x6RelERPInputValue OBJECT-TYPE
    SYNTAX INTEGER 
    ACCESS read-only
    STATUS mandatory
    DESCRIPTION
        "This variable is used to read the inputs of the digital I/O port.
        The OCTETS are interpreted bit-by-bit, with each bit corresponding to an input.
        Bit 0 corresponds to the LSB.
        OCTET 1: unused
        OCTET 2: unused
        OCTET 3, Bit 0-3: Digital inputs 8-11
                 Bit 4-7: unused
        OCTET 4, Bit 0-7: Digital inputs 0-7"
    ::= { wtWebioEA12x6RelERPInOut 4 }
    

-- Output Interface Table

wtWebioEA12x6RelERPOutputTable OBJECT-TYPE
    SYNTAX SEQUENCE OF WtWebioEA12x6RelERPOutputEntry
    ACCESS not-accessible
    STATUS mandatory
    DESCRIPTION
        "List of output indices."
    ::= { wtWebioEA12x6RelERPInOut 5 }

wtWebioEA12x6RelERPOutputEntry OBJECT-TYPE
    SYNTAX WtWebioEA12x6RelERPOutputEntry
    ACCESS not-accessible
    STATUS mandatory
    DESCRIPTION
        "Number of the outputs."
    INDEX  { wtWebioEA12x6RelERPOutputNo }
    ::= { wtWebioEA12x6RelERPOutputTable 1 }

WtWebioEA12x6RelERPOutputEntry ::= SEQUENCE {
    wtWebioEA12x6RelERPOutputNo 	INTEGER,
    wtWebioEA12x6RelERPOutputState	INTEGER
}

wtWebioEA12x6RelERPOutputNo OBJECT-TYPE
    SYNTAX INTEGER (1)
    ACCESS read-only
    STATUS mandatory
    DESCRIPTION
        "Output number."
    ::= { wtWebioEA12x6RelERPOutputEntry 1 }
    
wtWebioEA12x6RelERPOutputState OBJECT-TYPE
    SYNTAX INTEGER{
    wtWebioEA12x6RelERPOutputState-OFF(0),
    wtWebioEA12x6OutputState-ON(1)
    }
    ACCESS read-write
    STATUS mandatory
    DESCRIPTION
        "Setting and reading of the states of the outputs."
    ::= { wtWebioEA12x6RelERPOutputEntry 2 }    

wtWebioEA12x6RelERPOutputValue OBJECT-TYPE
    SYNTAX INTEGER
    ACCESS read-write
    STATUS mandatory
    DESCRIPTION
        "This variable is used to read and write the outputs of the digital I/O port. 
        The OCTETS are interpreted bit-by-bit, with each bit corresponding to an output. 
        Bit 0 corresponds to the LSB.
        OCTET 1: unused
        OCTET 2: unused
        OCTET 3: unused
        OCTET 4: Bit 0-5: Digital outputs 0-5"
    ::= { wtWebioEA12x6RelERPInOut 6 }
    
wtWebioEA12x6RelERPSetOutput OBJECT-TYPE
    SYNTAX OCTET STRING (SIZE (8))
    ACCESS read-write			-- write-only
    STATUS mandatory
    DESCRIPTION
        "This variable allows setting of individual digital outputs. The OCTETS are 
        interpreted bit-by-bit, with each bit corresponding to an output. Bit 0 corresponds 
        to the LSB.
        The first two OCTETS contain the mask which determines which of the outputs are to 
        be set (corresponding bit = 1) and which outputs are to remain unchanged 
        (corresponding bit = 0):
	OCTET 1 : unused
	OCTET 2 : unused
	OCTET 3 : unused
	OCTET 4 : Bit 0-5: Mask for digital outputs 0-5
	
	OCTETS 5-8 contain the level (1=HIGH, 0=LOW) which the inputs 
	should assume:
	OCTET 5 : unused
	OCTET 6 : unused
	OCTET 7 : unused
        OCTET 8 : Bit 0-5: Level of digital outputs 0-5"
    ::= { wtWebioEA12x6RelERPInOut 7 }
    
-- wtWebioEA12x6RelERPSessCntrl Group
--------------------------------

wtWebioEA12x6RelERPSessCntrlPassword OBJECT-TYPE
    SYNTAX OCTET STRING 
    ACCESS read-write
    STATUS mandatory
    DESCRIPTION
        "Entering this password opens a session which is ended by writing a 1 to 
        wtWebioEA12x6RelERPSessCntrlLogout. When read this variable provides a string of
        length zero."
    ::= { wtWebioEA12x6RelERPSessCntrl 1 }

wtWebioEA12x6RelERPSessCntrlConfigMode OBJECT-TYPE
    SYNTAX INTEGER {
    wtWebioEA12x6RelERPSessCntrl-NoSession(0),
    wtWebioEA12x6RelERPSessCntrl-Session(1)
    }
    ACCESS read-only
    STATUS mandatory
    DESCRIPTION
        "When the device is in SNMP configuration mode, the value 1 is
        returned, otherwise 0. If the read value is 0 even though the password
        was written, the device is already in config mode and the variables
        can only be read."
    ::= { wtWebioEA12x6RelERPSessCntrl 2 }

wtWebioEA12x6RelERPSessCntrlLogout OBJECT-TYPE
    SYNTAX INTEGER 
    ACCESS read-write
    STATUS mandatory
    DESCRIPTION
        "If the device is in configuration mode and the session was opened by
        this SNMP Manager, writing a 1 to this variable will end the session 
        and all parameters are stored.
        Writing a 2 discards all entries again. When read this variable
        provides the value 0."
    ::= { wtWebioEA12x6RelERPSessCntrl 3 }

wtWebioEA12x6RelERPSessCntrlAdminPassword OBJECT-TYPE
    SYNTAX OCTET STRING 
    ACCESS read-write
    STATUS mandatory
    DESCRIPTION
        "This password protects access to the variables with administrator rights.
        It can only be changed by the administrator. If no password was assigned,
        the valid password is public."
    ::= { wtWebioEA12x6RelERPSessCntrl 4 }

wtWebioEA12x6RelERPSessCntrlConfigPassword OBJECT-TYPE
    SYNTAX OCTET STRING 
    ACCESS read-write
    STATUS mandatory
    DESCRIPTION
        "This password protects access to the variables with configurator rights. It can
        be changed by the administrator and by the configurator. If no password was assigned, 
        the valid password is public. When read this variable provides a null-pointer."
    ::= { wtWebioEA12x6RelERPSessCntrl 5 }
    
-- wtWebioEA12x6RelERPText Group
------------------------

wtWebioEA12x6RelERPDeviceName OBJECT-TYPE
    SYNTAX OCTET STRING 
    ACCESS read-write
    STATUS mandatory
    DESCRIPTION
        "Name of the Webio, which is user definable."
    ::= { wtWebioEA12x6RelERPText 1 }

wtWebioEA12x6RelERPDeviceText OBJECT-TYPE
    SYNTAX OCTET STRING 
    ACCESS read-write
    STATUS mandatory
    DESCRIPTION
        "Description of the Webio, which is user definable."
    ::= { wtWebioEA12x6RelERPText 2 }
    
wtWebioEA12x6RelERPDeviceLocation OBJECT-TYPE
    SYNTAX OCTET STRING 
    ACCESS read-write
    STATUS mandatory
    DESCRIPTION
        "Description of the location of the Webio, which is user definable."
    ::= { wtWebioEA12x6RelERPText 3 }

wtWebioEA12x6RelERPDeviceContact OBJECT-TYPE
    SYNTAX OCTET STRING 
    ACCESS read-write
    STATUS mandatory
    DESCRIPTION
        "Contact address of the system operator of the Webio, which is user definable."
    ::= { wtWebioEA12x6RelERPText 4 }    

-- wtWebioEA12x6RelERPTimeZone Group
----------------------------

wtWebioEA12x6RelERPTzOffsetHrs OBJECT-TYPE
    SYNTAX INTEGER 
    ACCESS read-write
    STATUS mandatory
    DESCRIPTION
        "Offset hours for the time zone (winter time) with respect to UTC."
    ::= { wtWebioEA12x6RelERPTimeZone 1 }

wtWebioEA12x6RelERPTzOffsetMin OBJECT-TYPE
    SYNTAX INTEGER 
    ACCESS read-write
    STATUS mandatory
    DESCRIPTION
        "Offset minutes for the time zone (winter time) with respect to UTC."
    ::= { wtWebioEA12x6RelERPTimeZone 2 }

wtWebioEA12x6RelERPTzEnable OBJECT-TYPE
    SYNTAX OCTET STRING (SIZE(4))
    ACCESS read-write
    STATUS mandatory
    DESCRIPTION
        "Binary coded conditions:
        Octet 1: unused
        Octet 2: unused
        Octet 3: unused
        Octet 4:
        	Bit 1-7: unused
	        Bit 0  : Apply Timezone"
    ::= { wtWebioEA12x6RelERPTimeZone 3 }

wtWebioEA12x6RelERPStTzOffsetHrs OBJECT-TYPE
    SYNTAX INTEGER 
    ACCESS read-write
    STATUS mandatory
    DESCRIPTION
        "Offset hours of the time zone (summer time) with respect to UTC."
    ::= { wtWebioEA12x6RelERPTimeZone 4 }

wtWebioEA12x6RelERPStTzOffsetMin OBJECT-TYPE
    SYNTAX INTEGER 
    ACCESS read-write
    STATUS mandatory
    DESCRIPTION
        "Offset minutes of the time zone (summer time) with respect to UTC."
    ::= { wtWebioEA12x6RelERPTimeZone 5 }

wtWebioEA12x6RelERPStTzEnable OBJECT-TYPE
    SYNTAX OCTET STRING (SIZE(4))
    ACCESS read-write
    STATUS mandatory
    DESCRIPTION
        "Binary coded conditions:
        Octet 1: unused
        Octet 2: unused
        Octet 3: unused
        Octet 4:
        	Bit 1-7: unused
	        Bit 0  : Apply Summertime"
    ::= { wtWebioEA12x6RelERPTimeZone 6 }

wtWebioEA12x6RelERPStTzStartMonth OBJECT-TYPE
    SYNTAX INTEGER {
    	wtWebioEA12x6RelERPStartMonth-January(1),
    	wtWebioEA12x6RelERPStartMonth-February(2),
    	wtWebioEA12x6RelERPStartMonth-March(3),
    	wtWebioEA12x6RelERPStartMonth-April(4),
    	wtWebioEA12x6RelERPStartMonth-May(5),
    	wtWebioEA12x6RelERPStartMonth-June(6),
    	wtWebioEA12x6RelERPStartMonth-July(7),
    	wtWebioEA12x6RelERPStartMonth-August(8),
    	wtWebioEA12x6RelERPStartMonth-September(9),
    	wtWebioEA12x6RelERPStartMonth-October(10),
    	wtWebioEA12x6RelERPStartMonth-November(11),
    	wtWebioEA12x6RelERPStartMonth-December(12)
    	}
    	
    ACCESS read-write
    STATUS mandatory
    DESCRIPTION
        "Month in which the change is made from winter time to summer time."
    ::= { wtWebioEA12x6RelERPTimeZone 7 }

wtWebioEA12x6RelERPStTzStartMode OBJECT-TYPE
    SYNTAX INTEGER {
    	wtWebioEA12x6RelERPStartMode-first(1),
    	wtWebioEA12x6RelERPStartMode-second(2),
    	wtWebioEA12x6RelERPStartMode-third(3),
    	wtWebioEA12x6RelERPStartMode-fourth(4),
    	wtWebioEA12x6RelERPStartMode-last(5)
    	}
    	
    ACCESS read-write
    STATUS mandatory
    DESCRIPTION
        "Mode of the day of the week for which the change is made from winter time to summer time."
    ::= { wtWebioEA12x6RelERPTimeZone 8 }

wtWebioEA12x6RelERPStTzStartWday OBJECT-TYPE
    SYNTAX INTEGER {
    	wtWebioEA12x6RelERPStartWday-Sunday(1),
    	wtWebioEA12x6RelERPStartWday-Monday(2),
    	wtWebioEA12x6RelERPStartWday-Tuesday(3),
    	wtWebioEA12x6RelERPStartWday-Thursday(4),
    	wtWebioEA12x6RelERPStartWday-Wednesday(5),
    	wtWebioEA12x6RelERPStartWday-Friday(6),
    	wtWebioEA12x6RelERPStartWday-Saturday(7)
    	}
    	
    ACCESS read-write
    STATUS mandatory
    DESCRIPTION
        "Day of the week on which the change is made from winter time to summer time"
    ::= { wtWebioEA12x6RelERPTimeZone 9 }
    
wtWebioEA12x6RelERPStTzStartHrs OBJECT-TYPE
    SYNTAX INTEGER 
    ACCESS read-write
    STATUS mandatory
    DESCRIPTION
        "Hour in which the time zone is changed from winter to summer time with
        respect to UTC."
    ::= { wtWebioEA12x6RelERPTimeZone 10 }

wtWebioEA12x6RelERPStTzStartMin OBJECT-TYPE
    SYNTAX INTEGER 
    ACCESS read-write
    STATUS mandatory
    DESCRIPTION
        "Minute in which the time zone is changed from winter to summer time with
        respect to UTC."
    ::= { wtWebioEA12x6RelERPTimeZone 11 }
 
wtWebioEA12x6RelERPStTzStopMonth OBJECT-TYPE
    SYNTAX INTEGER {
    	wtWebioEA12x6RelERPStopMonth-January(1),
    	wtWebioEA12x6RelERPStopMonth-February(2),
    	wtWebioEA12x6RelERPStopMonth-March(3),
    	wtWebioEA12x6RelERPStopMonth-April(4),
    	wtWebioEA12x6RelERPStopMonth-May(5),
    	wtWebioEA12x6RelERPStopMonth-June(6),
    	wtWebioEA12x6RelERPStopMonth-July(7),
    	wtWebioEA12x6RelERPStopMonth-August(8),
    	wtWebioEA12x6RelERPStopMonth-September(9),
    	wtWebioEA12x6RelERPStopMonth-October(10),
    	wtWebioEA12x6RelERPStopMonth-November(11),
    	wtWebioEA12x6RelERPStopMonth-December(12)
    	}
    ACCESS read-write
    STATUS mandatory
    DESCRIPTION
        "Month in which the change is made from summer time to winter time."
   ::= { wtWebioEA12x6RelERPTimeZone 12 }

wtWebioEA12x6RelERPStTzStopMode OBJECT-TYPE
    SYNTAX INTEGER {
    	wtWebioEA12x6RelERPStopMode-first(1),
    	wtWebioEA12x6RelERPStopMode-second(2),
    	wtWebioEA12x6RelERPStopMode-third(3),
    	wtWebioEA12x6RelERPStopMode-fourth(4),
    	wtWebioEA12x6RelERPStopMode-last(5)
    	}
    ACCESS read-write
    STATUS mandatory
    DESCRIPTION
        "Mode of the week day on which the change is made from summer time to winter time."
    ::= { wtWebioEA12x6RelERPTimeZone 13 }

wtWebioEA12x6RelERPStTzStopWday OBJECT-TYPE
    SYNTAX INTEGER {
    	wtWebioEA12x6RelERPStopWday-Sunday(1),
    	wtWebioEA12x6RelERPStopWday-Monday(2),
    	wtWebioEA12x6RelERPStopWday-Tuesday(3),
    	wtWebioEA12x6RelERPStopWday-Thursday(4),
    	wtWebioEA12x6RelERPStopWday-Wednesday(5),
    	wtWebioEA12x6RelERPStopWday-Friday(6),
    	wtWebioEA12x6RelERPStopWday-Saturday(7)
    	}
    ACCESS read-write
    STATUS mandatory
    DESCRIPTION
        "Day of the week on which the change is made from summer time to winter time."
    ::= { wtWebioEA12x6RelERPTimeZone 14 }
    
wtWebioEA12x6RelERPStTzStopHrs OBJECT-TYPE
    SYNTAX INTEGER 
    ACCESS read-write
    STATUS mandatory
    DESCRIPTION
        "Hour at which the time zone is changed from summer to winter time with
        respect to UTC."
    ::= { wtWebioEA12x6RelERPTimeZone 15 }

wtWebioEA12x6RelERPStTzStopMin OBJECT-TYPE
    SYNTAX INTEGER 
    ACCESS read-write
    STATUS mandatory
    DESCRIPTION
        "Minute at which the time zone is changed from summer to winter time with
        respect to UTC."
    ::= { wtWebioEA12x6RelERPTimeZone 16 }

-- wtWebioEA12x6RelERPTimeServer Group
----------------------------

wtWebioEA12x6RelERPTimeServer1 OBJECT-TYPE
    SYNTAX OCTET STRING 
    ACCESS read-write
    STATUS mandatory
    DESCRIPTION
        "IP address or name of the 1st time server in ASCII"
    ::= { wtWebioEA12x6RelERPTimeServer 1 }

wtWebioEA12x6RelERPTimeServer2 OBJECT-TYPE
    SYNTAX OCTET STRING 
    ACCESS read-write
    STATUS mandatory
    DESCRIPTION
        "IP address or name of the 2nd time server in ASCII"
    ::= { wtWebioEA12x6RelERPTimeServer 2 }

wtWebioEA12x6RelERPTsEnable OBJECT-TYPE
    SYNTAX OCTET STRING (SIZE(4))
    ACCESS read-write
    STATUS mandatory
    DESCRIPTION
        "Binary coded conditions:
        Octet 1: unused
        Octet 2: unused
        Octet 3: unused
        Octet 4:
        	Bit 1-7: unused
	        Bit 0  : Apply Time Server"
    ::= { wtWebioEA12x6RelERPTimeServer 3 }

wtWebioEA12x6RelERPTsSyncTime OBJECT-TYPE
    SYNTAX INTEGER 
    ACCESS read-write
    STATUS mandatory
    DESCRIPTION
        "Daily synchronisation time with the time server (hour: 0-23)."
    ::= { wtWebioEA12x6RelERPTimeServer 4 }
      
    
-- wtWebioEA12x6RelERPDeviceClock Group
----------------------------

wtWebioEA12x6RelERPClockHrs OBJECT-TYPE
    SYNTAX INTEGER (0..23)
    ACCESS read-write
    STATUS mandatory
    DESCRIPTION
        "Clock hours taking into account the time zone settings."
    ::= { wtWebioEA12x6RelERPDeviceClock 1 }

wtWebioEA12x6RelERPClockMin OBJECT-TYPE
    SYNTAX INTEGER (0..59)
    ACCESS read-write
    STATUS mandatory
    DESCRIPTION
        "Clock minutes taking into account the time zone settings."
    ::= { wtWebioEA12x6RelERPDeviceClock 2 }

wtWebioEA12x6RelERPClockDay OBJECT-TYPE
    SYNTAX INTEGER (1..31)
    ACCESS read-write
    STATUS mandatory
    DESCRIPTION
        "Date: Day of the month, taking into account the time zone settings."
    ::= { wtWebioEA12x6RelERPDeviceClock 3 }

wtWebioEA12x6RelERPClockMonth OBJECT-TYPE
   SYNTAX INTEGER {
    	wtWebioEA12x6RelERPClockMonth-January(1),
    	wtWebioEA12x6RelERPClockMonth-February(2),
    	wtWebioEA12x6RelERPClockMonth-March(3),
    	wtWebioEA12x6RelERPClockMonth-April(4),
    	wtWebioEA12x6RelERPClockMonth-May(5),
    	wtWebioEA12x6RelERPClockMonth-June(6),
    	wtWebioEA12x6RelERPClockMonth-July(7),
    	wtWebioEA12x6RelERPClockMonth-August(8),
    	wtWebioEA12x6RelERPClockMonth-September(9),
    	wtWebioEA12x6RelERPClockMonth-October(10),
    	wtWebioEA12x6RelERPClockMonth-November(11),
    	wtWebioEA12x6RelERPClockMonth-December(12)
    	}
    ACCESS read-write
    STATUS mandatory
    DESCRIPTION
        "Date: Month, taking into account the time zone settings."
    ::= { wtWebioEA12x6RelERPDeviceClock 4 }

wtWebioEA12x6RelERPClockYear OBJECT-TYPE
    SYNTAX INTEGER (0..65535)
    ACCESS read-write
    STATUS mandatory
    DESCRIPTION
        "Date: Year, taking into account the time zone settings."
    ::= { wtWebioEA12x6RelERPDeviceClock 5 }

-- wtWebioEA12x6RelERPNetwork Group
------------------------

wtWebioEA12x6RelERPIpAddress OBJECT-TYPE
    SYNTAX IpAddress
    ACCESS read-write
    STATUS mandatory
    DESCRIPTION
        "IP address of the Webio"
    ::= { wtWebioEA12x6RelERPNetwork 1 }

wtWebioEA12x6RelERPSubnetMask OBJECT-TYPE
    SYNTAX IpAddress
    ACCESS read-write
    STATUS mandatory
    DESCRIPTION
        "Subnet mask of the Webio"
    ::= { wtWebioEA12x6RelERPNetwork 2 }

wtWebioEA12x6RelERPGateway OBJECT-TYPE
    SYNTAX IpAddress
    ACCESS read-write
    STATUS mandatory
    DESCRIPTION
        "Gateway of the Webio"
    ::= { wtWebioEA12x6RelERPNetwork 3 }

wtWebioEA12x6RelERPDnsServer1 OBJECT-TYPE
    SYNTAX OCTET STRING 
    ACCESS read-write
    STATUS mandatory
    DESCRIPTION
        "IP address of the 1st DNS server in ASCII"
    ::= { wtWebioEA12x6RelERPNetwork 4 }

wtWebioEA12x6RelERPDnsServer2 OBJECT-TYPE
    SYNTAX OCTET STRING 
    ACCESS read-write
    STATUS mandatory
    DESCRIPTION
        "IP address of the 2nd DNS server in ASCII"
    ::= { wtWebioEA12x6RelERPNetwork 5 }

wtWebioEA12x6RelERPAddConfig OBJECT-TYPE
    SYNTAX OCTET STRING 
    ACCESS read-write
    STATUS mandatory
    DESCRIPTION
        "Additional configuration (1=ON):
        Octet 1: unused
        Octet 2: unused
        Octet 3: unused
        Octet 4:
	        Bit 1: DHCP  enable
	        Bit 0: BOOTP enable"
    ::= { wtWebioEA12x6RelERPNetwork 6 }

--  wtWebioEA12x6RelERPHTTP Group
--------------------------------

wtWebioEA12x6RelERPStartup OBJECT-TYPE
    SYNTAX OCTET STRING 
    ACCESS read-write
    STATUS mandatory
    DESCRIPTION
        "Binary coded start page, more than one page must not be selected:
        Octet 1: unused
        Octet 2: unused
        Octet 3: unused
        Octet 4:
        	Bit 2: user.htm
        	Bit 1: home.htm
	        Bit 0: index.htm"
    ::= { wtWebioEA12x6RelERPHTTP 1 }

wtWebioEA12x6RelERPGetHeaderEnable OBJECT-TYPE
    SYNTAX OCTET STRING 
    ACCESS read-write
    STATUS mandatory
    DESCRIPTION
        "If bits are set, every answer of a short form GET question will be lead
        by the IP-address and name of the device (Header) or a HTTP header (HTTP):
        Octet 1: unused
        Octet 2: unused
        Octet 3: unused
        Octet 4:
        	Bit 2-7: unused
        	Bit 1  : GET HTTP enable
                Bit 0  : GET Header enable"
    ::= { wtWebioEA12x6RelERPHTTP 2 }

wtWebioEA12x6RelERPHttpInputTrigger OBJECT-TYPE
    SYNTAX OCTET STRING (SIZE (4))
    ACCESS read-write
    STATUS mandatory
    DESCRIPTION
        "Every change on the inputs causes their state to be transmitted to the 
        remote device. To minimize data traffic, individual inputs may be exempted 
        from this rule. Nevertheless every transmission will contain all input bits.
        If a bit is set (1), a change of state on the corresponding input 
        triggers a transmission. If the bit is not set (0), no transmission 
        takes place.
        The OCTETS are interpreted bit-by-bit, with each bit corresponding to an input. 
        Bit 0 corresponds to the LSB.
        OCTET 1: unused
        OCTET 2: unused
        OCTET 3, Bit 0-3: Digital inputs 8-11
                 Bit 4-7: unused
        OCTET 4, Bit 0-7: Digital inputs 0-7"
    ::= { wtWebioEA12x6RelERPHTTP 3 }

wtWebioEA12x6RelERPHttpPort OBJECT-TYPE
    SYNTAX INTEGER (1..65534)
    ACCESS read-write
    STATUS mandatory
    DESCRIPTION
       "Definition of the standard HTML port (Default: 80)."
    ::= { wtWebioEA12x6RelERPHTTP 4 }        
    
    
-- wtWebioEA12x6RelERPMail Group
--------------------------------

wtWebioEA12x6RelERPMailAdName OBJECT-TYPE
    SYNTAX OCTET STRING 
    ACCESS read-write
    STATUS mandatory
    DESCRIPTION
        "Device name for mail administration."
    ::= { wtWebioEA12x6RelERPMail 1 }
    
wtWebioEA12x6RelERPMailReply OBJECT-TYPE
    SYNTAX OCTET STRING 
    ACCESS read-write
    STATUS mandatory
    DESCRIPTION
        "Reply address for the mail server."
    ::= { wtWebioEA12x6RelERPMail 2 }
    
wtWebioEA12x6RelERPMailServer OBJECT-TYPE
    SYNTAX OCTET STRING 
    ACCESS read-write
    STATUS mandatory
    DESCRIPTION
        "Name or IP address of the mail server."
    ::= { wtWebioEA12x6RelERPMail 3 }
    
wtWebioEA12x6RelERPMailEnable OBJECT-TYPE
    SYNTAX OCTET STRING 
    ACCESS read-write
    STATUS mandatory
    DESCRIPTION
        "Set this bit to enable the sending of mails:
        Octet 1: unused
        Octet 2: unused
        Octet 3: unused
        Octet 4:
        	Bit 1-7: unused
                Bit 0  : Mail enable"
    ::= { wtWebioEA12x6RelERPMail 4 }

wtWebioEA12x6RelERPMailAuthentication OBJECT-TYPE
    SYNTAX OCTET STRING (SIZE (4))
    ACCESS read-write
    STATUS mandatory
    DESCRIPTION
        "Selection of the authentication modi:
        The OCTETS are interpreted bit-by-bit, 
        Bit 0 corresponds to the LSB.
        OCTET 1: unused
        OCTET 2: unused
        OCTET 3: unused
        OCTET 4: Bit 3-7: unused
        	 Bit 2  : POP3 before SMTP
        	 Bit 1  : ESMTP, authentication
        	 Bit 0  : SMTP, no authentication"
    ::= { wtWebioEA12x6RelERPMail 5 }
    
wtWebioEA12x6RelERPMailAuthUser OBJECT-TYPE
    SYNTAX OCTET STRING 
    ACCESS read-write
    STATUS mandatory
    DESCRIPTION
        "Name of the user to be authenticated."
    ::= { wtWebioEA12x6RelERPMail 6 }    
    
wtWebioEA12x6RelERPMailAuthPassword OBJECT-TYPE
    SYNTAX OCTET STRING 
    ACCESS read-write
    STATUS mandatory
    DESCRIPTION
        "Authentication password."
    ::= { wtWebioEA12x6RelERPMail 7 }    
    
wtWebioEA12x6RelERPMailPop3Server OBJECT-TYPE
    SYNTAX OCTET STRING 
    ACCESS read-write
    STATUS mandatory
    DESCRIPTION
        "Name or Ip-address of the POP3 Servers."
    ::= { wtWebioEA12x6RelERPMail 8 }        
    

--  wtWebioEA12x6RelERPSnmp Group
--------------------------------

wtWebioEA12x6RelERPSnmpEnable OBJECT-TYPE
    SYNTAX OCTET STRING 
    ACCESS read-write
    STATUS mandatory
    DESCRIPTION
        "Set bit 0 to enable SNMP.
        If disabled, the device did not respond to any SNMP requests.
        Bit 1 decided wether the community string of read operations 
        is compared with the system password or not:
        Octet 1: unused
        Octet 2: unused
        Octet 3: unused
        Octet 4:
        	Bit 1-7: unused
        	Bit 0  : SNMP enable"
    ::= { wtWebioEA12x6RelERPSNMP 1 }
    
wtWebioEA12x6RelERPSnmpCommunityStringRead OBJECT-TYPE
    SYNTAX OCTET STRING
    ACCESS read-write
    STATUS mandatory
    DESCRIPTION
        "Community string read only"
    ::= { wtWebioEA12x6RelERPSNMP 2 }

wtWebioEA12x6RelERPSnmpCommunityStringReadWrite OBJECT-TYPE
    SYNTAX OCTET STRING
    ACCESS read-write
    STATUS mandatory
    DESCRIPTION
        "Community string read / write"
    ::= { wtWebioEA12x6RelERPSNMP 3 }

wtWebioEA12x6RelERPSnmpSystemTrapManagerIP OBJECT-TYPE
    SYNTAX OCTET STRING 
    ACCESS read-write
    STATUS mandatory
    DESCRIPTION
        "Name or IP address of the TCP server which accepts the system trap."
    ::= { wtWebioEA12x6RelERPSNMP 4 }
    
wtWebioEA12x6RelERPSnmpSystemTrapEnable OBJECT-TYPE
    SYNTAX OCTET STRING (SIZE(4))
    ACCESS read-write
    STATUS mandatory
    DESCRIPTION
        "Binary coded trigger conditions:
        Octet 1: unused
        Octet 2: unused
        Octet 3: unused
        Octet 4:
	        Bit 0:   ColdStart
	        Bit 1:   WarmStart
	        Bit 2:   Diag messages
	        Bit 3-7: unused"
    ::= { wtWebioEA12x6RelERPSNMP 5 }    

-- wtWebioEA12x6RelERPUdp Group
--------------------------------   

wtWebioEA12x6RelERPUdpAdminPort OBJECT-TYPE
    SYNTAX INTEGER
    ACCESS read-write
    STATUS mandatory
    DESCRIPTION
        "Udp port to which the Udp queries ( short form GET requests) can be sent. This
        port number must be unique within the device."
    ::= { wtWebioEA12x6RelERPUDP 1 }

wtWebioEA12x6RelERPUdpEnable OBJECT-TYPE
    SYNTAX OCTET STRING 
    ACCESS read-write
    STATUS mandatory
    DESCRIPTION
        "Set this bit to enable UDP support:
        Octet 1: unused
        Octet 2: unused
        Octet 3: unused
        Octet 4:
        	Bit 1-7: unused
                Bit 0  : UDP enable"
    ::= { wtWebioEA12x6RelERPUDP 2 }

wtWebioEA12x6RelERPUdpRemotePort OBJECT-TYPE
    SYNTAX INTEGER
    ACCESS read-write
    STATUS mandatory
    DESCRIPTION
        "Udp remote port setting.
        If this value is set to zero, the source port read from a request will be used 
        as destination port for the answer.
        A non zero value forced the destination port to this value."
    ::= { wtWebioEA12x6RelERPUDP 3 }
    
--  wtWebioEA12x6RelERPBinary Group
--------------------------------

wtWebioEA12x6RelERPBinaryModeCount OBJECT-TYPE
    SYNTAX INTEGER (1..2)
    ACCESS read-only
    STATUS mandatory
    DESCRIPTION
        "Number of independent binary channels."
    ::= { wtWebioEA12x6RelERPBinary 1 }
    
-- Binary Interface Table

wtWebioEA12x6RelERPBinaryIfTable OBJECT-TYPE
    SYNTAX SEQUENCE OF WtWebioEA12x6RelERPBinaryIfEntry
    ACCESS not-accessible
    STATUS mandatory
    DESCRIPTION
        "Table of indices."
    ::= { wtWebioEA12x6RelERPBinary 2 }

wtWebioEA12x6RelERPBinaryIfEntry OBJECT-TYPE
    SYNTAX WtWebioEA12x6RelERPBinaryIfEntry
    ACCESS not-accessible
    STATUS mandatory
    DESCRIPTION
        "Indices of the binary channels."
    INDEX  { wtWebioEA12x6RelERPBinaryModeNo }
    ::= { wtWebioEA12x6RelERPBinaryIfTable 1 }

WtWebioEA12x6RelERPBinaryIfEntry ::= SEQUENCE {
    wtWebioEA12x6RelERPBinaryModeNo INTEGER
}

wtWebioEA12x6RelERPBinaryModeNo OBJECT-TYPE
    SYNTAX INTEGER (1..2)
    ACCESS read-only
    STATUS mandatory
    DESCRIPTION
        "Number of the binary channel."
    ::= { wtWebioEA12x6RelERPBinaryIfEntry 1 }

-- Binary Table
--------------------------------

wtWebioEA12x6RelERPBinaryTable OBJECT-TYPE
    SYNTAX SEQUENCE OF WtWebioEA12x6RelERPBinaryEntry
    ACCESS not-accessible
    STATUS mandatory
    DESCRIPTION
        "Table of properties of the binary mode."
    ::= { wtWebioEA12x6RelERPBinary 3 }

wtWebioEA12x6RelERPBinaryEntry OBJECT-TYPE
    SYNTAX WtWebioEA12x6RelERPBinaryEntry
    ACCESS not-accessible
    STATUS mandatory
    DESCRIPTION
        "Binary properties."
    INDEX  { wtWebioEA12x6RelERPBinaryModeNo }
    ::= { wtWebioEA12x6RelERPBinaryTable 1 }

WtWebioEA12x6RelERPBinaryEntry ::= SEQUENCE {
    wtWebioEA12x6RelERPBinaryOperationMode		OCTET STRING,
    wtWebioEA12x6RelERPBinaryTcpServerLocalPort		INTEGER,
    wtWebioEA12x6RelERPBinaryTcpServerInputTrigger	OCTET STRING,
    wtWebioEA12x6RelERPBinaryTcpServerApplicationMode	OCTET STRING,
    wtWebioEA12x6RelERPBinaryTcpClientLocalPort		INTEGER,
    wtWebioEA12x6RelERPBinaryTcpClientServerPort	INTEGER,
    wtWebioEA12x6RelERPBinaryTcpClientServerIpAddr	OCTET STRING,
    wtWebioEA12x6RelERPBinaryTcpClientServerPassword	OCTET STRING,
    wtWebioEA12x6RelERPBinaryTcpClientInactivity	INTEGER,
    wtWebioEA12x6RelERPBinaryTcpClientInputTrigger	OCTET STRING,
    wtWebioEA12x6RelERPBinaryTcpClientInterval		INTEGER,
    wtWebioEA12x6RelERPBinaryTcpClientApplicationMode	OCTET STRING,
    wtWebioEA12x6RelERPBinaryUdpPeerLocalPort		INTEGER,
    wtWebioEA12x6RelERPBinaryUdpPeerRemotePort		INTEGER,
    wtWebioEA12x6RelERPBinaryUdpPeerRemoteIpAddr	OCTET STRING,
    wtWebioEA12x6RelERPBinaryUdpPeerInputTrigger	OCTET STRING,
    wtWebioEA12x6RelERPBinaryUdpPeerInterval		INTEGER,
    wtWebioEA12x6RelERPBinaryUdpPeerApplicationMode	OCTET STRING,
    wtWebioEA12x6RelERPBinaryConnectedPort		INTEGER,
    wtWebioEA12x6RelERPBinaryConnectedIpAddr		IpAddress,
    wtWebioEA12x6RelERPBinaryTcpServerClientHttpPort	INTEGER,
    wtWebioEA12x6RelERPBinaryTcpClientServerHttpPort	INTEGER
    
}

wtWebioEA12x6RelERPBinaryOperationMode OBJECT-TYPE
    SYNTAX OCTET STRING (SIZE (4))
    ACCESS read-write
    STATUS mandatory
    DESCRIPTION
        "Selection of the operation mode:
        The OCTETS are interpreted bit-by-bit,
        Bit 0 corresponds to the LSB.
        OCTET 1: unused
        OCTET 2: unused
        OCTET 3: unused
        OCTET 4: Bit 3-7: unused
        	 Bit 2  : UDP Peer
        	 Bit 1  : TCP Client
        	 Bit 0  : TCP Server"
    ::= { wtWebioEA12x6RelERPBinaryEntry 1 }

wtWebioEA12x6RelERPBinaryTcpServerLocalPort OBJECT-TYPE
    SYNTAX INTEGER (1..65535)
    ACCESS read-write
    STATUS mandatory
    DESCRIPTION
        "Local TCP port for data exchange in this server mode.
        This port number must be unique within the device.
	Reserved port number must not be used (refere to the manual)."
    ::= { wtWebioEA12x6RelERPBinaryEntry 2 }

wtWebioEA12x6RelERPBinaryTcpServerInputTrigger OBJECT-TYPE
    SYNTAX OCTET STRING (SIZE (4))
    ACCESS read-write
    STATUS mandatory
    DESCRIPTION
        "Every change on the inputs causes their state to be transmitted to the 
        remote device. To minimize data traffic, individual inputs may be exempted 
        from this rule. Nevertheless every transmission will contain all input bits.
        If a bit is set (1), a change of state on the corresponding input 
        triggers a transmission. If the bit is not set (0), no transmission 
        takes place.
        The OCTETS are interpreted bit-by-bit, with each bit corresponding to an input. 
        Bit 0 corresponds to the LSB.
        OCTET 1: unused
        OCTET 2: unused
        OCTET 3, Bit 0-3: Digital inputs 8-11
                 Bit 4-7: unused
        OCTET 4, Bit 0-7: Digital inputs 0-7"
    ::= { wtWebioEA12x6RelERPBinaryEntry 3 }

wtWebioEA12x6RelERPBinaryTcpServerApplicationMode OBJECT-TYPE
    SYNTAX OCTET STRING (SIZE (4))
    ACCESS read-write
    STATUS mandatory
    DESCRIPTION
        "Selection of the application mode:
        The OCTETS are interpreted bit-by-bit,
        Bit 0 corresponds to the LSB.
        OCTET 1: unused
        OCTET 2: unused
        OCTET 3: unused
        OCTET 4: Bit 4-7: unused
        	 Bit 3  : OPC Device
        	 Bit 2  : Box2Box Slave
        	 Bit 1  : Compatible 50xxx
        	 Bit 0  : Default"
    ::= { wtWebioEA12x6RelERPBinaryEntry 4 }
    
wtWebioEA12x6RelERPBinaryTcpClientLocalPort OBJECT-TYPE
    SYNTAX INTEGER (1..65535)
    ACCESS read-write
    STATUS mandatory
    DESCRIPTION
        "Local TCP port for data exchange in this client mode.
        This port number must be unique within the device.
	Reserved port number must not be used (refere to the manual)."
    ::= { wtWebioEA12x6RelERPBinaryEntry 5 }

wtWebioEA12x6RelERPBinaryTcpClientServerPort OBJECT-TYPE
    SYNTAX INTEGER (1..65535)
    ACCESS read-write
    STATUS mandatory
    DESCRIPTION
        "Port number of the server. A complete set of port number, IP address
        and a valid input/output mask starts this mode.
        No data exchange take place when setting the server port to zero."
    ::= { wtWebioEA12x6RelERPBinaryEntry 6 }

wtWebioEA12x6RelERPBinaryTcpClientServerIpAddr OBJECT-TYPE
    SYNTAX OCTET STRING
    ACCESS read-write
    STATUS mandatory
    DESCRIPTION
        "Ip address of the server. A complete set of port number, IP address
        and a valid input/output mask starts this mode.
        No data exchange take place when setting the server IP address to 0.0.0.0."
    ::= { wtWebioEA12x6RelERPBinaryEntry 7 }

wtWebioEA12x6RelERPBinaryTcpClientServerPassword OBJECT-TYPE
    SYNTAX OCTET STRING
    ACCESS read-write
    STATUS mandatory
    DESCRIPTION
        "Building a connection may be protected by the 
        administrator password of the server. Enter the server password
        to establish the connection, if a server administrator password
        exists."
    ::= { wtWebioEA12x6RelERPBinaryEntry 8 }

wtWebioEA12x6RelERPBinaryTcpClientInactivity OBJECT-TYPE
    SYNTAX INTEGER 
    ACCESS read-write
    STATUS mandatory
    DESCRIPTION
        "Connection timeout in 100ms. If no data are exchanged within the specified  
        time, the device closes the connection to the server.
        The value 0 deactivates the timer. Using the Box2Box mode this function is
        disabled."
    ::= { wtWebioEA12x6RelERPBinaryEntry 9 }
    
wtWebioEA12x6RelERPBinaryTcpClientInputTrigger OBJECT-TYPE
    SYNTAX OCTET STRING (SIZE (4))
    ACCESS read-write
    STATUS mandatory
    DESCRIPTION
        "Every change on the inputs causes their state to be transmitted to the 
        remote device. To minimize data traffic, individual inputs may be exempted 
        from this rule. Nevertheless every transmission will contain all input bits.
        If a bit is set (1), a change of state on the corresponding input 
        triggers a transmission. If the bit is not set (0), no transmission 
        takes place.
        The OCTETS are interpreted bit-by-bit, with each bit corresponding to an input. 
        Bit 0 corresponds to the LSB.
        OCTET 1: unused
        OCTET 2: unused
        OCTET 3, Bit 0-3: Digital inputs 8-11
                 Bit 4-7: unused
        OCTET 4, Bit 0-7: Digital inputs 0-7"
    ::= { wtWebioEA12x6RelERPBinaryEntry 10 }
 
wtWebioEA12x6RelERPBinaryTcpClientInterval OBJECT-TYPE
    SYNTAX INTEGER (0..65535)
    ACCESS read-write
    STATUS mandatory
    DESCRIPTION
        "Configurable interval with a 100ms base, in which the Webio device sends
        data to the configured application. A interval of zero stopps the 
        periodical sending."
    ::= { wtWebioEA12x6RelERPBinaryEntry 11 }

wtWebioEA12x6RelERPBinaryTcpClientApplicationMode OBJECT-TYPE
    SYNTAX OCTET STRING (SIZE (4))
    ACCESS read-write
    STATUS mandatory
    DESCRIPTION
        "Selection of the application mode:
        The OCTETS are interpreted bit-by-bit,
        Bit 0 corresponds to the LSB.
        OCTET 1: unused
        OCTET 2: unused
        OCTET 3: unused
        OCTET 4: Bit 3-7: unused
        	 Bit 2  : Box2Box Slave
        	 Bit 1  : Compatible 50xxx
        	 Bit 0  : Default"
    ::= { wtWebioEA12x6RelERPBinaryEntry 12 }

wtWebioEA12x6RelERPBinaryUdpPeerLocalPort OBJECT-TYPE
    SYNTAX INTEGER (1..65535)
    ACCESS read-write
    STATUS mandatory
    DESCRIPTION
        "Local UDP port for data exchange in this peer to peer mode.
        This port number must be unique within the device.
	Reserved port number must not be used (refere to the manual)."
    ::= { wtWebioEA12x6RelERPBinaryEntry 13 }

wtWebioEA12x6RelERPBinaryUdpPeerRemotePort OBJECT-TYPE
    SYNTAX INTEGER (1..65535)
    ACCESS read-write
    STATUS mandatory
    DESCRIPTION
        "Port number of the remote device. A complete set of port number, IP address
        and a valid input/output mask starts this mode.
        No data exchange take place when setting the remote port to zero."
    ::= { wtWebioEA12x6RelERPBinaryEntry 14 }

wtWebioEA12x6RelERPBinaryUdpPeerRemoteIpAddr OBJECT-TYPE
    SYNTAX OCTET STRING
    ACCESS read-write
    STATUS mandatory
    DESCRIPTION
        "Ip address of the remote device. A complete set of port number, IP address
        and a valid input/output mask starts this mode.
        No data exchange take place when setting the remote device IP address to 0.0.0.0."
    ::= { wtWebioEA12x6RelERPBinaryEntry 15 }

wtWebioEA12x6RelERPBinaryUdpPeerInputTrigger OBJECT-TYPE
    SYNTAX OCTET STRING (SIZE (4))
    ACCESS read-write
    STATUS mandatory
    DESCRIPTION
        "Every change on the inputs causes their state to be transmitted to the 
        remote device. To minimize data traffic, individual inputs may be exempted 
        from this rule. Nevertheless every transmission will contain all input bits.
        If a bit is set (1), a change of state on the corresponding input 
        triggers a transmission. If the bit is not set (0), no transmission 
        takes place.
        The OCTETS are interpreted bit-by-bit, with each bit corresponding to an input. 
        Bit 0 corresponds to the LSB.
        OCTET 1: unused
        OCTET 2: unused
        OCTET 3, Bit 0-3: Digital inputs 8-11
                 Bit 4-7: unused
        OCTET 4, Bit 0-7: Digital inputs 0-7"
    ::= { wtWebioEA12x6RelERPBinaryEntry 16 }

wtWebioEA12x6RelERPBinaryUdpPeerInterval OBJECT-TYPE
    SYNTAX INTEGER (0..65535)
    ACCESS read-write
    STATUS mandatory
    DESCRIPTION
        "Configurable interval with a 100ms base, in which the Webio device sends
        data to the configured remote device. A interval of zero stopps the 
        periodical sending."
    ::= { wtWebioEA12x6RelERPBinaryEntry 17 }

wtWebioEA12x6RelERPBinaryUdpPeerApplicationMode OBJECT-TYPE
    SYNTAX OCTET STRING (SIZE (4))
    ACCESS read-write
    STATUS mandatory
    DESCRIPTION
        "Selection of the application mode:
        The OCTETS are interpreted bit-by-bit,
        Bit 0 corresponds to the LSB.
        OCTET 1: unused
        OCTET 2: unused
        OCTET 3: unused
        OCTET 4: Bit 3-7: unused
        	 Bit 2  : Box2Box Slave
        	 Bit 1  : Compatible 50xxx
        	 Bit 0  : Default"
    ::= { wtWebioEA12x6RelERPBinaryEntry 18 }

wtWebioEA12x6RelERPBinaryConnectedPort OBJECT-TYPE
    SYNTAX INTEGER (1..65535)
    ACCESS read-only
    STATUS mandatory
    DESCRIPTION
        "Port number of the remote device, after connection has been established.
        In case of no connection or missing port informations a zero will be read."
    ::= { wtWebioEA12x6RelERPBinaryEntry 19 }

wtWebioEA12x6RelERPBinaryConnectedIpAddr OBJECT-TYPE
    SYNTAX IpAddress
    ACCESS read-only
    STATUS mandatory
    DESCRIPTION
        "IP address of the remote device, after connection has been established.
        In case of no connection or missing port informations 0.0.0.0 will be read."
    ::= { wtWebioEA12x6RelERPBinaryEntry 20 } 

wtWebioEA12x6RelERPBinaryTcpServerClientHttpPort OBJECT-TYPE
    SYNTAX INTEGER (1..65535)
    ACCESS read-write
    STATUS mandatory
    DESCRIPTION
        "HTTP port number of the remote device at TCP Server Mode. If an mailfunction occurs 
        status informations will be send to this port. 
        Not used at mode Compatible 50xxx."
    ::= { wtWebioEA12x6RelERPBinaryEntry 21 }
    
wtWebioEA12x6RelERPBinaryTcpClientServerHttpPort OBJECT-TYPE
    SYNTAX INTEGER (1..65535)
    ACCESS read-write
    STATUS mandatory
    DESCRIPTION
        "HTTP port number of the remote device at TCP Client Mode. In the operating mode
        Box2Box connection status informations will be exchanged through this port."
    ::= { wtWebioEA12x6RelERPBinaryEntry 22 }            
    
--  wtWebioEA12x6RelERPSyslog Group
--------------------------------
    
wtWebioEA12x6RelERPSyslogServerIP OBJECT-TYPE
    SYNTAX OCTET STRING 
    ACCESS read-write
    STATUS mandatory
    DESCRIPTION
        "Name or IP address of the Syslog server, which accepts the Syslog messgaes."
    ::= { wtWebioEA12x6RelERPSyslog 1 }
    
wtWebioEA12x6RelERPSyslogServerPort OBJECT-TYPE
    SYNTAX INTEGER
    ACCESS read-write
    STATUS mandatory
    DESCRIPTION
        "Portnumber of the Syslog servers, default 514."
    ::= { wtWebioEA12x6RelERPSyslog 2 }

wtWebioEA12x6RelERPSyslogSystemMessagesEnable OBJECT-TYPE
    SYNTAX OCTET STRING (SIZE(4))
    ACCESS read-write
    STATUS mandatory
    DESCRIPTION
        "Binary coded trigger conditions:
        Octet 1: unused
        Octet 2: unused
        Octet 3: unused
        Octet 4:
	        Bit 0:   ColdStart
	        Bit 1:   WarmStart
	        Bit 2:   Diag Messages
	        Bit 3-7: unused"
    ::= { wtWebioEA12x6RelERPSyslog 3 }    

wtWebioEA12x6RelERPSyslogEnable OBJECT-TYPE
    SYNTAX OCTET STRING 
    ACCESS read-write
    STATUS mandatory
    DESCRIPTION
        "Set bit 0to enable Syslog:
        Octet 1: unused
        Octet 2: unused
        Octet 3: unused
        Octet 4:
        	Bit 1-7: unused
                Bit 0  : Syslog enable"
    ::= { wtWebioEA12x6RelERPSyslog 4 }

--  wtWebioEA12x6RelERPFTP Group
--------------------------------

wtWebioEA12x6RelERPFTPServerIP OBJECT-TYPE
    SYNTAX OCTET STRING 
    ACCESS read-write
    STATUS mandatory
    DESCRIPTION
        "Name or IP address of the FTP server, which accepts the FTP messages."
    ::= { wtWebioEA12x6RelERPFTP 1 }
    
wtWebioEA12x6RelERPFTPServerControlPort OBJECT-TYPE
    SYNTAX INTEGER
    ACCESS read-write
    STATUS mandatory
    DESCRIPTION
        "Portnumber of the control port of the FTP server, default 21."
    ::= { wtWebioEA12x6RelERPFTP 2 }
    
wtWebioEA12x6RelERPFTPUserName OBJECT-TYPE
    SYNTAX OCTET STRING 
    ACCESS read-write
    STATUS mandatory
    DESCRIPTION
        "FTP Loggin: user name."
    ::= { wtWebioEA12x6RelERPFTP 3 }
    
wtWebioEA12x6RelERPFTPPassword OBJECT-TYPE
    SYNTAX OCTET STRING 
    ACCESS read-write
    STATUS mandatory
    DESCRIPTION
        "FTP Loggin: user password."
    ::= { wtWebioEA12x6RelERPFTP 4 }

wtWebioEA12x6RelERPFTPAccount OBJECT-TYPE
    SYNTAX OCTET STRING 
    ACCESS read-write
    STATUS mandatory
    DESCRIPTION
        "FTP Loggin: name of account."
    ::= { wtWebioEA12x6RelERPFTP 5 }

wtWebioEA12x6RelERPFTPOption OBJECT-TYPE
    SYNTAX OCTET STRING 
    ACCESS read-write
    STATUS mandatory
    DESCRIPTION
        "Bit 0 switches the FTP Server in Passiv-Mode,
        the Client controls the data connection on its own:
        Octet 1: unused
        Octet 2: unused
        Octet 3: unused
        Octet 4:
        	Bit 1-7: unused
                Bit 0  : PASV enable"
    ::= { wtWebioEA12x6RelERPFTP 6 }
    
wtWebioEA12x6RelERPFTPEnable OBJECT-TYPE
    SYNTAX OCTET STRING 
    ACCESS read-write
    STATUS mandatory
    DESCRIPTION
        "Set Bit 0 to enable FTP:
        Octet 1: unused
        Octet 2: unused
        Octet 3: unused
        Octet 4:
        	Bit 1-7: unused
                Bit 0  : FTP enable"
    ::= { wtWebioEA12x6RelERPFTP 7 }  

--  wtWebioEA12x6RelERPWayBack Group
--------------------------------

wtWebioEA12x6RelERPWayBackEnable OBJECT-TYPE
    SYNTAX OCTET STRING 
    ACCESS read-write
    STATUS mandatory
    DESCRIPTION
        "Set Bit 0 to enable WayBack:
        Octet 1: unused
        Octet 2: unused
        Octet 3: unused
        Octet 4:
        	Bit 1-7: unused
                Bit 0  : WayBack enable"
    ::= { wtWebioEA12x6RelERPWayBack 1 }    

wtWebioEA12x6RelERPWayBackServerControlPort OBJECT-TYPE
    SYNTAX INTEGER
    ACCESS read-write
    STATUS mandatory
    DESCRIPTION
        "Portnumber of the control port of the FTP server, default 21."
    ::= { wtWebioEA12x6RelERPWayBack 2 }
    
wtWebioEA12x6RelERPWayBackFTPPassword OBJECT-TYPE
    SYNTAX OCTET STRING 
    ACCESS read-write
    STATUS mandatory
    DESCRIPTION
        "WayBack FTP Loggin: Password of the user."
    ::= { wtWebioEA12x6RelERPWayBack 3 }    
    
wtWebioEA12x6RelERPWayBackFTPResponse OBJECT-TYPE
    SYNTAX OCTET STRING 
    ACCESS read-write
    STATUS mandatory
    DESCRIPTION
        "WayBack FTP response: return message after login."
    ::= { wtWebioEA12x6RelERPWayBack 4 }
    
wtWebioEA12x6RelERPWayBackFTPTimeOut OBJECT-TYPE
    SYNTAX OCTET STRING 
    ACCESS read-write
    STATUS mandatory
    DESCRIPTION
        "WayBack FTP Timeout: a request must be finished within this periode of time."
    ::= { wtWebioEA12x6RelERPWayBack 5 }    
    
--  wtWebioEA12x6RelERPOutputMode Group
--------------------------------

-- OutputMode Table

wtWebioEA12x6RelERPOutputModeTable OBJECT-TYPE
    SYNTAX SEQUENCE OF WtWebioEA12x6RelERPOutputModeEntry
    ACCESS not-accessible
    STATUS mandatory
    DESCRIPTION
        "Table of output mode configurations dependent on the output indices."
    ::= { wtWebioEA12x6RelERPOutputMode 1 }

wtWebioEA12x6RelERPOutputModeEntry OBJECT-TYPE
    SYNTAX WtWebioEA12x6RelERPOutputModeEntry
    ACCESS not-accessible
    STATUS mandatory
    DESCRIPTION
        "Output mode configurations of the individual outputs."
    INDEX  { wtWebioEA12x6RelERPOutputNo }
    ::= { wtWebioEA12x6RelERPOutputModeTable 1 }

WtWebioEA12x6RelERPOutputModeEntry ::= SEQUENCE {
    wtWebioEA12x6RelERPOutputModeBit	OCTET STRING
}

wtWebioEA12x6RelERPOutputModeBit OBJECT-TYPE
    SYNTAX OCTET STRING (SIZE (4))
    ACCESS read-write
    STATUS mandatory
    DESCRIPTION
        "This binary coded output mode defines the individual operation mode for any
        output. More than one mode must not be selected.
        The OCTETS are interpreted bit-by-bit, with each set of octets corresponding to an output. 
        Bit 0 corresponds to the LSB.
        OCTET 1: unused
        OCTET 2: unused
        OCTET 3: unused
        OCTET 4: Bit 6-7: unused
        	 Bit 5  : Logic
        	 Bit 4  : Binary 2
        	 Bit 3  : Binary 1
        	 Bit 2  : SNMP
        	 Bit 1  : UDP ASCII
        	 Bit 0  : HTTP"
    ::= { wtWebioEA12x6RelERPOutputModeEntry 1 }
    
wtWebioEA12x6RelERPSafetyTimeout OBJECT-TYPE
    SYNTAX INTEGER (0..65535)
    ACCESS read-write
    STATUS mandatory
    DESCRIPTION
        "After this period of time (multiple of 100ms) without receiving data
        outputs switch to their Safety States. For each output a independend safety state
        could be defined."
    ::= { wtWebioEA12x6RelERPOutputMode 2 }
 
     
-- wtWebioEA12x6RelERPAlarm Group
----------------------------

wtWebioEA12x6RelERPAlarmCount OBJECT-TYPE
    SYNTAX INTEGER (1..12)
    ACCESS read-only
    STATUS mandatory
    DESCRIPTION
        "Number of independent alarms."
    ::= { wtWebioEA12x6RelERPAlarm 1 }
    
-- Alarm Interface Table

wtWebioEA12x6RelERPAlarmIfTable OBJECT-TYPE
    SYNTAX SEQUENCE OF WtWebioEA12x6RelERPAlarmIfEntry
    ACCESS not-accessible
    STATUS mandatory
    DESCRIPTION
        "List of alarm indices."
    ::= { wtWebioEA12x6RelERPAlarm 2 }

wtWebioEA12x6RelERPAlarmIfEntry OBJECT-TYPE
    SYNTAX WtWebioEA12x6RelERPAlarmIfEntry
    ACCESS not-accessible
    STATUS mandatory
    DESCRIPTION
        "Numbers of the alarms."
    INDEX  { wtWebioEA12x6RelERPAlarmNo }
    ::= { wtWebioEA12x6RelERPAlarmIfTable 1 }

WtWebioEA12x6RelERPAlarmIfEntry ::= SEQUENCE {
    wtWebioEA12x6RelERPAlarmNo INTEGER
}

wtWebioEA12x6RelERPAlarmNo OBJECT-TYPE
    SYNTAX INTEGER (1..12)
    ACCESS read-only
    STATUS mandatory
    DESCRIPTION
        "Numbers of the alarms."
    ::= { wtWebioEA12x6RelERPAlarmIfEntry 1 }

-- Alarm Table

wtWebioEA12x6RelERPAlarmTable OBJECT-TYPE
    SYNTAX SEQUENCE OF WtWebioEA12x6RelERPAlarmEntry
    ACCESS not-accessible
    STATUS mandatory
    DESCRIPTION
        "List of settings depending on the alarm number."
    ::= { wtWebioEA12x6RelERPAlarm 3 }

wtWebioEA12x6RelERPAlarmEntry OBJECT-TYPE
    SYNTAX WtWebioEA12x6RelERPAlarmEntry
    ACCESS not-accessible
    STATUS mandatory
    DESCRIPTION
        "Alarm parameters of the individual alarms."
    INDEX  { wtWebioEA12x6RelERPAlarmNo }
    ::= { wtWebioEA12x6RelERPAlarmTable 1 }

WtWebioEA12x6RelERPAlarmEntry ::= SEQUENCE {
    wtWebioEA12x6RelERPAlarmInputTrigger		OCTET STRING,
    wtWebioEA12x6RelERPAlarmOutputTrigger		OCTET STRING,
    wtWebioEA12x6RelERPAlarmSystemTrigger		OCTET STRING,
    wtWebioEA12x6RelERPAlarmMaxCounterValue		OCTET STRING,
    wtWebioEA12x6RelERPAlarmInterval			OCTET STRING,
    wtWebioEA12x6RelERPAlarmEnable			OCTET STRING,
    wtWebioEA12x6RelERPAlarmMailAddr			OCTET STRING,
    wtWebioEA12x6RelERPAlarmMailSubject			OCTET STRING,
    wtWebioEA12x6RelERPAlarmMailText			OCTET STRING,
    wtWebioEA12x6RelERPAlarmSnmpManagerIP		OCTET STRING,
    wtWebioEA12x6RelERPAlarmSnmpTrapText		OCTET STRING,
    wtWebioEA12x6RelERPAlarmUdpIpAddr			OCTET STRING,
    wtWebioEA12x6RelERPAlarmUdpPort			INTEGER,
    wtWebioEA12x6RelERPAlarmUdpText			OCTET STRING,
    wtWebioEA12x6RelERPAlarmTcpIpAddr			OCTET STRING,
    wtWebioEA12x6RelERPAlarmTcpPort			INTEGER,
    wtWebioEA12x6RelERPAlarmTcpText			OCTET STRING,    
    wtWebioEA12x6RelERPAlarmSyslogIpAddr		OCTET STRING,
    wtWebioEA12x6RelERPAlarmSyslogPort			INTEGER,
    wtWebioEA12x6RelERPAlarmSyslogText			OCTET STRING,
    wtWebioEA12x6RelERPAlarmFtpDataPort			OCTET STRING,
    wtWebioEA12x6RelERPAlarmFtpFileName			OCTET STRING,
    wtWebioEA12x6RelERPAlarmFtpText			OCTET STRING,
    wtWebioEA12x6RelERPAlarmFtpOption			OCTET STRING,
    wtWebioEA12x6RelERPAlarmTimerCron			OCTET STRING,

    wtWebioEA12x6RelERPAlarmMailReleaseSubject		OCTET STRING,
    wtWebioEA12x6RelERPAlarmMailReleaseText		OCTET STRING,
    wtWebioEA12x6RelERPAlarmSnmpTrapReleaseText		OCTET STRING,
    wtWebioEA12x6RelERPAlarmUdpReleaseText		OCTET STRING,
    wtWebioEA12x6RelERPAlarmTcpReleaseText		OCTET STRING,    
    wtWebioEA12x6RelERPAlarmSyslogReleaseText		OCTET STRING,
    wtWebioEA12x6RelERPAlarmFtpReleaseText		OCTET STRING        
    
}

wtWebioEA12x6RelERPAlarmInputTrigger OBJECT-TYPE
    SYNTAX OCTET STRING (SIZE(12))
    ACCESS read-write
    STATUS mandatory
    DESCRIPTION
        "This variable allows setting of individual input trigger conditions. 
        The OCTETS are interpreted bit-by-bit, with each bit corresponding to an input. 
        Bit 0 corresponds to the LSB.
	The first four OCTETS contain the mask which determines which of the inputs are to 
	be considered (corresponding bit = 1) and which inputs are to ignore 
	(corresponding bit = 0):
	OCTET 1 : unused
	OCTET 2 : unused
	OCTET 3, Bit 0-3: Mask for digital inputs 8-11
		 Bit 4-7: unused
	OCTET 4, Bit 0-7: Mask for digital inputs 0-7
	
	OCTETS 5-8 contain the level (1=HIGH, 0=LOW) which the inputs 
	should assume:
	OCTET 5 : unused
	OCTET 6 : unused
	OCTET 7, Bit 0-3: Level of digital inputs 8-11
		 Bit 4-7: unused
        OCTET 8, Bit 0-7: Level of digital inputs 0-7
        
	OCTETS 9-12 contain the ANY bit (1=ON, 0=OFF). Inputs masked with the any bit trigger with any change 
	of the corresponding input bit. Settings in OCTET 5-9 are then unused:
	OCTET 9 : unused
	OCTET 11, Bit 0-7   : ANY bits of digital inputs 8-11
		  Bit 12-15 : unused
	OCTET 12, Bit 0-7   : ANY bits of digital inputs 0-7"
        
    ::= { wtWebioEA12x6RelERPAlarmEntry 1 }

wtWebioEA12x6RelERPAlarmOutputTrigger OBJECT-TYPE
    SYNTAX OCTET STRING (SIZE(12))
    ACCESS read-write
    STATUS mandatory
    DESCRIPTION
        "This variable allows setting of individual output trigger conditions. 
        The OCTETS are interpreted bit-by-bit, with each bit corresponding to an output. 
        Bit 0 corresponds to the LSB.
	The first four OCTETS contain the mask which determines which of the outputs are to 
	be considered (corresponding bit = 1) and which outputs are to ignore 
	(corresponding bit = 0):
	OCTET 1 : unused
	OCTET 2 : unused
	OCTET 3 : unused
	OCTET 4, Bit 0-5: Mask for digital outputs 0-5
	
	OCTETS 5-8 contain the level (1=HIGH, 0=LOW) which the outputs 
	should assume:
	OCTET 5 : unused
	OCTET 6 : unused
	OCTET 7 : unused
        OCTET 8, Bit 0-5: Level of digital outputs 0-5

	OCTETS 9-12 contain the ANY bit (1=ON, 0=OFF). Outputs masked with the any bit trigger with any change 
	of the corresponding output bit. Settings in OCTET 5-9 are then unused:
	OCTET 9 : unused
	OCTET 10: unused
	OCTET 11: unused
	OCTET 12: Bit 0-5: ANY bits of digital outputs 0-5"
        
    ::= { wtWebioEA12x6RelERPAlarmEntry 2 }
    
wtWebioEA12x6RelERPAlarmSystemTrigger OBJECT-TYPE
    SYNTAX OCTET STRING (SIZE(4))
    ACCESS read-write
    STATUS mandatory
    DESCRIPTION
        "Binary coded trigger conditions:
        The OCTETS are interpreted bit-by-bit.
        Bit 0 corresponds to the LSB.
        OCTET 1: unused
        OCTET 2: unused
        OCTET 3: unused
        OCTET 4, 
        	 Bit 4-7: unused
        	 Bit 3  : Warm Start
        	 Bit 2  : Cold Start
        	 Bit 1  : Timer
        	 Bit 0  : Load Control"
    ::= { wtWebioEA12x6RelERPAlarmEntry 3 }

wtWebioEA12x6RelERPAlarmMaxCounterValue OBJECT-TYPE
    SYNTAX OCTET STRING 
    ACCESS read-write
    STATUS mandatory
    DESCRIPTION
        "This variable configures a max. counter value. If an input counter value
        exceeds this max. value, the corresponding alarm is triggered. Input counters with
        its mask bit unset in wtWebioEA12x6RelERPAlarmInputTrigger are not considered."
    ::= { wtWebioEA12x6RelERPAlarmEntry 4 }

wtWebioEA12x6RelERPAlarmInterval OBJECT-TYPE
    SYNTAX OCTET STRING 
    ACCESS read-write
    STATUS mandatory
    DESCRIPTION
        "Send interval for alarm messages."
    ::= { wtWebioEA12x6RelERPAlarmEntry 5 }

wtWebioEA12x6RelERPAlarmEnable OBJECT-TYPE
    SYNTAX OCTET STRING (SIZE(4))
    ACCESS read-write
    STATUS mandatory
    DESCRIPTION
        "Binary coded alarm enable:
        Octet 1: unused
        Octet 2: unused
        Octet 3: unused
        Octet 4:
		Bit 0:	Mail Enable
        	Bit 1:	SNMP Trap enable
        	Bit 2:  UDP enable
        	Bit 3:  Send inputs to pending TCP connections
        	Bit 4:  TCP Client enable
        	Bit 5:	Syslog Messages enable
        	Bit 6-7: unused"
    ::= { wtWebioEA12x6RelERPAlarmEntry 6 }

wtWebioEA12x6RelERPAlarmMailAddr OBJECT-TYPE
    SYNTAX OCTET STRING 
    ACCESS read-write
    STATUS mandatory
    DESCRIPTION
        "E-Mail address for sending the alarm mail to."
    ::= { wtWebioEA12x6RelERPAlarmEntry 7 }

wtWebioEA12x6RelERPAlarmMailSubject OBJECT-TYPE
    SYNTAX OCTET STRING 
    ACCESS read-write
    STATUS mandatory
    DESCRIPTION
        "Subject line for alarm mail."
    ::= { wtWebioEA12x6RelERPAlarmEntry 8 }

wtWebioEA12x6RelERPAlarmMailText OBJECT-TYPE
    SYNTAX OCTET STRING 
    ACCESS read-write
    STATUS mandatory
    DESCRIPTION
        "Alarm mail text: 
        States of the Webio device can be included by using special tags.
        Please refer to the respective Webio manual"
    ::= { wtWebioEA12x6RelERPAlarmEntry 9 }

wtWebioEA12x6RelERPAlarmSnmpManagerIP OBJECT-TYPE
    SYNTAX OCTET STRING 
    ACCESS read-write
    STATUS mandatory
    DESCRIPTION
        "IP address of the SNMP Manager to which the Webio device should send SNMP traps."
    ::= { wtWebioEA12x6RelERPAlarmEntry 10 }

wtWebioEA12x6RelERPAlarmSnmpTrapText OBJECT-TYPE
    SYNTAX OCTET STRING 
    ACCESS read-write
    STATUS mandatory
    DESCRIPTION
        "This text appears in the trap body."
    ::= { wtWebioEA12x6RelERPAlarmEntry 11 }
    
wtWebioEA12x6RelERPAlarmUdpIpAddr OBJECT-TYPE
    SYNTAX OCTET STRING 
    ACCESS read-write
    STATUS mandatory
    DESCRIPTION
        "IP address of the UDP listener to which the Webio device should send UDP traps."
    ::= { wtWebioEA12x6RelERPAlarmEntry 12 }    

wtWebioEA12x6RelERPAlarmUdpPort OBJECT-TYPE
    SYNTAX INTEGER (1..65535) 
    ACCESS read-write
    STATUS mandatory
    DESCRIPTION
        "Port number of the UDP listener to which the Webio device should send UDP traps."
    ::= { wtWebioEA12x6RelERPAlarmEntry 13 }    

wtWebioEA12x6RelERPAlarmUdpText OBJECT-TYPE
    SYNTAX OCTET STRING 
    ACCESS read-write
    STATUS mandatory
    DESCRIPTION
        "This text appears in the UDP trap body."
    ::= { wtWebioEA12x6RelERPAlarmEntry 14 }
    
wtWebioEA12x6RelERPAlarmTcpIpAddr OBJECT-TYPE
    SYNTAX OCTET STRING
    ACCESS read-write
    STATUS mandatory
    DESCRIPTION
        "IP address of the TCP listener to which the Webio device should send TCP traps."
    ::= { wtWebioEA12x6RelERPAlarmEntry 15 }    

wtWebioEA12x6RelERPAlarmTcpPort OBJECT-TYPE
    SYNTAX INTEGER (1..65535) 
    ACCESS read-write
    STATUS mandatory
    DESCRIPTION
        "Port number of the TCP listener to which the Webio device should send TCP traps."
    ::= { wtWebioEA12x6RelERPAlarmEntry 16 }    

wtWebioEA12x6RelERPAlarmTcpText OBJECT-TYPE
    SYNTAX OCTET STRING 
    ACCESS read-write
    STATUS mandatory
    DESCRIPTION
        "This text appears in the TCP trap body."
    ::= { wtWebioEA12x6RelERPAlarmEntry 17 }

wtWebioEA12x6RelERPAlarmSyslogIpAddr OBJECT-TYPE
    SYNTAX OCTET STRING 
    ACCESS read-write
    STATUS mandatory
    DESCRIPTION
        "IP address of the syslog server to which the Webio device should send syslog messages."
    ::= { wtWebioEA12x6RelERPAlarmEntry 18 }    

wtWebioEA12x6RelERPAlarmSyslogPort OBJECT-TYPE
    SYNTAX INTEGER (1..65535) 
    ACCESS read-write
    STATUS mandatory
    DESCRIPTION
        "Port number of the syslog server to which the Webio device should send syslog messages."
    ::= { wtWebioEA12x6RelERPAlarmEntry 19 }    

wtWebioEA12x6RelERPAlarmSyslogText OBJECT-TYPE
    SYNTAX OCTET STRING 
    ACCESS read-write
    STATUS mandatory
    DESCRIPTION
        "Every message starts with the priority key, a time stamp and the host ip address, according RFC3164.
        This text appears in the following syslog message body."
    ::= { wtWebioEA12x6RelERPAlarmEntry 20 }    
    
wtWebioEA12x6RelERPAlarmFtpDataPort OBJECT-TYPE
    SYNTAX OCTET STRING 
    ACCESS read-write
    STATUS mandatory
    DESCRIPTION
        "Local data port: 1..65535 or AUTO: the next free port will be assigned."
    ::= { wtWebioEA12x6RelERPAlarmEntry 21 }
    
wtWebioEA12x6RelERPAlarmFtpFileName OBJECT-TYPE
    SYNTAX OCTET STRING 
    ACCESS read-write
    STATUS mandatory
    DESCRIPTION
        "Name of the file including path informations."
    ::= { wtWebioEA12x6RelERPAlarmEntry 22 }
    
wtWebioEA12x6RelERPAlarmFtpText OBJECT-TYPE
    SYNTAX OCTET STRING 
    ACCESS read-write
    STATUS mandatory
    DESCRIPTION
        "Message text to store on the FTP server."
    ::= { wtWebioEA12x6RelERPAlarmEntry 23 }

wtWebioEA12x6RelERPAlarmFtpOption OBJECT-TYPE
    SYNTAX OCTET STRING (SIZE(4))
    ACCESS read-write
    STATUS mandatory
    DESCRIPTION
        "Binary coded options, select only one option at the same time:
        STORE  = replace file
        APPEND = append message at the end of the file
        
        Octet 1: unused
        Octet 2: unused
        Octet 3: unused
        Octet 4:
		Bit 0  :	STORE
		Bit 1  :	APPEND
        	Bit 2-7:	unused"
    ::= { wtWebioEA12x6RelERPAlarmEntry 24 }      
    
wtWebioEA12x6RelERPAlarmTimerCron OBJECT-TYPE
    SYNTAX OCTET STRING
    ACCESS read-write
    STATUS mandatory
    DESCRIPTION
        "This entry contains 5 space or tab seperated text fields for time trigger definition.
        Each field must match with the actual time to trigger a message, weekday and day of month
        are interpreted separatley.
        1: Minutes	Range 0-59
        2. Hours	Range 0-23, 0 is midnight
        3: Day of month	Range 1-31
        4: Month	Range 1-12
        5: Weekday	Range 0-6, 0 is sunday
        
        Syntax for every field:
         - an asterix (*) enables every possible setting of a field
         - single numbers seperated by commas
         - a partition within the allowed range (1-5)
         - step size within an partition of the allowed range (0-59/2: every second minute)."
    ::= { wtWebioEA12x6RelERPAlarmEntry 25 }      


wtWebioEA12x6RelERPAlarmMailReleaseSubject OBJECT-TYPE
    SYNTAX OCTET STRING 
    ACCESS read-write
    STATUS mandatory
    DESCRIPTION
       "Subject line for alarm mail."
    ::= { wtWebioEA12x6RelERPAlarmEntry 26 }

wtWebioEA12x6RelERPAlarmMailReleaseText OBJECT-TYPE
    SYNTAX OCTET STRING 
    ACCESS read-write
    STATUS mandatory
    DESCRIPTION
        "Release Alarm mail text: 
        States of the Webio device can be included by using special tags.
        Please refer to the respective Webio manual"
    ::= { wtWebioEA12x6RelERPAlarmEntry 27 }    

wtWebioEA12x6RelERPAlarmSnmpTrapReleaseText OBJECT-TYPE
    SYNTAX OCTET STRING 
    ACCESS read-write
    STATUS mandatory
    DESCRIPTION
        "This text appears in the trap body."
    ::= { wtWebioEA12x6RelERPAlarmEntry 28 }

wtWebioEA12x6RelERPAlarmUdpReleaseText OBJECT-TYPE
    SYNTAX OCTET STRING 
    ACCESS read-write
    STATUS mandatory
    DESCRIPTION
        "This text appears in the UDP trap body."
    ::= { wtWebioEA12x6RelERPAlarmEntry 29 }

wtWebioEA12x6RelERPAlarmTcpReleaseText OBJECT-TYPE
    SYNTAX OCTET STRING 
    ACCESS read-write
    STATUS mandatory
    DESCRIPTION
        "This text appears in the TCP trap body."
    ::= { wtWebioEA12x6RelERPAlarmEntry 30 }

wtWebioEA12x6RelERPAlarmSyslogReleaseText OBJECT-TYPE
    SYNTAX OCTET STRING 
    ACCESS read-write
    STATUS mandatory
    DESCRIPTION
        "Every message starts with the priority key, a time stamp and the host ip address, according RFC3164.
        This text appears in the following syslog message body."
    ::= { wtWebioEA12x6RelERPAlarmEntry 31 }

wtWebioEA12x6RelERPAlarmFtpReleaseText OBJECT-TYPE
    SYNTAX OCTET STRING 
    ACCESS read-write
    STATUS mandatory
    DESCRIPTION
        "Message text to store on the FTP server."
    ::= { wtWebioEA12x6RelERPAlarmEntry 32 }

-- wtWebioEA12x6RelERPPorts Group
----------------------------

-- Input Port Table

wtWebioEA12x6RelERPInputPortTable OBJECT-TYPE
    SYNTAX SEQUENCE OF WtWebioEA12x6RelERPInputPortEntry
    ACCESS not-accessible
    STATUS mandatory
    DESCRIPTION
        "List of settings depending on the input number."
    ::= { wtWebioEA12x6RelERPPorts 1 }

wtWebioEA12x6RelERPInputPortEntry OBJECT-TYPE
    SYNTAX WtWebioEA12x6RelERPInputPortEntry
    ACCESS not-accessible
    STATUS mandatory
    DESCRIPTION
        "Input parameter for the individual inputs."
    INDEX  { wtWebioEA12x6RelERPInputNo }
    ::= { wtWebioEA12x6RelERPInputPortTable 1 }

WtWebioEA12x6RelERPInputPortEntry ::= SEQUENCE {
    wtWebioEA12x6RelERPPortInputName				OCTET STRING,
    wtWebioEA12x6RelERPPortInputText				OCTET STRING,
    wtWebioEA12x6RelERPPortInputMode				OCTET STRING,
    wtWebioEA12x6RelERPPortInputFilter				INTEGER,
    wtWebioEA12x6RelERPPortInputBicountPulsePolarity		OCTET STRING,
    wtWebioEA12x6RelERPPortInputBicountInactivTimeout		INTEGER
}

wtWebioEA12x6RelERPPortInputName OBJECT-TYPE
    SYNTAX OCTET STRING 
    ACCESS read-write
    STATUS mandatory
    DESCRIPTION
        "Name of the input."
    ::= { wtWebioEA12x6RelERPInputPortEntry 1 }

wtWebioEA12x6RelERPPortInputText OBJECT-TYPE
    SYNTAX OCTET STRING 
    ACCESS read-write
    STATUS mandatory
    DESCRIPTION
        "Description of the input."
    ::= { wtWebioEA12x6RelERPInputPortEntry 2 }

wtWebioEA12x6RelERPPortInputMode OBJECT-TYPE
    SYNTAX OCTET STRING (SIZE(4))
    ACCESS read-write
    STATUS mandatory
    DESCRIPTION
        "Binary coded modes:
        Selecting short pulse detection enable by setting the corresponding bit to 1 enables 
        interrupt support for counting. Only positive edges are accepted as trigger 
        source. The maximum counting frequenz equals 2000 Hz.
        This mode is available for inputs 0-3 only.
        Selecting counter clear on read by setting the corresponding bit to 1 enables
        the corresponding counter to be cleared automatically every time it is read,
        except HTTP reading with user rights.
        The OCTETS are interpreted bit-by-bit, with each bit corresponding to an input. 
        Bit 0 corresponds to the LSB.
        Selection for input 0-3:
        OCTET 1: unused
        OCTET 2: unused
        OCTET 3: unused
        OCTET 4, Bit 3-7: unused
        	 Bit 2  : Counter clear on read
        	 Bit 1  : Change detection enable (default)
        	 Bit 0  : Short Pulse detection enable
        	 
	Selection for inputs 4-11:
	OCTET 1: unused
	OCTET 2: unused
	OCTET 3: unused
	OCTET 4, Bit 2-7: unused
		 Bit 1  : Counter clear on read
		 Bit 0  : Change detection enable (default)"
    ::= { wtWebioEA12x6RelERPInputPortEntry 3 }    
    
wtWebioEA12x6RelERPPortInputFilter OBJECT-TYPE
    SYNTAX INTEGER 
    ACCESS read-write
    STATUS mandatory
    DESCRIPTION
        "Pulses with a duration shorter than here specified (duration in 1/1000 sec),
	are ignored."
    ::= { wtWebioEA12x6RelERPInputPortEntry 4 }
    
wtWebioEA12x6RelERPPortInputBicountPulsePolarity OBJECT-TYPE
    SYNTAX OCTET STRING (SIZE (4))
    ACCESS read-write
    STATUS mandatory
    DESCRIPTION
        "This value defines the polarity of the input pulse.
        OCTET 1: unused
        OCTET 2: unused
        OCTET 3: unused
        	OCTET 4: 
        	 Bit 0   : negative polarity
        	 Bit 1   : positive polarity
        	 Bit 2-7 : unused"
    ::= { wtWebioEA12x6RelERPInputPortEntry 5 }

wtWebioEA12x6RelERPPortInputBicountInactivTimeout OBJECT-TYPE
    SYNTAX INTEGER 
    ACCESS read-write
    STATUS mandatory
    DESCRIPTION
        "Pulse chains with a duration shorter than here specified (in 1/10 sek),
	are ignored."
    ::= { wtWebioEA12x6RelERPInputPortEntry 6 }
    
-- Output Port Table

wtWebioEA12x6RelERPOutputPortTable OBJECT-TYPE
    SYNTAX SEQUENCE OF WtWebioEA12x6RelERPOutputPortEntry
    ACCESS not-accessible
    STATUS mandatory
    DESCRIPTION
        "List of settings depending on the output number."
    ::= { wtWebioEA12x6RelERPPorts 2 }

wtWebioEA12x6RelERPOutputPortEntry OBJECT-TYPE
    SYNTAX WtWebioEA12x6RelERPOutputPortEntry
    ACCESS not-accessible
    STATUS mandatory
    DESCRIPTION
        "Output parameters of the individual outputs."
    INDEX  { wtWebioEA12x6RelERPOutputNo }
    ::= { wtWebioEA12x6RelERPOutputPortTable 1 }

WtWebioEA12x6RelERPOutputPortEntry ::= SEQUENCE {
    wtWebioEA12x6RelERPPortOutputName			OCTET STRING,
    wtWebioEA12x6RelERPPortOutputText			OCTET STRING,
    wtWebioEA12x6RelERPPortOutputGroupMode		OCTET STRING,
    wtWebioEA12x6RelERPPortOutputSafetyState		OCTET STRING,
    wtWebioEA12x6RelERPPortLogicInputMask		OCTET STRING,
    wtWebioEA12x6RelERPPortLogicInputInverter		OCTET STRING,
    wtWebioEA12x6RelERPPortLogicFunction		OCTET STRING,
    wtWebioEA12x6RelERPPortLogicOutputInverter		OCTET STRING,
    wtWebioEA12x6RelERPPortPulseDuration		INTEGER,
    wtWebioEA12x6RelERPPortPulsePolarity		OCTET STRING
    
}

wtWebioEA12x6RelERPPortOutputName OBJECT-TYPE
    SYNTAX OCTET STRING 
    ACCESS read-write
    STATUS mandatory
    DESCRIPTION
        "Name of the output."
    ::= { wtWebioEA12x6RelERPOutputPortEntry 1 }

wtWebioEA12x6RelERPPortOutputText OBJECT-TYPE
    SYNTAX OCTET STRING 
    ACCESS read-write
    STATUS mandatory
    DESCRIPTION
        "Description of the output."
    ::= { wtWebioEA12x6RelERPOutputPortEntry 2 }

wtWebioEA12x6RelERPPortOutputGroupMode OBJECT-TYPE
    SYNTAX OCTET STRING 
    ACCESS read-write
    STATUS mandatory
    DESCRIPTION
        "Unused in this device 57634"
    ::= { wtWebioEA12x6RelERPOutputPortEntry 3 }

wtWebioEA12x6RelERPPortOutputSafetyState OBJECT-TYPE
    SYNTAX OCTET STRING 
    ACCESS read-write
    STATUS mandatory
    DESCRIPTION
        "This variable allows setting of individual digital outputs. The OCTETS are 
        interpreted bit-by-bit, with each bit corresponding to an output. Bit 0 corresponds 
        to the LSB.
        The first four OCTETS contain the mask which determines which of the outputs are to 
        be set (corresponding bit = 1) and which outputs are to remain unchanged 
        (corresponding bit = 0):
        OCTET 1		: unused
        OCTET 2		: unused
        OCTET 3		: unused
        OCTET 4, Bit 1-7: unused
        	 Bit 0	: Mask for digital output
        OCTETS 5-8 contain the level (1=HIGH=Relais closed, 0=LOW Relais open) which the outputs to be changed 
        should assume:
        OCTET 5		: unused
        OCTET 6		: unused
        OCTET 7		: unused
        OCTET 8, Bit 1-7: unused
        	 Bit 0  : Level of digital output"
    ::= { wtWebioEA12x6RelERPOutputPortEntry 4 }

wtWebioEA12x6RelERPPortLogicInputMask OBJECT-TYPE
    SYNTAX OCTET STRING (SIZE (4))
    ACCESS read-write
    STATUS mandatory
    DESCRIPTION
        "Selecting one of these inputs by setting the corresponding bit to 1 
        enables the logic function for the output identified by the index within 
        this table. The calculation take place in 4 steps:
        1. Selecting inputs				(wtWebioEA12x6RelERPPortLogicInputMask)
        2. Inverting inputs if necessary	(wtWebioEA12x6RelERPPortLogicInputInverter)
        3. Logical combination				(wtWebioEA12x6RelERPPortLogicFunction)
        4. Inverting the result if necessary	(wtWebioEA12x6RelERPPortLogicOutputInverter)
        OCTET 1: unused
        OCTET 2: unused
        OCTET 3: Bit 0-3 : inputs 8-11
        	 Bit 4-7 : unused
        OCTET 4: 
        	 Bit 0-7 : inputs 0-7"
    ::= { wtWebioEA12x6RelERPOutputPortEntry 5 }

wtWebioEA12x6RelERPPortLogicInputInverter OBJECT-TYPE
    SYNTAX OCTET STRING (SIZE (4))
    ACCESS read-write
    STATUS mandatory
    DESCRIPTION
        "Every input bit selected here will be inverted.
        OCTET 1: unused
        OCTET 2: unused
        OCTET 3: Bit 0-3 : inputs 8-11
        	 Bit 4-7 : unused
        OCTET 4: 
        	 Bit 0-7 : inputs 0-7"
    ::= { wtWebioEA12x6RelERPOutputPortEntry 6 }

wtWebioEA12x6RelERPPortLogicFunction OBJECT-TYPE
    SYNTAX OCTET STRING (SIZE (4))
    ACCESS read-write
    STATUS mandatory
    DESCRIPTION
        "This determines the logic function. No more than one function
        may be selected.
        OCTET 1: unused
        OCTET 2: unused
        OCTET 3: unused
        OCTET 4: 
        	 Bit 0   : logic function OR (default)
        	 Bit 1   : logic function AND
        	 Bit 2-7 : unused"
    ::= { wtWebioEA12x6RelERPOutputPortEntry 7 }

wtWebioEA12x6RelERPPortLogicOutputInverter OBJECT-TYPE
    SYNTAX OCTET STRING (SIZE (4))
    ACCESS read-write
    STATUS mandatory
    DESCRIPTION
        "The logical operation result could be inverteted by setting the corresponding
        bit to 1.
        OCTET 1: unused
        OCTET 2: unused
        OCTET 3: unused
        	OCTET 4: 
        	 Bit 0   : Output Inverter enable
        	 Bit 1-7 : unused"
    ::= { wtWebioEA12x6RelERPOutputPortEntry 8 }

wtWebioEA12x6RelERPPortPulseDuration OBJECT-TYPE
    SYNTAX INTEGER
    ACCESS read-write
    STATUS mandatory
    DESCRIPTION
        "Pulse length in 1/1000 sec. Setting this value to zero, disables the pulse output."
    ::= { wtWebioEA12x6RelERPOutputPortEntry 9 }

wtWebioEA12x6RelERPPortPulsePolarity OBJECT-TYPE
    SYNTAX OCTET STRING (SIZE (4))
    ACCESS read-write
    STATUS mandatory
    DESCRIPTION
        "This value defines the polarity of the output pulse, if wtWebioEA12x6RelERPPortPulseDuration is not set to zero.
        After the pulse is finished, the output switches back to the opposite state.
        OCTET 1: unused
        OCTET 2: unused
        OCTET 3: unused
        	OCTET 4: 
        	 Bit 0   : negative polarity
        	 Bit 1   : positive polarity
        	 Bit 2-7 : unused"
    ::= { wtWebioEA12x6RelERPOutputPortEntry 10 }

-- wtWebioEA12x6RelERPManufact Group
----------------------------

wtWebioEA12x6RelERPMfName OBJECT-TYPE
    SYNTAX OCTET STRING 
    ACCESS read-write
    STATUS mandatory
    DESCRIPTION
        "Manufacturer company name"
    ::= { wtWebioEA12x6RelERPManufact 1 }

wtWebioEA12x6RelERPMfAddr OBJECT-TYPE
    SYNTAX OCTET STRING 
    ACCESS read-write
    STATUS mandatory
    DESCRIPTION
        "Manufacturer address."
    ::= { wtWebioEA12x6RelERPManufact 2 }

wtWebioEA12x6RelERPMfHotline OBJECT-TYPE
    SYNTAX OCTET STRING 
    ACCESS read-write
    STATUS mandatory
    DESCRIPTION
        "Manufacturer hotline."
    ::= { wtWebioEA12x6RelERPManufact 3 }

wtWebioEA12x6RelERPMfInternet OBJECT-TYPE
    SYNTAX OCTET STRING 
    ACCESS read-write
    STATUS mandatory
    DESCRIPTION
        "Manufacturer Internet address."
    ::= { wtWebioEA12x6RelERPManufact 4 }

wtWebioEA12x6RelERPMfDeviceTyp OBJECT-TYPE
    SYNTAX OCTET STRING 
    ACCESS read-write
    STATUS mandatory
    DESCRIPTION
        "Manufacturer device name (model number)."
    ::= { wtWebioEA12x6RelERPManufact 5 }

wtWebioEA12x6RelERPMfOrderNo OBJECT-TYPE
    SYNTAX OCTET STRING 
    ACCESS read-write
    STATUS mandatory
    DESCRIPTION
        "Manufacturer part number."
    ::= { wtWebioEA12x6RelERPManufact 6 }

-- wtWebioEA12x6RelERPDiag Group
----------------------------

wtWebioEA12x6RelERPDiagErrorCount OBJECT-TYPE
    SYNTAX INTEGER
    ACCESS read-only
    STATUS mandatory
    DESCRIPTION
        "Number of entries in the error memory."
    ::= { wtWebioEA12x6RelERPDiag 1 }

wtWebioEA12x6RelERPDiagBinaryError OBJECT-TYPE
    SYNTAX OCTET STRING 
    ACCESS read-only
    STATUS mandatory
    DESCRIPTION
        "Error causes coded bit-by-bit."
    ::= { wtWebioEA12x6RelERPDiag 2 }

wtWebioEA12x6RelERPDiagErrorIndex OBJECT-TYPE
    SYNTAX INTEGER
    ACCESS read-write
    STATUS mandatory
    DESCRIPTION
        "The value of this variable is used as an index to read 
        an error massege from wtWebioEA12x6RelERPDiagErrorMessage.
        Errors are numbered from 1 to wtWebioEA12x6RelERPDiagErrorCount.
        Writing a valid value into this variable, making the appropriate 
        message readable from wtWebioEA12x6RelERPDiagErrorMessage."
    ::= { wtWebioEA12x6RelERPDiag 3 }

wtWebioEA12x6RelERPDiagErrorMessage OBJECT-TYPE
    SYNTAX OCTET STRING 
    ACCESS read-only
    STATUS mandatory
    DESCRIPTION
        "Using wtWebioEA12x6RelERPDiagErrorIndex as an index, the appropriate message is available."
    ::= { wtWebioEA12x6RelERPDiag 4 }
    
wtWebioEA12x6RelERPDiagErrorClear OBJECT-TYPE
    SYNTAX INTEGER
    ACCESS write-only
    STATUS mandatory
    DESCRIPTION
        "Writing 1 into this variable clears all diagnosis messages."
    ::= { wtWebioEA12x6RelERPDiag 5 }


-- TRAP DEFINITIONS

-- Diese SNMP-Traps werden gesendet, wenn die Alarmtriggerbedingungen zutreffen 

wtWebioEA12x6RelERPAlert1 TRAP-TYPE
    ENTERPRISE  wtWebioEA12x6RelERP
    VARIABLES   { wtWebioEA12x6RelERPAlarmSnmpTrapText }
    DESCRIPTION
        "This SNMP trap is generated when Alarm 1 was triggered,
        SNMP trap enable is set and
        SNMP is enabled."
    -- NMS trap annotation
    --#TYPE "Webio Digital Alarm 1"
    --#SUMMARY "Alarm 1: %s"
    --#ARGUMENTS {0}
    --#SEVERITY INFORMATIONAL
    --#TIMEINDEX 99
    --#STATE OPERATIONAL    
    ::= 41

wtWebioEA12x6RelERPAlert2 TRAP-TYPE
    ENTERPRISE  wtWebioEA12x6RelERP
    VARIABLES   { wtWebioEA12x6RelERPAlarmSnmpTrapText }
    DESCRIPTION
        "This SNMP trap is generated when Alarm 2 was triggered,
        SNMP trap enable is set and
        SNMP is enabled."
    -- NMS trap annotation
    --#TYPE "Webio Digital Alarm 2"
    --#SUMMARY "Alarm 2: %s"
    --#ARGUMENTS {0}
    --#SEVERITY INFORMATIONAL
    --#TIMEINDEX 99
    --#STATE OPERATIONAL    
    ::= 42

wtWebioEA12x6RelERPAlert3 TRAP-TYPE
    ENTERPRISE  wtWebioEA12x6RelERP
    VARIABLES   { wtWebioEA12x6RelERPAlarmSnmpTrapText }
    DESCRIPTION
        "This SNMP trap is generated when Alarm 3 was triggered,
        SNMP trap enable is set and
        SNMP is enabled."
    -- NMS trap annotation
    --#TYPE "Webio Digital Alarm 3"
    --#SUMMARY "Alarm 3: %s"
    --#ARGUMENTS {0}
    --#SEVERITY INFORMATIONAL
    --#TIMEINDEX 99
    --#STATE OPERATIONAL    
    ::= 43

wtWebioEA12x6RelERPAlert4 TRAP-TYPE
    ENTERPRISE  wtWebioEA12x6RelERP
    VARIABLES   { wtWebioEA12x6RelERPAlarmSnmpTrapText }
    DESCRIPTION
        "This SNMP trap is generated when Alarm 4 was triggered,
        SNMP trap enable is set and
        SNMP is enabled."
    -- NMS trap annotation
    --#TYPE "Webio Digital Alarm 4"
    --#SUMMARY "Alarm 4: %s"
    --#ARGUMENTS {0}
    --#SEVERITY INFORMATIONAL
    --#TIMEINDEX 99
    --#STATE OPERATIONAL    
    ::= 44

wtWebioEA12x6RelERPAlert5 TRAP-TYPE
    ENTERPRISE  wtWebioEA12x6RelERP
    VARIABLES   { wtWebioEA12x6RelERPAlarmSnmpTrapText }
    DESCRIPTION
        "This SNMP trap is generated when Alarm 5 was triggered,
        SNMP trap enable is set and
        SNMP is enabled."
    -- NMS trap annotation
    --#TYPE "Webio Digital Alarm 5"
    --#SUMMARY "Alarm 5: %s"
    --#ARGUMENTS {0}
    --#SEVERITY INFORMATIONAL
    --#TIMEINDEX 99
    --#STATE OPERATIONAL    
    ::= 45

wtWebioEA12x6RelERPAlert6 TRAP-TYPE
    ENTERPRISE  wtWebioEA12x6RelERP
    VARIABLES   { wtWebioEA12x6RelERPAlarmSnmpTrapText }
    DESCRIPTION
        "This SNMP trap is generated when Alarm 6 was triggered,
        SNMP trap enable is set and
        SNMP is enabled."
    -- NMS trap annotation
    --#TYPE "Webio Digital Alarm 6"
    --#SUMMARY "Alarm 6: %s"
    --#ARGUMENTS {0}
    --#SEVERITY INFORMATIONAL
    --#TIMEINDEX 99
    --#STATE OPERATIONAL    
    ::= 46

wtWebioEA12x6RelERPAlert7 TRAP-TYPE
    ENTERPRISE  wtWebioEA12x6RelERP
    VARIABLES   { wtWebioEA12x6RelERPAlarmSnmpTrapText }
    DESCRIPTION
        "This SNMP trap is generated when Alarm 7 was triggered,
        SNMP trap enable is set and
        SNMP is enabled."
    -- NMS trap annotation
    --#TYPE "Webio Digital Alarm 7"
    --#SUMMARY "Alarm 7: %s"
    --#ARGUMENTS {0}
    --#SEVERITY INFORMATIONAL
    --#TIMEINDEX 99
    --#STATE OPERATIONAL    
    ::= 47

wtWebioEA12x6RelERPAlert8 TRAP-TYPE
    ENTERPRISE  wtWebioEA12x6RelERP
    VARIABLES   { wtWebioEA12x6RelERPAlarmSnmpTrapText }
    DESCRIPTION
        "This SNMP trap is generated when Alarm 8 was triggered,
        SNMP trap enable is set and
        SNMP is enabled."
    -- NMS trap annotation
    --#TYPE "Webio Digital Alarm 8"
    --#SUMMARY "Alarm 8: %s"
    --#ARGUMENTS {0}
    --#SEVERITY INFORMATIONAL
    --#TIMEINDEX 99
    --#STATE OPERATIONAL    
    ::= 48

wtWebioEA12x6RelERPAlert9 TRAP-TYPE
    ENTERPRISE  wtWebioEA12x6RelERP
    VARIABLES   { wtWebioEA12x6RelERPAlarmSnmpTrapText }
    DESCRIPTION
        "This SNMP trap is generated when Alarm 9 was triggered,
        SNMP trap enable is set and
        SNMP is enabled."
    -- NMS trap annotation
    --#TYPE "Webio Digital Alarm 9"
    --#SUMMARY "Alarm 9: %s"
    --#ARGUMENTS {0}
    --#SEVERITY INFORMATIONAL
    --#TIMEINDEX 99
    --#STATE OPERATIONAL    
    ::= 49

wtWebioEA12x6RelERPAlert10 TRAP-TYPE
    ENTERPRISE  wtWebioEA12x6RelERP
    VARIABLES   { wtWebioEA12x6RelERPAlarmSnmpTrapText }
    DESCRIPTION
        "This SNMP trap is generated when Alarm 10 was triggered,
        SNMP trap enable is set and
        SNMP is enabled."
    -- NMS trap annotation
    --#TYPE "Webio Digital Alarm 10"
    --#SUMMARY "Alarm 10: %s"
    --#ARGUMENTS {0}
    --#SEVERITY INFORMATIONAL
    --#TIMEINDEX 99
    --#STATE OPERATIONAL    
    ::= 50

wtWebioEA12x6RelERPAlert11 TRAP-TYPE
    ENTERPRISE  wtWebioEA12x6RelERP
    VARIABLES   { wtWebioEA12x6RelERPAlarmSnmpTrapText }
    DESCRIPTION
        "This SNMP trap is generated when Alarm 11 was triggered,
        SNMP trap enable is set and
        SNMP is enabled."
    -- NMS trap annotation
    --#TYPE "Webio Digital Alarm 11"
    --#SUMMARY "Alarm 11: %s"
    --#ARGUMENTS {0}
    --#SEVERITY INFORMATIONAL
    --#TIMEINDEX 99
    --#STATE OPERATIONAL    
    ::= 51

wtWebioEA12x6RelERPAlert12 TRAP-TYPE
    ENTERPRISE  wtWebioEA12x6RelERP
    VARIABLES   { wtWebioEA12x6RelERPAlarmSnmpTrapText }
    DESCRIPTION
        "This SNMP trap is generated when Alarm 12 was triggered,
        SNMP trap enable is set and
        SNMP is enabled."
    -- NMS trap annotation
    --#TYPE "Webio Digital Alarm 12"
    --#SUMMARY "Alarm 12: %s"
    --#ARGUMENTS {0}
    --#SEVERITY INFORMATIONAL
    --#TIMEINDEX 99
    --#STATE OPERATIONAL    
    ::= 52

wtWebioEA12x6RelERPAlert13 TRAP-TYPE
    ENTERPRISE  wtWebioEA12x6RelERP
    VARIABLES   { wtWebioEA12x6RelERPAlarmSnmpTrapReleaseText }
    DESCRIPTION
        "This SNMP trap is generated when Alarm 1 was released,
        SNMP trap enable is set and
        SNMP is enabled."
    -- NMS trap annotation
    --#TYPE "Webio Digital Release Alarm 1"
    --#SUMMARY "Release Alarm 1: %s"
    --#ARGUMENTS {0}
    --#SEVERITY INFORMATIONAL
    --#TIMEINDEX 99
    --#STATE OPERATIONAL    
    ::= 71

wtWebioEA12x6RelERPAlert14 TRAP-TYPE
    ENTERPRISE  wtWebioEA12x6RelERP
    VARIABLES   { wtWebioEA12x6RelERPAlarmSnmpTrapReleaseText }
    DESCRIPTION
        "This SNMP trap is generated when Alarm 2 was released,
        SNMP trap enable is set and
        SNMP is enabled."
    -- NMS trap annotation
    --#TYPE "Webio Digital Release Alarm 2"
    --#SUMMARY "Release Alarm 2: %s"
    --#ARGUMENTS {0}
    --#SEVERITY INFORMATIONAL
    --#TIMEINDEX 99
    --#STATE OPERATIONAL    
    ::= 72

wtWebioEA12x6RelERPAlert15 TRAP-TYPE
    ENTERPRISE  wtWebioEA12x6RelERP
    VARIABLES   { wtWebioEA12x6RelERPAlarmSnmpTrapReleaseText }
    DESCRIPTION
        "This SNMP trap is generated when Alarm 3 was released,
        SNMP trap enable is set and
        SNMP is enabled."
    -- NMS trap annotation
    --#TYPE "Webio Digital Release Alarm 3"
    --#SUMMARY "Release Alarm 3: %s"
    --#ARGUMENTS {0}
    --#SEVERITY INFORMATIONAL
    --#TIMEINDEX 99
    --#STATE OPERATIONAL    
    ::= 73

wtWebioEA12x6RelERPAlert16 TRAP-TYPE
    ENTERPRISE  wtWebioEA12x6RelERP
    VARIABLES   { wtWebioEA12x6RelERPAlarmSnmpTrapReleaseText }
    DESCRIPTION
        "This SNMP trap is generated when Alarm 4 was released,
        SNMP trap enable is set and
        SNMP is enabled."
    -- NMS trap annotation
    --#TYPE "Webio Digital Release Alarm 4"
    --#SUMMARY "Release Alarm 4: %s"
    --#ARGUMENTS {0}
    --#SEVERITY INFORMATIONAL
    --#TIMEINDEX 99
    --#STATE OPERATIONAL    
    ::= 74

wtWebioEA12x6RelERPAlert17 TRAP-TYPE
    ENTERPRISE  wtWebioEA12x6RelERP
    VARIABLES   { wtWebioEA12x6RelERPAlarmSnmpTrapReleaseText }
    DESCRIPTION
        "This SNMP trap is generated when Alarm 5 was released,
        SNMP trap enable is set and
        SNMP is enabled."
    -- NMS trap annotation
    --#TYPE "Webio Digital Release Alarm 5"
    --#SUMMARY "Release Alarm 5: %s"
    --#ARGUMENTS {0}
    --#SEVERITY INFORMATIONAL
    --#TIMEINDEX 99
    --#STATE OPERATIONAL    
    ::= 75

wtWebioEA12x6RelERPAlert18 TRAP-TYPE
    ENTERPRISE  wtWebioEA12x6RelERP
    VARIABLES   { wtWebioEA12x6RelERPAlarmSnmpTrapReleaseText }
    DESCRIPTION
        "This SNMP trap is generated when Alarm 6 was released,
        SNMP trap enable is set and
        SNMP is enabled."
    -- NMS trap annotation
    --#TYPE "Webio Digital Release Alarm 6"
    --#SUMMARY "Release Alarm 6: %s"
    --#ARGUMENTS {0}
    --#SEVERITY INFORMATIONAL
    --#TIMEINDEX 99
    --#STATE OPERATIONAL    
    ::= 76

wtWebioEA12x6RelERPAlert19 TRAP-TYPE
    ENTERPRISE  wtWebioEA12x6RelERP
    VARIABLES   { wtWebioEA12x6RelERPAlarmSnmpTrapReleaseText }
    DESCRIPTION
        "This SNMP trap is generated when Alarm 7 was released,
        SNMP trap enable is set and
        SNMP is enabled."
    -- NMS trap annotation
    --#TYPE "Webio Digital Release Alarm 7"
    --#SUMMARY "Release Alarm 7: %s"
    --#ARGUMENTS {0}
    --#SEVERITY INFORMATIONAL
    --#TIMEINDEX 99
    --#STATE OPERATIONAL    
    ::= 77

wtWebioEA12x6RelERPAlert20 TRAP-TYPE
    ENTERPRISE  wtWebioEA12x6RelERP
    VARIABLES   { wtWebioEA12x6RelERPAlarmSnmpTrapReleaseText }
    DESCRIPTION
        "This SNMP trap is generated when Alarm 8 was released,
        SNMP trap enable is set and
        SNMP is enabled."
    -- NMS trap annotation
    --#TYPE "Webio Digital Release Alarm 8"
    --#SUMMARY "Release Alarm 8: %s"
    --#ARGUMENTS {0}
    --#SEVERITY INFORMATIONAL
    --#TIMEINDEX 99
    --#STATE OPERATIONAL    
    ::= 78

wtWebioEA12x6RelERPAlert21 TRAP-TYPE
    ENTERPRISE  wtWebioEA12x6RelERP
    VARIABLES   { wtWebioEA12x6RelERPAlarmSnmpTrapReleaseText }
    DESCRIPTION
        "This SNMP trap is generated when Alarm 9 was released,
        SNMP trap enable is set and
        SNMP is enabled."
    -- NMS trap annotation
    --#TYPE "Webio Digital Release Alarm 9"
    --#SUMMARY "Release Alarm 9: %s"
    --#ARGUMENTS {0}
    --#SEVERITY INFORMATIONAL
    --#TIMEINDEX 99
    --#STATE OPERATIONAL    
    ::= 79

wtWebioEA12x6RelERPAlert22 TRAP-TYPE
    ENTERPRISE  wtWebioEA12x6RelERP
    VARIABLES   { wtWebioEA12x6RelERPAlarmSnmpTrapReleaseText }
    DESCRIPTION
        "This SNMP trap is generated when Alarm 10 was released,
        SNMP trap enable is set and
        SNMP is enabled."
    -- NMS trap annotation
    --#TYPE "Webio Digital Release Alarm 10"
    --#SUMMARY "Release Alarm 10: %s"
    --#ARGUMENTS {0}
    --#SEVERITY INFORMATIONAL
    --#TIMEINDEX 99
    --#STATE OPERATIONAL    
    ::= 80

wtWebioEA12x6RelERPAlert23 TRAP-TYPE
    ENTERPRISE  wtWebioEA12x6RelERP
    VARIABLES   { wtWebioEA12x6RelERPAlarmSnmpTrapReleaseText }
    DESCRIPTION
        "This SNMP trap is generated when Alarm 11 was released,
        SNMP trap enable is set and
        SNMP is enabled."
    -- NMS trap annotation
    --#TYPE "Webio Digital Release Alarm 11"
    --#SUMMARY "Release Alarm 11: %s"
    --#ARGUMENTS {0}
    --#SEVERITY INFORMATIONAL
    --#TIMEINDEX 99
    --#STATE OPERATIONAL    
    ::= 81

wtWebioEA12x6RelERPAlert24 TRAP-TYPE
    ENTERPRISE  wtWebioEA12x6RelERP
    VARIABLES   { wtWebioEA12x6RelERPAlarmSnmpTrapReleaseText }
    DESCRIPTION
        "This SNMP trap is generated when Alarm 12 was released,
        SNMP trap enable is set and
        SNMP is enabled."
    -- NMS trap annotation
    --#TYPE "Webio Digital Release Alarm 12"
    --#SUMMARY "Release Alarm 12: %s"
    --#ARGUMENTS {0}
    --#SEVERITY INFORMATIONAL
    --#TIMEINDEX 99
    --#STATE OPERATIONAL    
    ::= 82

wtWebioEA12x6RelERPAlertDiag TRAP-TYPE
    ENTERPRISE  wtWebioEA12x6RelERP
    VARIABLES   { 	
    		wtWebioEA12x6RelERPDiagErrorIndex,
    	  	wtWebioEA12x6RelERPDiagErrorMessage
    		}
    DESCRIPTION
        "This SNMP trap is generated when a diagnosis/error message was triggered,
        SNMP trap enable is set and
        SNMP is enabled."
    -- NMS trap annotation
    --#TYPE "Webio Digital Diagnose Error"
    --#SUMMARY "Diagnose error index: %d, Message: %s."
    --#ARGUMENTS {0,1}
    --#SEVERITY MAJOR
    --#TIMEINDEX 99
    --#STATE DEGRADED    
    ::= 110

--------------------------------------------------------------------------------
--------------------------------------------------------------------------------
--------------------------------------------------------------------------------

-- wtIpWatcherInOut Group
------------------------

wtIpWatcherInputs OBJECT-TYPE
    SYNTAX INTEGER (1..2)
    ACCESS read-only
    STATUS mandatory
    DESCRIPTION
        "Number of idependent inputs."
    ::= { wtIpWatcherInOut 1 }

wtIpWatcherOutputs OBJECT-TYPE
    SYNTAX INTEGER (1..2)
    ACCESS read-only
    STATUS mandatory
    DESCRIPTION
        "Number of idependent outputs."
    ::= { wtIpWatcherInOut 2 }

-- Input Interface Table

wtIpWatcherInputTable OBJECT-TYPE
    SYNTAX SEQUENCE OF WtIpWatcherInputEntry
    ACCESS not-accessible
    STATUS mandatory
    DESCRIPTION
        "List of input indices."
    ::= { wtIpWatcherInOut 3 }

wtIpWatcherInputEntry OBJECT-TYPE
    SYNTAX WtIpWatcherInputEntry
    ACCESS not-accessible
    STATUS mandatory
    DESCRIPTION
        "Number of the inputs."
    INDEX  { wtIpWatcherInputNo }
    ::= { wtIpWatcherInputTable 1 }

WtIpWatcherInputEntry ::= SEQUENCE {
    wtIpWatcherInputNo INTEGER,
    wtIpWatcherInputCounter INTEGER,
    wtIpWatcherInputCounterClear INTEGER,
    wtIpWatcherInputState INTEGER
    
}

wtIpWatcherInputNo OBJECT-TYPE
    SYNTAX INTEGER (1)
    ACCESS read-only
    STATUS mandatory
    DESCRIPTION
        "Index numbers of the inputs."
    ::= { wtIpWatcherInputEntry 1 }

wtIpWatcherInputCounter OBJECT-TYPE
    SYNTAX INTEGER (1)
    ACCESS read-only
    STATUS mandatory
    DESCRIPTION
        "Value of the input counter."
    ::= { wtIpWatcherInputEntry 2 }
    
wtIpWatcherInputCounterClear OBJECT-TYPE
    SYNTAX INTEGER
    ACCESS read-only
    STATUS mandatory
    DESCRIPTION
        "Clears the input counter after returning its value."
    ::= { wtIpWatcherInputEntry 3 }
    
wtIpWatcherInputState OBJECT-TYPE
    SYNTAX INTEGER{
    wtIpWatcherInputState-OFF(0),
    wtIpWatcherInputState-ON(1)
    }
    ACCESS read-only
    STATUS mandatory
    DESCRIPTION
        "Value of a single input bit."
    ::= { wtIpWatcherInputEntry 4 }    
    
wtIpWatcherInputValue OBJECT-TYPE
    SYNTAX INTEGER 
    ACCESS read-only
    STATUS mandatory
    DESCRIPTION
        "This variable is used to read the inputs of the digital I/O port.
        The OCTETS are interpreted bit-by-bit, with each bit corresponding to an output.
        Bit 0 corresponds to the LSB.
        OCTET 1: unused
        OCTET 2: unused
        OCTET 3: unused
        OCTET 4, Bit 0-1: Digital outputs 0-1"
    ::= { wtIpWatcherInOut 4 }
    

-- Output Interface Table

wtIpWatcherOutputTable OBJECT-TYPE
    SYNTAX SEQUENCE OF WtIpWatcherOutputEntry
    ACCESS not-accessible
    STATUS mandatory
    DESCRIPTION
        "List of output indices."
    ::= { wtIpWatcherInOut 5 }

wtIpWatcherOutputEntry OBJECT-TYPE
    SYNTAX WtIpWatcherOutputEntry
    ACCESS not-accessible
    STATUS mandatory
    DESCRIPTION
        "Number of the outputs."
    INDEX  { wtIpWatcherOutputNo }
    ::= { wtIpWatcherOutputTable 1 }

WtIpWatcherOutputEntry ::= SEQUENCE {
    wtIpWatcherOutputNo 	INTEGER,
    wtIpWatcherOutputState 	INTEGER    
}

wtIpWatcherOutputNo OBJECT-TYPE
    SYNTAX INTEGER (1)
    ACCESS read-only
    STATUS mandatory
    DESCRIPTION
        "Output number."
    ::= { wtIpWatcherOutputEntry 1 }

wtIpWatcherOutputState OBJECT-TYPE
    SYNTAX INTEGER{
    wtIpWatcherOutputState-OFF(0),
    wtIpWatcherOutputState-ON(1)
    }
    ACCESS read-write
    STATUS mandatory
    DESCRIPTION
        "Value of a single output bit."
    ::= { wtIpWatcherOutputEntry 2 }
    

wtIpWatcherOutputValue OBJECT-TYPE
    SYNTAX INTEGER
    ACCESS read-write
    STATUS mandatory
    DESCRIPTION
        "This variable is used to read and write the outputs of the digital I/O port. 
        The OCTETS are interpreted bit-by-bit, with each bit corresponding to an output. 
        Bit 0 corresponds to the LSB.
        OCTET 1: unused
        OCTET 2: unused
        OCTET 3: unused
        OCTET 4, Bit 0-1: Digital outputs 0-1
        	 Bit 2-7: ungenutzt"
    ::= { wtIpWatcherInOut 6 }
    
wtIpWatcherSetOutput OBJECT-TYPE
    SYNTAX OCTET STRING (SIZE (8))
    ACCESS read-write			-- write-only
    STATUS mandatory
    DESCRIPTION
        "This variable allows setting of individual digital outputs. The OCTETS are 
        interpreted bit-by-bit, with each bit corresponding to an output. Bit 0 corresponds 
        to the LSB.
        The first two OCTETS contain the mask which determines which of the outputs are to 
        be set (corresponding bit = 1) and which outputs are to remain unchanged 
        (corresponding bit = 0):
	OCTET 1 : unused
	OCTET 2 : unused
	OCTET 3 : unused
	OCTET 4, Bit 0-1: Mask for digital outputs 0-1
	
	OCTETS 5-8 contain the level (1=HIGH, 0=LOW) which the outputs 
	should assume:
	OCTET 5 : unused
	OCTET 6 : unused
	OCTET 7 : unused
        OCTET 8, Bit 0-1: Level of digital outputs 0-1"
    ::= { wtIpWatcherInOut 7 }

-- Alarm Output Interface Table

wtIpWatcherAlarmOutputTable OBJECT-TYPE
    SYNTAX SEQUENCE OF WtIpWatcherAlarmOutputEntry
    ACCESS not-accessible
    STATUS mandatory
    DESCRIPTION
        "List of alarm indices.."
    ::= { wtIpWatcherInOut 8 }

wtIpWatcherAlarmOutputEntry OBJECT-TYPE
    SYNTAX WtIpWatcherAlarmOutputEntry
    ACCESS not-accessible
    STATUS mandatory
    DESCRIPTION
        "Index reference."
    INDEX  { wtIpWatcherAlarmNo }
    ::= { wtIpWatcherAlarmOutputTable 1 }

WtIpWatcherAlarmOutputEntry ::= SEQUENCE {
    wtIpWatcherAlarmOutputState	INTEGER,
    wtIpWatcherAlarmTriggerState	INTEGER
}

wtIpWatcherAlarmOutputState OBJECT-TYPE
    SYNTAX INTEGER{
    wtIpWatcherAlarmOutputState-OFF(0),
    wtIpWatcherAlarmOutputState-ON(1)
    }
    ACCESS read-write
    STATUS mandatory
    DESCRIPTION
        "State of the alarm."
    ::= { wtIpWatcherAlarmOutputEntry 1 }

wtIpWatcherAlarmTriggerState OBJECT-TYPE
    SYNTAX INTEGER{
    wtIpWatcherAlarmTriggerState-OFF(0),
    wtIpWatcherAlarmTriggerState-ON(1)
    }
    ACCESS read-only
    STATUS mandatory
    DESCRIPTION
        "State of the trigger condition."
    ::= { wtIpWatcherAlarmOutputEntry 2 }    
        
-- wtIpWatcherSessCntrl Group
--------------------------------

wtIpWatcherSessCntrlPassword OBJECT-TYPE
    SYNTAX OCTET STRING 
    ACCESS read-write
    STATUS mandatory
    DESCRIPTION
        "Entering this password opens a session which is ended by writing a 1 to 
        wtIpWatcherSessCntrlLogout. When read this variable provides a string of
        length zero."
    ::= { wtIpWatcherSessCntrl 1 }

wtIpWatcherSessCntrlConfigMode OBJECT-TYPE
    SYNTAX INTEGER {
    wtIpWatcherSessCntrl-NoSession(0),
    wtIpWatcherSessCntrl-Session(1)
    }
    ACCESS read-only
    STATUS mandatory
    DESCRIPTION
        "When the device is in SNMP configuration mode, the value 1 is
        returned, otherwise 0. If the read value is 0 even though the password
        was written, the device is already in config mode and the variables
        can only be read."
    ::= { wtIpWatcherSessCntrl 2 }

wtIpWatcherSessCntrlLogout OBJECT-TYPE
    SYNTAX INTEGER 
    ACCESS read-write
    STATUS mandatory
    DESCRIPTION
        "If the device is in configuration mode and the session was opened by
        this SNMP Manager, writing a 1 to this variable will end the session 
        and all parameters are stored.
        Writing a 2 discards all entries again. When read this variable
        provides the value 0."
    ::= { wtIpWatcherSessCntrl 3 }

wtIpWatcherSessCntrlAdminPassword OBJECT-TYPE
    SYNTAX OCTET STRING 
    ACCESS read-write
    STATUS mandatory
    DESCRIPTION
        "This password protects access to the variables with administrator rights.
        It can only be changed by the administrator. If no password was assigned,
        the valid password is public."
    ::= { wtIpWatcherSessCntrl 4 }

wtIpWatcherSessCntrlConfigPassword OBJECT-TYPE
    SYNTAX OCTET STRING 
    ACCESS read-write
    STATUS mandatory
    DESCRIPTION
        "This password protects access to the variables with configurator rights. It can
        be changed by the administrator and by the configurator. If no password was assigned, 
        the valid password is public. When read this variable provides a null-pointer."
    ::= { wtIpWatcherSessCntrl 5 }
    
-- wtIpWatcherText Group
------------------------

wtIpWatcherDeviceName OBJECT-TYPE
    SYNTAX OCTET STRING 
    ACCESS read-write
    STATUS mandatory
    DESCRIPTION
        "Name of the Webio, which is user definable."
    ::= { wtIpWatcherText 1 }

wtIpWatcherDeviceText OBJECT-TYPE
    SYNTAX OCTET STRING 
    ACCESS read-write
    STATUS mandatory
    DESCRIPTION
        "Description of the Webio, which is user definable."
    ::= { wtIpWatcherText 2 }
    
wtIpWatcherDeviceLocation OBJECT-TYPE
    SYNTAX OCTET STRING 
    ACCESS read-write
    STATUS mandatory
    DESCRIPTION
        "Description of the location of the Webio, which is user definable."
    ::= { wtIpWatcherText 3 }

wtIpWatcherDeviceContact OBJECT-TYPE
    SYNTAX OCTET STRING 
    ACCESS read-write
    STATUS mandatory
    DESCRIPTION
        "Contact address of the system operator of the Webio, which is user definable."
    ::= { wtIpWatcherText 4 }    

-- wtIpWatcherTimeZone Group
----------------------------

wtIpWatcherTzOffsetHrs OBJECT-TYPE
    SYNTAX INTEGER 
    ACCESS read-write
    STATUS mandatory
    DESCRIPTION
        "Offset hours for the time zone (winter time) with respect to UTC."
    ::= { wtIpWatcherTimeZone 1 }

wtIpWatcherTzOffsetMin OBJECT-TYPE
    SYNTAX INTEGER 
    ACCESS read-write
    STATUS mandatory
    DESCRIPTION
        "Offset minutes for the time zone (winter time) with respect to UTC."
    ::= { wtIpWatcherTimeZone 2 }

wtIpWatcherTzEnable OBJECT-TYPE
    SYNTAX OCTET STRING (SIZE(4))
    ACCESS read-write
    STATUS mandatory
    DESCRIPTION
        "Binary coded conditions:
        Octet 1: unused
        Octet 2: unused
        Octet 3: unused
        Octet 4:
        	Bit 1-7: unused
	        Bit 0  : Apply Timezone"
    ::= { wtIpWatcherTimeZone 3 }

wtIpWatcherStTzOffsetHrs OBJECT-TYPE
    SYNTAX INTEGER 
    ACCESS read-write
    STATUS mandatory
    DESCRIPTION
        "Offset hours of the time zone (summer time) with respect to UTC."
    ::= { wtIpWatcherTimeZone 4 }

wtIpWatcherStTzOffsetMin OBJECT-TYPE
    SYNTAX INTEGER 
    ACCESS read-write
    STATUS mandatory
    DESCRIPTION
        "Offset minutes of the time zone (summer time) with respect to UTC."
    ::= { wtIpWatcherTimeZone 5 }

wtIpWatcherStTzEnable OBJECT-TYPE
    SYNTAX OCTET STRING (SIZE(4))
    ACCESS read-write
    STATUS mandatory
    DESCRIPTION
        "Binary coded conditions:
        Octet 1: unused
        Octet 2: unused
        Octet 3: unused
        Octet 4:
        	Bit 1-7: unused
	        Bit 0  : Apply Summertime"
    ::= { wtIpWatcherTimeZone 6 }

wtIpWatcherStTzStartMonth OBJECT-TYPE
    SYNTAX INTEGER {
    	wtIpWatcherStartMonth-January(1),
    	wtIpWatcherStartMonth-February(2),
    	wtIpWatcherStartMonth-March(3),
    	wtIpWatcherStartMonth-April(4),
    	wtIpWatcherStartMonth-May(5),
    	wtIpWatcherStartMonth-June(6),
    	wtIpWatcherStartMonth-July(7),
    	wtIpWatcherStartMonth-August(8),
    	wtIpWatcherStartMonth-September(9),
    	wtIpWatcherStartMonth-October(10),
    	wtIpWatcherStartMonth-November(11),
    	wtIpWatcherStartMonth-December(12)
    	}
    	
    ACCESS read-write
    STATUS mandatory
    DESCRIPTION
        "Month in which the change is made from winter time to summer time."
    ::= { wtIpWatcherTimeZone 7 }

wtIpWatcherStTzStartMode OBJECT-TYPE
    SYNTAX INTEGER {
    	wtIpWatcherStartMode-first(1),
    	wtIpWatcherStartMode-second(2),
    	wtIpWatcherStartMode-third(3),
    	wtIpWatcherStartMode-fourth(4),
    	wtIpWatcherStartMode-last(5)
    	}
    	
    ACCESS read-write
    STATUS mandatory
    DESCRIPTION
        "Mode of the day of the week for which the change is made from winter time to summer time."
    ::= { wtIpWatcherTimeZone 8 }

wtIpWatcherStTzStartWday OBJECT-TYPE
    SYNTAX INTEGER {
    	wtIpWatcherStartWday-Sunday(1),
    	wtIpWatcherStartWday-Monday(2),
    	wtIpWatcherStartWday-Tuesday(3),
    	wtIpWatcherStartWday-Thursday(4),
    	wtIpWatcherStartWday-Wednesday(5),
    	wtIpWatcherStartWday-Friday(6),
    	wtIpWatcherStartWday-Saturday(7)
    	}
    	
    ACCESS read-write
    STATUS mandatory
    DESCRIPTION
        "Day of the week on which the change is made from winter time to summer time"
    ::= { wtIpWatcherTimeZone 9 }
    
wtIpWatcherStTzStartHrs OBJECT-TYPE
    SYNTAX INTEGER 
    ACCESS read-write
    STATUS mandatory
    DESCRIPTION
        "Hour in which the time zone is changed from winter to summer time with
        respect to UTC."
    ::= { wtIpWatcherTimeZone 10 }

wtIpWatcherStTzStartMin OBJECT-TYPE
    SYNTAX INTEGER 
    ACCESS read-write
    STATUS mandatory
    DESCRIPTION
        "Minute in which the time zone is changed from winter to summer time with
        respect to UTC."
    ::= { wtIpWatcherTimeZone 11 }
 
wtIpWatcherStTzStopMonth OBJECT-TYPE
    SYNTAX INTEGER {
    	wtIpWatcherStopMonth-January(1),
    	wtIpWatcherStopMonth-February(2),
    	wtIpWatcherStopMonth-March(3),
    	wtIpWatcherStopMonth-April(4),
    	wtIpWatcherStopMonth-May(5),
    	wtIpWatcherStopMonth-June(6),
    	wtIpWatcherStopMonth-July(7),
    	wtIpWatcherStopMonth-August(8),
    	wtIpWatcherStopMonth-September(9),
    	wtIpWatcherStopMonth-October(10),
    	wtIpWatcherStopMonth-November(11),
    	wtIpWatcherStopMonth-December(12)
    	}
    ACCESS read-write
    STATUS mandatory
    DESCRIPTION
        "Month in which the change is made from summer time to winter time."
   ::= { wtIpWatcherTimeZone 12 }

wtIpWatcherStTzStopMode OBJECT-TYPE
    SYNTAX INTEGER {
    	wtIpWatcherStopMode-first(1),
    	wtIpWatcherStopMode-second(2),
    	wtIpWatcherStopMode-third(3),
    	wtIpWatcherStopMode-fourth(4),
    	wtIpWatcherStopMode-last(5)
    	}
    ACCESS read-write
    STATUS mandatory
    DESCRIPTION
        "Mode of the week day on which the change is made from summer time to winter time."
    ::= { wtIpWatcherTimeZone 13 }

wtIpWatcherStTzStopWday OBJECT-TYPE
    SYNTAX INTEGER {
    	wtIpWatcherStopWday-Sunday(1),
    	wtIpWatcherStopWday-Monday(2),
    	wtIpWatcherStopWday-Tuesday(3),
    	wtIpWatcherStopWday-Thursday(4),
    	wtIpWatcherStopWday-Wednesday(5),
    	wtIpWatcherStopWday-Friday(6),
    	wtIpWatcherStopWday-Saturday(7)
    	}
    ACCESS read-write
    STATUS mandatory
    DESCRIPTION
        "Day of the week on which the change is made from summer time to winter time."
    ::= { wtIpWatcherTimeZone 14 }
    
wtIpWatcherStTzStopHrs OBJECT-TYPE
    SYNTAX INTEGER 
    ACCESS read-write
    STATUS mandatory
    DESCRIPTION
        "Hour at which the time zone is changed from summer to winter time with
        respect to UTC."
    ::= { wtIpWatcherTimeZone 15 }

wtIpWatcherStTzStopMin OBJECT-TYPE
    SYNTAX INTEGER 
    ACCESS read-write
    STATUS mandatory
    DESCRIPTION
        "Minute at which the time zone is changed from summer to winter time with
        respect to UTC."
    ::= { wtIpWatcherTimeZone 16 }

-- wtIpWatcherTimeServer Group
----------------------------

wtIpWatcherTimeServer1 OBJECT-TYPE
    SYNTAX OCTET STRING 
    ACCESS read-write
    STATUS mandatory
    DESCRIPTION
        "IP address or name of the 1st time server in ASCII"
    ::= { wtIpWatcherTimeServer 1 }

wtIpWatcherTimeServer2 OBJECT-TYPE
    SYNTAX OCTET STRING 
    ACCESS read-write
    STATUS mandatory
    DESCRIPTION
        "IP address or name of the 2nd time server in ASCII"
    ::= { wtIpWatcherTimeServer 2 }

wtIpWatcherTsEnable OBJECT-TYPE
    SYNTAX OCTET STRING (SIZE(4))
    ACCESS read-write
    STATUS mandatory
    DESCRIPTION
        "Binary coded conditions:
        Octet 1: unused
        Octet 2: unused
        Octet 3: unused
        Octet 4:
        	Bit 1-7: unused
	        Bit 0  : Apply Time Server"
    ::= { wtIpWatcherTimeServer 3 }

wtIpWatcherTsSyncTime OBJECT-TYPE
    SYNTAX INTEGER 
    ACCESS read-write
    STATUS mandatory
    DESCRIPTION
        "Daily synchronisation time with the time server (hour: 0-23)."
    ::= { wtIpWatcherTimeServer 4 }
      
    
-- wtIpWatcherDeviceClock Group
----------------------------

wtIpWatcherClockHrs OBJECT-TYPE
    SYNTAX INTEGER (0..23)
    ACCESS read-write
    STATUS mandatory
    DESCRIPTION
        "Clock hours taking into account the time zone settings."
    ::= { wtIpWatcherDeviceClock 1 }

wtIpWatcherClockMin OBJECT-TYPE
    SYNTAX INTEGER (0..59)
    ACCESS read-write
    STATUS mandatory
    DESCRIPTION
        "Clock minutes taking into account the time zone settings."
    ::= { wtIpWatcherDeviceClock 2 }

wtIpWatcherClockDay OBJECT-TYPE
    SYNTAX INTEGER (1..31)
    ACCESS read-write
    STATUS mandatory
    DESCRIPTION
        "Date: Day of the month, taking into account the time zone settings."
    ::= { wtIpWatcherDeviceClock 3 }

wtIpWatcherClockMonth OBJECT-TYPE
   SYNTAX INTEGER {
    	wtIpWatcherClockMonth-January(1),
    	wtIpWatcherClockMonth-February(2),
    	wtIpWatcherClockMonth-March(3),
    	wtIpWatcherClockMonth-April(4),
    	wtIpWatcherClockMonth-May(5),
    	wtIpWatcherClockMonth-June(6),
    	wtIpWatcherClockMonth-July(7),
    	wtIpWatcherClockMonth-August(8),
    	wtIpWatcherClockMonth-September(9),
    	wtIpWatcherClockMonth-October(10),
    	wtIpWatcherClockMonth-November(11),
    	wtIpWatcherClockMonth-December(12)
    	}
    ACCESS read-write
    STATUS mandatory
    DESCRIPTION
        "Date: Month, taking into account the time zone settings."
    ::= { wtIpWatcherDeviceClock 4 }

wtIpWatcherClockYear OBJECT-TYPE
    SYNTAX INTEGER (0..65535)
    ACCESS read-write
    STATUS mandatory
    DESCRIPTION
        "Date: Year, taking into account the time zone settings."
    ::= { wtIpWatcherDeviceClock 5 }

-- wtIpWatcherNetwork Group
------------------------

wtIpWatcherIpAddress OBJECT-TYPE
    SYNTAX IpAddress
    ACCESS read-write
    STATUS mandatory
    DESCRIPTION
        "IP address of the Webio"
    ::= { wtIpWatcherNetwork 1 }

wtIpWatcherSubnetMask OBJECT-TYPE
    SYNTAX IpAddress
    ACCESS read-write
    STATUS mandatory
    DESCRIPTION
        "Subnet mask of the Webio"
    ::= { wtIpWatcherNetwork 2 }

wtIpWatcherGateway OBJECT-TYPE
    SYNTAX IpAddress
    ACCESS read-write
    STATUS mandatory
    DESCRIPTION
        "Gateway of the Webio"
    ::= { wtIpWatcherNetwork 3 }

wtIpWatcherDnsServer1 OBJECT-TYPE
    SYNTAX OCTET STRING 
    ACCESS read-write
    STATUS mandatory
    DESCRIPTION
        "IP address of the 1st DNS server in ASCII"
    ::= { wtIpWatcherNetwork 4 }

wtIpWatcherDnsServer2 OBJECT-TYPE
    SYNTAX OCTET STRING 
    ACCESS read-write
    STATUS mandatory
    DESCRIPTION
        "IP address of the 2nd DNS server in ASCII"
    ::= { wtIpWatcherNetwork 5 }

wtIpWatcherAddConfig OBJECT-TYPE
    SYNTAX OCTET STRING 
    ACCESS read-write
    STATUS mandatory
    DESCRIPTION
        "Additional configuration (1=ON):
        Octet 1: unused
        Octet 2: unused
        Octet 3: unused
        Octet 4:
	        Bit 1: DHCP  enable
	        Bit 0: BOOTP enable"
    ::= { wtIpWatcherNetwork 6 }

--  wtIpWatcherHTTP Group
--------------------------------

wtIpWatcherHttpPort OBJECT-TYPE
    SYNTAX INTEGER (1..65534)
    ACCESS read-write
    STATUS mandatory
    DESCRIPTION
       "Definition of the standard HTML port (Default: 80)."
    ::= { wtIpWatcherHTTP 4 }        
    
    
-- wtIpWatcherMail Group
--------------------------------

wtIpWatcherMailAdName OBJECT-TYPE
    SYNTAX OCTET STRING 
    ACCESS read-write
    STATUS mandatory
    DESCRIPTION
        "Device name for mail administration."
    ::= { wtIpWatcherMail 1 }
    
wtIpWatcherMailReply OBJECT-TYPE
    SYNTAX OCTET STRING 
    ACCESS read-write
    STATUS mandatory
    DESCRIPTION
        "Reply address for the mail server."
    ::= { wtIpWatcherMail 2 }
    
wtIpWatcherMailServer OBJECT-TYPE
    SYNTAX OCTET STRING 
    ACCESS read-write
    STATUS mandatory
    DESCRIPTION
        "Name or IP address of the mail server."
    ::= { wtIpWatcherMail 3 }
    
wtIpWatcherMailEnable OBJECT-TYPE
    SYNTAX OCTET STRING 
    ACCESS read-write
    STATUS mandatory
    DESCRIPTION
        "Set this bit to enable the sending of mails:
        Octet 1: unused
        Octet 2: unused
        Octet 3: unused
        Octet 4:
        	Bit 1-7: unused
                Bit 0  : Mail enable"
    ::= { wtIpWatcherMail 4 }

wtIpWatcherMailAuthentication OBJECT-TYPE
    SYNTAX OCTET STRING (SIZE (4))
    ACCESS read-write
    STATUS mandatory
    DESCRIPTION
        "Selection of the authentication modi:
        The OCTETS are interpreted bit-by-bit,
        Bit 0 corresponds to the LSB.
        OCTET 1: unused
        OCTET 2: unused
        OCTET 3: unused
        OCTET 4: Bit 3-7: unused
        	 Bit 2  : POP3 before SMTP
        	 Bit 1  : ESMTP, authentication
        	 Bit 0  : SMTP, no authentication"
    ::= { wtIpWatcherMail 5 }
    
wtIpWatcherMailAuthUser OBJECT-TYPE
    SYNTAX OCTET STRING 
    ACCESS read-write
    STATUS mandatory
    DESCRIPTION
        "Name of the user to be authenticated."
    ::= { wtIpWatcherMail 6 }    
    
wtIpWatcherMailAuthPassword OBJECT-TYPE
    SYNTAX OCTET STRING 
    ACCESS read-write
    STATUS mandatory
    DESCRIPTION
        "Authentication password."
    ::= { wtIpWatcherMail 7 }    
    
wtIpWatcherMailPop3Server OBJECT-TYPE
    SYNTAX OCTET STRING 
    ACCESS read-write
    STATUS mandatory
    DESCRIPTION
        "Name or Ip-address of the POP3 Servers."
    ::= { wtIpWatcherMail 8 }        
    

--  wtIpWatcherSnmp Group
--------------------------------

wtIpWatcherSnmpEnable OBJECT-TYPE
    SYNTAX OCTET STRING 
    ACCESS read-write
    STATUS mandatory
    DESCRIPTION
        "Set bit 0 to enable SNMP.
        If disabled, the device did not respond to any SNMP requests.
        Bit 1 decided wether the community string of read operations 
        is compared with the system password or not:
        Octet 1: unused
        Octet 2: unused
        Octet 3: unused
        Octet 4:
        	Bit 1-7: unused
        	Bit 0  : SNMP enable"
    ::= { wtIpWatcherSNMP 1 }
    
wtIpWatcherSnmpCommunityStringRead OBJECT-TYPE
    SYNTAX OCTET STRING
    ACCESS read-write
    STATUS mandatory
    DESCRIPTION
        "Community string read only"
    ::= { wtIpWatcherSNMP 2 }

wtIpWatcherSnmpCommunityStringReadWrite OBJECT-TYPE
    SYNTAX OCTET STRING
    ACCESS read-write
    STATUS mandatory
    DESCRIPTION
        "Community string read / write"
    ::= { wtIpWatcherSNMP 3 }

wtIpWatcherSnmpSystemTrapManagerIP OBJECT-TYPE
    SYNTAX OCTET STRING 
    ACCESS read-write
    STATUS mandatory
    DESCRIPTION
        "Name or IP address of the TCP server which accepts the system trap."
    ::= { wtIpWatcherSNMP 4 }
    
wtIpWatcherSnmpSystemTrapEnable OBJECT-TYPE
    SYNTAX OCTET STRING (SIZE(4))
    ACCESS read-write
    STATUS mandatory
    DESCRIPTION
        "Binary coded trigger conditions:
        Octet 1: unused
        Octet 2: unused
        Octet 3: unused
        Octet 4:
	        Bit 0:   ColdStart
	        Bit 1:   WarmStart
	        Bit 2:   Diag messages
	        Bit 3-7: unused"
    ::= { wtIpWatcherSNMP 5 }    

-- wtIpWatcherUDP Group
--------------------------------   

wtIpWatcherUdpAdminPort OBJECT-TYPE
    SYNTAX INTEGER
    ACCESS read-write
    STATUS mandatory
    DESCRIPTION
        "Udp port to which the Udp queries ( short form GET requests) can be sent. This
        port number must be unique within the device."
    ::= { wtIpWatcherUDP 1 }

wtIpWatcherUdpEnable OBJECT-TYPE
    SYNTAX OCTET STRING 
    ACCESS read-write
    STATUS mandatory
    DESCRIPTION
        "Set this bit to enable UDP support:
        Octet 1: unused
        Octet 2: unused
        Octet 3: unused
        Octet 4:
        	Bit 1-7: unused
                Bit 0  : UDP enable"
    ::= { wtIpWatcherUDP 2 }

wtIpWatcherUdpRemotePort OBJECT-TYPE
    SYNTAX INTEGER
    ACCESS read-write
    STATUS mandatory
    DESCRIPTION
        "Udp remote port setting.
        If this value is set to zero, the source port read from a request will be used 
        as destination port for the answer.
        A non zero value forced the destination port to this value."
    ::= { wtIpWatcherUDP 3 }
    
--  wtIpWatcherSyslog Group
--------------------------------
    
wtIpWatcherSyslogServerIP OBJECT-TYPE
    SYNTAX OCTET STRING 
    ACCESS read-write
    STATUS mandatory
    DESCRIPTION
        "Name or IP address of the Syslog server, which accepts the Syslog messgaes."
    ::= { wtIpWatcherSyslog 1 }
    
wtIpWatcherSyslogServerPort OBJECT-TYPE
    SYNTAX INTEGER
    ACCESS read-write
    STATUS mandatory
    DESCRIPTION
        "Portnumber of the Syslog servers, default 514."
    ::= { wtIpWatcherSyslog 2 }

wtIpWatcherSyslogSystemMessagesEnable OBJECT-TYPE
    SYNTAX OCTET STRING (SIZE(4))
    ACCESS read-write
    STATUS mandatory
    DESCRIPTION
        "Binary coded trigger conditions:
        Octet 1: unused
        Octet 2: unused
        Octet 3: unused
        Octet 4:
	        Bit 0:   ColdStart
	        Bit 1:   WarmStart
	        Bit 2:   Diag Messages
	        Bit 3-7: unused"
    ::= { wtIpWatcherSyslog 3 }    

wtIpWatcherSyslogEnable OBJECT-TYPE
    SYNTAX OCTET STRING 
    ACCESS read-write
    STATUS mandatory
    DESCRIPTION
        "Set bit 0to enable Syslog:
        Octet 1: unused
        Octet 2: unused
        Octet 3: unused
        Octet 4:
        	Bit 1-7: unused
                Bit 0  : Syslog enable"
    ::= { wtIpWatcherSyslog 4 }

--  wtIpWatcherFTP Group
--------------------------------

wtIpWatcherFTPServerIP OBJECT-TYPE
    SYNTAX OCTET STRING 
    ACCESS read-write
    STATUS mandatory
    DESCRIPTION
        "Name or IP address of the FTP server, which accepts the FTP messages."
    ::= { wtIpWatcherFTP 1 }
    
wtIpWatcherFTPServerControlPort OBJECT-TYPE
    SYNTAX INTEGER
    ACCESS read-write
    STATUS mandatory
    DESCRIPTION
        "Portnumber of the control port of the FTP server, default 21."
    ::= { wtIpWatcherFTP 2 }
    
wtIpWatcherFTPUserName OBJECT-TYPE
    SYNTAX OCTET STRING 
    ACCESS read-write
    STATUS mandatory
    DESCRIPTION
        "FTP Loggin: user name."
    ::= { wtIpWatcherFTP 3 }
    
wtIpWatcherFTPPassword OBJECT-TYPE
    SYNTAX OCTET STRING 
    ACCESS read-write
    STATUS mandatory
    DESCRIPTION
        "FTP Loggin: user password."
    ::= { wtIpWatcherFTP 4 }

wtIpWatcherFTPAccount OBJECT-TYPE
    SYNTAX OCTET STRING 
    ACCESS read-write
    STATUS mandatory
    DESCRIPTION
        "FTP Loggin: name of account."
    ::= { wtIpWatcherFTP 5 }

wtIpWatcherFTPOption OBJECT-TYPE
    SYNTAX OCTET STRING 
    ACCESS read-write
    STATUS mandatory
    DESCRIPTION
        "Bit 0 switches the FTP Server in Passiv-Mode,
        the Client controls the data connection on its own:
        Octet 1: unused
        Octet 2: unused
        Octet 3: unused
        Octet 4:
        	Bit 1-7: unused
                Bit 0  : PASV enable"
    ::= { wtIpWatcherFTP 6 }
    
wtIpWatcherFTPEnable OBJECT-TYPE
    SYNTAX OCTET STRING 
    ACCESS read-write
    STATUS mandatory
    DESCRIPTION
        "Set Bit 0 to enable FTP:
        Octet 1: unused
        Octet 2: unused
        Octet 3: unused
        Octet 4:
        	Bit 1-7: unused
                Bit 0  : FTP enable"
    ::= { wtIpWatcherFTP 7 }
    
-- wtIpWatcherIpList Group
----------------------------

wtIpWatcherIpListCount OBJECT-TYPE
    SYNTAX INTEGER
    ACCESS read-only
    STATUS mandatory
    DESCRIPTION
        "Number of Ip addresses."
    ::= { wtIpWatcherIpList 1 }
    
-- IpList Interface Table

wtIpWatcherIpListIfTable OBJECT-TYPE
    SYNTAX SEQUENCE OF WtIpWatcherIpListIfEntry
    ACCESS not-accessible
    STATUS mandatory
    DESCRIPTION
        "Table of inices."
    ::= { wtIpWatcherIpList 2 }

wtIpWatcherIpListIfEntry OBJECT-TYPE
    SYNTAX WtIpWatcherIpListIfEntry
    ACCESS not-accessible
    STATUS mandatory
    DESCRIPTION
        "Table entry."
    INDEX  { wtIpWatcherIpListNo }
    ::= { wtIpWatcherIpListIfTable 1 }

WtIpWatcherIpListIfEntry ::= SEQUENCE {
    wtIpWatcherIpListNo 	INTEGER
}

wtIpWatcherIpListNo OBJECT-TYPE
    SYNTAX INTEGER (1..999)
    ACCESS read-only
    STATUS mandatory
    DESCRIPTION
        "List number of this entry."
    ::= { wtIpWatcherIpListIfEntry 1 }

-- IpList Table

wtIpWatcherIpListTable OBJECT-TYPE
    SYNTAX SEQUENCE OF WtIpWatcherIpListEntry
    ACCESS not-accessible
    STATUS mandatory
    DESCRIPTION
        "List of ip addresses."
    ::= { wtIpWatcherIpList 3 }

wtIpWatcherIpListEntry OBJECT-TYPE
    SYNTAX WtIpWatcherIpListEntry
    ACCESS not-accessible
    STATUS mandatory
    DESCRIPTION
        "List entry."
    INDEX  { wtIpWatcherIpListNo }
    ::= { wtIpWatcherIpListTable 1 }

WtIpWatcherIpListEntry ::= SEQUENCE {
    wtIpWatcherIpListName 	OCTET STRING,
    wtIpWatcherIpListPort 	INTEGER,
    wtIpWatcherIpListService 	OCTET STRING,
    wtIpWatcherIpListEnable 	OCTET STRING,
    wtIpWatcherIpListAlias 	OCTET STRING
}

wtIpWatcherIpListName OBJECT-TYPE
    SYNTAX OCTET STRING 
    ACCESS read-write
    STATUS mandatory
    DESCRIPTION
        "Name or IP address."
    ::= { wtIpWatcherIpListEntry 1 }
    
wtIpWatcherIpListPort OBJECT-TYPE
    SYNTAX INTEGER 
    ACCESS read-write
    STATUS mandatory
    DESCRIPTION
        "Port number, zero in the case of broadcast or Ping."
    ::= { wtIpWatcherIpListEntry 2 }
    
wtIpWatcherIpListService OBJECT-TYPE
    SYNTAX OCTET STRING 
    ACCESS read-write
    STATUS mandatory
    DESCRIPTION
        "Binary coded scan mode, only one mode can be selected at a particular time:
        Octet 1: unused
        Octet 2: unused
        Octet 3: unused
        Octet 4:
		Bit 0:	Ping enable
        	Bit 1-7: unused"
    ::= { wtIpWatcherIpListEntry 3 }
    
wtIpWatcherIpListEnable OBJECT-TYPE
    SYNTAX OCTET STRING 
    ACCESS read-write
    STATUS mandatory
    DESCRIPTION
        "Binary coded alarm enable:
        Octet 1: unused
        Octet 2: unused
        Octet 3: unused
        Octet 4:
		Bit 0:	enabled in Alarm 1
        	Bit 1:	enabled in Alarm 2
        	Bit 2:  enabled in Alarm 3
        	Bit 3:  enabled in Alarm 4
        	Bit 4-7: unused"
    ::= { wtIpWatcherIpListEntry 4 }

wtIpWatcherIpListAlias OBJECT-TYPE
    SYNTAX OCTET STRING 
    ACCESS read-write
    STATUS mandatory
    DESCRIPTION
        "Alias Name"
    ::= { wtIpWatcherIpListEntry 5 }

 
-- wtIpWatcherAlarm Group
----------------------------

wtIpWatcherAlarmCount OBJECT-TYPE
    SYNTAX INTEGER (1..4)
    ACCESS read-only
    STATUS mandatory
    DESCRIPTION
        "Number of independent alarms."
    ::= { wtIpWatcherAlarm 1 }
    
-- Alarm Interface Table

wtIpWatcherAlarmIfTable OBJECT-TYPE
    SYNTAX SEQUENCE OF WtIpWatcherAlarmIfEntry
    ACCESS not-accessible
    STATUS mandatory
    DESCRIPTION
        "List of alarm indices."
    ::= { wtIpWatcherAlarm 2 }

wtIpWatcherAlarmIfEntry OBJECT-TYPE
    SYNTAX WtIpWatcherAlarmIfEntry
    ACCESS not-accessible
    STATUS mandatory
    DESCRIPTION
        "Numbers of the alarms."
    INDEX  { wtIpWatcherAlarmNo }
    ::= { wtIpWatcherAlarmIfTable 1 }

WtIpWatcherAlarmIfEntry ::= SEQUENCE {
    wtIpWatcherAlarmNo INTEGER
}

wtIpWatcherAlarmNo OBJECT-TYPE
    SYNTAX INTEGER (1..4)
    ACCESS read-only
    STATUS mandatory
    DESCRIPTION
        "Numbers of the alarms."
    ::= { wtIpWatcherAlarmIfEntry 1 }

-- Alarm Table

wtIpWatcherAlarmTable OBJECT-TYPE
    SYNTAX SEQUENCE OF WtIpWatcherAlarmEntry
    ACCESS not-accessible
    STATUS mandatory
    DESCRIPTION
        "List of settings depending on the alarm number."
    ::= { wtIpWatcherAlarm 3 }

wtIpWatcherAlarmEntry OBJECT-TYPE
    SYNTAX WtIpWatcherAlarmEntry
    ACCESS not-accessible
    STATUS mandatory
    DESCRIPTION
        "Alarm parameters of the individual alarms."
    INDEX  { wtIpWatcherAlarmNo }
    ::= { wtIpWatcherAlarmTable 1 }

WtIpWatcherAlarmEntry ::= SEQUENCE {
    wtIpWatcherAlarmInterval			OCTET STRING,
    wtIpWatcherAlarmEnable			OCTET STRING,
    wtIpWatcherAlarmMailAddr			OCTET STRING,
    wtIpWatcherAlarmMailSubject			OCTET STRING,
    wtIpWatcherAlarmMailText			OCTET STRING,
    wtIpWatcherAlarmSnmpManagerIP		OCTET STRING,
    wtIpWatcherAlarmSnmpTrapText		OCTET STRING,
    wtIpWatcherAlarmUdpIpAddr			OCTET STRING,
    wtIpWatcherAlarmUdpPort			INTEGER,
    wtIpWatcherAlarmUdpText			OCTET STRING,
    wtIpWatcherAlarmTcpIpAddr			OCTET STRING,
    wtIpWatcherAlarmTcpPort			INTEGER,
    wtIpWatcherAlarmTcpText			OCTET STRING,    
    wtIpWatcherAlarmSyslogIpAddr		OCTET STRING,
    wtIpWatcherAlarmSyslogPort			INTEGER,
    wtIpWatcherAlarmSyslogText			OCTET STRING,
    wtIpWatcherAlarmFtpDataPort			OCTET STRING,
    wtIpWatcherAlarmFtpFileName			OCTET STRING,
    wtIpWatcherAlarmFtpText			OCTET STRING,
    wtIpWatcherAlarmFtpOption			OCTET STRING,
    wtIpWatcherAlarmTimerCron			OCTET STRING,
    
    wtIpWatcherAlarmMailReleaseSubject		OCTET STRING,
    wtIpWatcherAlarmMailReleaseText		OCTET STRING,
    wtIpWatcherAlarmSnmpTrapReleaseText		OCTET STRING,
    wtIpWatcherAlarmUdpReleaseText		OCTET STRING,
    wtIpWatcherAlarmTcpReleaseText		OCTET STRING,    
    wtIpWatcherAlarmSyslogReleaseText		OCTET STRING,
    wtIpWatcherAlarmFtpReleaseText		OCTET STRING,
    
    wtIpWatcherAlarmName			OCTET STRING,
    wtIpWatcherAlarmGlobalEnable		OCTET STRING,
    wtIpWatcherAlarmCounterClear		OCTET STRING,
    wtIpWatcherAlarmAckEnable			OCTET STRING,
    wtIpWatcherAlarmAckPort			INTEGER,
    wtIpWatcherAlarmSetPort			INTEGER,
    
    wtIpWatcherAlarmMailTrgClearSubject		OCTET STRING,
    wtIpWatcherAlarmMailTrgClearText		OCTET STRING,
    wtIpWatcherAlarmSnmpTrapTrgClearText	OCTET STRING,
    wtIpWatcherAlarmUdpTrgClearText		OCTET STRING,
    wtIpWatcherAlarmTcpTrgClearText		OCTET STRING,    
    wtIpWatcherAlarmSyslogTrgClearText		OCTET STRING,
    wtIpWatcherAlarmFtpTrgClearText		OCTET STRING,
    
    wtIpWatcherAlarmMailTrapTxEnable		OCTET STRING,
    wtIpWatcherAlarmSnmpTrapTrapTxEnable	OCTET STRING,
    wtIpWatcherAlarmUdpTrapTxEnable		OCTET STRING,
    wtIpWatcherAlarmTcpTrapTxEnable		OCTET STRING,    
    wtIpWatcherAlarmSyslogTrapTxEnable		OCTET STRING,
    wtIpWatcherAlarmFtpTrapTxEnable		OCTET STRING,
    
    wtIpWatcherAlarmTriggerCount		INTEGER,
    wtIpWatcherAlarmPollingRate			INTEGER
}




wtIpWatcherAlarmInterval OBJECT-TYPE
    SYNTAX OCTET STRING 
    ACCESS read-write
    STATUS mandatory
    DESCRIPTION
        "Send interval for alarm messages."
    ::= { wtIpWatcherAlarmEntry 5 }

wtIpWatcherAlarmEnable OBJECT-TYPE
    SYNTAX OCTET STRING (SIZE(4))
    ACCESS read-write
    STATUS mandatory
    DESCRIPTION
        "Binary coded alarm enable:
        Octet 1: unused
        Octet 2: unused
        Octet 3: unused
        Octet 4:
		Bit 0:	Mail Enable
        	Bit 1:	SNMP Trap enable
        	Bit 2:  UDP enable
        	Bit 3:  Send inputs to pending TCP connections
        	Bit 4:  TCP Client enable
        	Bit 5:	Syslog Messages enable
        	Bit 6-7: unused"
    ::= { wtIpWatcherAlarmEntry 6 }

wtIpWatcherAlarmMailAddr OBJECT-TYPE
    SYNTAX OCTET STRING 
    ACCESS read-write
    STATUS mandatory
    DESCRIPTION
        "E-Mail address for sending the alarm mail to."
    ::= { wtIpWatcherAlarmEntry 7 }

wtIpWatcherAlarmMailSubject OBJECT-TYPE
    SYNTAX OCTET STRING 
    ACCESS read-write
    STATUS mandatory
    DESCRIPTION
        "Subject line for alarm mail."
    ::= { wtIpWatcherAlarmEntry 8 }

wtIpWatcherAlarmMailText OBJECT-TYPE
    SYNTAX OCTET STRING 
    ACCESS read-write
    STATUS mandatory
    DESCRIPTION
        "Alarm mail text: 
        States of the Webio device can be included by using special tags.
        Please refer to the respective Webio manual"
    ::= { wtIpWatcherAlarmEntry 9 }

wtIpWatcherAlarmSnmpManagerIP OBJECT-TYPE
    SYNTAX OCTET STRING 
    ACCESS read-write
    STATUS mandatory
    DESCRIPTION
        "IP address of the SNMP Manager to which the Webio device should send SNMP traps."
    ::= { wtIpWatcherAlarmEntry 10 }

wtIpWatcherAlarmSnmpTrapText OBJECT-TYPE
    SYNTAX OCTET STRING 
    ACCESS read-write
    STATUS mandatory
    DESCRIPTION
        "This text appears in the trap body."
    ::= { wtIpWatcherAlarmEntry 11 }
    
wtIpWatcherAlarmUdpIpAddr OBJECT-TYPE
    SYNTAX OCTET STRING 
    ACCESS read-write
    STATUS mandatory
    DESCRIPTION
        "IP address of the UDP listener to which the Webio device should send UDP traps."
    ::= { wtIpWatcherAlarmEntry 12 }    

wtIpWatcherAlarmUdpPort OBJECT-TYPE
    SYNTAX INTEGER (1..65535) 
    ACCESS read-write
    STATUS mandatory
    DESCRIPTION
        "Port number of the UDP listener to which the Webio device should send UDP traps."
    ::= { wtIpWatcherAlarmEntry 13 }    

wtIpWatcherAlarmUdpText OBJECT-TYPE
    SYNTAX OCTET STRING 
    ACCESS read-write
    STATUS mandatory
    DESCRIPTION
        "This text appears in the UDP trap body."
    ::= { wtIpWatcherAlarmEntry 14 }
    
wtIpWatcherAlarmTcpIpAddr OBJECT-TYPE
    SYNTAX OCTET STRING
    ACCESS read-write
    STATUS mandatory
    DESCRIPTION
        "IP address of the TCP listener to which the Webio device should send TCP traps."
    ::= { wtIpWatcherAlarmEntry 15 }    

wtIpWatcherAlarmTcpPort OBJECT-TYPE
    SYNTAX INTEGER (1..65535) 
    ACCESS read-write
    STATUS mandatory
    DESCRIPTION
        "Port number of the TCP listener to which the Webio device should send TCP traps."
    ::= { wtIpWatcherAlarmEntry 16 }    

wtIpWatcherAlarmTcpText OBJECT-TYPE
    SYNTAX OCTET STRING 
    ACCESS read-write
    STATUS mandatory
    DESCRIPTION
        "This text appears in the TCP trap body."
    ::= { wtIpWatcherAlarmEntry 17 }

wtIpWatcherAlarmSyslogIpAddr OBJECT-TYPE
    SYNTAX OCTET STRING 
    ACCESS read-write
    STATUS mandatory
    DESCRIPTION
        "IP address of the syslog server to which the Webio device should send syslog messages."
    ::= { wtIpWatcherAlarmEntry 18 }    

wtIpWatcherAlarmSyslogPort OBJECT-TYPE
    SYNTAX INTEGER (1..65535) 
    ACCESS read-write
    STATUS mandatory
    DESCRIPTION
        "Port number of the syslog server to which the Webio device should send syslog messages."
    ::= { wtIpWatcherAlarmEntry 19 }    

wtIpWatcherAlarmSyslogText OBJECT-TYPE
    SYNTAX OCTET STRING 
    ACCESS read-write
    STATUS mandatory
    DESCRIPTION
        "Every message starts with the priority key, a time stamp and the host ip address, according RFC3164.
        This text appears in the following syslog message body."
    ::= { wtIpWatcherAlarmEntry 20 }    
    
wtIpWatcherAlarmFtpDataPort OBJECT-TYPE
    SYNTAX OCTET STRING 
    ACCESS read-write
    STATUS mandatory
    DESCRIPTION
        "Local data port: 1..65535 or AUTO: the next free port will be assigned."
    ::= { wtIpWatcherAlarmEntry 21 }
    
wtIpWatcherAlarmFtpFileName OBJECT-TYPE
    SYNTAX OCTET STRING 
    ACCESS read-write
    STATUS mandatory
    DESCRIPTION
        "Name of the file including path informations."
    ::= { wtIpWatcherAlarmEntry 22 }
    
wtIpWatcherAlarmFtpText OBJECT-TYPE
    SYNTAX OCTET STRING 
    ACCESS read-write
    STATUS mandatory
    DESCRIPTION
        "Message text to store on the FTP server."
    ::= { wtIpWatcherAlarmEntry 23 }

wtIpWatcherAlarmFtpOption OBJECT-TYPE
    SYNTAX OCTET STRING (SIZE(4))
    ACCESS read-write
    STATUS mandatory
    DESCRIPTION
        "Binary coded options, select only one option at the same time:
        STORE  = replace file
        APPEND = append message at the end of the file
        
        Octet 1: unused
        Octet 2: unused
        Octet 3: unused
        Octet 4:
		Bit 0  :	STORE
		Bit 1  :	APPEND
        	Bit 2-7:	unused"
    ::= { wtIpWatcherAlarmEntry 24 }      
    
wtIpWatcherAlarmTimerCron OBJECT-TYPE
    SYNTAX OCTET STRING
    ACCESS read-write
    STATUS mandatory
    DESCRIPTION
        "This entry contains 5 space or tab seperated text fields for time trigger definition.
        Each field must match with the actual time to trigger a message, weekday and day of month
        are interpreted separatley.
        1: Minutes	Range 0-59
        2. Hours	Range 0-23, 0 is midnight
        3: Day of month	Range 1-31
        4: Month	Range 1-12
        5: Weekday	Range 0-6, 0 is sunday
        
        Syntax for every field:
         - an asterix (*) enables every possible setting of a field
         - single numbers seperated by commas
         - a partition within the allowed range (1-5)
         - step size within an partition of the allowed range (0-59/2: every second minute)."
    ::= { wtIpWatcherAlarmEntry 25 }      

wtIpWatcherAlarmMailReleaseSubject OBJECT-TYPE
    SYNTAX OCTET STRING 
    ACCESS read-write
    STATUS mandatory
    DESCRIPTION
       "Subject line for alarm mail."
    ::= { wtIpWatcherAlarmEntry 26 }

wtIpWatcherAlarmMailReleaseText OBJECT-TYPE
    SYNTAX OCTET STRING 
    ACCESS read-write
    STATUS mandatory
    DESCRIPTION
        "Release Alarm mail text: 
        States of the Webio device can be included by using special tags.
        Please refer to the respective Webio manual"
    ::= { wtIpWatcherAlarmEntry 27 }    

wtIpWatcherAlarmSnmpTrapReleaseText OBJECT-TYPE
    SYNTAX OCTET STRING 
    ACCESS read-write
    STATUS mandatory
    DESCRIPTION
        "This text appears in the trap body."
    ::= { wtIpWatcherAlarmEntry 28 }

wtIpWatcherAlarmUdpReleaseText OBJECT-TYPE
    SYNTAX OCTET STRING 
    ACCESS read-write
    STATUS mandatory
    DESCRIPTION
        "This text appears in the UDP trap body."
    ::= { wtIpWatcherAlarmEntry 29 }

wtIpWatcherAlarmTcpReleaseText OBJECT-TYPE
    SYNTAX OCTET STRING 
    ACCESS read-write
    STATUS mandatory
    DESCRIPTION
        "This text appears in the TCP trap body."
    ::= { wtIpWatcherAlarmEntry 30 }

wtIpWatcherAlarmSyslogReleaseText OBJECT-TYPE
    SYNTAX OCTET STRING 
    ACCESS read-write
    STATUS mandatory
    DESCRIPTION
        "Every message starts with the priority key, a time stamp and the host ip address, according RFC3164.
        This text appears in the following syslog message body."
    ::= { wtIpWatcherAlarmEntry 31 }

wtIpWatcherAlarmFtpReleaseText OBJECT-TYPE
    SYNTAX OCTET STRING 
    ACCESS read-write
    STATUS mandatory
    DESCRIPTION
        "Message text to store on the FTP server."
    ::= { wtIpWatcherAlarmEntry 32 }

wtIpWatcherAlarmName OBJECT-TYPE
    SYNTAX OCTET STRING 
    ACCESS read-write
    STATUS mandatory
    DESCRIPTION
        "Name of the alarm."
    ::= { wtIpWatcherAlarmEntry 33 }    

wtIpWatcherAlarmGlobalEnable OBJECT-TYPE
    SYNTAX OCTET STRING 
    ACCESS read-write
    STATUS mandatory
    DESCRIPTION
        "Binary coded alarm activation:
        Die OCTETS werden bitweise interpretiert.
        Bit 0 entspricht dem LSB.
        OCTET 1: unused
        OCTET 2: unused
        OCTET 3: unused
        OCTET 4, Bit 1-7: unused
        	 Bit 0  : Alarm enable"
    ::= { wtIpWatcherAlarmEntry 34 }    

wtIpWatcherAlarmCounterClear OBJECT-TYPE
    SYNTAX OCTET STRING 
    ACCESS read-write
    STATUS mandatory
    DESCRIPTION
        "Binary coded options:
        The OCTETS are interpreted bit-by-bit. 
        Bit 0 corresponds to the LSB.
        OCTET 1: unused
        OCTET 2: unused
        OCTET 3: unused
        OCTET 4, Bit 2-7: unused
        	 Bit 1  : Counter clear on Alarm acknowledge 
        	 Bit 0  : Counter clear on Alarm send"
    ::= { wtIpWatcherAlarmEntry 35 }


    wtIpWatcherAlarmAckEnable OBJECT-TYPE
    SYNTAX OCTET STRING 
    ACCESS read-write
    STATUS mandatory
    DESCRIPTION
        "Binary coded options:
        The OCTETS are interpreted bit-by-bit. 
        Bit 0 corresponds to the LSB.
        OCTET 1: unused
        OCTET 2: unused
        OCTET 3: unused
        OCTET 4, Bit 2-7: unused
        	 Bit 1  : Software acknowledge enable
        	 Bit 0  : Hardware acknowledge enable"
    ::= { wtIpWatcherAlarmEntry 36 }


    wtIpWatcherAlarmAckPort OBJECT-TYPE
    SYNTAX INTEGER 
    ACCESS read-write
    STATUS mandatory
    DESCRIPTION
        "Number of the input, which clears the alarm (1-6)."
    ::= { wtIpWatcherAlarmEntry 37 }

    wtIpWatcherAlarmSetPort OBJECT-TYPE
    SYNTAX INTEGER 
    ACCESS read-write
    STATUS mandatory
    DESCRIPTION
        "Number of the output, which will be set by this alarm (1-6).
        The configuration of pulse mode and polarity defined in the port output section is used."
    ::= { wtIpWatcherAlarmEntry 38 }
    
wtIpWatcherAlarmMailTrgClearSubject OBJECT-TYPE
    SYNTAX OCTET STRING 
    ACCESS read-write
    STATUS mandatory
    DESCRIPTION
        "Subject line for alarm mail."
    ::= { wtIpWatcherAlarmEntry 39 }

wtIpWatcherAlarmMailTrgClearText OBJECT-TYPE
    SYNTAX OCTET STRING 
    ACCESS read-write
    STATUS mandatory
    DESCRIPTION
        "Alarm mail text: 
        States of the Webio device can be included by using special tags.
        Please refer to the respective Webio manual"
    ::= { wtIpWatcherAlarmEntry 40 }    

wtIpWatcherAlarmSnmpTrapTrgClearText OBJECT-TYPE
    SYNTAX OCTET STRING 
    ACCESS read-write
    STATUS mandatory
    DESCRIPTION
        "This text appears in the trap body."
    ::= { wtIpWatcherAlarmEntry 41 }

wtIpWatcherAlarmUdpTrgClearText OBJECT-TYPE
    SYNTAX OCTET STRING 
    ACCESS read-write
    STATUS mandatory
    DESCRIPTION
        "This text appears in the UDP trap body."
    ::= { wtIpWatcherAlarmEntry 42 }

wtIpWatcherAlarmTcpTrgClearText OBJECT-TYPE
    SYNTAX OCTET STRING 
    ACCESS read-write
    STATUS mandatory
    DESCRIPTION
      "This text appears in the TCP trap body."
    ::= { wtIpWatcherAlarmEntry 43 }

wtIpWatcherAlarmSyslogTrgClearText OBJECT-TYPE
    SYNTAX OCTET STRING 
    ACCESS read-write
    STATUS mandatory
    DESCRIPTION
        "Every message starts with the priority key, a time stamp and the host ip address, according RFC3164.
        This text appears in the following syslog message body."
    ::= { wtIpWatcherAlarmEntry 44 }

wtIpWatcherAlarmFtpTrgClearText OBJECT-TYPE
    SYNTAX OCTET STRING 
    ACCESS read-write
    STATUS mandatory
    DESCRIPTION
        "Message text to store on the FTP server."
    ::= { wtIpWatcherAlarmEntry 45 }     

    wtIpWatcherAlarmMailTrapTxEnable OBJECT-TYPE
    SYNTAX OCTET STRING 
    ACCESS read-write
    STATUS mandatory
    DESCRIPTION
        "Binary coded options:
        The OCTETS are interpreted bit-by-bit. 
        Bit 0 corresponds to the LSB.
        OCTET 1: unused
        OCTET 2: unused
        OCTET 3: unused
        OCTET 4, Bit 4-7: unused
        	 Bit 3  : Alarm OFF message enable
        	 Bit 2  : Trigger OFF message enable
        	 Bit 1  : Re-Trigger message enable
        	 Bit 0  : Alarm ON message enable"
    ::= { wtIpWatcherAlarmEntry 46 }

    wtIpWatcherAlarmSnmpTrapTrapTxEnable OBJECT-TYPE
    SYNTAX OCTET STRING 
    ACCESS read-write
    STATUS mandatory
    DESCRIPTION
        "Binary coded options:
        The OCTETS are interpreted bit-by-bit. 
        Bit 0 corresponds to the LSB.
        OCTET 1: unused
        OCTET 2: unused
        OCTET 3: unused
        OCTET 4, Bit 4-7: unused
        	 Bit 3  : Alarm OFF message enable
        	 Bit 2  : Trigger OFF message enable
        	 Bit 1  : Re-Trigger message enable
        	 Bit 0  : Alarm ON message enable"
    ::= { wtIpWatcherAlarmEntry 47 }

    wtIpWatcherAlarmUdpTrapTxEnable OBJECT-TYPE
    SYNTAX OCTET STRING 
    ACCESS read-write
    STATUS mandatory
    DESCRIPTION
        "Binary coded options:
        The OCTETS are interpreted bit-by-bit. 
        Bit 0 corresponds to the LSB.
        OCTET 1: unused
        OCTET 2: unused
        OCTET 3: unused
        OCTET 4, Bit 4-7: unused
        	 Bit 3  : Alarm OFF message enable
        	 Bit 2  : Trigger OFF message enable
        	 Bit 1  : Re-Trigger message enable
        	 Bit 0  : Alarm ON message enable"
    ::= { wtIpWatcherAlarmEntry 48 }

    wtIpWatcherAlarmTcpTrapTxEnable OBJECT-TYPE
    SYNTAX OCTET STRING 
    ACCESS read-write
    STATUS mandatory
    DESCRIPTION
        "Binary coded options:
        The OCTETS are interpreted bit-by-bit. 
        Bit 0 corresponds to the LSB.
        OCTET 1: unused
        OCTET 2: unused
        OCTET 3: unused
        OCTET 4, Bit 4-7: unused
        	 Bit 3  : Alarm OFF message enable
        	 Bit 2  : Trigger OFF message enable
        	 Bit 1  : Re-Trigger message enable
        	 Bit 0  : Alarm ON message enable"
    ::= { wtIpWatcherAlarmEntry 49 }

    wtIpWatcherAlarmSyslogTrapTxEnable OBJECT-TYPE
    SYNTAX OCTET STRING 
    ACCESS read-write
    STATUS mandatory
    DESCRIPTION
        "Binary coded options:
        The OCTETS are interpreted bit-by-bit. 
        Bit 0 corresponds to the LSB.
        OCTET 1: unused
        OCTET 2: unused
        OCTET 3: unused
        OCTET 4, Bit 4-7: unused
        	 Bit 3  : Alarm OFF message enable
        	 Bit 2  : Trigger OFF message enable
        	 Bit 1  : Re-Trigger message enable
        	 Bit 0  : Alarm ON message enable"
    ::= { wtIpWatcherAlarmEntry 50 }

    wtIpWatcherAlarmFtpTrapTxEnable OBJECT-TYPE
    SYNTAX OCTET STRING 
    ACCESS read-write
    STATUS mandatory
    DESCRIPTION
        "Binary coded options:
        The OCTETS are interpreted bit-by-bit. 
        Bit 0 corresponds to the LSB.
        OCTET 1: unused
        OCTET 2: unused
        OCTET 3: unused
        OCTET 4, Bit 4-7: unused
        	 Bit 3  : Alarm OFF message enable
        	 Bit 2  : Trigger OFF message enable
        	 Bit 1  : Re-Trigger message enable
        	 Bit 0  : Alarm ON message enable"
    ::= { wtIpWatcherAlarmEntry 51 }
    
    wtIpWatcherAlarmTriggerCount OBJECT-TYPE
    SYNTAX INTEGER 
    ACCESS read-write
    STATUS mandatory
    DESCRIPTION
        "Alarm will be send if the trigger condition occours TriggerCount times."
    ::= { wtIpWatcherAlarmEntry 52 }

    wtIpWatcherAlarmPollingRate OBJECT-TYPE
    SYNTAX INTEGER 
    ACCESS read-write
    STATUS mandatory
    DESCRIPTION
        "Time in seconds."
    ::= { wtIpWatcherAlarmEntry 53 }

-- wtIpWatcherPorts Group
----------------------------

-- Input Port Table

wtIpWatcherInputPortTable OBJECT-TYPE
    SYNTAX SEQUENCE OF WtIpWatcherInputPortEntry
    ACCESS not-accessible
    STATUS mandatory
    DESCRIPTION
        "List of settings depending on the input number."
    ::= { wtIpWatcherPorts 1 }

wtIpWatcherInputPortEntry OBJECT-TYPE
    SYNTAX WtIpWatcherInputPortEntry
    ACCESS not-accessible
    STATUS mandatory
    DESCRIPTION
        "Input parameter for the individual inputs."
    INDEX  { wtIpWatcherInputNo }
    ::= { wtIpWatcherInputPortTable 1 }

WtIpWatcherInputPortEntry ::= SEQUENCE {
    wtIpWatcherPortInputName			OCTET STRING,
    wtIpWatcherPortInputText			OCTET STRING,
    wtIpWatcherPortInputFilter			INTEGER    
    }

wtIpWatcherPortInputName OBJECT-TYPE
    SYNTAX OCTET STRING 
    ACCESS read-write
    STATUS mandatory
    DESCRIPTION
        "Name of the input."
    ::= { wtIpWatcherInputPortEntry 1 }

wtIpWatcherPortInputText OBJECT-TYPE
    SYNTAX OCTET STRING 
    ACCESS read-write
    STATUS mandatory
    DESCRIPTION
        "Description of the input."
    ::= { wtIpWatcherInputPortEntry 2 }

wtIpWatcherPortInputFilter OBJECT-TYPE
    SYNTAX INTEGER 
    ACCESS read-write
    STATUS mandatory
    DESCRIPTION
        "Pulses with a duration shorter than here specified (duration in 1/1000 sec),
	are ignored."
    ::= { wtIpWatcherInputPortEntry 4 }
    
-- Output Port Table

wtIpWatcherOutputPortTable OBJECT-TYPE
    SYNTAX SEQUENCE OF WtIpWatcherOutputPortEntry
    ACCESS not-accessible
    STATUS mandatory
    DESCRIPTION
        "List of settings depending on the output number."
    ::= { wtIpWatcherPorts 2 }

wtIpWatcherOutputPortEntry OBJECT-TYPE
    SYNTAX WtIpWatcherOutputPortEntry
    ACCESS not-accessible
    STATUS mandatory
    DESCRIPTION
        "Output parameters of the individual outputs."
    INDEX  { wtIpWatcherOutputNo }
    ::= { wtIpWatcherOutputPortTable 1 }

WtIpWatcherOutputPortEntry ::= SEQUENCE {
    wtIpWatcherPortOutputName			OCTET STRING,
    wtIpWatcherPortOutputText			OCTET STRING,
    wtIpWatcherPortPulseDuration		INTEGER,
    wtIpWatcherPortPulsePolarity		OCTET STRING
    
}

wtIpWatcherPortOutputName OBJECT-TYPE
    SYNTAX OCTET STRING 
    ACCESS read-write
    STATUS mandatory
    DESCRIPTION
        "Name of the output."
    ::= { wtIpWatcherOutputPortEntry 1 }

wtIpWatcherPortOutputText OBJECT-TYPE
    SYNTAX OCTET STRING 
    ACCESS read-write
    STATUS mandatory
    DESCRIPTION
        "Description of the output."
    ::= { wtIpWatcherOutputPortEntry 2 }

wtIpWatcherPortPulseDuration OBJECT-TYPE
    SYNTAX INTEGER
    ACCESS read-write
    STATUS mandatory
    DESCRIPTION
        "Pulse length in 1/1000 sec. Setting this value to zero, disables the pulse output."
    ::= { wtIpWatcherOutputPortEntry 9 }

wtIpWatcherPortPulsePolarity OBJECT-TYPE
    SYNTAX OCTET STRING (SIZE (4))
    ACCESS read-write
    STATUS mandatory
    DESCRIPTION
        "This value defines the polarity of the output pulse, if wtIpWatcherPortPulseDuration is not set to zero.
        After the pulse is finished, the output switches back to the opposite state.
        OCTET 1: unused
        OCTET 2: unused
        OCTET 3: unused
        	OCTET 4: 
        	 Bit 0   : negative polarity
        	 Bit 1   : positive polarity
        	 Bit 2-7 : unused"
    ::= { wtIpWatcherOutputPortEntry 10 }

-- wtIpWatcherManufact Group
----------------------------

wtIpWatcherMfName OBJECT-TYPE
    SYNTAX OCTET STRING 
    ACCESS read-write
    STATUS mandatory
    DESCRIPTION
        "Manufacturer company name"
    ::= { wtIpWatcherManufact 1 }

wtIpWatcherMfAddr OBJECT-TYPE
    SYNTAX OCTET STRING 
    ACCESS read-write
    STATUS mandatory
    DESCRIPTION
        "Manufacturer address."
    ::= { wtIpWatcherManufact 2 }

wtIpWatcherMfHotline OBJECT-TYPE
    SYNTAX OCTET STRING 
    ACCESS read-write
    STATUS mandatory
    DESCRIPTION
        "Manufacturer hotline."
    ::= { wtIpWatcherManufact 3 }

wtIpWatcherMfInternet OBJECT-TYPE
    SYNTAX OCTET STRING 
    ACCESS read-write
    STATUS mandatory
    DESCRIPTION
        "Manufacturer Internet address."
    ::= { wtIpWatcherManufact 4 }

wtIpWatcherMfDeviceTyp OBJECT-TYPE
    SYNTAX OCTET STRING 
    ACCESS read-write
    STATUS mandatory
    DESCRIPTION
        "Manufacturer device name (model number)."
    ::= { wtIpWatcherManufact 5 }

-- wtIpWatcherDiag Group
----------------------------

wtIpWatcherDiagErrorCount OBJECT-TYPE
    SYNTAX INTEGER
    ACCESS read-only
    STATUS mandatory
    DESCRIPTION
        "Number of entries in the error memory."
    ::= { wtIpWatcherDiag 1 }

wtIpWatcherDiagBinaryError OBJECT-TYPE
    SYNTAX OCTET STRING 
    ACCESS read-only
    STATUS mandatory
    DESCRIPTION
        "Error causes coded bit-by-bit."
    ::= { wtIpWatcherDiag 2 }

wtIpWatcherDiagErrorIndex OBJECT-TYPE
    SYNTAX INTEGER
    ACCESS read-write
    STATUS mandatory
    DESCRIPTION
        "The value of this variable is used as an index to read 
        an error massege from wtIpWatcherDiagErrorMessage.
        Errors are numbered from 1 to wtIpWatcherDiagErrorCount.
        Writing a valid value into this variable, making the appropriate 
        message readable from wtIpWatcherDiagErrorMessage."
    ::= { wtIpWatcherDiag 3 }

wtIpWatcherDiagErrorMessage OBJECT-TYPE
    SYNTAX OCTET STRING 
    ACCESS read-only
    STATUS mandatory
    DESCRIPTION
        "Using wtIpWatcherDiagErrorIndex as an index, the appropriate message is available."
    ::= { wtIpWatcherDiag 4 }
    
wtIpWatcherDiagErrorClear OBJECT-TYPE
    SYNTAX INTEGER
    ACCESS write-only
    STATUS mandatory
    DESCRIPTION
        "Writing 1 into this variable clears all diagnosis messages."
    ::= { wtIpWatcherDiag 5 }


-- TRAP DEFINITIONS

-- Diese SNMP-Traps werden gesendet, wenn die Alarmtriggerbedingungen zutreffen 

wtIpWatcherAlert1 TRAP-TYPE
    ENTERPRISE  wtIpWatcher
    VARIABLES   { wtIpWatcherAlarmSnmpTrapText }
    DESCRIPTION
        "This SNMP trap is generated when Alarm 1 was triggered,
        SNMP trap enable is set and
        SNMP is enabled."
    -- NMS trap annotation
    --#TYPE "IP Watcher Alarm 1"
    --#SUMMARY "Alarm 1: %s"
    --#ARGUMENTS {0}
    --#SEVERITY INFORMATIONAL
    --#TIMEINDEX 99
    --#STATE OPERATIONAL    
    ::= 41

wtIpWatcherAlert2 TRAP-TYPE
    ENTERPRISE  wtIpWatcher
    VARIABLES   { wtIpWatcherAlarmSnmpTrapText }
    DESCRIPTION
        "This SNMP trap is generated when Alarm 2 was triggered,
        SNMP trap enable is set and
        SNMP is enabled."
    -- NMS trap annotation
    --#TYPE "IP Watcher Alarm 2"
    --#SUMMARY "Alarm 2: %s"
    --#ARGUMENTS {0}
    --#SEVERITY INFORMATIONAL
    --#TIMEINDEX 99
    --#STATE OPERATIONAL    
    ::= 42

wtIpWatcherAlert3 TRAP-TYPE
    ENTERPRISE  wtIpWatcher
    VARIABLES   { wtIpWatcherAlarmSnmpTrapText }
    DESCRIPTION
        "This SNMP trap is generated when Alarm 3 was triggered,
        SNMP trap enable is set and
        SNMP is enabled."
    -- NMS trap annotation
    --#TYPE "IP Watcher Alarm 3"
    --#SUMMARY "Alarm 3: %s"
    --#ARGUMENTS {0}
    --#SEVERITY INFORMATIONAL
    --#TIMEINDEX 99
    --#STATE OPERATIONAL    
    ::= 43

wtIpWatcherAlert4 TRAP-TYPE
    ENTERPRISE  wtIpWatcher
    VARIABLES   { wtIpWatcherAlarmSnmpTrapText }
    DESCRIPTION
        "This SNMP trap is generated when Alarm 4 was triggered,
        SNMP trap enable is set and
        SNMP is enabled."
    -- NMS trap annotation
    --#TYPE "IP Watcher Alarm 4"
    --#SUMMARY "Alarm 4: %s"
    --#ARGUMENTS {0}
    --#SEVERITY INFORMATIONAL
    --#TIMEINDEX 99
    --#STATE OPERATIONAL    
    ::= 44

wtIpWatcherAlert5 TRAP-TYPE
    ENTERPRISE  wtIpWatcher
    VARIABLES   { wtIpWatcherAlarmSnmpTrapText }
    DESCRIPTION
        "This SNMP trap is generated when Alarm 5 was triggered,
        SNMP trap enable is set and
        SNMP is enabled."
    -- NMS trap annotation
    --#TYPE "IP Watcher Alarm 5"
    --#SUMMARY "Alarm 5: %s"
    --#ARGUMENTS {0}
    --#SEVERITY INFORMATIONAL
    --#TIMEINDEX 99
    --#STATE OPERATIONAL    
    ::= 45

wtIpWatcherAlert6 TRAP-TYPE
    ENTERPRISE  wtIpWatcher
    VARIABLES   { wtIpWatcherAlarmSnmpTrapText }
    DESCRIPTION
        "This SNMP trap is generated when Alarm 6 was triggered,
        SNMP trap enable is set and
        SNMP is enabled."
    -- NMS trap annotation
    --#TYPE "IP Watcher Alarm 6"
    --#SUMMARY "Alarm 6: %s"
    --#ARGUMENTS {0}
    --#SEVERITY INFORMATIONAL
    --#TIMEINDEX 99
    --#STATE OPERATIONAL    
    ::= 46

wtIpWatcherAlert7 TRAP-TYPE
    ENTERPRISE  wtIpWatcher
    VARIABLES   { wtIpWatcherAlarmSnmpTrapText }
    DESCRIPTION
        "This SNMP trap is generated when Alarm 7 was triggered,
        SNMP trap enable is set and
        SNMP is enabled."
    -- NMS trap annotation
    --#TYPE "IP Watcher Alarm 7"
    --#SUMMARY "Alarm 7: %s"
    --#ARGUMENTS {0}
    --#SEVERITY INFORMATIONAL
    --#TIMEINDEX 99
    --#STATE OPERATIONAL    
    ::= 47

wtIpWatcherAlert8 TRAP-TYPE
    ENTERPRISE  wtIpWatcher
    VARIABLES   { wtIpWatcherAlarmSnmpTrapText }
    DESCRIPTION
        "This SNMP trap is generated when Alarm 8 was triggered,
        SNMP trap enable is set and
        SNMP is enabled."
    -- NMS trap annotation
    --#TYPE "IP Watcher Alarm 8"
    --#SUMMARY "Alarm 8: %s"
    --#ARGUMENTS {0}
    --#SEVERITY INFORMATIONAL
    --#TIMEINDEX 99
    --#STATE OPERATIONAL    
    ::= 48

wtIpWatcherAlert9 TRAP-TYPE
    ENTERPRISE  wtIpWatcher
    VARIABLES   { wtIpWatcherAlarmSnmpTrapText }
    DESCRIPTION
        "This SNMP trap is generated when Alarm 9 was triggered,
        SNMP trap enable is set and
        SNMP is enabled."
    -- NMS trap annotation
    --#TYPE "IP Watcher Alarm 9"
    --#SUMMARY "Alarm 9: %s"
    --#ARGUMENTS {0}
    --#SEVERITY INFORMATIONAL
    --#TIMEINDEX 99
    --#STATE OPERATIONAL    
    ::= 49

wtIpWatcherAlert10 TRAP-TYPE
    ENTERPRISE  wtIpWatcher
    VARIABLES   { wtIpWatcherAlarmSnmpTrapText }
    DESCRIPTION
        "This SNMP trap is generated when Alarm 10 was triggered,
        SNMP trap enable is set and
        SNMP is enabled."
    -- NMS trap annotation
    --#TYPE "IP Watcher Alarm 10"
    --#SUMMARY "Alarm 10: %s"
    --#ARGUMENTS {0}
    --#SEVERITY INFORMATIONAL
    --#TIMEINDEX 99
    --#STATE OPERATIONAL    
    ::= 50

wtIpWatcherAlert11 TRAP-TYPE
    ENTERPRISE  wtIpWatcher
    VARIABLES   { wtIpWatcherAlarmSnmpTrapText }
    DESCRIPTION
        "This SNMP trap is generated when Alarm 11 was triggered,
        SNMP trap enable is set and
        SNMP is enabled."
    -- NMS trap annotation
    --#TYPE "IP Watcher Alarm 11"
    --#SUMMARY "Alarm 11: %s"
    --#ARGUMENTS {0}
    --#SEVERITY INFORMATIONAL
    --#TIMEINDEX 99
    --#STATE OPERATIONAL    
    ::= 51

wtIpWatcherAlert12 TRAP-TYPE
    ENTERPRISE  wtIpWatcher
    VARIABLES   { wtIpWatcherAlarmSnmpTrapText }
    DESCRIPTION
        "This SNMP trap is generated when Alarm 12 was triggered,
        SNMP trap enable is set and
        SNMP is enabled."
    -- NMS trap annotation
    --#TYPE "IP Watcher Alarm 12"
    --#SUMMARY "Alarm 12: %s"
    --#ARGUMENTS {0}
    --#SEVERITY INFORMATIONAL
    --#TIMEINDEX 99
    --#STATE OPERATIONAL    
    ::= 52

wtIpWatcherAlert13 TRAP-TYPE
    ENTERPRISE  wtIpWatcher
    VARIABLES   { wtIpWatcherAlarmSnmpTrapReleaseText }
    DESCRIPTION
        "This SNMP trap is generated when Alarm 1 was released,
        SNMP trap enable is set and
        SNMP is enabled."
    -- NMS trap annotation
    --#TYPE "IP Watcher Release Alarm 1"
    --#SUMMARY "Release Alarm 1: %s"
    --#ARGUMENTS {0}
    --#SEVERITY INFORMATIONAL
    --#TIMEINDEX 99
    --#STATE OPERATIONAL    
    ::= 71

wtIpWatcherAlert14 TRAP-TYPE
    ENTERPRISE  wtIpWatcher
    VARIABLES   { wtIpWatcherAlarmSnmpTrapReleaseText }
    DESCRIPTION
        "This SNMP trap is generated when Alarm 2 was released,
        SNMP trap enable is set and
        SNMP is enabled."
    -- NMS trap annotation
    --#TYPE "IP Watcher Release Alarm 2"
    --#SUMMARY "Release Alarm 2: %s"
    --#ARGUMENTS {0}
    --#SEVERITY INFORMATIONAL
    --#TIMEINDEX 99
    --#STATE OPERATIONAL    
    ::= 72

wtIpWatcherAlert15 TRAP-TYPE
    ENTERPRISE  wtIpWatcher
    VARIABLES   { wtIpWatcherAlarmSnmpTrapReleaseText }
    DESCRIPTION
        "This SNMP trap is generated when Alarm 3 was released,
        SNMP trap enable is set and
        SNMP is enabled."
    -- NMS trap annotation
    --#TYPE "IP Watcher Release Alarm 3"
    --#SUMMARY "Release Alarm 3: %s"
    --#ARGUMENTS {0}
    --#SEVERITY INFORMATIONAL
    --#TIMEINDEX 99
    --#STATE OPERATIONAL    
    ::= 73

wtIpWatcherAlert16 TRAP-TYPE
    ENTERPRISE  wtIpWatcher
    VARIABLES   { wtIpWatcherAlarmSnmpTrapReleaseText }
    DESCRIPTION
        "This SNMP trap is generated when Alarm 4 was released,
        SNMP trap enable is set and
        SNMP is enabled."
    -- NMS trap annotation
    --#TYPE "IP Watcher Release Alarm 4"
    --#SUMMARY "Release Alarm 4: %s"
    --#ARGUMENTS {0}
    --#SEVERITY INFORMATIONAL
    --#TIMEINDEX 99
    --#STATE OPERATIONAL    
    ::= 74

wtIpWatcherAlert17 TRAP-TYPE
    ENTERPRISE  wtIpWatcher
    VARIABLES   { wtIpWatcherAlarmSnmpTrapReleaseText }
    DESCRIPTION
        "This SNMP trap is generated when Alarm 5 was released,
        SNMP trap enable is set and
        SNMP is enabled."
    -- NMS trap annotation
    --#TYPE "IP Watcher Release Alarm 5"
    --#SUMMARY "Release Alarm 5: %s"
    --#ARGUMENTS {0}
    --#SEVERITY INFORMATIONAL
    --#TIMEINDEX 99
    --#STATE OPERATIONAL    
    ::= 75

wtIpWatcherAlert18 TRAP-TYPE
    ENTERPRISE  wtIpWatcher
    VARIABLES   { wtIpWatcherAlarmSnmpTrapReleaseText }
    DESCRIPTION
        "This SNMP trap is generated when Alarm 6 was released,
        SNMP trap enable is set and
        SNMP is enabled."
    -- NMS trap annotation
    --#TYPE "IP Watcher Release Alarm 6"
    --#SUMMARY "Release Alarm 6: %s"
    --#ARGUMENTS {0}
    --#SEVERITY INFORMATIONAL
    --#TIMEINDEX 99
    --#STATE OPERATIONAL    
    ::= 76

wtIpWatcherAlert19 TRAP-TYPE
    ENTERPRISE  wtIpWatcher
    VARIABLES   { wtIpWatcherAlarmSnmpTrapReleaseText }
    DESCRIPTION
        "This SNMP trap is generated when Alarm 7 was released,
        SNMP trap enable is set and
        SNMP is enabled."
    -- NMS trap annotation
    --#TYPE "IP Watcher Release Alarm 7"
    --#SUMMARY "Release Alarm 7: %s"
    --#ARGUMENTS {0}
    --#SEVERITY INFORMATIONAL
    --#TIMEINDEX 99
    --#STATE OPERATIONAL    
    ::= 77

wtIpWatcherAlert20 TRAP-TYPE
    ENTERPRISE  wtIpWatcher
    VARIABLES   { wtIpWatcherAlarmSnmpTrapReleaseText }
    DESCRIPTION
        "This SNMP trap is generated when Alarm 8 was released,
        SNMP trap enable is set and
        SNMP is enabled."
    -- NMS trap annotation
    --#TYPE "IP Watcher Release Alarm 8"
    --#SUMMARY "Release Alarm 8: %s"
    --#ARGUMENTS {0}
    --#SEVERITY INFORMATIONAL
    --#TIMEINDEX 99
    --#STATE OPERATIONAL    
    ::= 78

wtIpWatcherAlert21 TRAP-TYPE
    ENTERPRISE  wtIpWatcher
    VARIABLES   { wtIpWatcherAlarmSnmpTrapReleaseText }
    DESCRIPTION
        "This SNMP trap is generated when Alarm 9 was released,
        SNMP trap enable is set and
        SNMP is enabled."
    -- NMS trap annotation
    --#TYPE "IP Watcher Release Alarm 9"
    --#SUMMARY "Release Alarm 9: %s"
    --#ARGUMENTS {0}
    --#SEVERITY INFORMATIONAL
    --#TIMEINDEX 99
    --#STATE OPERATIONAL    
    ::= 79

wtIpWatcherAlert22 TRAP-TYPE
    ENTERPRISE  wtIpWatcher
    VARIABLES   { wtIpWatcherAlarmSnmpTrapReleaseText }
    DESCRIPTION
        "This SNMP trap is generated when Alarm 10 was released,
        SNMP trap enable is set and
        SNMP is enabled."
    -- NMS trap annotation
    --#TYPE "IP Watcher Release Alarm 10"
    --#SUMMARY "Release Alarm 10: %s"
    --#ARGUMENTS {0}
    --#SEVERITY INFORMATIONAL
    --#TIMEINDEX 99
    --#STATE OPERATIONAL    
    ::= 80

wtIpWatcherAlert23 TRAP-TYPE
    ENTERPRISE  wtIpWatcher
    VARIABLES   { wtIpWatcherAlarmSnmpTrapReleaseText }
    DESCRIPTION
        "This SNMP trap is generated when Alarm 11 was released,
        SNMP trap enable is set and
        SNMP is enabled."
    -- NMS trap annotation
    --#TYPE "IP Watcher Release Alarm 11"
    --#SUMMARY "Release Alarm 11: %s"
    --#ARGUMENTS {0}
    --#SEVERITY INFORMATIONAL
    --#TIMEINDEX 99
    --#STATE OPERATIONAL    
    ::= 81

wtIpWatcherAlert24 TRAP-TYPE
    ENTERPRISE  wtIpWatcher
    VARIABLES   { wtIpWatcherAlarmSnmpTrapReleaseText }
    DESCRIPTION
        "This SNMP trap is generated when Alarm 12 was released,
        SNMP trap enable is set and
        SNMP is enabled."
    -- NMS trap annotation
    --#TYPE "IP Watcher Release Alarm 12"
    --#SUMMARY "Release Alarm 12: %s"
    --#ARGUMENTS {0}
    --#SEVERITY INFORMATIONAL
    --#TIMEINDEX 99
    --#STATE OPERATIONAL    
    ::= 82

wtIpWatcherAlert25 TRAP-TYPE
    ENTERPRISE  wtIpWatcher
    VARIABLES   { wtIpWatcherAlarmSnmpTrapTrgClearText }
    DESCRIPTION
        "This SNMP trap is generated when the trigger of the Alarm 1 was released,
        SNMP trap enable is set and
        SNMP is enabled."
    -- NMS trap annotation
    --#TYPE "IP Watcher Alarm 1"
    --#SUMMARY "Alarm 1: %s"
    --#ARGUMENTS {0}
    --#SEVERITY INFORMATIONAL
    --#TIMEINDEX 99
    --#STATE OPERATIONAL    
    ::= 91

wtIpWatcherAlert26 TRAP-TYPE
    ENTERPRISE  wtIpWatcher
    VARIABLES   { wtIpWatcherAlarmSnmpTrapTrgClearText }
    DESCRIPTION
        "This SNMP trap is generated when the trigger of the Alarm 2 was released,
        SNMP trap enable is set and
        SNMP is enabled."
    -- NMS trap annotation
    --#TYPE "IP Watcher Alarm 2"
    --#SUMMARY "Release Alarm 2: %s"
    --#ARGUMENTS {0}
    --#SEVERITY INFORMATIONAL
    --#TIMEINDEX 99
    --#STATE OPERATIONAL    
    ::= 92

wtIpWatcherAlert27 TRAP-TYPE
    ENTERPRISE  wtIpWatcher
    VARIABLES   { wtIpWatcherAlarmSnmpTrapTrgClearText }
    DESCRIPTION
        "This SNMP trap is generated when the trigger of the Alarm 3 was released,
        SNMP trap enable is set and
        SNMP is enabled."
    -- NMS trap annotation
    --#TYPE "IP Watcher Alarm 3"
    --#SUMMARY "Release Alarm 3: %s"
    --#ARGUMENTS {0}
    --#SEVERITY INFORMATIONAL
    --#TIMEINDEX 99
    --#STATE OPERATIONAL    
    ::= 93

wtIpWatcherAlert28 TRAP-TYPE
    ENTERPRISE  wtIpWatcher
    VARIABLES   { wtIpWatcherAlarmSnmpTrapTrgClearText }
    DESCRIPTION
        "This SNMP trap is generated when the trigger of the Alarm 4 was released,
        SNMP trap enable is set and
        SNMP is enabled."
    -- NMS trap annotation
    --#TYPE "IP Watcher Alarm 4"
    --#SUMMARY "Release Alarm 4: %s"
    --#ARGUMENTS {0}
    --#SEVERITY INFORMATIONAL
    --#TIMEINDEX 99
    --#STATE OPERATIONAL    
    ::= 94

wtIpWatcherAlert29 TRAP-TYPE
    ENTERPRISE  wtIpWatcher
    VARIABLES   { wtIpWatcherAlarmSnmpTrapTrgClearText }
    DESCRIPTION
        "This SNMP trap is generated when the trigger of the Alarm 5 was released,
        SNMP trap enable is set and
        SNMP is enabled."
    -- NMS trap annotation
    --#TYPE "IP Watcher Alarm 5"
    --#SUMMARY "Release Alarm 5: %s"
    --#ARGUMENTS {0}
    --#SEVERITY INFORMATIONAL
    --#TIMEINDEX 99
    --#STATE OPERATIONAL    
    ::= 95

wtIpWatcherAlert30 TRAP-TYPE
    ENTERPRISE  wtIpWatcher
    VARIABLES   { wtIpWatcherAlarmSnmpTrapTrgClearText }
    DESCRIPTION
        "This SNMP trap is generated when the trigger of the Alarm 6 was released,
        SNMP trap enable is set and
        SNMP is enabled."
    -- NMS trap annotation
    --#TYPE "IP Watcher Alarm 6"
    --#SUMMARY "Release Alarm 6: %s"
    --#ARGUMENTS {0}
    --#SEVERITY INFORMATIONAL
    --#TIMEINDEX 99
    --#STATE OPERATIONAL    
    ::= 96

wtIpWatcherAlert31 TRAP-TYPE
    ENTERPRISE  wtIpWatcher
    VARIABLES   { wtIpWatcherAlarmSnmpTrapTrgClearText }
    DESCRIPTION
        "This SNMP trap is generated when the trigger of the Alarm 7 was released,
        SNMP trap enable is set and
        SNMP is enabled."
    -- NMS trap annotation
    --#TYPE "IP Watcher Alarm 7"
    --#SUMMARY "Release Alarm 7: %s"
    --#ARGUMENTS {0}
    --#SEVERITY INFORMATIONAL
    --#TIMEINDEX 99
    --#STATE OPERATIONAL    
    ::= 97

wtIpWatcherAlert32 TRAP-TYPE
    ENTERPRISE  wtIpWatcher
    VARIABLES   { wtIpWatcherAlarmSnmpTrapTrgClearText }
    DESCRIPTION
        "This SNMP trap is generated when the trigger of the Alarm 8 was released,
        SNMP trap enable is set and
        SNMP is enabled."
    -- NMS trap annotation
    --#TYPE "IP Watcher Alarm 8"
    --#SUMMARY "Release Alarm 8: %s"
    --#ARGUMENTS {0}
    --#SEVERITY INFORMATIONAL
    --#TIMEINDEX 99
    --#STATE OPERATIONAL    
    ::= 98

wtIpWatcherAlert33 TRAP-TYPE
    ENTERPRISE  wtIpWatcher
    VARIABLES   { wtIpWatcherAlarmSnmpTrapTrgClearText }
    DESCRIPTION
        "This SNMP trap is generated when the trigger of the Alarm 9 was released,
        SNMP trap enable is set and
        SNMP is enabled."
    -- NMS trap annotation
    --#TYPE "IP Watcher Alarm 9"
    --#SUMMARY "Release Alarm 9: %s"
    --#ARGUMENTS {0}
    --#SEVERITY INFORMATIONAL
    --#TIMEINDEX 99
    --#STATE OPERATIONAL    
    ::= 99

wtIpWatcherAlert34 TRAP-TYPE
    ENTERPRISE  wtIpWatcher
    VARIABLES   { wtIpWatcherAlarmSnmpTrapTrgClearText }
    DESCRIPTION
        "This SNMP trap is generated when the trigger of the Alarm 10 was released,
        SNMP trap enable is set and
        SNMP is enabled."
    -- NMS trap annotation
    --#TYPE "IP Watcher Alarm 10"
    --#SUMMARY "Release Alarm 10: %s"
    --#ARGUMENTS {0}
    --#SEVERITY INFORMATIONAL
    --#TIMEINDEX 99
    --#STATE OPERATIONAL    
    ::= 100

wtIpWatcherAlert35 TRAP-TYPE
    ENTERPRISE  wtIpWatcher
    VARIABLES   { wtIpWatcherAlarmSnmpTrapTrgClearText }
    DESCRIPTION
        "This SNMP trap is generated when the trigger of the Alarm 11 was released,
        SNMP trap enable is set and
        SNMP is enabled."
    -- NMS trap annotation
    --#TYPE "IP Watcher Alarm 11"
    --#SUMMARY "Release Alarm 11: %s"
    --#ARGUMENTS {0}
    --#SEVERITY INFORMATIONAL
    --#TIMEINDEX 99
    --#STATE OPERATIONAL    
    ::= 101

wtIpWatcherAlert36 TRAP-TYPE
    ENTERPRISE  wtIpWatcher
    VARIABLES   { wtIpWatcherAlarmSnmpTrapTrgClearText }
    DESCRIPTION
        "This SNMP trap is generated when the trigger of the Alarm 12 was released,
        SNMP trap enable is set and
        SNMP is enabled."
    -- NMS trap annotation
    --#TYPE "IP Watcher Alarm 12"
    --#SUMMARY "Release Alarm 12: %s"
    --#ARGUMENTS {0}
    --#SEVERITY INFORMATIONAL
    --#TIMEINDEX 99
    --#STATE OPERATIONAL    
    ::= 102

wtIpWatcherAlertDiag TRAP-TYPE
    ENTERPRISE  wtIpWatcher
    VARIABLES   { 	
    		wtIpWatcherDiagErrorIndex,
    	  	wtIpWatcherDiagErrorMessage
    		}
    DESCRIPTION
        "This SNMP trap is generated when a diagnosis/error message was triggered,
        SNMP trap enable is set and
        SNMP is enabled."
    -- NMS trap annotation
    --#TYPE "IP Watcher Diagnose Error"
    --#SUMMARY "Diagnose error index: %d, Message: %s."
    --#ARGUMENTS {0,1}
    --#SEVERITY MAJOR
    --#TIMEINDEX 99
    --#STATE DEGRADED    
    ::= 110

--------------------------------------------------------------------------------
--------------------------------------------------------------------------------
--------------------------------------------------------------------------------

-- wtWebioEA2x2-24VInOut Group
------------------------

wtWebioEA2x2-24VInputs OBJECT-TYPE
    SYNTAX INTEGER (1..2)
    ACCESS read-only
    STATUS mandatory
    DESCRIPTION
        "Number of idependent inputs."
    ::= { wtWebioEA2x2-24VInOut 1 }

wtWebioEA2x2-24VOutputs OBJECT-TYPE
    SYNTAX INTEGER (1..2)
    ACCESS read-only
    STATUS mandatory
    DESCRIPTION
        "Number of idependent outputs."
    ::= { wtWebioEA2x2-24VInOut 2 }

-- Input Interface Table

wtWebioEA2x2-24VInputTable OBJECT-TYPE
    SYNTAX SEQUENCE OF WtWebioEA2x2-24VInputEntry
    ACCESS not-accessible
    STATUS mandatory
    DESCRIPTION
        "List of input indices."
    ::= { wtWebioEA2x2-24VInOut 3 }

wtWebioEA2x2-24VInputEntry OBJECT-TYPE
    SYNTAX WtWebioEA2x2-24VInputEntry
    ACCESS not-accessible
    STATUS mandatory
    DESCRIPTION
        "Number of the inputs."
    INDEX  { wtWebioEA2x2-24VInputNo }
    ::= { wtWebioEA2x2-24VInputTable 1 }

WtWebioEA2x2-24VInputEntry ::= SEQUENCE {
    wtWebioEA2x2-24VInputNo INTEGER,
    wtWebioEA2x2-24VInputCounter INTEGER,
    wtWebioEA2x2-24VInputCounterClear INTEGER,
    wtWebioEA2x2-24VInputState INTEGER
    
}

wtWebioEA2x2-24VInputNo OBJECT-TYPE
    SYNTAX INTEGER (1)
    ACCESS read-only
    STATUS mandatory
    DESCRIPTION
        "Index numbers of the inputs."
    ::= { wtWebioEA2x2-24VInputEntry 1 }

wtWebioEA2x2-24VInputCounter OBJECT-TYPE
    SYNTAX INTEGER (1)
    ACCESS read-only
    STATUS mandatory
    DESCRIPTION
        "Value of the input counter."
    ::= { wtWebioEA2x2-24VInputEntry 2 }
    
wtWebioEA2x2-24VInputCounterClear OBJECT-TYPE
    SYNTAX INTEGER
    ACCESS read-only
    STATUS mandatory
    DESCRIPTION
        "Clears the input counter after returning its value."
    ::= { wtWebioEA2x2-24VInputEntry 3 }
    
wtWebioEA2x2-24VInputState OBJECT-TYPE
    SYNTAX INTEGER{
    wtWebioEA2x2-24VInputState-OFF(0),
    wtWebioEA2x2-24VInputState-ON(1)
    }
    ACCESS read-only
    STATUS mandatory
    DESCRIPTION
        "Value of a single input bit."
    ::= { wtWebioEA2x2-24VInputEntry 4 }    
    
wtWebioEA2x2-24VInputValue OBJECT-TYPE
    SYNTAX INTEGER 
    ACCESS read-only
    STATUS mandatory
    DESCRIPTION
        "This variable is used to read the inputs of the digital I/O port.
        The OCTETS are interpreted bit-by-bit, with each bit corresponding to an output.
        Bit 0 corresponds to the LSB.
        OCTET 1: unused
        OCTET 2: unused
        OCTET 3: unused
        OCTET 4, Bit 0-1: Digital outputs 0-1"
    ::= { wtWebioEA2x2-24VInOut 4 }
    

-- Output Interface Table

wtWebioEA2x2-24VOutputTable OBJECT-TYPE
    SYNTAX SEQUENCE OF WtWebioEA2x2-24VOutputEntry
    ACCESS not-accessible
    STATUS mandatory
    DESCRIPTION
        "List of output indices."
    ::= { wtWebioEA2x2-24VInOut 5 }

wtWebioEA2x2-24VOutputEntry OBJECT-TYPE
    SYNTAX WtWebioEA2x2-24VOutputEntry
    ACCESS not-accessible
    STATUS mandatory
    DESCRIPTION
        "Number of the outputs."
    INDEX  { wtWebioEA2x2-24VOutputNo }
    ::= { wtWebioEA2x2-24VOutputTable 1 }

WtWebioEA2x2-24VOutputEntry ::= SEQUENCE {
    wtWebioEA2x2-24VOutputNo INTEGER,
    wtWebioEA2x2-24VOutputState INTEGER    
}

wtWebioEA2x2-24VOutputNo OBJECT-TYPE
    SYNTAX INTEGER (1)
    ACCESS read-only
    STATUS mandatory
    DESCRIPTION
        "Output number."
    ::= { wtWebioEA2x2-24VOutputEntry 1 }

wtWebioEA2x2-24VOutputState OBJECT-TYPE
    SYNTAX INTEGER{
    wtWebioEA2x2-24VOutputState-OFF(0),
    wtWebioEA2x2-24VOutputState-ON(1)
    }
    ACCESS read-write
    STATUS mandatory
    DESCRIPTION
        "Value of a single output bit."
    ::= { wtWebioEA2x2-24VOutputEntry 2 }
    

wtWebioEA2x2-24VOutputValue OBJECT-TYPE
    SYNTAX INTEGER
    ACCESS read-write
    STATUS mandatory
    DESCRIPTION
        "This variable is used to read and write the outputs of the digital I/O port. 
        The OCTETS are interpreted bit-by-bit, with each bit corresponding to an output. 
        Bit 0 corresponds to the LSB.
        OCTET 1: unused
        OCTET 2: unused
        OCTET 3: unused
        OCTET 4, Bit 0-1: Digital outputs 0-1
        	 Bit 2-7: ungenutzt"
    ::= { wtWebioEA2x2-24VInOut 6 }
    
wtWebioEA2x2-24VSetOutput OBJECT-TYPE
    SYNTAX OCTET STRING (SIZE (8))
    ACCESS read-write			-- write-only
    STATUS mandatory
    DESCRIPTION
        "This variable allows setting of individual digital outputs. The OCTETS are 
        interpreted bit-by-bit, with each bit corresponding to an output. Bit 0 corresponds 
        to the LSB.
        The first two OCTETS contain the mask which determines which of the outputs are to 
        be set (corresponding bit = 1) and which outputs are to remain unchanged 
        (corresponding bit = 0):
	OCTET 1 : unused
	OCTET 2 : unused
	OCTET 3 : unused
	OCTET 4, Bit 0-1: Mask for digital outputs 0-1
	
	OCTETS 5-8 contain the level (1=HIGH, 0=LOW) which the outputs 
	should assume:
	OCTET 5 : unused
	OCTET 6 : unused
	OCTET 7 : unused
        OCTET 8, Bit 0-1: Level of digital outputs 0-1"
    ::= { wtWebioEA2x2-24VInOut 7 }
    
-- wtWebioEA2x2-24VSessCntrl Group
--------------------------------

wtWebioEA2x2-24VSessCntrlPassword OBJECT-TYPE
    SYNTAX OCTET STRING 
    ACCESS read-write
    STATUS mandatory
    DESCRIPTION
        "Entering this password opens a session which is ended by writing a 1 to 
        wtWebioEA2x2-24VSessCntrlLogout. When read this variable provides a string of
        length zero."
    ::= { wtWebioEA2x2-24VSessCntrl 1 }

wtWebioEA2x2-24VSessCntrlConfigMode OBJECT-TYPE
    SYNTAX INTEGER {
    wtWebioEA2x2-24VSessCntrl-NoSession(0),
    wtWebioEA2x2-24VSessCntrl-Session(1)
    }
    ACCESS read-only
    STATUS mandatory
    DESCRIPTION
        "When the device is in SNMP configuration mode, the value 1 is
        returned, otherwise 0. If the read value is 0 even though the password
        was written, the device is already in config mode and the variables
        can only be read."
    ::= { wtWebioEA2x2-24VSessCntrl 2 }

wtWebioEA2x2-24VSessCntrlLogout OBJECT-TYPE
    SYNTAX INTEGER 
    ACCESS read-write
    STATUS mandatory
    DESCRIPTION
        "If the device is in configuration mode and the session was opened by
        this SNMP Manager, writing a 1 to this variable will end the session 
        and all parameters are stored.
        Writing a 2 discards all entries again. When read this variable
        provides the value 0."
    ::= { wtWebioEA2x2-24VSessCntrl 3 }

wtWebioEA2x2-24VSessCntrlAdminPassword OBJECT-TYPE
    SYNTAX OCTET STRING 
    ACCESS read-write
    STATUS mandatory
    DESCRIPTION
        "This password protects access to the variables with administrator rights.
        It can only be changed by the administrator. If no password was assigned,
        the valid password is public."
    ::= { wtWebioEA2x2-24VSessCntrl 4 }

wtWebioEA2x2-24VSessCntrlConfigPassword OBJECT-TYPE
    SYNTAX OCTET STRING 
    ACCESS read-write
    STATUS mandatory
    DESCRIPTION
        "This password protects access to the variables with configurator rights. It can
        be changed by the administrator and by the configurator. If no password was assigned, 
        the valid password is public. When read this variable provides a null-pointer."
    ::= { wtWebioEA2x2-24VSessCntrl 5 }
    
-- wtWebioEA2x2-24VText Group
------------------------

wtWebioEA2x2-24VDeviceName OBJECT-TYPE
    SYNTAX OCTET STRING 
    ACCESS read-write
    STATUS mandatory
    DESCRIPTION
        "Name of the Webio, which is user definable."
    ::= { wtWebioEA2x2-24VText 1 }

wtWebioEA2x2-24VDeviceText OBJECT-TYPE
    SYNTAX OCTET STRING 
    ACCESS read-write
    STATUS mandatory
    DESCRIPTION
        "Description of the Webio, which is user definable."
    ::= { wtWebioEA2x2-24VText 2 }
    
wtWebioEA2x2-24VDeviceLocation OBJECT-TYPE
    SYNTAX OCTET STRING 
    ACCESS read-write
    STATUS mandatory
    DESCRIPTION
        "Description of the location of the Webio, which is user definable."
    ::= { wtWebioEA2x2-24VText 3 }

wtWebioEA2x2-24VDeviceContact OBJECT-TYPE
    SYNTAX OCTET STRING 
    ACCESS read-write
    STATUS mandatory
    DESCRIPTION
        "Contact address of the system operator of the Webio, which is user definable."
    ::= { wtWebioEA2x2-24VText 4 }    

-- wtWebioEA2x2-24VTimeZone Group
----------------------------

wtWebioEA2x2-24VTzOffsetHrs OBJECT-TYPE
    SYNTAX INTEGER 
    ACCESS read-write
    STATUS mandatory
    DESCRIPTION
        "Offset hours for the time zone (winter time) with respect to UTC."
    ::= { wtWebioEA2x2-24VTimeZone 1 }

wtWebioEA2x2-24VTzOffsetMin OBJECT-TYPE
    SYNTAX INTEGER 
    ACCESS read-write
    STATUS mandatory
    DESCRIPTION
        "Offset minutes for the time zone (winter time) with respect to UTC."
    ::= { wtWebioEA2x2-24VTimeZone 2 }

wtWebioEA2x2-24VTzEnable OBJECT-TYPE
    SYNTAX OCTET STRING (SIZE(4))
    ACCESS read-write
    STATUS mandatory
    DESCRIPTION
        "Binary coded conditions:
        Octet 1: unused
        Octet 2: unused
        Octet 3: unused
        Octet 4:
        	Bit 1-7: unused
	        Bit 0  : Apply Timezone"
    ::= { wtWebioEA2x2-24VTimeZone 3 }

wtWebioEA2x2-24VStTzOffsetHrs OBJECT-TYPE
    SYNTAX INTEGER 
    ACCESS read-write
    STATUS mandatory
    DESCRIPTION
        "Offset hours of the time zone (summer time) with respect to UTC."
    ::= { wtWebioEA2x2-24VTimeZone 4 }

wtWebioEA2x2-24VStTzOffsetMin OBJECT-TYPE
    SYNTAX INTEGER 
    ACCESS read-write
    STATUS mandatory
    DESCRIPTION
        "Offset minutes of the time zone (summer time) with respect to UTC."
    ::= { wtWebioEA2x2-24VTimeZone 5 }

wtWebioEA2x2-24VStTzEnable OBJECT-TYPE
    SYNTAX OCTET STRING (SIZE(4))
    ACCESS read-write
    STATUS mandatory
    DESCRIPTION
        "Binary coded conditions:
        Octet 1: unused
        Octet 2: unused
        Octet 3: unused
        Octet 4:
        	Bit 1-7: unused
	        Bit 0  : Apply Summertime"
    ::= { wtWebioEA2x2-24VTimeZone 6 }

wtWebioEA2x2-24VStTzStartMonth OBJECT-TYPE
    SYNTAX INTEGER {
    	wtWebioEA2x2-24VStartMonth-January(1),
    	wtWebioEA2x2-24VStartMonth-February(2),
    	wtWebioEA2x2-24VStartMonth-March(3),
    	wtWebioEA2x2-24VStartMonth-April(4),
    	wtWebioEA2x2-24VStartMonth-May(5),
    	wtWebioEA2x2-24VStartMonth-June(6),
    	wtWebioEA2x2-24VStartMonth-July(7),
    	wtWebioEA2x2-24VStartMonth-August(8),
    	wtWebioEA2x2-24VStartMonth-September(9),
    	wtWebioEA2x2-24VStartMonth-October(10),
    	wtWebioEA2x2-24VStartMonth-November(11),
    	wtWebioEA2x2-24VStartMonth-December(12)
    	}
    	
    ACCESS read-write
    STATUS mandatory
    DESCRIPTION
        "Month in which the change is made from winter time to summer time."
    ::= { wtWebioEA2x2-24VTimeZone 7 }

wtWebioEA2x2-24VStTzStartMode OBJECT-TYPE
    SYNTAX INTEGER {
    	wtWebioEA2x2-24VStartMode-first(1),
    	wtWebioEA2x2-24VStartMode-second(2),
    	wtWebioEA2x2-24VStartMode-third(3),
    	wtWebioEA2x2-24VStartMode-fourth(4),
    	wtWebioEA2x2-24VStartMode-last(5)
    	}
    	
    ACCESS read-write
    STATUS mandatory
    DESCRIPTION
        "Mode of the day of the week for which the change is made from winter time to summer time."
    ::= { wtWebioEA2x2-24VTimeZone 8 }

wtWebioEA2x2-24VStTzStartWday OBJECT-TYPE
    SYNTAX INTEGER {
    	wtWebioEA2x2-24VStartWday-Sunday(1),
    	wtWebioEA2x2-24VStartWday-Monday(2),
    	wtWebioEA2x2-24VStartWday-Tuesday(3),
    	wtWebioEA2x2-24VStartWday-Thursday(4),
    	wtWebioEA2x2-24VStartWday-Wednesday(5),
    	wtWebioEA2x2-24VStartWday-Friday(6),
    	wtWebioEA2x2-24VStartWday-Saturday(7)
    	}
    	
    ACCESS read-write
    STATUS mandatory
    DESCRIPTION
        "Day of the week on which the change is made from winter time to summer time"
    ::= { wtWebioEA2x2-24VTimeZone 9 }
    
wtWebioEA2x2-24VStTzStartHrs OBJECT-TYPE
    SYNTAX INTEGER 
    ACCESS read-write
    STATUS mandatory
    DESCRIPTION
        "Hour in which the time zone is changed from winter to summer time with
        respect to UTC."
    ::= { wtWebioEA2x2-24VTimeZone 10 }

wtWebioEA2x2-24VStTzStartMin OBJECT-TYPE
    SYNTAX INTEGER 
    ACCESS read-write
    STATUS mandatory
    DESCRIPTION
        "Minute in which the time zone is changed from winter to summer time with
        respect to UTC."
    ::= { wtWebioEA2x2-24VTimeZone 11 }
 
wtWebioEA2x2-24VStTzStopMonth OBJECT-TYPE
    SYNTAX INTEGER {
    	wtWebioEA2x2-24VStopMonth-January(1),
    	wtWebioEA2x2-24VStopMonth-February(2),
    	wtWebioEA2x2-24VStopMonth-March(3),
    	wtWebioEA2x2-24VStopMonth-April(4),
    	wtWebioEA2x2-24VStopMonth-May(5),
    	wtWebioEA2x2-24VStopMonth-June(6),
    	wtWebioEA2x2-24VStopMonth-July(7),
    	wtWebioEA2x2-24VStopMonth-August(8),
    	wtWebioEA2x2-24VStopMonth-September(9),
    	wtWebioEA2x2-24VStopMonth-October(10),
    	wtWebioEA2x2-24VStopMonth-November(11),
    	wtWebioEA2x2-24VStopMonth-December(12)
    	}
    ACCESS read-write
    STATUS mandatory
    DESCRIPTION
        "Month in which the change is made from summer time to winter time."
   ::= { wtWebioEA2x2-24VTimeZone 12 }

wtWebioEA2x2-24VStTzStopMode OBJECT-TYPE
    SYNTAX INTEGER {
    	wtWebioEA2x2-24VStopMode-first(1),
    	wtWebioEA2x2-24VStopMode-second(2),
    	wtWebioEA2x2-24VStopMode-third(3),
    	wtWebioEA2x2-24VStopMode-fourth(4),
    	wtWebioEA2x2-24VStopMode-last(5)
    	}
    ACCESS read-write
    STATUS mandatory
    DESCRIPTION
        "Mode of the week day on which the change is made from summer time to winter time."
    ::= { wtWebioEA2x2-24VTimeZone 13 }

wtWebioEA2x2-24VStTzStopWday OBJECT-TYPE
    SYNTAX INTEGER {
    	wtWebioEA2x2-24VStopWday-Sunday(1),
    	wtWebioEA2x2-24VStopWday-Monday(2),
    	wtWebioEA2x2-24VStopWday-Tuesday(3),
    	wtWebioEA2x2-24VStopWday-Thursday(4),
    	wtWebioEA2x2-24VStopWday-Wednesday(5),
    	wtWebioEA2x2-24VStopWday-Friday(6),
    	wtWebioEA2x2-24VStopWday-Saturday(7)
    	}
    ACCESS read-write
    STATUS mandatory
    DESCRIPTION
        "Day of the week on which the change is made from summer time to winter time."
    ::= { wtWebioEA2x2-24VTimeZone 14 }
    
wtWebioEA2x2-24VStTzStopHrs OBJECT-TYPE
    SYNTAX INTEGER 
    ACCESS read-write
    STATUS mandatory
    DESCRIPTION
        "Hour at which the time zone is changed from summer to winter time with
        respect to UTC."
    ::= { wtWebioEA2x2-24VTimeZone 15 }

wtWebioEA2x2-24VStTzStopMin OBJECT-TYPE
    SYNTAX INTEGER 
    ACCESS read-write
    STATUS mandatory
    DESCRIPTION
        "Minute at which the time zone is changed from summer to winter time with
        respect to UTC."
    ::= { wtWebioEA2x2-24VTimeZone 16 }

-- wtWebioEA2x2-24VTimeServer Group
----------------------------

wtWebioEA2x2-24VTimeServer1 OBJECT-TYPE
    SYNTAX OCTET STRING 
    ACCESS read-write
    STATUS mandatory
    DESCRIPTION
        "IP address or name of the 1st time server in ASCII"
    ::= { wtWebioEA2x2-24VTimeServer 1 }

wtWebioEA2x2-24VTimeServer2 OBJECT-TYPE
    SYNTAX OCTET STRING 
    ACCESS read-write
    STATUS mandatory
    DESCRIPTION
        "IP address or name of the 2nd time server in ASCII"
    ::= { wtWebioEA2x2-24VTimeServer 2 }

wtWebioEA2x2-24VTsEnable OBJECT-TYPE
    SYNTAX OCTET STRING (SIZE(4))
    ACCESS read-write
    STATUS mandatory
    DESCRIPTION
        "Binary coded conditions:
        Octet 1: unused
        Octet 2: unused
        Octet 3: unused
        Octet 4:
        	Bit 1-7: unused
	        Bit 0  : Apply Time Server"
    ::= { wtWebioEA2x2-24VTimeServer 3 }

wtWebioEA2x2-24VTsSyncTime OBJECT-TYPE
    SYNTAX INTEGER 
    ACCESS read-write
    STATUS mandatory
    DESCRIPTION
        "Daily synchronisation time with the time server (hour: 0-23)."
    ::= { wtWebioEA2x2-24VTimeServer 4 }
      
    
-- wtWebioEA2x2-24VDeviceClock Group
----------------------------

wtWebioEA2x2-24VClockHrs OBJECT-TYPE
    SYNTAX INTEGER (0..23)
    ACCESS read-write
    STATUS mandatory
    DESCRIPTION
        "Clock hours taking into account the time zone settings."
    ::= { wtWebioEA2x2-24VDeviceClock 1 }

wtWebioEA2x2-24VClockMin OBJECT-TYPE
    SYNTAX INTEGER (0..59)
    ACCESS read-write
    STATUS mandatory
    DESCRIPTION
        "Clock minutes taking into account the time zone settings."
    ::= { wtWebioEA2x2-24VDeviceClock 2 }

wtWebioEA2x2-24VClockDay OBJECT-TYPE
    SYNTAX INTEGER (1..31)
    ACCESS read-write
    STATUS mandatory
    DESCRIPTION
        "Date: Day of the month, taking into account the time zone settings."
    ::= { wtWebioEA2x2-24VDeviceClock 3 }

wtWebioEA2x2-24VClockMonth OBJECT-TYPE
   SYNTAX INTEGER {
    	wtWebioEA2x2-24VClockMonth-January(1),
    	wtWebioEA2x2-24VClockMonth-February(2),
    	wtWebioEA2x2-24VClockMonth-March(3),
    	wtWebioEA2x2-24VClockMonth-April(4),
    	wtWebioEA2x2-24VClockMonth-May(5),
    	wtWebioEA2x2-24VClockMonth-June(6),
    	wtWebioEA2x2-24VClockMonth-July(7),
    	wtWebioEA2x2-24VClockMonth-August(8),
    	wtWebioEA2x2-24VClockMonth-September(9),
    	wtWebioEA2x2-24VClockMonth-October(10),
    	wtWebioEA2x2-24VClockMonth-November(11),
    	wtWebioEA2x2-24VClockMonth-December(12)
    	}
    ACCESS read-write
    STATUS mandatory
    DESCRIPTION
        "Date: Month, taking into account the time zone settings."
    ::= { wtWebioEA2x2-24VDeviceClock 4 }

wtWebioEA2x2-24VClockYear OBJECT-TYPE
    SYNTAX INTEGER (0..65535)
    ACCESS read-write
    STATUS mandatory
    DESCRIPTION
        "Date: Year, taking into account the time zone settings."
    ::= { wtWebioEA2x2-24VDeviceClock 5 }

-- wtWebioEA2x2-24VNetwork Group
------------------------

wtWebioEA2x2-24VIpAddress OBJECT-TYPE
    SYNTAX IpAddress
    ACCESS read-write
    STATUS mandatory
    DESCRIPTION
        "IP address of the Webio"
    ::= { wtWebioEA2x2-24VNetwork 1 }

wtWebioEA2x2-24VSubnetMask OBJECT-TYPE
    SYNTAX IpAddress
    ACCESS read-write
    STATUS mandatory
    DESCRIPTION
        "Subnet mask of the Webio"
    ::= { wtWebioEA2x2-24VNetwork 2 }

wtWebioEA2x2-24VGateway OBJECT-TYPE
    SYNTAX IpAddress
    ACCESS read-write
    STATUS mandatory
    DESCRIPTION
        "Gateway of the Webio"
    ::= { wtWebioEA2x2-24VNetwork 3 }

wtWebioEA2x2-24VDnsServer1 OBJECT-TYPE
    SYNTAX OCTET STRING 
    ACCESS read-write
    STATUS mandatory
    DESCRIPTION
        "IP address of the 1st DNS server in ASCII"
    ::= { wtWebioEA2x2-24VNetwork 4 }

wtWebioEA2x2-24VDnsServer2 OBJECT-TYPE
    SYNTAX OCTET STRING 
    ACCESS read-write
    STATUS mandatory
    DESCRIPTION
        "IP address of the 2nd DNS server in ASCII"
    ::= { wtWebioEA2x2-24VNetwork 5 }

wtWebioEA2x2-24VAddConfig OBJECT-TYPE
    SYNTAX OCTET STRING 
    ACCESS read-write
    STATUS mandatory
    DESCRIPTION
        "Additional configuration (1=ON):
        Octet 1: unused
        Octet 2: unused
        Octet 3: unused
        Octet 4:
	        Bit 1: DHCP  enable
	        Bit 0: BOOTP enable"
    ::= { wtWebioEA2x2-24VNetwork 6 }

--  wtWebioEA2x2-24VHTTP Group
--------------------------------

wtWebioEA2x2-24VStartup OBJECT-TYPE
    SYNTAX OCTET STRING 
    ACCESS read-write
    STATUS mandatory
    DESCRIPTION
        "Binary coded start page, more than one page must not be selected:
        Octet 1: unused
        Octet 2: unused
        Octet 3: unused
        Octet 4:
        	Bit 2: user.htm
        	Bit 1: home.htm
	        Bit 0: index.htm"
    ::= { wtWebioEA2x2-24VHTTP 1 }

wtWebioEA2x2-24VGetHeaderEnable OBJECT-TYPE
    SYNTAX OCTET STRING 
    ACCESS read-write
    STATUS mandatory
    DESCRIPTION
        "If bits are set, every answer of a short form GET question will be lead
        by the IP-address and name of the device (Header) or a HTTP header (HTTP):
        Octet 1: unused
        Octet 2: unused
        Octet 3: unused
        Octet 4:
        	Bit 2-7: unused
        	Bit 1  : GET HTTP enable
                Bit 0  : GET Header enable"
    ::= { wtWebioEA2x2-24VHTTP 2 }

wtWebioEA2x2-24VHttpInputTrigger OBJECT-TYPE
    SYNTAX OCTET STRING (SIZE (4))
    ACCESS read-write
    STATUS mandatory
    DESCRIPTION
        "Every change on the inputs causes their state to be transmitted to the 
        remote device. To minimize data traffic, individual inputs may be exempted 
        from this rule. Nevertheless every transmission will contain all input bits.
        If a bit is set (1), a change of state on the corresponding input 
        triggers a transmission. If the bit is not set (0), no transmission 
        takes place.
        The OCTETS are interpreted bit-by-bit, with each bit corresponding to an input. 
        Bit 0 corresponds to the LSB.
        OCTET 1: unused
        OCTET 2: unused
        OCTET 3: unused
        OCTET 4, Bit 0-1: Digital inputs 0-1"
    ::= { wtWebioEA2x2-24VHTTP 3 }

wtWebioEA2x2-24VHttpPort OBJECT-TYPE
    SYNTAX INTEGER (1..65534)
    ACCESS read-write
    STATUS mandatory
    DESCRIPTION
       "Definition of the standard HTML port (Default: 80)."
    ::= { wtWebioEA2x2-24VHTTP 4 }        
    
    
-- wtWebioEA2x2-24VMail Group
--------------------------------

wtWebioEA2x2-24VMailAdName OBJECT-TYPE
    SYNTAX OCTET STRING 
    ACCESS read-write
    STATUS mandatory
    DESCRIPTION
        "Device name for mail administration."
    ::= { wtWebioEA2x2-24VMail 1 }
    
wtWebioEA2x2-24VMailReply OBJECT-TYPE
    SYNTAX OCTET STRING 
    ACCESS read-write
    STATUS mandatory
    DESCRIPTION
        "Reply address for the mail server."
    ::= { wtWebioEA2x2-24VMail 2 }
    
wtWebioEA2x2-24VMailServer OBJECT-TYPE
    SYNTAX OCTET STRING 
    ACCESS read-write
    STATUS mandatory
    DESCRIPTION
        "Name or IP address of the mail server."
    ::= { wtWebioEA2x2-24VMail 3 }
    
wtWebioEA2x2-24VMailEnable OBJECT-TYPE
    SYNTAX OCTET STRING 
    ACCESS read-write
    STATUS mandatory
    DESCRIPTION
        "Set this bit to enable the sending of mails:
        Octet 1: unused
        Octet 2: unused
        Octet 3: unused
        Octet 4:
        	Bit 1-7: unused
                Bit 0  : Mail enable"
    ::= { wtWebioEA2x2-24VMail 4 }

wtWebioEA2x2-24VMailAuthentication OBJECT-TYPE
    SYNTAX OCTET STRING (SIZE (4))
    ACCESS read-write
    STATUS mandatory
    DESCRIPTION
        "Selection of the authentication modi:
        The OCTETS are interpreted bit-by-bit,
        Bit 0 corresponds to the LSB.
        OCTET 1: unused
        OCTET 2: unused
        OCTET 3: unused
        OCTET 4: Bit 3-7: unused
        	 Bit 2  : POP3 before SMTP
        	 Bit 1  : ESMTP, authentication
        	 Bit 0  : SMTP, no authentication"
    ::= { wtWebioEA2x2-24VMail 5 }
    
wtWebioEA2x2-24VMailAuthUser OBJECT-TYPE
    SYNTAX OCTET STRING 
    ACCESS read-write
    STATUS mandatory
    DESCRIPTION
        "Name of the user to be authenticated."
    ::= { wtWebioEA2x2-24VMail 6 }    
    
wtWebioEA2x2-24VMailAuthPassword OBJECT-TYPE
    SYNTAX OCTET STRING 
    ACCESS read-write
    STATUS mandatory
    DESCRIPTION
        "Authentication password."
    ::= { wtWebioEA2x2-24VMail 7 }    
    
wtWebioEA2x2-24VMailPop3Server OBJECT-TYPE
    SYNTAX OCTET STRING 
    ACCESS read-write
    STATUS mandatory
    DESCRIPTION
        "Name or Ip-address of the POP3 Servers."
    ::= { wtWebioEA2x2-24VMail 8 }        
    

--  wtWebioEA2x2-24VSnmp Group
--------------------------------

wtWebioEA2x2-24VSnmpEnable OBJECT-TYPE
    SYNTAX OCTET STRING 
    ACCESS read-write
    STATUS mandatory
    DESCRIPTION
        "Set bit 0 to enable SNMP.
        If disabled, the device did not respond to any SNMP requests.
        Bit 1 decided wether the community string of read operations 
        is compared with the system password or not:
        Octet 1: unused
        Octet 2: unused
        Octet 3: unused
        Octet 4:
        	Bit 1-7: unused
        	Bit 0  : SNMP enable"
    ::= { wtWebioEA2x2-24VSNMP 1 }
    
wtWebioEA2x2-24VSnmpCommunityStringRead OBJECT-TYPE
    SYNTAX OCTET STRING
    ACCESS read-write
    STATUS mandatory
    DESCRIPTION
        "Community string read only"
    ::= { wtWebioEA2x2-24VSNMP 2 }

wtWebioEA2x2-24VSnmpCommunityStringReadWrite OBJECT-TYPE
    SYNTAX OCTET STRING
    ACCESS read-write
    STATUS mandatory
    DESCRIPTION
        "Community string read / write"
    ::= { wtWebioEA2x2-24VSNMP 3 }

wtWebioEA2x2-24VSnmpSystemTrapManagerIP OBJECT-TYPE
    SYNTAX OCTET STRING 
    ACCESS read-write
    STATUS mandatory
    DESCRIPTION
        "Name or IP address of the TCP server which accepts the system trap."
    ::= { wtWebioEA2x2-24VSNMP 4 }
    
wtWebioEA2x2-24VSnmpSystemTrapEnable OBJECT-TYPE
    SYNTAX OCTET STRING (SIZE(4))
    ACCESS read-write
    STATUS mandatory
    DESCRIPTION
        "Binary coded trigger conditions:
        Octet 1: unused
        Octet 2: unused
        Octet 3: unused
        Octet 4:
	        Bit 0:   ColdStart
	        Bit 1:   WarmStart
	        Bit 2:   Diag messages
	        Bit 3-7: unused"
    ::= { wtWebioEA2x2-24VSNMP 5 }    

-- wtWebioEA2x2-24VUDP Group
--------------------------------   

wtWebioEA2x2-24VUdpAdminPort OBJECT-TYPE
    SYNTAX INTEGER
    ACCESS read-write
    STATUS mandatory
    DESCRIPTION
        "Udp port to which the Udp queries ( short form GET requests) can be sent. This
        port number must be unique within the device."
    ::= { wtWebioEA2x2-24VUDP 1 }

wtWebioEA2x2-24VUdpEnable OBJECT-TYPE
    SYNTAX OCTET STRING 
    ACCESS read-write
    STATUS mandatory
    DESCRIPTION
        "Set this bit to enable UDP support:
        Octet 1: unused
        Octet 2: unused
        Octet 3: unused
        Octet 4:
        	Bit 1-7: unused
                Bit 0  : UDP enable"
    ::= { wtWebioEA2x2-24VUDP 2 }

wtWebioEA2x2-24VUdpRemotePort OBJECT-TYPE
    SYNTAX INTEGER
    ACCESS read-write
    STATUS mandatory
    DESCRIPTION
        "Udp remote port setting.
        If this value is set to zero, the source port read from a request will be used 
        as destination port for the answer.
        A non zero value forced the destination port to this value."
    ::= { wtWebioEA2x2-24VUDP 3 }
    
--  wtWebioEA2x2-24VBinary Group
--------------------------------

wtWebioEA2x2-24VBinaryModeCount OBJECT-TYPE
    SYNTAX INTEGER (1..2)
    ACCESS read-only
    STATUS mandatory
    DESCRIPTION
        "Number of independent binary channels."
    ::= { wtWebioEA2x2-24VBinary 1 }
    
-- Binary Interface Table

wtWebioEA2x2-24VBinaryIfTable OBJECT-TYPE
    SYNTAX SEQUENCE OF WtWebioEA2x2-24VBinaryIfEntry
    ACCESS not-accessible
    STATUS mandatory
    DESCRIPTION
        "Table of indices."
    ::= { wtWebioEA2x2-24VBinary 2 }

wtWebioEA2x2-24VBinaryIfEntry OBJECT-TYPE
    SYNTAX WtWebioEA2x2-24VBinaryIfEntry
    ACCESS not-accessible
    STATUS mandatory
    DESCRIPTION
        "Indices of the binary channels."
    INDEX  { wtWebioEA2x2-24VBinaryModeNo }
    ::= { wtWebioEA2x2-24VBinaryIfTable 1 }

WtWebioEA2x2-24VBinaryIfEntry ::= SEQUENCE {
    wtWebioEA2x2-24VBinaryModeNo INTEGER
}

wtWebioEA2x2-24VBinaryModeNo OBJECT-TYPE
    SYNTAX INTEGER (1..2)
    ACCESS read-only
    STATUS mandatory
    DESCRIPTION
        "Number of the binary channel."
    ::= { wtWebioEA2x2-24VBinaryIfEntry 1 }

-- Binary Table
--------------------------------

wtWebioEA2x2-24VBinaryTable OBJECT-TYPE
    SYNTAX SEQUENCE OF WtWebioEA2x2-24VBinaryEntry
    ACCESS not-accessible
    STATUS mandatory
    DESCRIPTION
        "Table of properties of the binary mode."
    ::= { wtWebioEA2x2-24VBinary 3 }

wtWebioEA2x2-24VBinaryEntry OBJECT-TYPE
    SYNTAX WtWebioEA2x2-24VBinaryEntry
    ACCESS not-accessible
    STATUS mandatory
    DESCRIPTION
        "Binary properties."
    INDEX  { wtWebioEA2x2-24VBinaryModeNo }
    ::= { wtWebioEA2x2-24VBinaryTable 1 }

WtWebioEA2x2-24VBinaryEntry ::= SEQUENCE {
    wtWebioEA2x2-24VBinaryOperationMode			OCTET STRING,
    wtWebioEA2x2-24VBinaryTcpServerLocalPort		INTEGER,
    wtWebioEA2x2-24VBinaryTcpServerInputTrigger		OCTET STRING,
    wtWebioEA2x2-24VBinaryTcpServerApplicationMode	OCTET STRING,
    wtWebioEA2x2-24VBinaryTcpClientLocalPort		INTEGER,
    wtWebioEA2x2-24VBinaryTcpClientServerPort		INTEGER,
    wtWebioEA2x2-24VBinaryTcpClientServerIpAddr		OCTET STRING,
    wtWebioEA2x2-24VBinaryTcpClientServerPassword	OCTET STRING,
    wtWebioEA2x2-24VBinaryTcpClientInactivity		INTEGER,
    wtWebioEA2x2-24VBinaryTcpClientInputTrigger		OCTET STRING,
    wtWebioEA2x2-24VBinaryTcpClientInterval		INTEGER,
    wtWebioEA2x2-24VBinaryTcpClientApplicationMode	OCTET STRING,
    wtWebioEA2x2-24VBinaryUdpPeerLocalPort		INTEGER,
    wtWebioEA2x2-24VBinaryUdpPeerRemotePort		INTEGER,
    wtWebioEA2x2-24VBinaryUdpPeerRemoteIpAddr		OCTET STRING,
    wtWebioEA2x2-24VBinaryUdpPeerInputTrigger		OCTET STRING,
    wtWebioEA2x2-24VBinaryUdpPeerInterval		INTEGER,
    wtWebioEA2x2-24VBinaryUdpPeerApplicationMode	OCTET STRING,
    wtWebioEA2x2-24VBinaryConnectedPort			INTEGER,
    wtWebioEA2x2-24VBinaryConnectedIpAddr		IpAddress,
    wtWebioEA2x2-24VBinaryTcpServerClientHttpPort	INTEGER,
    wtWebioEA2x2-24VBinaryTcpClientServerHttpPort	INTEGER
    
}

wtWebioEA2x2-24VBinaryOperationMode OBJECT-TYPE
    SYNTAX OCTET STRING (SIZE (4))
    ACCESS read-write
    STATUS mandatory
    DESCRIPTION
        "Selection of the operation mode:
        The OCTETS are interpreted bit-by-bit,
        Bit 0 corresponds to the LSB.
        OCTET 1: unused
        OCTET 2: unused
        OCTET 3: unused
        OCTET 4: Bit 3-7: unused
        	 Bit 2  : UDP Peer
        	 Bit 1  : TCP Client
        	 Bit 0  : TCP Server"
    ::= { wtWebioEA2x2-24VBinaryEntry 1 }

wtWebioEA2x2-24VBinaryTcpServerLocalPort OBJECT-TYPE
    SYNTAX INTEGER (1..65535)
    ACCESS read-write
    STATUS mandatory
    DESCRIPTION
        "Local TCP port for data exchange in this server mode.
        This port number must be unique within the device.
	Reserved port number must not be used (refere to the manual)."
    ::= { wtWebioEA2x2-24VBinaryEntry 2 }

wtWebioEA2x2-24VBinaryTcpServerInputTrigger OBJECT-TYPE
    SYNTAX OCTET STRING (SIZE (4))
    ACCESS read-write
    STATUS mandatory
    DESCRIPTION
        "Every change on the inputs causes their state to be transmitted to the 
        remote device. To minimize data traffic, individual inputs may be exempted 
        from this rule. Nevertheless every transmission will contain all input bits.
        If a bit is set (1), a change of state on the corresponding input 
        triggers a transmission. If the bit is not set (0), no transmission 
        takes place.
        The OCTETS are interpreted bit-by-bit, with each bit corresponding to an input. 
        Bit 0 corresponds to the LSB.
        OCTET 1: unused
        OCTET 2: unused
        OCTET 3: unused
        OCTET 4, Bit 0-1: Digital inputs 0-1"
    ::= { wtWebioEA2x2-24VBinaryEntry 3 }

wtWebioEA2x2-24VBinaryTcpServerApplicationMode OBJECT-TYPE
    SYNTAX OCTET STRING (SIZE (4))
    ACCESS read-write
    STATUS mandatory
    DESCRIPTION
        "Selection of the application mode:
        The OCTETS are interpreted bit-by-bit,
        Bit 0 corresponds to the LSB.
        OCTET 1: unused
        OCTET 2: unused
        OCTET 3: unused
        OCTET 4: Bit 4-7: unused
        	 Bit 3  : OPC Device
        	 Bit 2  : Box2Box Slave
        	 Bit 1  : Compatible 50xxx
        	 Bit 0  : Default"
    ::= { wtWebioEA2x2-24VBinaryEntry 4 }
    
wtWebioEA2x2-24VBinaryTcpClientLocalPort OBJECT-TYPE
    SYNTAX INTEGER (1..65535)
    ACCESS read-write
    STATUS mandatory
    DESCRIPTION
        "Local TCP port for data exchange in this client mode.
        This port number must be unique within the device.
	Reserved port number must not be used (refere to the manual)."
    ::= { wtWebioEA2x2-24VBinaryEntry 5 }

wtWebioEA2x2-24VBinaryTcpClientServerPort OBJECT-TYPE
    SYNTAX INTEGER (1..65535)
    ACCESS read-write
    STATUS mandatory
    DESCRIPTION
        "Port number of the server. A complete set of port number, IP address
        and a valid input/output mask starts this mode.
        No data exchange take place when setting the server port to zero."
    ::= { wtWebioEA2x2-24VBinaryEntry 6 }

wtWebioEA2x2-24VBinaryTcpClientServerIpAddr OBJECT-TYPE
    SYNTAX OCTET STRING
    ACCESS read-write
    STATUS mandatory
    DESCRIPTION
        "Ip address of the server. A complete set of port number, IP address
        and a valid input/output mask starts this mode.
        No data exchange take place when setting the server IP address to 0.0.0.0."
    ::= { wtWebioEA2x2-24VBinaryEntry 7 }

wtWebioEA2x2-24VBinaryTcpClientServerPassword OBJECT-TYPE
    SYNTAX OCTET STRING
    ACCESS read-write
    STATUS mandatory
    DESCRIPTION
        "Building a connection may be protected by the 
        administrator password of the server. Enter the server password
        to establish the connection, if a server administrator password
        exists."
    ::= { wtWebioEA2x2-24VBinaryEntry 8 }

wtWebioEA2x2-24VBinaryTcpClientInactivity OBJECT-TYPE
    SYNTAX INTEGER 
    ACCESS read-write
    STATUS mandatory
    DESCRIPTION
        "Connection timeout in 100ms. If no data are exchanged within the specified  
        time, the device closes the connection to the server.
        The value 0 deactivates the timer. Using the Box2Box mode this function is
        disabled."
    ::= { wtWebioEA2x2-24VBinaryEntry 9 }
    
wtWebioEA2x2-24VBinaryTcpClientInputTrigger OBJECT-TYPE
    SYNTAX OCTET STRING (SIZE (4))
    ACCESS read-write
    STATUS mandatory
    DESCRIPTION
        "Every change on the inputs causes their state to be transmitted to the 
        remote device. To minimize data traffic, individual inputs may be exempted 
        from this rule. Nevertheless every transmission will contain all input bits.
        If a bit is set (1), a change of state on the corresponding input 
        triggers a transmission. If the bit is not set (0), no transmission 
        takes place.
        The OCTETS are interpreted bit-by-bit, with each bit corresponding to an input. 
        Bit 0 corresponds to the LSB.
        OCTET 1: unused
        OCTET 2: unused
        OCTET 3: unused
        OCTET 4, Bit 0-1: Digital inputs 0-1"
    ::= { wtWebioEA2x2-24VBinaryEntry 10 }
 
wtWebioEA2x2-24VBinaryTcpClientInterval OBJECT-TYPE
    SYNTAX INTEGER (0..65535)
    ACCESS read-write
    STATUS mandatory
    DESCRIPTION
        "Configurable interval with a 100ms base, in which the Webio device sends
        data to the configured application. A interval of zero stopps the 
        periodical sending."
    ::= { wtWebioEA2x2-24VBinaryEntry 11 }

wtWebioEA2x2-24VBinaryTcpClientApplicationMode OBJECT-TYPE
    SYNTAX OCTET STRING (SIZE (4))
    ACCESS read-write
    STATUS mandatory
    DESCRIPTION
        "Selection of the application mode:
        The OCTETS are interpreted bit-by-bit,
        Bit 0 corresponds to the LSB.
        OCTET 1: unused
        OCTET 2: unused
        OCTET 3: unused
        OCTET 4: Bit 3-7: unused
        	 Bit 2  : Box2Box Slave
        	 Bit 1  : Compatible 50xxx
        	 Bit 0  : Default"
    ::= { wtWebioEA2x2-24VBinaryEntry 12 }

wtWebioEA2x2-24VBinaryUdpPeerLocalPort OBJECT-TYPE
    SYNTAX INTEGER (1..65535)
    ACCESS read-write
    STATUS mandatory
    DESCRIPTION
        "Local UDP port for data exchange in this peer to peer mode.
        This port number must be unique within the device.
	Reserved port number must not be used (refere to the manual)."
    ::= { wtWebioEA2x2-24VBinaryEntry 13 }

wtWebioEA2x2-24VBinaryUdpPeerRemotePort OBJECT-TYPE
    SYNTAX INTEGER (1..65535)
    ACCESS read-write
    STATUS mandatory
    DESCRIPTION
        "Port number of the remote device. A complete set of port number, IP address
        and a valid input/output mask starts this mode.
        No data exchange take place when setting the remote port to zero."
    ::= { wtWebioEA2x2-24VBinaryEntry 14 }

wtWebioEA2x2-24VBinaryUdpPeerRemoteIpAddr OBJECT-TYPE
    SYNTAX OCTET STRING
    ACCESS read-write
    STATUS mandatory
    DESCRIPTION
        "Ip address of the remote device. A complete set of port number, IP address
        and a valid input/output mask starts this mode.
        No data exchange take place when setting the remote device IP address to 0.0.0.0."
    ::= { wtWebioEA2x2-24VBinaryEntry 15 }

wtWebioEA2x2-24VBinaryUdpPeerInputTrigger OBJECT-TYPE
    SYNTAX OCTET STRING (SIZE (4))
    ACCESS read-write
    STATUS mandatory
    DESCRIPTION
        "Every change on the inputs causes their state to be transmitted to the 
        remote device. To minimize data traffic, individual inputs may be exempted 
        from this rule. Nevertheless every transmission will contain all input bits.
        If a bit is set (1), a change of state on the corresponding input 
        triggers a transmission. If the bit is not set (0), no transmission 
        takes place.
        The OCTETS are interpreted bit-by-bit, with each bit corresponding to an input. 
        Bit 0 corresponds to the LSB.
        OCTET 1: unused
        OCTET 2: unused
        OCTET 3: unused
        OCTET 4, Bit 0-1: Digital inputs 0-1"
    ::= { wtWebioEA2x2-24VBinaryEntry 16 }

wtWebioEA2x2-24VBinaryUdpPeerInterval OBJECT-TYPE
    SYNTAX INTEGER (0..65535)
    ACCESS read-write
    STATUS mandatory
    DESCRIPTION
        "Configurable interval with a 100ms base, in which the Webio device sends
        data to the configured remote device. A interval of zero stopps the 
        periodical sending."
    ::= { wtWebioEA2x2-24VBinaryEntry 17 }

wtWebioEA2x2-24VBinaryUdpPeerApplicationMode OBJECT-TYPE
    SYNTAX OCTET STRING (SIZE (4))
    ACCESS read-write
    STATUS mandatory
    DESCRIPTION
        "Selection of the application mode:
        The OCTETS are interpreted bit-by-bit, with each bit corresponding to an output. 
        Bit 0 corresponds to the LSB.
        OCTET 1: unused
        OCTET 2: unused
        OCTET 3: unused
        OCTET 4: Bit 3-7: unused
        	 Bit 2  : Box2Box Slave
        	 Bit 1  : Compatible 50xxx
        	 Bit 0  : Default"
    ::= { wtWebioEA2x2-24VBinaryEntry 18 }

wtWebioEA2x2-24VBinaryConnectedPort OBJECT-TYPE
    SYNTAX INTEGER (1..65535)
    ACCESS read-only
    STATUS mandatory
    DESCRIPTION
        "Port number of the remote device, after connection has been established.
        In case of no connection or missing port informations a zero will be read."
    ::= { wtWebioEA2x2-24VBinaryEntry 19 }

wtWebioEA2x2-24VBinaryConnectedIpAddr OBJECT-TYPE
    SYNTAX IpAddress
    ACCESS read-only
    STATUS mandatory
    DESCRIPTION
        "IP address of the remote device, after connection has been established.
        In case of no connection or missing port informations 0.0.0.0 will be read."
    ::= { wtWebioEA2x2-24VBinaryEntry 20 } 

wtWebioEA2x2-24VBinaryTcpServerClientHttpPort OBJECT-TYPE
    SYNTAX INTEGER (1..65535)
    ACCESS read-write
    STATUS mandatory
    DESCRIPTION
        "HTTP port number of the remote device at TCP Server Mode. If an mailfunction occurs 
        status informations will be send to this port. 
        Not used at mode Compatible 50xxx."
    ::= { wtWebioEA2x2-24VBinaryEntry 21 }
    
wtWebioEA2x2-24VBinaryTcpClientServerHttpPort OBJECT-TYPE
    SYNTAX INTEGER (1..65535)
    ACCESS read-write
    STATUS mandatory
    DESCRIPTION
        "HTTP port number of the remote device at TCP Client Mode. In the operating mode
        Box2Box connection status informations will be exchanged through this port."
    ::= { wtWebioEA2x2-24VBinaryEntry 22 }            
    
--  wtWebioEA2x2-24VSyslog Group
--------------------------------
    
wtWebioEA2x2-24VSyslogServerIP OBJECT-TYPE
    SYNTAX OCTET STRING 
    ACCESS read-write
    STATUS mandatory
    DESCRIPTION
        "Name or IP address of the Syslog server, which accepts the Syslog messgaes."
    ::= { wtWebioEA2x2-24VSyslog 1 }
    
wtWebioEA2x2-24VSyslogServerPort OBJECT-TYPE
    SYNTAX INTEGER
    ACCESS read-write
    STATUS mandatory
    DESCRIPTION
        "Portnumber of the Syslog servers, default 514."
    ::= { wtWebioEA2x2-24VSyslog 2 }

wtWebioEA2x2-24VSyslogSystemMessagesEnable OBJECT-TYPE
    SYNTAX OCTET STRING (SIZE(4))
    ACCESS read-write
    STATUS mandatory
    DESCRIPTION
        "Binary coded trigger conditions:
        Octet 1: unused
        Octet 2: unused
        Octet 3: unused
        Octet 4:
	        Bit 0:   ColdStart
	        Bit 1:   WarmStart
	        Bit 2:   Diag Messages
	        Bit 3-7: unused"
    ::= { wtWebioEA2x2-24VSyslog 3 }    

wtWebioEA2x2-24VSyslogEnable OBJECT-TYPE
    SYNTAX OCTET STRING 
    ACCESS read-write
    STATUS mandatory
    DESCRIPTION
        "Set bit 0to enable Syslog:
        Octet 1: unused
        Octet 2: unused
        Octet 3: unused
        Octet 4:
        	Bit 1-7: unused
                Bit 0  : Syslog enable"
    ::= { wtWebioEA2x2-24VSyslog 4 }

--  wtWebioEA2x2-24VFTP Group
--------------------------------

wtWebioEA2x2-24VFTPServerIP OBJECT-TYPE
    SYNTAX OCTET STRING 
    ACCESS read-write
    STATUS mandatory
    DESCRIPTION
        "Name or IP address of the FTP server, which accepts the FTP messages."
    ::= { wtWebioEA2x2-24VFTP 1 }
    
wtWebioEA2x2-24VFTPServerControlPort OBJECT-TYPE
    SYNTAX INTEGER
    ACCESS read-write
    STATUS mandatory
    DESCRIPTION
        "Portnumber of the control port of the FTP server, default 21."
    ::= { wtWebioEA2x2-24VFTP 2 }
    
wtWebioEA2x2-24VFTPUserName OBJECT-TYPE
    SYNTAX OCTET STRING 
    ACCESS read-write
    STATUS mandatory
    DESCRIPTION
        "FTP Loggin: user name."
    ::= { wtWebioEA2x2-24VFTP 3 }
    
wtWebioEA2x2-24VFTPPassword OBJECT-TYPE
    SYNTAX OCTET STRING 
    ACCESS read-write
    STATUS mandatory
    DESCRIPTION
        "FTP Loggin: user password."
    ::= { wtWebioEA2x2-24VFTP 4 }

wtWebioEA2x2-24VFTPAccount OBJECT-TYPE
    SYNTAX OCTET STRING 
    ACCESS read-write
    STATUS mandatory
    DESCRIPTION
        "FTP Loggin: name of account."
    ::= { wtWebioEA2x2-24VFTP 5 }

wtWebioEA2x2-24VFTPOption OBJECT-TYPE
    SYNTAX OCTET STRING 
    ACCESS read-write
    STATUS mandatory
    DESCRIPTION
        "Bit 0 switches the FTP Server in Passiv-Mode,
        the Client controls the data connection on its own:
        Octet 1: unused
        Octet 2: unused
        Octet 3: unused
        Octet 4:
        	Bit 1-7: unused
                Bit 0  : PASV enable"
    ::= { wtWebioEA2x2-24VFTP 6 }
    
wtWebioEA2x2-24VFTPEnable OBJECT-TYPE
    SYNTAX OCTET STRING 
    ACCESS read-write
    STATUS mandatory
    DESCRIPTION
        "Set Bit 0 to enable FTP:
        Octet 1: unused
        Octet 2: unused
        Octet 3: unused
        Octet 4:
        	Bit 1-7: unused
                Bit 0  : FTP enable"
    ::= { wtWebioEA2x2-24VFTP 7 }  
    
--  wtWebioEA2x2-24VOutputMode Group
--------------------------------

-- OutputMode Table

wtWebioEA2x2-24VOutputModeTable OBJECT-TYPE
    SYNTAX SEQUENCE OF WtWebioEA2x2-24VOutputModeEntry
    ACCESS not-accessible
    STATUS mandatory
    DESCRIPTION
        "Table of output mode configurations dependent on the output indices."
    ::= { wtWebioEA2x2-24VOutputMode 1 }

wtWebioEA2x2-24VOutputModeEntry OBJECT-TYPE
    SYNTAX WtWebioEA2x2-24VOutputModeEntry
    ACCESS not-accessible
    STATUS mandatory
    DESCRIPTION
        "Output mode configurations of the individual outputs."
    INDEX  { wtWebioEA2x2-24VOutputNo }
    ::= { wtWebioEA2x2-24VOutputModeTable 1 }

WtWebioEA2x2-24VOutputModeEntry ::= SEQUENCE {
    wtWebioEA2x2-24VOutputModeBit	OCTET STRING
}

wtWebioEA2x2-24VOutputModeBit OBJECT-TYPE
    SYNTAX OCTET STRING (SIZE (4))
    ACCESS read-write
    STATUS mandatory
    DESCRIPTION
        "This binary coded output mode defines the individual operation mode for any
        output. More than one mode must not be selected.
        The OCTETS are interpreted bit-by-bit, with each bit corresponding to an output. 
        Bit 0 corresponds to the LSB.
        OCTET 1: unused
        OCTET 2: unused
        OCTET 3: unused
        OCTET 4: Bit 6-7: unused
        	 Bit 5  : Logic
        	 Bit 4  : Binary 2
        	 Bit 3  : Binary 1
        	 Bit 2  : SNMP
        	 Bit 1  : UDP ASCII
        	 Bit 0  : HTTP"
    ::= { wtWebioEA2x2-24VOutputModeEntry 1 }
    
wtWebioEA2x2-24VSafetyTimeout OBJECT-TYPE
    SYNTAX INTEGER (0..65535)
    ACCESS read-write
    STATUS mandatory
    DESCRIPTION
        "After this period of time (multiple of 100ms) without receiving data
        outputs switch to their Safety States. For each output a independend safety state
        could be defined."
    ::= { wtWebioEA2x2-24VOutputMode 2 }
 
wtWebioEA2x2-24VPowerSupplyEnable OBJECT-TYPE
    SYNTAX OCTET STRING 
    ACCESS read-write
    STATUS mandatory
    DESCRIPTION
        "Setting this enable bit turns on the intarnal 24V power supply of the outputs.
        All currents out must not exceed 150mA. At overcurrent condition the power supply will
        be shut down automatically. To reset the ocvercurrent protection circuit
        write 1 into wtWebioEA2x2-24VDiagErrorClear.
        
        Octet 1: unused
        Octet 2: unused
        Octet 3: unused
        Octet 4:
        	Bit 1-7: unused
                Bit 0  : Power Supply enable"
    ::= { wtWebioEA2x2-24VOutputMode 4 } 
    
-- wtWebioEA2x2-24VAlarm Group
----------------------------

wtWebioEA2x2-24VAlarmCount OBJECT-TYPE
    SYNTAX INTEGER (1..4)
    ACCESS read-only
    STATUS mandatory
    DESCRIPTION
        "Number of independent alarms."
    ::= { wtWebioEA2x2-24VAlarm 1 }
    
-- Alarm Interface Table

wtWebioEA2x2-24VAlarmIfTable OBJECT-TYPE
    SYNTAX SEQUENCE OF WtWebioEA2x2-24VAlarmIfEntry
    ACCESS not-accessible
    STATUS mandatory
    DESCRIPTION
        "List of alarm indices."
    ::= { wtWebioEA2x2-24VAlarm 2 }

wtWebioEA2x2-24VAlarmIfEntry OBJECT-TYPE
    SYNTAX WtWebioEA2x2-24VAlarmIfEntry
    ACCESS not-accessible
    STATUS mandatory
    DESCRIPTION
        "Numbers of the alarms."
    INDEX  { wtWebioEA2x2-24VAlarmNo }
    ::= { wtWebioEA2x2-24VAlarmIfTable 1 }

WtWebioEA2x2-24VAlarmIfEntry ::= SEQUENCE {
    wtWebioEA2x2-24VAlarmNo INTEGER
}

wtWebioEA2x2-24VAlarmNo OBJECT-TYPE
    SYNTAX INTEGER (1..4)
    ACCESS read-only
    STATUS mandatory
    DESCRIPTION
        "Numbers of the alarms."
    ::= { wtWebioEA2x2-24VAlarmIfEntry 1 }

-- Alarm Table

wtWebioEA2x2-24VAlarmTable OBJECT-TYPE
    SYNTAX SEQUENCE OF WtWebioEA2x2-24VAlarmEntry
    ACCESS not-accessible
    STATUS mandatory
    DESCRIPTION
        "List of settings depending on the alarm number."
    ::= { wtWebioEA2x2-24VAlarm 3 }

wtWebioEA2x2-24VAlarmEntry OBJECT-TYPE
    SYNTAX WtWebioEA2x2-24VAlarmEntry
    ACCESS not-accessible
    STATUS mandatory
    DESCRIPTION
        "Alarm parameters of the individual alarms."
    INDEX  { wtWebioEA2x2-24VAlarmNo }
    ::= { wtWebioEA2x2-24VAlarmTable 1 }

WtWebioEA2x2-24VAlarmEntry ::= SEQUENCE {
    wtWebioEA2x2-24VAlarmInputTrigger		OCTET STRING,
    wtWebioEA2x2-24VAlarmOutputTrigger		OCTET STRING,
    wtWebioEA2x2-24VAlarmSystemTrigger		OCTET STRING,
    wtWebioEA2x2-24VAlarmMaxCounterValue	OCTET STRING,
    wtWebioEA2x2-24VAlarmInterval		OCTET STRING,
    wtWebioEA2x2-24VAlarmEnable			OCTET STRING,
    wtWebioEA2x2-24VAlarmMailAddr		OCTET STRING,
    wtWebioEA2x2-24VAlarmMailSubject		OCTET STRING,
    wtWebioEA2x2-24VAlarmMailText		OCTET STRING,
    wtWebioEA2x2-24VAlarmSnmpManagerIP		OCTET STRING,
    wtWebioEA2x2-24VAlarmSnmpTrapText		OCTET STRING,
    wtWebioEA2x2-24VAlarmUdpIpAddr		OCTET STRING,
    wtWebioEA2x2-24VAlarmUdpPort		INTEGER,
    wtWebioEA2x2-24VAlarmUdpText		OCTET STRING,
    wtWebioEA2x2-24VAlarmTcpIpAddr		OCTET STRING,
    wtWebioEA2x2-24VAlarmTcpPort		INTEGER,
    wtWebioEA2x2-24VAlarmTcpText		OCTET STRING,    
    wtWebioEA2x2-24VAlarmSyslogIpAddr		OCTET STRING,
    wtWebioEA2x2-24VAlarmSyslogPort		INTEGER,
    wtWebioEA2x2-24VAlarmSyslogText		OCTET STRING,
    wtWebioEA2x2-24VAlarmFtpDataPort		OCTET STRING,
    wtWebioEA2x2-24VAlarmFtpFileName		OCTET STRING,
    wtWebioEA2x2-24VAlarmFtpText		OCTET STRING,
    wtWebioEA2x2-24VAlarmFtpOption		OCTET STRING,
    wtWebioEA2x2-24VAlarmTimerCron		OCTET STRING,
    
    wtWebioEA2x2-24VAlarmMailReleaseSubject	OCTET STRING,
    wtWebioEA2x2-24VAlarmMailReleaseText	OCTET STRING,
    wtWebioEA2x2-24VAlarmSnmpTrapReleaseText	OCTET STRING,
    wtWebioEA2x2-24VAlarmUdpReleaseText		OCTET STRING,
    wtWebioEA2x2-24VAlarmTcpReleaseText		OCTET STRING,    
    wtWebioEA2x2-24VAlarmSyslogReleaseText	OCTET STRING,
    wtWebioEA2x2-24VAlarmFtpReleaseText		OCTET STRING    
    
}

wtWebioEA2x2-24VAlarmInputTrigger OBJECT-TYPE
    SYNTAX OCTET STRING (SIZE(12))
    ACCESS read-write
    STATUS mandatory
    DESCRIPTION
        "This variable allows setting of individual input trigger conditions. 
        The OCTETS are interpreted bit-by-bit, with each bit corresponding to an input. 
        Bit 0 corresponds to the LSB.
	The first four OCTETS contain the mask which determines which of the inputs are to 
	be considered (corresponding bit = 1) and which inputs are to ignore 
	(corresponding bit = 0):
	OCTET 1 : unused
	OCTET 2 : unused
	OCTET 3 : unused
	OCTET 4, Bit 0-1: Mask for digital inputs 0-1
	
	OCTETS 5-8 contain the level (1=HIGH, 0=LOW) which the inputs 
	should assume:
	OCTET 5 : unused
	OCTET 6 : unused
	OCTET 7 : unused
        OCTET 8, Bit 0-1: Level of digital inputs 0-1
        
	OCTETS 9-12 contain the ANY bit (1=ON, 0=OFF). Inputs masked with the any bit trigger with any change 
	of the corresponding input bit. Settings in OCTET 5-9 are then unused:
	OCTET 9: unused
	OCTET 10: unused
	OCTET 11: unused
	OCTET 12, Bit 0-1: ANY bits of digital inputs 0-1"
        
    ::= { wtWebioEA2x2-24VAlarmEntry 1 }

wtWebioEA2x2-24VAlarmOutputTrigger OBJECT-TYPE
    SYNTAX OCTET STRING (SIZE(12))
    ACCESS read-write
    STATUS mandatory
    DESCRIPTION
        "This variable allows setting of individual output trigger conditions. 
        The OCTETS are interpreted bit-by-bit, with each bit corresponding to an output. 
        Bit 0 corresponds to the LSB.
	The first four OCTETS contain the mask which determines which of the outputs are to 
	be considered (corresponding bit = 1) and which outputs are to ignore 
	(corresponding bit = 0):
	OCTET 1 : unused
	OCTET 2 : unused
	OCTET 3 : unused
	OCTET 4, Bit 0-1: Mask for digital outputs 0-1
	
	OCTETS 5-8 contain the level (1=HIGH, 0=LOW) which the outputs 
	should assume:
	OCTET 5 : unused
	OCTET 6 : unused
	OCTET 7 : unused
        OCTET 8, Bit 0-1: Level of digital outputs 0-1

	OCTETS 9-12 contain the ANY bit (1=ON, 0=OFF). Outputs masked with the any bit trigger with any change 
	of the corresponding output bit. Settings in OCTET 5-9 are then unused:
	OCTET 9: unused
	OCTET 10: unused
	OCTET 11: unused
	OCTET 12, Bit 0-1: ANY bits of digital outputs 0-1"
        
    ::= { wtWebioEA2x2-24VAlarmEntry 2 }
    
wtWebioEA2x2-24VAlarmSystemTrigger OBJECT-TYPE
    SYNTAX OCTET STRING (SIZE(4))
    ACCESS read-write
    STATUS mandatory
    DESCRIPTION
        "Binary coded trigger conditions:
        The OCTETS are interpreted bit-by-bit.
        Bit 0 corresponds to the LSB.
        OCTET 1: unused
        OCTET 2: unused
        OCTET 3: unused
        OCTET 4, 
        	 Bit 4-7: unused
        	 Bit 3  : Warm Start
        	 Bit 2  : Cold Start
        	 Bit 1  : Timer
        	 Bit 0  : unused"
    ::= { wtWebioEA2x2-24VAlarmEntry 3 }

wtWebioEA2x2-24VAlarmMaxCounterValue OBJECT-TYPE
    SYNTAX OCTET STRING 
    ACCESS read-write
    STATUS mandatory
    DESCRIPTION
        "This variable configures a max. counter value. If an input counter value
        exceeds this max. value, the corresponding alarm is triggered. Input counters with
        its mask bit unset in wtWebioEA2x2-24VAlarmInputTrigger are not considered."
    ::= { wtWebioEA2x2-24VAlarmEntry 4 }

wtWebioEA2x2-24VAlarmInterval OBJECT-TYPE
    SYNTAX OCTET STRING 
    ACCESS read-write
    STATUS mandatory
    DESCRIPTION
        "Send interval for alarm messages."
    ::= { wtWebioEA2x2-24VAlarmEntry 5 }

wtWebioEA2x2-24VAlarmEnable OBJECT-TYPE
    SYNTAX OCTET STRING (SIZE(4))
    ACCESS read-write
    STATUS mandatory
    DESCRIPTION
        "Binary coded alarm enable:
        Octet 1: unused
        Octet 2: unused
        Octet 3: unused
        Octet 4:
		Bit 0:	Mail Enable
        	Bit 1:	SNMP Trap enable
        	Bit 2:  UDP enable
        	Bit 3:  Send inputs to pending TCP connections
        	Bit 4:  TCP Client enable
        	Bit 5:	Syslog Messages enable
        	Bit 6-7: unused"
    ::= { wtWebioEA2x2-24VAlarmEntry 6 }

wtWebioEA2x2-24VAlarmMailAddr OBJECT-TYPE
    SYNTAX OCTET STRING 
    ACCESS read-write
    STATUS mandatory
    DESCRIPTION
        "E-Mail address for sending the alarm mail to."
    ::= { wtWebioEA2x2-24VAlarmEntry 7 }

wtWebioEA2x2-24VAlarmMailSubject OBJECT-TYPE
    SYNTAX OCTET STRING 
    ACCESS read-write
    STATUS mandatory
    DESCRIPTION
        "Subject line for alarm mail."
    ::= { wtWebioEA2x2-24VAlarmEntry 8 }

wtWebioEA2x2-24VAlarmMailText OBJECT-TYPE
    SYNTAX OCTET STRING 
    ACCESS read-write
    STATUS mandatory
    DESCRIPTION
        "Alarm mail text: 
        States of the Webio device can be included by using special tags.
        Please refer to the respective Webio manual"
    ::= { wtWebioEA2x2-24VAlarmEntry 9 }

wtWebioEA2x2-24VAlarmSnmpManagerIP OBJECT-TYPE
    SYNTAX OCTET STRING 
    ACCESS read-write
    STATUS mandatory
    DESCRIPTION
        "IP address of the SNMP Manager to which the Webio device should send SNMP traps."
    ::= { wtWebioEA2x2-24VAlarmEntry 10 }

wtWebioEA2x2-24VAlarmSnmpTrapText OBJECT-TYPE
    SYNTAX OCTET STRING 
    ACCESS read-write
    STATUS mandatory
    DESCRIPTION
        "This text appears in the trap body."
    ::= { wtWebioEA2x2-24VAlarmEntry 11 }
    
wtWebioEA2x2-24VAlarmUdpIpAddr OBJECT-TYPE
    SYNTAX OCTET STRING 
    ACCESS read-write
    STATUS mandatory
    DESCRIPTION
        "IP address of the UDP listener to which the Webio device should send UDP traps."
    ::= { wtWebioEA2x2-24VAlarmEntry 12 }    

wtWebioEA2x2-24VAlarmUdpPort OBJECT-TYPE
    SYNTAX INTEGER (1..65535) 
    ACCESS read-write
    STATUS mandatory
    DESCRIPTION
        "Port number of the UDP listener to which the Webio device should send UDP traps."
    ::= { wtWebioEA2x2-24VAlarmEntry 13 }    

wtWebioEA2x2-24VAlarmUdpText OBJECT-TYPE
    SYNTAX OCTET STRING 
    ACCESS read-write
    STATUS mandatory
    DESCRIPTION
        "This text appears in the UDP trap body."
    ::= { wtWebioEA2x2-24VAlarmEntry 14 }
    
wtWebioEA2x2-24VAlarmTcpIpAddr OBJECT-TYPE
    SYNTAX OCTET STRING
    ACCESS read-write
    STATUS mandatory
    DESCRIPTION
        "IP address of the TCP listener to which the Webio device should send TCP traps."
    ::= { wtWebioEA2x2-24VAlarmEntry 15 }    

wtWebioEA2x2-24VAlarmTcpPort OBJECT-TYPE
    SYNTAX INTEGER (1..65535) 
    ACCESS read-write
    STATUS mandatory
    DESCRIPTION
        "Port number of the TCP listener to which the Webio device should send TCP traps."
    ::= { wtWebioEA2x2-24VAlarmEntry 16 }    

wtWebioEA2x2-24VAlarmTcpText OBJECT-TYPE
    SYNTAX OCTET STRING 
    ACCESS read-write
    STATUS mandatory
    DESCRIPTION
        "This text appears in the TCP trap body."
    ::= { wtWebioEA2x2-24VAlarmEntry 17 }

wtWebioEA2x2-24VAlarmSyslogIpAddr OBJECT-TYPE
    SYNTAX OCTET STRING 
    ACCESS read-write
    STATUS mandatory
    DESCRIPTION
        "IP address of the syslog server to which the Webio device should send syslog messages."
    ::= { wtWebioEA2x2-24VAlarmEntry 18 }    

wtWebioEA2x2-24VAlarmSyslogPort OBJECT-TYPE
    SYNTAX INTEGER (1..65535) 
    ACCESS read-write
    STATUS mandatory
    DESCRIPTION
        "Port number of the syslog server to which the Webio device should send syslog messages."
    ::= { wtWebioEA2x2-24VAlarmEntry 19 }    

wtWebioEA2x2-24VAlarmSyslogText OBJECT-TYPE
    SYNTAX OCTET STRING 
    ACCESS read-write
    STATUS mandatory
    DESCRIPTION
        "Every message starts with the priority key, a time stamp and the host ip address, according RFC3164.
        This text appears in the following syslog message body."
    ::= { wtWebioEA2x2-24VAlarmEntry 20 }    
    
wtWebioEA2x2-24VAlarmFtpDataPort OBJECT-TYPE
    SYNTAX OCTET STRING 
    ACCESS read-write
    STATUS mandatory
    DESCRIPTION
        "Local data port: 1..65535 or AUTO: the next free port will be assigned."
    ::= { wtWebioEA2x2-24VAlarmEntry 21 }
    
wtWebioEA2x2-24VAlarmFtpFileName OBJECT-TYPE
    SYNTAX OCTET STRING 
    ACCESS read-write
    STATUS mandatory
    DESCRIPTION
        "Name of the file including path informations."
    ::= { wtWebioEA2x2-24VAlarmEntry 22 }
    
wtWebioEA2x2-24VAlarmFtpText OBJECT-TYPE
    SYNTAX OCTET STRING 
    ACCESS read-write
    STATUS mandatory
    DESCRIPTION
        "Message text to store on the FTP server."
    ::= { wtWebioEA2x2-24VAlarmEntry 23 }

wtWebioEA2x2-24VAlarmFtpOption OBJECT-TYPE
    SYNTAX OCTET STRING (SIZE(4))
    ACCESS read-write
    STATUS mandatory
    DESCRIPTION
        "Binary coded options, select only one option at the same time:
        STORE  = replace file
        APPEND = append message at the end of the file
        
        Octet 1: unused
        Octet 2: unused
        Octet 3: unused
        Octet 4:
		Bit 0  :	STORE
		Bit 1  :	APPEND
        	Bit 2-7:	unused"
    ::= { wtWebioEA2x2-24VAlarmEntry 24 }      
    
wtWebioEA2x2-24VAlarmTimerCron OBJECT-TYPE
    SYNTAX OCTET STRING
    ACCESS read-write
    STATUS mandatory
    DESCRIPTION
        "This entry contains 5 space or tab seperated text fields for time trigger definition.
        Each field must match with the actual time to trigger a message, weekday and day of month
        are interpreted separatley.
        1: Minutes	Range 0-59
        2. Hours	Range 0-23, 0 is midnight
        3: Day of month	Range 1-31
        4: Month	Range 1-12
        5: Weekday	Range 0-6, 0 is sunday
        
        Syntax for every field:
         - an asterix (*) enables every possible setting of a field
         - single numbers seperated by commas
         - a partition within the allowed range (1-5)
         - step size within an partition of the allowed range (0-59/2: every second minute)."
    ::= { wtWebioEA2x2-24VAlarmEntry 25 }      

wtWebioEA2x2-24VAlarmMailReleaseSubject OBJECT-TYPE
    SYNTAX OCTET STRING 
    ACCESS read-write
    STATUS mandatory
    DESCRIPTION
       "Subject line for alarm mail."
    ::= { wtWebioEA2x2-24VAlarmEntry 26 }

wtWebioEA2x2-24VAlarmMailReleaseText OBJECT-TYPE
    SYNTAX OCTET STRING 
    ACCESS read-write
    STATUS mandatory
    DESCRIPTION
        "Release Alarm mail text: 
        States of the Webio device can be included by using special tags.
        Please refer to the respective Webio manual"
    ::= { wtWebioEA2x2-24VAlarmEntry 27 }    

wtWebioEA2x2-24VAlarmSnmpTrapReleaseText OBJECT-TYPE
    SYNTAX OCTET STRING 
    ACCESS read-write
    STATUS mandatory
    DESCRIPTION
        "This text appears in the trap body."
    ::= { wtWebioEA2x2-24VAlarmEntry 28 }

wtWebioEA2x2-24VAlarmUdpReleaseText OBJECT-TYPE
    SYNTAX OCTET STRING 
    ACCESS read-write
    STATUS mandatory
    DESCRIPTION
        "This text appears in the UDP trap body."
    ::= { wtWebioEA2x2-24VAlarmEntry 29 }

wtWebioEA2x2-24VAlarmTcpReleaseText OBJECT-TYPE
    SYNTAX OCTET STRING 
    ACCESS read-write
    STATUS mandatory
    DESCRIPTION
        "This text appears in the TCP trap body."
    ::= { wtWebioEA2x2-24VAlarmEntry 30 }

wtWebioEA2x2-24VAlarmSyslogReleaseText OBJECT-TYPE
    SYNTAX OCTET STRING 
    ACCESS read-write
    STATUS mandatory
    DESCRIPTION
        "Every message starts with the priority key, a time stamp and the host ip address, according RFC3164.
        This text appears in the following syslog message body."
    ::= { wtWebioEA2x2-24VAlarmEntry 31 }

wtWebioEA2x2-24VAlarmFtpReleaseText OBJECT-TYPE
    SYNTAX OCTET STRING 
    ACCESS read-write
    STATUS mandatory
    DESCRIPTION
        "Message text to store on the FTP server."
    ::= { wtWebioEA2x2-24VAlarmEntry 32 }


-- wtWebioEA2x2-24VPorts Group
----------------------------

-- Input Port Table

wtWebioEA2x2-24VInputPortTable OBJECT-TYPE
    SYNTAX SEQUENCE OF WtWebioEA2x2-24VInputPortEntry
    ACCESS not-accessible
    STATUS mandatory
    DESCRIPTION
        "List of settings depending on the input number."
    ::= { wtWebioEA2x2-24VPorts 1 }

wtWebioEA2x2-24VInputPortEntry OBJECT-TYPE
    SYNTAX WtWebioEA2x2-24VInputPortEntry
    ACCESS not-accessible
    STATUS mandatory
    DESCRIPTION
        "Input parameter for the individual inputs."
    INDEX  { wtWebioEA2x2-24VInputNo }
    ::= { wtWebioEA2x2-24VInputPortTable 1 }

WtWebioEA2x2-24VInputPortEntry ::= SEQUENCE {
    wtWebioEA2x2-24VPortInputName			OCTET STRING,
    wtWebioEA2x2-24VPortInputText			OCTET STRING,
    wtWebioEA2x2-24VPortInputMode			OCTET STRING,
    wtWebioEA2x2-24VPortInputFilter			INTEGER,
    wtWebioEA2x2-24VPortInputBicountPulsePolarity	OCTET STRING,
    wtWebioEA2x2-24VPortInputBicountInactivTimeout	INTEGER
    
}

wtWebioEA2x2-24VPortInputName OBJECT-TYPE
    SYNTAX OCTET STRING 
    ACCESS read-write
    STATUS mandatory
    DESCRIPTION
        "Name of the input."
    ::= { wtWebioEA2x2-24VInputPortEntry 1 }

wtWebioEA2x2-24VPortInputText OBJECT-TYPE
    SYNTAX OCTET STRING 
    ACCESS read-write
    STATUS mandatory
    DESCRIPTION
        "Description of the input."
    ::= { wtWebioEA2x2-24VInputPortEntry 2 }

wtWebioEA2x2-24VPortInputMode OBJECT-TYPE
    SYNTAX OCTET STRING (SIZE(4))
    ACCESS read-write
    STATUS mandatory
    DESCRIPTION
        "Binary coded modes:
        Selecting short pulse detection enable by setting the corresponding bit to 1 enables 
        interrupt support for counting. Only positive edges are accepted as trigger 
        source. The maximum counting frequenz equals 2000 Hz.
        This mode is available for inputs 0-3 only.
        Selecting counter clear on read by setting the corresponding bit to 1 enables
        the corresponding counter to be cleared automatically every time it is read,
        except HTTP reading with user rights.
        The OCTETS are interpreted bit-by-bit,
        Bit 0 corresponds to the LSB.
        Selection for input 0-1:
        OCTET 1: unused
        OCTET 2: unused
        OCTET 3: unused
        OCTET 4, Bit 4-7: unused
		 Bit 3	: Bidirectional counter enable
        	 Bit 2  : Counter clear on read
        	 Bit 1  : Change detection enable (default)
        	 Bit 0  : Short Pulse detection enable"
    ::= { wtWebioEA2x2-24VInputPortEntry 3 }    
    
wtWebioEA2x2-24VPortInputFilter OBJECT-TYPE
    SYNTAX INTEGER 
    ACCESS read-write
    STATUS mandatory
    DESCRIPTION
        "Pulses with a duration shorter than here specified (duration in 1/1000 sec),
	are ignored."
    ::= { wtWebioEA2x2-24VInputPortEntry 4 }
    
wtWebioEA2x2-24VPortInputBicountPulsePolarity OBJECT-TYPE
    SYNTAX OCTET STRING (SIZE (4))
    ACCESS read-write
    STATUS mandatory
    DESCRIPTION
        "This value defines the polarity of the input pulse.
        OCTET 1: unused
        OCTET 2: unused
        OCTET 3: unused
        	OCTET 4: 
        	 Bit 0   : negative polarity
        	 Bit 1   : positive polarity
        	 Bit 2-7 : unused"
    ::= { wtWebioEA2x2-24VInputPortEntry 5 }

wtWebioEA2x2-24VPortInputBicountInactivTimeout OBJECT-TYPE
    SYNTAX INTEGER 
    ACCESS read-write
    STATUS mandatory
    DESCRIPTION
        "Pulse chains with a duration shorter than here specified (in 1/10 sek),
	are ignored."
    ::= { wtWebioEA2x2-24VInputPortEntry 6 }
        
-- Output Port Table

wtWebioEA2x2-24VOutputPortTable OBJECT-TYPE
    SYNTAX SEQUENCE OF WtWebioEA2x2-24VOutputPortEntry
    ACCESS not-accessible
    STATUS mandatory
    DESCRIPTION
        "List of settings depending on the output number."
    ::= { wtWebioEA2x2-24VPorts 2 }

wtWebioEA2x2-24VOutputPortEntry OBJECT-TYPE
    SYNTAX WtWebioEA2x2-24VOutputPortEntry
    ACCESS not-accessible
    STATUS mandatory
    DESCRIPTION
        "Output parameters of the individual outputs."
    INDEX  { wtWebioEA2x2-24VOutputNo }
    ::= { wtWebioEA2x2-24VOutputPortTable 1 }

WtWebioEA2x2-24VOutputPortEntry ::= SEQUENCE {
    wtWebioEA2x2-24VPortOutputName			OCTET STRING,
    wtWebioEA2x2-24VPortOutputText			OCTET STRING,
    wtWebioEA2x2-24VPortOutputGroupMode		OCTET STRING,
    wtWebioEA2x2-24VPortOutputSafetyState		OCTET STRING,
    wtWebioEA2x2-24VPortLogicInputMask		OCTET STRING,
    wtWebioEA2x2-24VPortLogicInputInverter		OCTET STRING,
    wtWebioEA2x2-24VPortLogicFunction		OCTET STRING,
    wtWebioEA2x2-24VPortLogicOutputInverter		OCTET STRING,
    wtWebioEA2x2-24VPortPulseDuration		INTEGER,
    wtWebioEA2x2-24VPortPulsePolarity		OCTET STRING
    
}

wtWebioEA2x2-24VPortOutputName OBJECT-TYPE
    SYNTAX OCTET STRING 
    ACCESS read-write
    STATUS mandatory
    DESCRIPTION
        "Name of the output."
    ::= { wtWebioEA2x2-24VOutputPortEntry 1 }

wtWebioEA2x2-24VPortOutputText OBJECT-TYPE
    SYNTAX OCTET STRING 
    ACCESS read-write
    STATUS mandatory
    DESCRIPTION
        "Description of the output."
    ::= { wtWebioEA2x2-24VOutputPortEntry 2 }

wtWebioEA2x2-24VPortOutputGroupMode OBJECT-TYPE
    SYNTAX OCTET STRING 
    ACCESS read-write
    STATUS mandatory
    DESCRIPTION
        "It is possible to connect outputs together to increase the output current.
        This could be done by connecting 2 or 4 outputs in a group together. All bits
        of such a group has to be set all together in the same way. This variable
        configures this group scheme. If one ouput bit of a group is set, all other 
        output bits of the same group will be set in the same manner.
        More than one configuration must not be selected.
	Selection for ouputs 0-1:
        Octet 1: unused
        Octet 2: unused
        Octet 3: unused
        OCTET 4: Bit 0   : ouputs 0,1 disconnected (default)
        	 Bit 1   : ouputs 0+1 connected"
    ::= { wtWebioEA2x2-24VOutputPortEntry 3 }

wtWebioEA2x2-24VPortOutputSafetyState OBJECT-TYPE
    SYNTAX OCTET STRING 
    ACCESS read-write
    STATUS mandatory
    DESCRIPTION
        "This variable allows setting of individual digital outputs. The OCTETS are 
        interpreted bit-by-bit, with each bit corresponding to an output. Bit 0 corresponds 
        to the LSB.
        The first four OCTETS contain the mask which determines which of the outputs are to 
        be set (corresponding bit = 1) and which outputs are to remain unchanged 
        (corresponding bit = 0):
        OCTET 1		: unused
        OCTET 2		: unused
        OCTET 3		: unused
        OCTET 4, Bit 1-7: unused
        	 Bit 0	: Mask for digital output
        OCTETS 5-8 contain the level (1=HIGH, 0=LOW) which the outputs to be changed 
        should assume:
        OCTET 5		: unused
        OCTET 6		: unused
        OCTET 7		: unused
        OCTET 8, Bit 1-7: unused
        	 Bit 0  : Level of digital output"
    ::= { wtWebioEA2x2-24VOutputPortEntry 4 }

wtWebioEA2x2-24VPortLogicInputMask OBJECT-TYPE
    SYNTAX OCTET STRING (SIZE (4))
    ACCESS read-write
    STATUS mandatory
    DESCRIPTION
        "Selecting one of these inputs by setting the corresponding bit to 1 
        enables the logic function for the output identified by the index within 
        this table. The calculation take place in 4 steps:
        1. Selecting inputs				(wtWebioEA2x2-24VPortLogicInputMask)
        2. Inverting inputs if necessary	(wtWebioEA2x2-24VPortLogicInputInverter)
        3. Logical combination				(wtWebioEA2x2-24VPortLogicFunction)
        4. Inverting the result if necessary	(wtWebioEA2x2-24VPortLogicOutputInverter)
        OCTET 1: unused
        OCTET 2: unused
        OCTET 3: unused
        OCTET 4: Bit 0-1 : inputs 0-1"
    ::= { wtWebioEA2x2-24VOutputPortEntry 5 }

wtWebioEA2x2-24VPortLogicInputInverter OBJECT-TYPE
    SYNTAX OCTET STRING (SIZE (4))
    ACCESS read-write
    STATUS mandatory
    DESCRIPTION
        "Every input bit selected here will be inverted.
        OCTET 1: unused
        OCTET 2: unused
        OCTET 3: unused
        OCTET 4: Bit 0-1 : inputs 0-1"
    ::= { wtWebioEA2x2-24VOutputPortEntry 6 }

wtWebioEA2x2-24VPortLogicFunction OBJECT-TYPE
    SYNTAX OCTET STRING (SIZE (4))
    ACCESS read-write
    STATUS mandatory
    DESCRIPTION
        "This determines the logic function. No more than one function
        may be selected.
        OCTET 1: unused
        OCTET 2: unused
        OCTET 3: unused
        OCTET 4: 
        	 Bit 0   : logic function OR (default)
        	 Bit 1   : logic function AND
        	 Bit 2-7 : unused"
    ::= { wtWebioEA2x2-24VOutputPortEntry 7 }

wtWebioEA2x2-24VPortLogicOutputInverter OBJECT-TYPE
    SYNTAX OCTET STRING (SIZE (4))
    ACCESS read-write
    STATUS mandatory
    DESCRIPTION
        "The logical operation result could be inverteted by setting the corresponding
        bit to 1.
        OCTET 1: unused
        OCTET 2: unused
        OCTET 3: unused
        	OCTET 4: 
        	 Bit 0   : Output Inverter enable
        	 Bit 1-7 : unused"
    ::= { wtWebioEA2x2-24VOutputPortEntry 8 }

wtWebioEA2x2-24VPortPulseDuration OBJECT-TYPE
    SYNTAX INTEGER
    ACCESS read-write
    STATUS mandatory
    DESCRIPTION
        "Pulse length in 1/1000 sec. Setting this value to zero, disables the pulse output."
    ::= { wtWebioEA2x2-24VOutputPortEntry 9 }

wtWebioEA2x2-24VPortPulsePolarity OBJECT-TYPE
    SYNTAX OCTET STRING (SIZE (4))
    ACCESS read-write
    STATUS mandatory
    DESCRIPTION
        "This value defines the polarity of the output pulse, if wtWebioEA2x2-24VPortPulseDuration is not set to zero.
        After the pulse is finished, the output switches back to the opposite state.
        OCTET 1: unused
        OCTET 2: unused
        OCTET 3: unused
        	OCTET 4: 
        	 Bit 0   : negative polarity
        	 Bit 1   : positive polarity
        	 Bit 2-7 : unused"
    ::= { wtWebioEA2x2-24VOutputPortEntry 10 }

-- wtWebioEA2x2-24VManufact Group
----------------------------

wtWebioEA2x2-24VMfName OBJECT-TYPE
    SYNTAX OCTET STRING 
    ACCESS read-write
    STATUS mandatory
    DESCRIPTION
        "Manufacturer company name"
    ::= { wtWebioEA2x2-24VManufact 1 }

wtWebioEA2x2-24VMfAddr OBJECT-TYPE
    SYNTAX OCTET STRING 
    ACCESS read-write
    STATUS mandatory
    DESCRIPTION
        "Manufacturer address."
    ::= { wtWebioEA2x2-24VManufact 2 }

wtWebioEA2x2-24VMfHotline OBJECT-TYPE
    SYNTAX OCTET STRING 
    ACCESS read-write
    STATUS mandatory
    DESCRIPTION
        "Manufacturer hotline."
    ::= { wtWebioEA2x2-24VManufact 3 }

wtWebioEA2x2-24VMfInternet OBJECT-TYPE
    SYNTAX OCTET STRING 
    ACCESS read-write
    STATUS mandatory
    DESCRIPTION
        "Manufacturer Internet address."
    ::= { wtWebioEA2x2-24VManufact 4 }

wtWebioEA2x2-24VMfDeviceTyp OBJECT-TYPE
    SYNTAX OCTET STRING 
    ACCESS read-write
    STATUS mandatory
    DESCRIPTION
        "Manufacturer device name (model number)."
    ::= { wtWebioEA2x2-24VManufact 5 }

-- wtWebioEA2x2-24VDiag Group
----------------------------

wtWebioEA2x2-24VDiagErrorCount OBJECT-TYPE
    SYNTAX INTEGER
    ACCESS read-only
    STATUS mandatory
    DESCRIPTION
        "Number of entries in the error memory."
    ::= { wtWebioEA2x2-24VDiag 1 }

wtWebioEA2x2-24VDiagBinaryError OBJECT-TYPE
    SYNTAX OCTET STRING 
    ACCESS read-only
    STATUS mandatory
    DESCRIPTION
        "Error causes coded bit-by-bit."
    ::= { wtWebioEA2x2-24VDiag 2 }

wtWebioEA2x2-24VDiagErrorIndex OBJECT-TYPE
    SYNTAX INTEGER
    ACCESS read-write
    STATUS mandatory
    DESCRIPTION
        "The value of this variable is used as an index to read 
        an error massege from wtWebioEA2x2-24VDiagErrorMessage.
        Errors are numbered from 1 to wtWebioEA2x2-24VDiagErrorCount.
        Writing a valid value into this variable, making the appropriate 
        message readable from wtWebioEA2x2-24VDiagErrorMessage."
    ::= { wtWebioEA2x2-24VDiag 3 }

wtWebioEA2x2-24VDiagErrorMessage OBJECT-TYPE
    SYNTAX OCTET STRING 
    ACCESS read-only
    STATUS mandatory
    DESCRIPTION
        "Using wtWebioEA2x2-24VDiagErrorIndex as an index, the appropriate message is available."
    ::= { wtWebioEA2x2-24VDiag 4 }
    
wtWebioEA2x2-24VDiagErrorClear OBJECT-TYPE
    SYNTAX INTEGER
    ACCESS write-only
    STATUS mandatory
    DESCRIPTION
        "Writing 1 into this variable clears all diagnosis messages."
    ::= { wtWebioEA2x2-24VDiag 5 }


-- TRAP DEFINITIONS

-- Diese SNMP-Traps werden gesendet, wenn die Alarmtriggerbedingungen zutreffen 

wtWebioEA2x2-24VAlert1 TRAP-TYPE
    ENTERPRISE  wtWebioEA2x2-24V
    VARIABLES   { wtWebioEA2x2-24VAlarmSnmpTrapText }
    DESCRIPTION
        "This SNMP trap is generated when Alarm 1 was triggered,
        SNMP trap enable is set and
        SNMP is enabled."
    -- NMS trap annotation
    --#TYPE "Webio Digital Alarm 1"
    --#SUMMARY "Alarm 1: %s"
    --#ARGUMENTS {0}
    --#SEVERITY INFORMATIONAL
    --#TIMEINDEX 99
    --#STATE OPERATIONAL    
    ::= 41

wtWebioEA2x2-24VAlert2 TRAP-TYPE
    ENTERPRISE  wtWebioEA2x2-24V
    VARIABLES   { wtWebioEA2x2-24VAlarmSnmpTrapText }
    DESCRIPTION
        "This SNMP trap is generated when Alarm 2 was triggered,
        SNMP trap enable is set and
        SNMP is enabled."
    -- NMS trap annotation
    --#TYPE "Webio Digital Alarm 2"
    --#SUMMARY "Alarm 2: %s"
    --#ARGUMENTS {0}
    --#SEVERITY INFORMATIONAL
    --#TIMEINDEX 99
    --#STATE OPERATIONAL    
    ::= 42

wtWebioEA2x2-24VAlert3 TRAP-TYPE
    ENTERPRISE  wtWebioEA2x2-24V
    VARIABLES   { wtWebioEA2x2-24VAlarmSnmpTrapText }
    DESCRIPTION
        "This SNMP trap is generated when Alarm 3 was triggered,
        SNMP trap enable is set and
        SNMP is enabled."
    -- NMS trap annotation
    --#TYPE "Webio Digital Alarm 3"
    --#SUMMARY "Alarm 3: %s"
    --#ARGUMENTS {0}
    --#SEVERITY INFORMATIONAL
    --#TIMEINDEX 99
    --#STATE OPERATIONAL    
    ::= 43

wtWebioEA2x2-24VAlert4 TRAP-TYPE
    ENTERPRISE  wtWebioEA2x2-24V
    VARIABLES   { wtWebioEA2x2-24VAlarmSnmpTrapText }
    DESCRIPTION
        "This SNMP trap is generated when Alarm 4 was triggered,
        SNMP trap enable is set and
        SNMP is enabled."
    -- NMS trap annotation
    --#TYPE "Webio Digital Alarm 4"
    --#SUMMARY "Alarm 4: %s"
    --#ARGUMENTS {0}
    --#SEVERITY INFORMATIONAL
    --#TIMEINDEX 99
    --#STATE OPERATIONAL    
    ::= 44

wtWebioEA2x2-24VAlert5 TRAP-TYPE
    ENTERPRISE  wtWebioEA2x2-24V
    VARIABLES   { wtWebioEA2x2-24VAlarmSnmpTrapText }
    DESCRIPTION
        "This SNMP trap is generated when Alarm 5 was triggered,
        SNMP trap enable is set and
        SNMP is enabled."
    -- NMS trap annotation
    --#TYPE "Webio Digital Alarm 5"
    --#SUMMARY "Alarm 5: %s"
    --#ARGUMENTS {0}
    --#SEVERITY INFORMATIONAL
    --#TIMEINDEX 99
    --#STATE OPERATIONAL    
    ::= 45

wtWebioEA2x2-24VAlert6 TRAP-TYPE
    ENTERPRISE  wtWebioEA2x2-24V
    VARIABLES   { wtWebioEA2x2-24VAlarmSnmpTrapText }
    DESCRIPTION
        "This SNMP trap is generated when Alarm 6 was triggered,
        SNMP trap enable is set and
        SNMP is enabled."
    -- NMS trap annotation
    --#TYPE "Webio Digital Alarm 6"
    --#SUMMARY "Alarm 6: %s"
    --#ARGUMENTS {0}
    --#SEVERITY INFORMATIONAL
    --#TIMEINDEX 99
    --#STATE OPERATIONAL    
    ::= 46

wtWebioEA2x2-24VAlert7 TRAP-TYPE
    ENTERPRISE  wtWebioEA2x2-24V
    VARIABLES   { wtWebioEA2x2-24VAlarmSnmpTrapText }
    DESCRIPTION
        "This SNMP trap is generated when Alarm 7 was triggered,
        SNMP trap enable is set and
        SNMP is enabled."
    -- NMS trap annotation
    --#TYPE "Webio Digital Alarm 7"
    --#SUMMARY "Alarm 7: %s"
    --#ARGUMENTS {0}
    --#SEVERITY INFORMATIONAL
    --#TIMEINDEX 99
    --#STATE OPERATIONAL    
    ::= 47

wtWebioEA2x2-24VAlert8 TRAP-TYPE
    ENTERPRISE  wtWebioEA2x2-24V
    VARIABLES   { wtWebioEA2x2-24VAlarmSnmpTrapText }
    DESCRIPTION
        "This SNMP trap is generated when Alarm 8 was triggered,
        SNMP trap enable is set and
        SNMP is enabled."
    -- NMS trap annotation
    --#TYPE "Webio Digital Alarm 8"
    --#SUMMARY "Alarm 8: %s"
    --#ARGUMENTS {0}
    --#SEVERITY INFORMATIONAL
    --#TIMEINDEX 99
    --#STATE OPERATIONAL    
    ::= 48

wtWebioEA2x2-24VAlert9 TRAP-TYPE
    ENTERPRISE  wtWebioEA2x2-24V
    VARIABLES   { wtWebioEA2x2-24VAlarmSnmpTrapText }
    DESCRIPTION
        "This SNMP trap is generated when Alarm 9 was triggered,
        SNMP trap enable is set and
        SNMP is enabled."
    -- NMS trap annotation
    --#TYPE "Webio Digital Alarm 9"
    --#SUMMARY "Alarm 9: %s"
    --#ARGUMENTS {0}
    --#SEVERITY INFORMATIONAL
    --#TIMEINDEX 99
    --#STATE OPERATIONAL    
    ::= 49

wtWebioEA2x2-24VAlert10 TRAP-TYPE
    ENTERPRISE  wtWebioEA2x2-24V
    VARIABLES   { wtWebioEA2x2-24VAlarmSnmpTrapText }
    DESCRIPTION
        "This SNMP trap is generated when Alarm 10 was triggered,
        SNMP trap enable is set and
        SNMP is enabled."
    -- NMS trap annotation
    --#TYPE "Webio Digital Alarm 10"
    --#SUMMARY "Alarm 10: %s"
    --#ARGUMENTS {0}
    --#SEVERITY INFORMATIONAL
    --#TIMEINDEX 99
    --#STATE OPERATIONAL    
    ::= 50

wtWebioEA2x2-24VAlert11 TRAP-TYPE
    ENTERPRISE  wtWebioEA2x2-24V
    VARIABLES   { wtWebioEA2x2-24VAlarmSnmpTrapText }
    DESCRIPTION
        "This SNMP trap is generated when Alarm 11 was triggered,
        SNMP trap enable is set and
        SNMP is enabled."
    -- NMS trap annotation
    --#TYPE "Webio Digital Alarm 11"
    --#SUMMARY "Alarm 11: %s"
    --#ARGUMENTS {0}
    --#SEVERITY INFORMATIONAL
    --#TIMEINDEX 99
    --#STATE OPERATIONAL    
    ::= 51

wtWebioEA2x2-24VAlert12 TRAP-TYPE
    ENTERPRISE  wtWebioEA2x2-24V
    VARIABLES   { wtWebioEA2x2-24VAlarmSnmpTrapText }
    DESCRIPTION
        "This SNMP trap is generated when Alarm 12 was triggered,
        SNMP trap enable is set and
        SNMP is enabled."
    -- NMS trap annotation
    --#TYPE "Webio Digital Alarm 12"
    --#SUMMARY "Alarm 12: %s"
    --#ARGUMENTS {0}
    --#SEVERITY INFORMATIONAL
    --#TIMEINDEX 99
    --#STATE OPERATIONAL    
    ::= 52

wtWebioEA2x2-24VAlert13 TRAP-TYPE
    ENTERPRISE  wtWebioEA2x2-24V
    VARIABLES   { wtWebioEA2x2-24VAlarmSnmpTrapReleaseText }
    DESCRIPTION
        "This SNMP trap is generated when Alarm 1 was released,
        SNMP trap enable is set and
        SNMP is enabled."
    -- NMS trap annotation
    --#TYPE "Webio Digital Release Alarm 1"
    --#SUMMARY "Release Alarm 1: %s"
    --#ARGUMENTS {0}
    --#SEVERITY INFORMATIONAL
    --#TIMEINDEX 99
    --#STATE OPERATIONAL    
    ::= 71

wtWebioEA2x2-24VAlert14 TRAP-TYPE
    ENTERPRISE  wtWebioEA2x2-24V
    VARIABLES   { wtWebioEA2x2-24VAlarmSnmpTrapReleaseText }
    DESCRIPTION
        "This SNMP trap is generated when Alarm 2 was released,
        SNMP trap enable is set and
        SNMP is enabled."
    -- NMS trap annotation
    --#TYPE "Webio Digital Release Alarm 2"
    --#SUMMARY "Release Alarm 2: %s"
    --#ARGUMENTS {0}
    --#SEVERITY INFORMATIONAL
    --#TIMEINDEX 99
    --#STATE OPERATIONAL    
    ::= 72

wtWebioEA2x2-24VAlert15 TRAP-TYPE
    ENTERPRISE  wtWebioEA2x2-24V
    VARIABLES   { wtWebioEA2x2-24VAlarmSnmpTrapReleaseText }
    DESCRIPTION
        "This SNMP trap is generated when Alarm 3 was released,
        SNMP trap enable is set and
        SNMP is enabled."
    -- NMS trap annotation
    --#TYPE "Webio Digital Release Alarm 3"
    --#SUMMARY "Release Alarm 3: %s"
    --#ARGUMENTS {0}
    --#SEVERITY INFORMATIONAL
    --#TIMEINDEX 99
    --#STATE OPERATIONAL    
    ::= 73

wtWebioEA2x2-24VAlert16 TRAP-TYPE
    ENTERPRISE  wtWebioEA2x2-24V
    VARIABLES   { wtWebioEA2x2-24VAlarmSnmpTrapReleaseText }
    DESCRIPTION
        "This SNMP trap is generated when Alarm 4 was released,
        SNMP trap enable is set and
        SNMP is enabled."
    -- NMS trap annotation
    --#TYPE "Webio Digital Release Alarm 4"
    --#SUMMARY "Release Alarm 4: %s"
    --#ARGUMENTS {0}
    --#SEVERITY INFORMATIONAL
    --#TIMEINDEX 99
    --#STATE OPERATIONAL    
    ::= 74

wtWebioEA2x2-24VAlert17 TRAP-TYPE
    ENTERPRISE  wtWebioEA2x2-24V
    VARIABLES   { wtWebioEA2x2-24VAlarmSnmpTrapReleaseText }
    DESCRIPTION
        "This SNMP trap is generated when Alarm 5 was released,
        SNMP trap enable is set and
        SNMP is enabled."
    -- NMS trap annotation
    --#TYPE "Webio Digital Release Alarm 5"
    --#SUMMARY "Release Alarm 5: %s"
    --#ARGUMENTS {0}
    --#SEVERITY INFORMATIONAL
    --#TIMEINDEX 99
    --#STATE OPERATIONAL    
    ::= 75

wtWebioEA2x2-24VAlert18 TRAP-TYPE
    ENTERPRISE  wtWebioEA2x2-24V
    VARIABLES   { wtWebioEA2x2-24VAlarmSnmpTrapReleaseText }
    DESCRIPTION
        "This SNMP trap is generated when Alarm 6 was released,
        SNMP trap enable is set and
        SNMP is enabled."
    -- NMS trap annotation
    --#TYPE "Webio Digital Release Alarm 6"
    --#SUMMARY "Release Alarm 6: %s"
    --#ARGUMENTS {0}
    --#SEVERITY INFORMATIONAL
    --#TIMEINDEX 99
    --#STATE OPERATIONAL    
    ::= 76

wtWebioEA2x2-24VAlert19 TRAP-TYPE
    ENTERPRISE  wtWebioEA2x2-24V
    VARIABLES   { wtWebioEA2x2-24VAlarmSnmpTrapReleaseText }
    DESCRIPTION
        "This SNMP trap is generated when Alarm 7 was released,
        SNMP trap enable is set and
        SNMP is enabled."
    -- NMS trap annotation
    --#TYPE "Webio Digital Release Alarm 7"
    --#SUMMARY "Release Alarm 7: %s"
    --#ARGUMENTS {0}
    --#SEVERITY INFORMATIONAL
    --#TIMEINDEX 99
    --#STATE OPERATIONAL    
    ::= 77

wtWebioEA2x2-24VAlert20 TRAP-TYPE
    ENTERPRISE  wtWebioEA2x2-24V
    VARIABLES   { wtWebioEA2x2-24VAlarmSnmpTrapReleaseText }
    DESCRIPTION
        "This SNMP trap is generated when Alarm 8 was released,
        SNMP trap enable is set and
        SNMP is enabled."
    -- NMS trap annotation
    --#TYPE "Webio Digital Release Alarm 8"
    --#SUMMARY "Release Alarm 8: %s"
    --#ARGUMENTS {0}
    --#SEVERITY INFORMATIONAL
    --#TIMEINDEX 99
    --#STATE OPERATIONAL    
    ::= 78

wtWebioEA2x2-24VAlert21 TRAP-TYPE
    ENTERPRISE  wtWebioEA2x2-24V
    VARIABLES   { wtWebioEA2x2-24VAlarmSnmpTrapReleaseText }
    DESCRIPTION
        "This SNMP trap is generated when Alarm 9 was released,
        SNMP trap enable is set and
        SNMP is enabled."
    -- NMS trap annotation
    --#TYPE "Webio Digital Release Alarm 9"
    --#SUMMARY "Release Alarm 9: %s"
    --#ARGUMENTS {0}
    --#SEVERITY INFORMATIONAL
    --#TIMEINDEX 99
    --#STATE OPERATIONAL    
    ::= 79

wtWebioEA2x2-24VAlert22 TRAP-TYPE
    ENTERPRISE  wtWebioEA2x2-24V
    VARIABLES   { wtWebioEA2x2-24VAlarmSnmpTrapReleaseText }
    DESCRIPTION
        "This SNMP trap is generated when Alarm 10 was released,
        SNMP trap enable is set and
        SNMP is enabled."
    -- NMS trap annotation
    --#TYPE "Webio Digital Release Alarm 10"
    --#SUMMARY "Release Alarm 10: %s"
    --#ARGUMENTS {0}
    --#SEVERITY INFORMATIONAL
    --#TIMEINDEX 99
    --#STATE OPERATIONAL    
    ::= 80

wtWebioEA2x2-24VAlert23 TRAP-TYPE
    ENTERPRISE  wtWebioEA2x2-24V
    VARIABLES   { wtWebioEA2x2-24VAlarmSnmpTrapReleaseText }
    DESCRIPTION
        "This SNMP trap is generated when Alarm 11 was released,
        SNMP trap enable is set and
        SNMP is enabled."
    -- NMS trap annotation
    --#TYPE "Webio Digital Release Alarm 11"
    --#SUMMARY "Release Alarm 11: %s"
    --#ARGUMENTS {0}
    --#SEVERITY INFORMATIONAL
    --#TIMEINDEX 99
    --#STATE OPERATIONAL    
    ::= 81

wtWebioEA2x2-24VAlert24 TRAP-TYPE
    ENTERPRISE  wtWebioEA2x2-24V
    VARIABLES   { wtWebioEA2x2-24VAlarmSnmpTrapReleaseText }
    DESCRIPTION
        "This SNMP trap is generated when Alarm 12 was released,
        SNMP trap enable is set and
        SNMP is enabled."
    -- NMS trap annotation
    --#TYPE "Webio Digital Release Alarm 12"
    --#SUMMARY "Release Alarm 12: %s"
    --#ARGUMENTS {0}
    --#SEVERITY INFORMATIONAL
    --#TIMEINDEX 99
    --#STATE OPERATIONAL    
    ::= 82

wtWebioEA2x2-24VAlertDiag TRAP-TYPE
    ENTERPRISE  wtWebioEA2x2-24V
    VARIABLES   { 	
    		wtWebioEA2x2-24VDiagErrorIndex,
    	  	wtWebioEA2x2-24VDiagErrorMessage
    		}
    DESCRIPTION
        "This SNMP trap is generated when a diagnosis/error message was triggered,
        SNMP trap enable is set and
        SNMP is enabled."
    -- NMS trap annotation
    --#TYPE "Webio Digital Diagnose Error"
    --#SUMMARY "Diagnose error index: %d, Message: %s."
    --#ARGUMENTS {0,1}
    --#SEVERITY MAJOR
    --#TIMEINDEX 99
    --#STATE DEGRADED    
    ::= 110

--------------------------------------------------------------------------------
--------------------------------------------------------------------------------
--------------------------------------------------------------------------------

-- wtWebioEA2x2ERP-24VInOut Group
------------------------

wtWebioEA2x2ERP-24VInputs OBJECT-TYPE
    SYNTAX INTEGER (1..2)
    ACCESS read-only
    STATUS mandatory
    DESCRIPTION
        "Number of idependent inputs."
    ::= { wtWebioEA2x2ERP-24VInOut 1 }

wtWebioEA2x2ERP-24VOutputs OBJECT-TYPE
    SYNTAX INTEGER (1..2)
    ACCESS read-only
    STATUS mandatory
    DESCRIPTION
        "Number of idependent outputs."
    ::= { wtWebioEA2x2ERP-24VInOut 2 }

-- Input Interface Table

wtWebioEA2x2ERP-24VInputTable OBJECT-TYPE
    SYNTAX SEQUENCE OF WtWebioEA2x2ERP-24VInputEntry
    ACCESS not-accessible
    STATUS mandatory
    DESCRIPTION
        "List of input indices."
    ::= { wtWebioEA2x2ERP-24VInOut 3 }

wtWebioEA2x2ERP-24VInputEntry OBJECT-TYPE
    SYNTAX WtWebioEA2x2ERP-24VInputEntry
    ACCESS not-accessible
    STATUS mandatory
    DESCRIPTION
        "Number of the inputs."
    INDEX  { wtWebioEA2x2ERP-24VInputNo }
    ::= { wtWebioEA2x2ERP-24VInputTable 1 }

WtWebioEA2x2ERP-24VInputEntry ::= SEQUENCE {
    wtWebioEA2x2ERP-24VInputNo 			INTEGER,
    wtWebioEA2x2ERP-24VInputCounter 		INTEGER,
    wtWebioEA2x2ERP-24VInputCounterClear 	INTEGER,
    wtWebioEA2x2ERP-24VInputState 		INTEGER
    
}

wtWebioEA2x2ERP-24VInputNo OBJECT-TYPE
    SYNTAX INTEGER (1)
    ACCESS read-only
    STATUS mandatory
    DESCRIPTION
        "Index numbers of the inputs."
    ::= { wtWebioEA2x2ERP-24VInputEntry 1 }

wtWebioEA2x2ERP-24VInputCounter OBJECT-TYPE
    SYNTAX INTEGER (1)
    ACCESS read-only
    STATUS mandatory
    DESCRIPTION
        "Value of the input counter."
    ::= { wtWebioEA2x2ERP-24VInputEntry 2 }
    
wtWebioEA2x2ERP-24VInputCounterClear OBJECT-TYPE
    SYNTAX INTEGER
    ACCESS read-only
    STATUS mandatory
    DESCRIPTION
        "Clears the input counter after returning its value."
    ::= { wtWebioEA2x2ERP-24VInputEntry 3 }
    
wtWebioEA2x2ERP-24VInputState OBJECT-TYPE
    SYNTAX INTEGER{
    wtWebioEA2x2ERP-24VInputState-OFF(0),
    wtWebioEA2x2ERP-24VInputState-ON(1)
    }
    ACCESS read-only
    STATUS mandatory
    DESCRIPTION
        "Value of a single input bit."
    ::= { wtWebioEA2x2ERP-24VInputEntry 4 }    
    
wtWebioEA2x2ERP-24VInputValue OBJECT-TYPE
    SYNTAX INTEGER 
    ACCESS read-only
    STATUS mandatory
    DESCRIPTION
        "This variable is used to read the inputs of the digital I/O port.
        The OCTETS are interpreted bit-by-bit, with each bit corresponding to an output.
        Bit 0 corresponds to the LSB.
        OCTET 1: unused
        OCTET 2: unused
        OCTET 3: unused
        OCTET 4, Bit 0-1: Digital outputs 0-1"
    ::= { wtWebioEA2x2ERP-24VInOut 4 }
    

-- Output Interface Table

wtWebioEA2x2ERP-24VOutputTable OBJECT-TYPE
    SYNTAX SEQUENCE OF WtWebioEA2x2ERP-24VOutputEntry
    ACCESS not-accessible
    STATUS mandatory
    DESCRIPTION
        "List of output indices."
    ::= { wtWebioEA2x2ERP-24VInOut 5 }

wtWebioEA2x2ERP-24VOutputEntry OBJECT-TYPE
    SYNTAX WtWebioEA2x2ERP-24VOutputEntry
    ACCESS not-accessible
    STATUS mandatory
    DESCRIPTION
        "Number of the outputs."
    INDEX  { wtWebioEA2x2ERP-24VOutputNo }
    ::= { wtWebioEA2x2ERP-24VOutputTable 1 }

WtWebioEA2x2ERP-24VOutputEntry ::= SEQUENCE {
    wtWebioEA2x2ERP-24VOutputNo 	INTEGER,
    wtWebioEA2x2ERP-24VOutputState 	INTEGER    
}

wtWebioEA2x2ERP-24VOutputNo OBJECT-TYPE
    SYNTAX INTEGER (1)
    ACCESS read-only
    STATUS mandatory
    DESCRIPTION
        "Output number."
    ::= { wtWebioEA2x2ERP-24VOutputEntry 1 }

wtWebioEA2x2ERP-24VOutputState OBJECT-TYPE
    SYNTAX INTEGER{
    wtWebioEA2x2ERP-24VOutputState-OFF(0),
    wtWebioEA2x2ERP-24VOutputState-ON(1)
    }
    ACCESS read-write
    STATUS mandatory
    DESCRIPTION
        "Value of a single output bit."
    ::= { wtWebioEA2x2ERP-24VOutputEntry 2 }
    

wtWebioEA2x2ERP-24VOutputValue OBJECT-TYPE
    SYNTAX INTEGER
    ACCESS read-write
    STATUS mandatory
    DESCRIPTION
        "This variable is used to read and write the outputs of the digital I/O port. 
        The OCTETS are interpreted bit-by-bit, with each bit corresponding to an output. 
        Bit 0 corresponds to the LSB.
        OCTET 1: unused
        OCTET 2: unused
        OCTET 3: unused
        OCTET 4, Bit 0-1: Digital outputs 0-1
        	 Bit 2-7: ungenutzt"
    ::= { wtWebioEA2x2ERP-24VInOut 6 }
    
wtWebioEA2x2ERP-24VSetOutput OBJECT-TYPE
    SYNTAX OCTET STRING (SIZE (8))
    ACCESS read-write			-- write-only
    STATUS mandatory
    DESCRIPTION
        "This variable allows setting of individual digital outputs. The OCTETS are 
        interpreted bit-by-bit, with each bit corresponding to an output. Bit 0 corresponds 
        to the LSB.
        The first two OCTETS contain the mask which determines which of the outputs are to 
        be set (corresponding bit = 1) and which outputs are to remain unchanged 
        (corresponding bit = 0):
	OCTET 1 : unused
	OCTET 2 : unused
	OCTET 3 : unused
	OCTET 4, Bit 0-1: Mask for digital outputs 0-1
	
	OCTETS 5-8 contain the level (1=HIGH, 0=LOW) which the outputs 
	should assume:
	OCTET 5 : unused
	OCTET 6 : unused
	OCTET 7 : unused
        OCTET 8, Bit 0-1: Level of digital outputs 0-1"
    ::= { wtWebioEA2x2ERP-24VInOut 7 }
    
-- wtWebioEA2x2ERP-24VSessCntrl Group
--------------------------------

wtWebioEA2x2ERP-24VSessCntrlPassword OBJECT-TYPE
    SYNTAX OCTET STRING 
    ACCESS read-write
    STATUS mandatory
    DESCRIPTION
        "Entering this password opens a session which is ended by writing a 1 to 
        wtWebioEA2x2ERP-24VSessCntrlLogout. When read this variable provides a string of
        length zero."
    ::= { wtWebioEA2x2ERP-24VSessCntrl 1 }

wtWebioEA2x2ERP-24VSessCntrlConfigMode OBJECT-TYPE
    SYNTAX INTEGER {
    wtWebioEA2x2ERP-24VSessCntrl-NoSession(0),
    wtWebioEA2x2ERP-24VSessCntrl-Session(1)
    }
    ACCESS read-only
    STATUS mandatory
    DESCRIPTION
        "When the device is in SNMP configuration mode, the value 1 is
        returned, otherwise 0. If the read value is 0 even though the password
        was written, the device is already in config mode and the variables
        can only be read."
    ::= { wtWebioEA2x2ERP-24VSessCntrl 2 }

wtWebioEA2x2ERP-24VSessCntrlLogout OBJECT-TYPE
    SYNTAX INTEGER 
    ACCESS read-write
    STATUS mandatory
    DESCRIPTION
        "If the device is in configuration mode and the session was opened by
        this SNMP Manager, writing a 1 to this variable will end the session 
        and all parameters are stored.
        Writing a 2 discards all entries again. When read this variable
        provides the value 0."
    ::= { wtWebioEA2x2ERP-24VSessCntrl 3 }

wtWebioEA2x2ERP-24VSessCntrlAdminPassword OBJECT-TYPE
    SYNTAX OCTET STRING 
    ACCESS read-write
    STATUS mandatory
    DESCRIPTION
        "This password protects access to the variables with administrator rights.
        It can only be changed by the administrator. If no password was assigned,
        the valid password is public."
    ::= { wtWebioEA2x2ERP-24VSessCntrl 4 }

wtWebioEA2x2ERP-24VSessCntrlConfigPassword OBJECT-TYPE
    SYNTAX OCTET STRING 
    ACCESS read-write
    STATUS mandatory
    DESCRIPTION
        "This password protects access to the variables with configurator rights. It can
        be changed by the administrator and by the configurator. If no password was assigned, 
        the valid password is public. When read this variable provides a null-pointer."
    ::= { wtWebioEA2x2ERP-24VSessCntrl 5 }
    
-- wtWebioEA2x2ERP-24VText Group
------------------------

wtWebioEA2x2ERP-24VDeviceName OBJECT-TYPE
    SYNTAX OCTET STRING 
    ACCESS read-write
    STATUS mandatory
    DESCRIPTION
        "Name of the Webio, which is user definable."
    ::= { wtWebioEA2x2ERP-24VText 1 }

wtWebioEA2x2ERP-24VDeviceText OBJECT-TYPE
    SYNTAX OCTET STRING 
    ACCESS read-write
    STATUS mandatory
    DESCRIPTION
        "Description of the Webio, which is user definable."
    ::= { wtWebioEA2x2ERP-24VText 2 }
    
wtWebioEA2x2ERP-24VDeviceLocation OBJECT-TYPE
    SYNTAX OCTET STRING 
    ACCESS read-write
    STATUS mandatory
    DESCRIPTION
        "Description of the location of the Webio, which is user definable."
    ::= { wtWebioEA2x2ERP-24VText 3 }

wtWebioEA2x2ERP-24VDeviceContact OBJECT-TYPE
    SYNTAX OCTET STRING 
    ACCESS read-write
    STATUS mandatory
    DESCRIPTION
        "Contact address of the system operator of the Webio, which is user definable."
    ::= { wtWebioEA2x2ERP-24VText 4 }    

-- wtWebioEA2x2ERP-24VTimeZone Group
----------------------------

wtWebioEA2x2ERP-24VTzOffsetHrs OBJECT-TYPE
    SYNTAX INTEGER 
    ACCESS read-write
    STATUS mandatory
    DESCRIPTION
        "Offset hours for the time zone (winter time) with respect to UTC."
    ::= { wtWebioEA2x2ERP-24VTimeZone 1 }

wtWebioEA2x2ERP-24VTzOffsetMin OBJECT-TYPE
    SYNTAX INTEGER 
    ACCESS read-write
    STATUS mandatory
    DESCRIPTION
        "Offset minutes for the time zone (winter time) with respect to UTC."
    ::= { wtWebioEA2x2ERP-24VTimeZone 2 }

wtWebioEA2x2ERP-24VTzEnable OBJECT-TYPE
    SYNTAX OCTET STRING (SIZE(4))
    ACCESS read-write
    STATUS mandatory
    DESCRIPTION
        "Binary coded conditions:
        Octet 1: unused
        Octet 2: unused
        Octet 3: unused
        Octet 4:
        	Bit 1-7: unused
	        Bit 0  : Apply Timezone"
    ::= { wtWebioEA2x2ERP-24VTimeZone 3 }

wtWebioEA2x2ERP-24VStTzOffsetHrs OBJECT-TYPE
    SYNTAX INTEGER 
    ACCESS read-write
    STATUS mandatory
    DESCRIPTION
        "Offset hours of the time zone (summer time) with respect to UTC."
    ::= { wtWebioEA2x2ERP-24VTimeZone 4 }

wtWebioEA2x2ERP-24VStTzOffsetMin OBJECT-TYPE
    SYNTAX INTEGER 
    ACCESS read-write
    STATUS mandatory
    DESCRIPTION
        "Offset minutes of the time zone (summer time) with respect to UTC."
    ::= { wtWebioEA2x2ERP-24VTimeZone 5 }

wtWebioEA2x2ERP-24VStTzEnable OBJECT-TYPE
    SYNTAX OCTET STRING (SIZE(4))
    ACCESS read-write
    STATUS mandatory
    DESCRIPTION
        "Binary coded conditions:
        Octet 1: unused
        Octet 2: unused
        Octet 3: unused
        Octet 4:
        	Bit 1-7: unused
	        Bit 0  : Apply Summertime"
    ::= { wtWebioEA2x2ERP-24VTimeZone 6 }

wtWebioEA2x2ERP-24VStTzStartMonth OBJECT-TYPE
    SYNTAX INTEGER {
    	wtWebioEA2x2ERP-24VStartMonth-January(1),
    	wtWebioEA2x2ERP-24VStartMonth-February(2),
    	wtWebioEA2x2ERP-24VStartMonth-March(3),
    	wtWebioEA2x2ERP-24VStartMonth-April(4),
    	wtWebioEA2x2ERP-24VStartMonth-May(5),
    	wtWebioEA2x2ERP-24VStartMonth-June(6),
    	wtWebioEA2x2ERP-24VStartMonth-July(7),
    	wtWebioEA2x2ERP-24VStartMonth-August(8),
    	wtWebioEA2x2ERP-24VStartMonth-September(9),
    	wtWebioEA2x2ERP-24VStartMonth-October(10),
    	wtWebioEA2x2ERP-24VStartMonth-November(11),
    	wtWebioEA2x2ERP-24VStartMonth-December(12)
    	}
    	
    ACCESS read-write
    STATUS mandatory
    DESCRIPTION
        "Month in which the change is made from winter time to summer time."
    ::= { wtWebioEA2x2ERP-24VTimeZone 7 }

wtWebioEA2x2ERP-24VStTzStartMode OBJECT-TYPE
    SYNTAX INTEGER {
    	wtWebioEA2x2ERP-24VStartMode-first(1),
    	wtWebioEA2x2ERP-24VStartMode-second(2),
    	wtWebioEA2x2ERP-24VStartMode-third(3),
    	wtWebioEA2x2ERP-24VStartMode-fourth(4),
    	wtWebioEA2x2ERP-24VStartMode-last(5)
    	}
    	
    ACCESS read-write
    STATUS mandatory
    DESCRIPTION
        "Mode of the day of the week for which the change is made from winter time to summer time."
    ::= { wtWebioEA2x2ERP-24VTimeZone 8 }

wtWebioEA2x2ERP-24VStTzStartWday OBJECT-TYPE
    SYNTAX INTEGER {
    	wtWebioEA2x2ERP-24VStartWday-Sunday(1),
    	wtWebioEA2x2ERP-24VStartWday-Monday(2),
    	wtWebioEA2x2ERP-24VStartWday-Tuesday(3),
    	wtWebioEA2x2ERP-24VStartWday-Thursday(4),
    	wtWebioEA2x2ERP-24VStartWday-Wednesday(5),
    	wtWebioEA2x2ERP-24VStartWday-Friday(6),
    	wtWebioEA2x2ERP-24VStartWday-Saturday(7)
    	}
    	
    ACCESS read-write
    STATUS mandatory
    DESCRIPTION
        "Day of the week on which the change is made from winter time to summer time"
    ::= { wtWebioEA2x2ERP-24VTimeZone 9 }
    
wtWebioEA2x2ERP-24VStTzStartHrs OBJECT-TYPE
    SYNTAX INTEGER 
    ACCESS read-write
    STATUS mandatory
    DESCRIPTION
        "Hour in which the time zone is changed from winter to summer time with
        respect to UTC."
    ::= { wtWebioEA2x2ERP-24VTimeZone 10 }

wtWebioEA2x2ERP-24VStTzStartMin OBJECT-TYPE
    SYNTAX INTEGER 
    ACCESS read-write
    STATUS mandatory
    DESCRIPTION
        "Minute in which the time zone is changed from winter to summer time with
        respect to UTC."
    ::= { wtWebioEA2x2ERP-24VTimeZone 11 }
 
wtWebioEA2x2ERP-24VStTzStopMonth OBJECT-TYPE
    SYNTAX INTEGER {
    	wtWebioEA2x2ERP-24VStopMonth-January(1),
    	wtWebioEA2x2ERP-24VStopMonth-February(2),
    	wtWebioEA2x2ERP-24VStopMonth-March(3),
    	wtWebioEA2x2ERP-24VStopMonth-April(4),
    	wtWebioEA2x2ERP-24VStopMonth-May(5),
    	wtWebioEA2x2ERP-24VStopMonth-June(6),
    	wtWebioEA2x2ERP-24VStopMonth-July(7),
    	wtWebioEA2x2ERP-24VStopMonth-August(8),
    	wtWebioEA2x2ERP-24VStopMonth-September(9),
    	wtWebioEA2x2ERP-24VStopMonth-October(10),
    	wtWebioEA2x2ERP-24VStopMonth-November(11),
    	wtWebioEA2x2ERP-24VStopMonth-December(12)
    	}
    ACCESS read-write
    STATUS mandatory
    DESCRIPTION
        "Month in which the change is made from summer time to winter time."
   ::= { wtWebioEA2x2ERP-24VTimeZone 12 }

wtWebioEA2x2ERP-24VStTzStopMode OBJECT-TYPE
    SYNTAX INTEGER {
    	wtWebioEA2x2ERP-24VStopMode-first(1),
    	wtWebioEA2x2ERP-24VStopMode-second(2),
    	wtWebioEA2x2ERP-24VStopMode-third(3),
    	wtWebioEA2x2ERP-24VStopMode-fourth(4),
    	wtWebioEA2x2ERP-24VStopMode-last(5)
    	}
    ACCESS read-write
    STATUS mandatory
    DESCRIPTION
        "Mode of the week day on which the change is made from summer time to winter time."
    ::= { wtWebioEA2x2ERP-24VTimeZone 13 }

wtWebioEA2x2ERP-24VStTzStopWday OBJECT-TYPE
    SYNTAX INTEGER {
    	wtWebioEA2x2ERP-24VStopWday-Sunday(1),
    	wtWebioEA2x2ERP-24VStopWday-Monday(2),
    	wtWebioEA2x2ERP-24VStopWday-Tuesday(3),
    	wtWebioEA2x2ERP-24VStopWday-Thursday(4),
    	wtWebioEA2x2ERP-24VStopWday-Wednesday(5),
    	wtWebioEA2x2ERP-24VStopWday-Friday(6),
    	wtWebioEA2x2ERP-24VStopWday-Saturday(7)
    	}
    ACCESS read-write
    STATUS mandatory
    DESCRIPTION
        "Day of the week on which the change is made from summer time to winter time."
    ::= { wtWebioEA2x2ERP-24VTimeZone 14 }
    
wtWebioEA2x2ERP-24VStTzStopHrs OBJECT-TYPE
    SYNTAX INTEGER 
    ACCESS read-write
    STATUS mandatory
    DESCRIPTION
        "Hour at which the time zone is changed from summer to winter time with
        respect to UTC."
    ::= { wtWebioEA2x2ERP-24VTimeZone 15 }

wtWebioEA2x2ERP-24VStTzStopMin OBJECT-TYPE
    SYNTAX INTEGER 
    ACCESS read-write
    STATUS mandatory
    DESCRIPTION
        "Minute at which the time zone is changed from summer to winter time with
        respect to UTC."
    ::= { wtWebioEA2x2ERP-24VTimeZone 16 }

-- wtWebioEA2x2ERP-24VTimeServer Group
----------------------------

wtWebioEA2x2ERP-24VTimeServer1 OBJECT-TYPE
    SYNTAX OCTET STRING 
    ACCESS read-write
    STATUS mandatory
    DESCRIPTION
        "IP address or name of the 1st time server in ASCII"
    ::= { wtWebioEA2x2ERP-24VTimeServer 1 }

wtWebioEA2x2ERP-24VTimeServer2 OBJECT-TYPE
    SYNTAX OCTET STRING 
    ACCESS read-write
    STATUS mandatory
    DESCRIPTION
        "IP address or name of the 2nd time server in ASCII"
    ::= { wtWebioEA2x2ERP-24VTimeServer 2 }

wtWebioEA2x2ERP-24VTsEnable OBJECT-TYPE
    SYNTAX OCTET STRING (SIZE(4))
    ACCESS read-write
    STATUS mandatory
    DESCRIPTION
        "Binary coded conditions:
        Octet 1: unused
        Octet 2: unused
        Octet 3: unused
        Octet 4:
        	Bit 1-7: unused
	        Bit 0  : Apply Time Server"
    ::= { wtWebioEA2x2ERP-24VTimeServer 3 }

wtWebioEA2x2ERP-24VTsSyncTime OBJECT-TYPE
    SYNTAX INTEGER 
    ACCESS read-write
    STATUS mandatory
    DESCRIPTION
        "Daily synchronisation time with the time server (hour: 0-23)."
    ::= { wtWebioEA2x2ERP-24VTimeServer 4 }
      
    
-- wtWebioEA2x2ERP-24VDeviceClock Group
----------------------------

wtWebioEA2x2ERP-24VClockHrs OBJECT-TYPE
    SYNTAX INTEGER (0..23)
    ACCESS read-write
    STATUS mandatory
    DESCRIPTION
        "Clock hours taking into account the time zone settings."
    ::= { wtWebioEA2x2ERP-24VDeviceClock 1 }

wtWebioEA2x2ERP-24VClockMin OBJECT-TYPE
    SYNTAX INTEGER (0..59)
    ACCESS read-write
    STATUS mandatory
    DESCRIPTION
        "Clock minutes taking into account the time zone settings."
    ::= { wtWebioEA2x2ERP-24VDeviceClock 2 }

wtWebioEA2x2ERP-24VClockDay OBJECT-TYPE
    SYNTAX INTEGER (1..31)
    ACCESS read-write
    STATUS mandatory
    DESCRIPTION
        "Date: Day of the month, taking into account the time zone settings."
    ::= { wtWebioEA2x2ERP-24VDeviceClock 3 }

wtWebioEA2x2ERP-24VClockMonth OBJECT-TYPE
   SYNTAX INTEGER {
    	wtWebioEA2x2ERP-24VClockMonth-January(1),
    	wtWebioEA2x2ERP-24VClockMonth-February(2),
    	wtWebioEA2x2ERP-24VClockMonth-March(3),
    	wtWebioEA2x2ERP-24VClockMonth-April(4),
    	wtWebioEA2x2ERP-24VClockMonth-May(5),
    	wtWebioEA2x2ERP-24VClockMonth-June(6),
    	wtWebioEA2x2ERP-24VClockMonth-July(7),
    	wtWebioEA2x2ERP-24VClockMonth-August(8),
    	wtWebioEA2x2ERP-24VClockMonth-September(9),
    	wtWebioEA2x2ERP-24VClockMonth-October(10),
    	wtWebioEA2x2ERP-24VClockMonth-November(11),
    	wtWebioEA2x2ERP-24VClockMonth-December(12)
    	}
    ACCESS read-write
    STATUS mandatory
    DESCRIPTION
        "Date: Month, taking into account the time zone settings."
    ::= { wtWebioEA2x2ERP-24VDeviceClock 4 }

wtWebioEA2x2ERP-24VClockYear OBJECT-TYPE
    SYNTAX INTEGER (0..65535)
    ACCESS read-write
    STATUS mandatory
    DESCRIPTION
        "Date: Year, taking into account the time zone settings."
    ::= { wtWebioEA2x2ERP-24VDeviceClock 5 }

-- wtWebioEA2x2ERP-24VNetwork Group
------------------------

wtWebioEA2x2ERP-24VIpAddress OBJECT-TYPE
    SYNTAX IpAddress
    ACCESS read-write
    STATUS mandatory
    DESCRIPTION
        "IP address of the Webio"
    ::= { wtWebioEA2x2ERP-24VNetwork 1 }

wtWebioEA2x2ERP-24VSubnetMask OBJECT-TYPE
    SYNTAX IpAddress
    ACCESS read-write
    STATUS mandatory
    DESCRIPTION
        "Subnet mask of the Webio"
    ::= { wtWebioEA2x2ERP-24VNetwork 2 }

wtWebioEA2x2ERP-24VGateway OBJECT-TYPE
    SYNTAX IpAddress
    ACCESS read-write
    STATUS mandatory
    DESCRIPTION
        "Gateway of the Webio"
    ::= { wtWebioEA2x2ERP-24VNetwork 3 }

wtWebioEA2x2ERP-24VDnsServer1 OBJECT-TYPE
    SYNTAX OCTET STRING 
    ACCESS read-write
    STATUS mandatory
    DESCRIPTION
        "IP address of the 1st DNS server in ASCII"
    ::= { wtWebioEA2x2ERP-24VNetwork 4 }

wtWebioEA2x2ERP-24VDnsServer2 OBJECT-TYPE
    SYNTAX OCTET STRING 
    ACCESS read-write
    STATUS mandatory
    DESCRIPTION
        "IP address of the 2nd DNS server in ASCII"
    ::= { wtWebioEA2x2ERP-24VNetwork 5 }

wtWebioEA2x2ERP-24VAddConfig OBJECT-TYPE
    SYNTAX OCTET STRING 
    ACCESS read-write
    STATUS mandatory
    DESCRIPTION
        "Additional configuration (1=ON):
        Octet 1: unused
        Octet 2: unused
        Octet 3: unused
        Octet 4:
	        Bit 1: DHCP  enable
	        Bit 0: BOOTP enable"
    ::= { wtWebioEA2x2ERP-24VNetwork 6 }

--  wtWebioEA2x2ERP-24VHTTP Group
--------------------------------

wtWebioEA2x2ERP-24VStartup OBJECT-TYPE
    SYNTAX OCTET STRING 
    ACCESS read-write
    STATUS mandatory
    DESCRIPTION
        "Binary coded start page, more than one page must not be selected:
        Octet 1: unused
        Octet 2: unused
        Octet 3: unused
        Octet 4:
        	Bit 2: user.htm
        	Bit 1: home.htm
	        Bit 0: index.htm"
    ::= { wtWebioEA2x2ERP-24VHTTP 1 }

wtWebioEA2x2ERP-24VGetHeaderEnable OBJECT-TYPE
    SYNTAX OCTET STRING 
    ACCESS read-write
    STATUS mandatory
    DESCRIPTION
        "If bits are set, every answer of a short form GET question will be lead
        by the IP-address and name of the device (Header) or a HTTP header (HTTP):
        Octet 1: unused
        Octet 2: unused
        Octet 3: unused
        Octet 4:
        	Bit 2-7: unused
        	Bit 1  : GET HTTP enable
                Bit 0  : GET Header enable"
    ::= { wtWebioEA2x2ERP-24VHTTP 2 }

wtWebioEA2x2ERP-24VHttpInputTrigger OBJECT-TYPE
    SYNTAX OCTET STRING (SIZE (4))
    ACCESS read-write
    STATUS mandatory
    DESCRIPTION
        "Every change on the inputs causes their state to be transmitted to the 
        remote device. To minimize data traffic, individual inputs may be exempted 
        from this rule. Nevertheless every transmission will contain all input bits.
        If a bit is set (1), a change of state on the corresponding input 
        triggers a transmission. If the bit is not set (0), no transmission 
        takes place.
        The OCTETS are interpreted bit-by-bit, with each bit corresponding to an input. 
        Bit 0 corresponds to the LSB.
        OCTET 1: unused
        OCTET 2: unused
        OCTET 3: unused
        OCTET 4, Bit 0-1: Digital inputs 0-1"
    ::= { wtWebioEA2x2ERP-24VHTTP 3 }

wtWebioEA2x2ERP-24VHttpPort OBJECT-TYPE
    SYNTAX INTEGER (1..65534)
    ACCESS read-write
    STATUS mandatory
    DESCRIPTION
       "Definition of the standard HTML port (Default: 80)."
    ::= { wtWebioEA2x2ERP-24VHTTP 4 }        
    
    
-- wtWebioEA2x2ERP-24VMail Group
--------------------------------

wtWebioEA2x2ERP-24VMailAdName OBJECT-TYPE
    SYNTAX OCTET STRING 
    ACCESS read-write
    STATUS mandatory
    DESCRIPTION
        "Device name for mail administration."
    ::= { wtWebioEA2x2ERP-24VMail 1 }
    
wtWebioEA2x2ERP-24VMailReply OBJECT-TYPE
    SYNTAX OCTET STRING 
    ACCESS read-write
    STATUS mandatory
    DESCRIPTION
        "Reply address for the mail server."
    ::= { wtWebioEA2x2ERP-24VMail 2 }
    
wtWebioEA2x2ERP-24VMailServer OBJECT-TYPE
    SYNTAX OCTET STRING 
    ACCESS read-write
    STATUS mandatory
    DESCRIPTION
        "Name or IP address of the mail server."
    ::= { wtWebioEA2x2ERP-24VMail 3 }
    
wtWebioEA2x2ERP-24VMailEnable OBJECT-TYPE
    SYNTAX OCTET STRING 
    ACCESS read-write
    STATUS mandatory
    DESCRIPTION
        "Set this bit to enable the sending of mails:
        Octet 1: unused
        Octet 2: unused
        Octet 3: unused
        Octet 4:
        	Bit 1-7: unused
                Bit 0  : Mail enable"
    ::= { wtWebioEA2x2ERP-24VMail 4 }

wtWebioEA2x2ERP-24VMailAuthentication OBJECT-TYPE
    SYNTAX OCTET STRING (SIZE (4))
    ACCESS read-write
    STATUS mandatory
    DESCRIPTION
        "Selection of the authentication modi:
        The OCTETS are interpreted bit-by-bit,
        Bit 0 corresponds to the LSB.
        OCTET 1: unused
        OCTET 2: unused
        OCTET 3: unused
        OCTET 4: Bit 3-7: unused
        	 Bit 2  : POP3 before SMTP
        	 Bit 1  : ESMTP, authentication
        	 Bit 0  : SMTP, no authentication"
    ::= { wtWebioEA2x2ERP-24VMail 5 }
    
wtWebioEA2x2ERP-24VMailAuthUser OBJECT-TYPE
    SYNTAX OCTET STRING 
    ACCESS read-write
    STATUS mandatory
    DESCRIPTION
        "Name of the user to be authenticated."
    ::= { wtWebioEA2x2ERP-24VMail 6 }    
    
wtWebioEA2x2ERP-24VMailAuthPassword OBJECT-TYPE
    SYNTAX OCTET STRING 
    ACCESS read-write
    STATUS mandatory
    DESCRIPTION
        "Authentication password."
    ::= { wtWebioEA2x2ERP-24VMail 7 }    
    
wtWebioEA2x2ERP-24VMailPop3Server OBJECT-TYPE
    SYNTAX OCTET STRING 
    ACCESS read-write
    STATUS mandatory
    DESCRIPTION
        "Name or Ip-address of the POP3 Servers."
    ::= { wtWebioEA2x2ERP-24VMail 8 }        
    

--  wtWebioEA2x2ERP-24VSnmp Group
--------------------------------

wtWebioEA2x2ERP-24VSnmpEnable OBJECT-TYPE
    SYNTAX OCTET STRING 
    ACCESS read-write
    STATUS mandatory
    DESCRIPTION
        "Set bit 0 to enable SNMP.
        If disabled, the device did not respond to any SNMP requests.
        Bit 1 decided wether the community string of read operations 
        is compared with the system password or not:
        Octet 1: unused
        Octet 2: unused
        Octet 3: unused
        Octet 4:
        	Bit 1-7: unused
        	Bit 0  : SNMP enable"
    ::= { wtWebioEA2x2ERP-24VSNMP 1 }
    
wtWebioEA2x2ERP-24VSnmpCommunityStringRead OBJECT-TYPE
    SYNTAX OCTET STRING
    ACCESS read-write
    STATUS mandatory
    DESCRIPTION
        "Community string read only"
    ::= { wtWebioEA2x2ERP-24VSNMP 2 }

wtWebioEA2x2ERP-24VSnmpCommunityStringReadWrite OBJECT-TYPE
    SYNTAX OCTET STRING
    ACCESS read-write
    STATUS mandatory
    DESCRIPTION
        "Community string read / write"
    ::= { wtWebioEA2x2ERP-24VSNMP 3 }

wtWebioEA2x2ERP-24VSnmpSystemTrapManagerIP OBJECT-TYPE
    SYNTAX OCTET STRING 
    ACCESS read-write
    STATUS mandatory
    DESCRIPTION
        "Name or IP address of the TCP server which accepts the system trap."
    ::= { wtWebioEA2x2ERP-24VSNMP 4 }
    
wtWebioEA2x2ERP-24VSnmpSystemTrapEnable OBJECT-TYPE
    SYNTAX OCTET STRING (SIZE(4))
    ACCESS read-write
    STATUS mandatory
    DESCRIPTION
        "Binary coded trigger conditions:
        Octet 1: unused
        Octet 2: unused
        Octet 3: unused
        Octet 4:
	        Bit 0:   ColdStart
	        Bit 1:   WarmStart
	        Bit 2:   Diag messages
	        Bit 3-7: unused"
    ::= { wtWebioEA2x2ERP-24VSNMP 5 }    

-- wtWebioEA2x2ERP-24VUDP Group
--------------------------------   

wtWebioEA2x2ERP-24VUdpAdminPort OBJECT-TYPE
    SYNTAX INTEGER
    ACCESS read-write
    STATUS mandatory
    DESCRIPTION
        "Udp port to which the Udp queries ( short form GET requests) can be sent. This
        port number must be unique within the device."
    ::= { wtWebioEA2x2ERP-24VUDP 1 }

wtWebioEA2x2ERP-24VUdpEnable OBJECT-TYPE
    SYNTAX OCTET STRING 
    ACCESS read-write
    STATUS mandatory
    DESCRIPTION
        "Set this bit to enable UDP support:
        Octet 1: unused
        Octet 2: unused
        Octet 3: unused
        Octet 4:
        	Bit 1-7: unused
                Bit 0  : UDP enable"
    ::= { wtWebioEA2x2ERP-24VUDP 2 }

wtWebioEA2x2ERP-24VUdpRemotePort OBJECT-TYPE
    SYNTAX INTEGER
    ACCESS read-write
    STATUS mandatory
    DESCRIPTION
        "Udp remote port setting.
        If this value is set to zero, the source port read from a request will be used 
        as destination port for the answer.
        A non zero value forced the destination port to this value."
    ::= { wtWebioEA2x2ERP-24VUDP 3 }
    
--  wtWebioEA2x2ERP-24VBinary Group
--------------------------------

wtWebioEA2x2ERP-24VBinaryModeCount OBJECT-TYPE
    SYNTAX INTEGER (1..2)
    ACCESS read-only
    STATUS mandatory
    DESCRIPTION
        "Number of independent binary channels."
    ::= { wtWebioEA2x2ERP-24VBinary 1 }
    
-- Binary Interface Table

wtWebioEA2x2ERP-24VBinaryIfTable OBJECT-TYPE
    SYNTAX SEQUENCE OF WtWebioEA2x2ERP-24VBinaryIfEntry
    ACCESS not-accessible
    STATUS mandatory
    DESCRIPTION
        "Table of indices."
    ::= { wtWebioEA2x2ERP-24VBinary 2 }

wtWebioEA2x2ERP-24VBinaryIfEntry OBJECT-TYPE
    SYNTAX WtWebioEA2x2ERP-24VBinaryIfEntry
    ACCESS not-accessible
    STATUS mandatory
    DESCRIPTION
        "Indices of the binary channels."
    INDEX  { wtWebioEA2x2ERP-24VBinaryModeNo }
    ::= { wtWebioEA2x2ERP-24VBinaryIfTable 1 }

WtWebioEA2x2ERP-24VBinaryIfEntry ::= SEQUENCE {
    wtWebioEA2x2ERP-24VBinaryModeNo INTEGER
}

wtWebioEA2x2ERP-24VBinaryModeNo OBJECT-TYPE
    SYNTAX INTEGER (1..2)
    ACCESS read-only
    STATUS mandatory
    DESCRIPTION
        "Number of the binary channel."
    ::= { wtWebioEA2x2ERP-24VBinaryIfEntry 1 }

-- Binary Table
--------------------------------

wtWebioEA2x2ERP-24VBinaryTable OBJECT-TYPE
    SYNTAX SEQUENCE OF WtWebioEA2x2ERP-24VBinaryEntry
    ACCESS not-accessible
    STATUS mandatory
    DESCRIPTION
        "Table of properties of the binary mode."
    ::= { wtWebioEA2x2ERP-24VBinary 3 }

wtWebioEA2x2ERP-24VBinaryEntry OBJECT-TYPE
    SYNTAX WtWebioEA2x2ERP-24VBinaryEntry
    ACCESS not-accessible
    STATUS mandatory
    DESCRIPTION
        "Binary properties."
    INDEX  { wtWebioEA2x2ERP-24VBinaryModeNo }
    ::= { wtWebioEA2x2ERP-24VBinaryTable 1 }

WtWebioEA2x2ERP-24VBinaryEntry ::= SEQUENCE {
    wtWebioEA2x2ERP-24VBinaryOperationMode		OCTET STRING,
    wtWebioEA2x2ERP-24VBinaryTcpServerLocalPort		INTEGER,
    wtWebioEA2x2ERP-24VBinaryTcpServerInputTrigger	OCTET STRING,
    wtWebioEA2x2ERP-24VBinaryTcpServerApplicationMode	OCTET STRING,
    wtWebioEA2x2ERP-24VBinaryTcpClientLocalPort		INTEGER,
    wtWebioEA2x2ERP-24VBinaryTcpClientServerPort	INTEGER,
    wtWebioEA2x2ERP-24VBinaryTcpClientServerIpAddr	OCTET STRING,
    wtWebioEA2x2ERP-24VBinaryTcpClientServerPassword	OCTET STRING,
    wtWebioEA2x2ERP-24VBinaryTcpClientInactivity	INTEGER,
    wtWebioEA2x2ERP-24VBinaryTcpClientInputTrigger	OCTET STRING,
    wtWebioEA2x2ERP-24VBinaryTcpClientInterval		INTEGER,
    wtWebioEA2x2ERP-24VBinaryTcpClientApplicationMode	OCTET STRING,
    wtWebioEA2x2ERP-24VBinaryUdpPeerLocalPort		INTEGER,
    wtWebioEA2x2ERP-24VBinaryUdpPeerRemotePort		INTEGER,
    wtWebioEA2x2ERP-24VBinaryUdpPeerRemoteIpAddr	OCTET STRING,
    wtWebioEA2x2ERP-24VBinaryUdpPeerInputTrigger	OCTET STRING,
    wtWebioEA2x2ERP-24VBinaryUdpPeerInterval		INTEGER,
    wtWebioEA2x2ERP-24VBinaryUdpPeerApplicationMode	OCTET STRING,
    wtWebioEA2x2ERP-24VBinaryConnectedPort		INTEGER,
    wtWebioEA2x2ERP-24VBinaryConnectedIpAddr		IpAddress,
    wtWebioEA2x2ERP-24VBinaryTcpServerClientHttpPort	INTEGER,
    wtWebioEA2x2ERP-24VBinaryTcpClientServerHttpPort	INTEGER
    
}

wtWebioEA2x2ERP-24VBinaryOperationMode OBJECT-TYPE
    SYNTAX OCTET STRING (SIZE (4))
    ACCESS read-write
    STATUS mandatory
    DESCRIPTION
        "Selection of the operation mode:
        The OCTETS are interpreted bit-by-bit,
        Bit 0 corresponds to the LSB.
        OCTET 1: unused
        OCTET 2: unused
        OCTET 3: unused
        OCTET 4: Bit 3-7: unused
        	 Bit 2  : UDP Peer
        	 Bit 1  : TCP Client
        	 Bit 0  : TCP Server"
    ::= { wtWebioEA2x2ERP-24VBinaryEntry 1 }

wtWebioEA2x2ERP-24VBinaryTcpServerLocalPort OBJECT-TYPE
    SYNTAX INTEGER (1..65535)
    ACCESS read-write
    STATUS mandatory
    DESCRIPTION
        "Local TCP port for data exchange in this server mode.
        This port number must be unique within the device.
	Reserved port number must not be used (refere to the manual)."
    ::= { wtWebioEA2x2ERP-24VBinaryEntry 2 }

wtWebioEA2x2ERP-24VBinaryTcpServerInputTrigger OBJECT-TYPE
    SYNTAX OCTET STRING (SIZE (4))
    ACCESS read-write
    STATUS mandatory
    DESCRIPTION
        "Every change on the inputs causes their state to be transmitted to the 
        remote device. To minimize data traffic, individual inputs may be exempted 
        from this rule. Nevertheless every transmission will contain all input bits.
        If a bit is set (1), a change of state on the corresponding input 
        triggers a transmission. If the bit is not set (0), no transmission 
        takes place.
        The OCTETS are interpreted bit-by-bit, with each bit corresponding to an input. 
        Bit 0 corresponds to the LSB.
        OCTET 1: unused
        OCTET 2: unused
        OCTET 3: unused
        OCTET 4, Bit 0-1: Digital inputs 0-1"
    ::= { wtWebioEA2x2ERP-24VBinaryEntry 3 }

wtWebioEA2x2ERP-24VBinaryTcpServerApplicationMode OBJECT-TYPE
    SYNTAX OCTET STRING (SIZE (4))
    ACCESS read-write
    STATUS mandatory
    DESCRIPTION
        "Selection of the application mode:
        The OCTETS are interpreted bit-by-bit,
        Bit 0 corresponds to the LSB.
        OCTET 1: unused
        OCTET 2: unused
        OCTET 3: unused
        OCTET 4: Bit 4-7: unused
        	 Bit 3  : OPC Device
        	 Bit 2  : Box2Box Slave
        	 Bit 1  : Compatible 50xxx
        	 Bit 0  : Default"
    ::= { wtWebioEA2x2ERP-24VBinaryEntry 4 }
    
wtWebioEA2x2ERP-24VBinaryTcpClientLocalPort OBJECT-TYPE
    SYNTAX INTEGER (1..65535)
    ACCESS read-write
    STATUS mandatory
    DESCRIPTION
        "Local TCP port for data exchange in this client mode.
        This port number must be unique within the device.
	Reserved port number must not be used (refere to the manual)."
    ::= { wtWebioEA2x2ERP-24VBinaryEntry 5 }

wtWebioEA2x2ERP-24VBinaryTcpClientServerPort OBJECT-TYPE
    SYNTAX INTEGER (1..65535)
    ACCESS read-write
    STATUS mandatory
    DESCRIPTION
        "Port number of the server. A complete set of port number, IP address
        and a valid input/output mask starts this mode.
        No data exchange take place when setting the server port to zero."
    ::= { wtWebioEA2x2ERP-24VBinaryEntry 6 }

wtWebioEA2x2ERP-24VBinaryTcpClientServerIpAddr OBJECT-TYPE
    SYNTAX OCTET STRING
    ACCESS read-write
    STATUS mandatory
    DESCRIPTION
        "Ip address of the server. A complete set of port number, IP address
        and a valid input/output mask starts this mode.
        No data exchange take place when setting the server IP address to 0.0.0.0."
    ::= { wtWebioEA2x2ERP-24VBinaryEntry 7 }

wtWebioEA2x2ERP-24VBinaryTcpClientServerPassword OBJECT-TYPE
    SYNTAX OCTET STRING
    ACCESS read-write
    STATUS mandatory
    DESCRIPTION
        "Building a connection may be protected by the 
        administrator password of the server. Enter the server password
        to establish the connection, if a server administrator password
        exists."
    ::= { wtWebioEA2x2ERP-24VBinaryEntry 8 }

wtWebioEA2x2ERP-24VBinaryTcpClientInactivity OBJECT-TYPE
    SYNTAX INTEGER 
    ACCESS read-write
    STATUS mandatory
    DESCRIPTION
        "Connection timeout in 100ms. If no data are exchanged within the specified  
        time, the device closes the connection to the server.
        The value 0 deactivates the timer. Using the Box2Box mode this function is
        disabled."
    ::= { wtWebioEA2x2ERP-24VBinaryEntry 9 }
    
wtWebioEA2x2ERP-24VBinaryTcpClientInputTrigger OBJECT-TYPE
    SYNTAX OCTET STRING (SIZE (4))
    ACCESS read-write
    STATUS mandatory
    DESCRIPTION
        "Every change on the inputs causes their state to be transmitted to the 
        remote device. To minimize data traffic, individual inputs may be exempted 
        from this rule. Nevertheless every transmission will contain all input bits.
        If a bit is set (1), a change of state on the corresponding input 
        triggers a transmission. If the bit is not set (0), no transmission 
        takes place.
        The OCTETS are interpreted bit-by-bit, with each bit corresponding to an input. 
        Bit 0 corresponds to the LSB.
        OCTET 1: unused
        OCTET 2: unused
        OCTET 3: unused
        OCTET 4, Bit 0-1: Digital inputs 0-1"
    ::= { wtWebioEA2x2ERP-24VBinaryEntry 10 }
 
wtWebioEA2x2ERP-24VBinaryTcpClientInterval OBJECT-TYPE
    SYNTAX INTEGER (0..65535)
    ACCESS read-write
    STATUS mandatory
    DESCRIPTION
        "Configurable interval with a 100ms base, in which the Webio device sends
        data to the configured application. A interval of zero stopps the 
        periodical sending."
    ::= { wtWebioEA2x2ERP-24VBinaryEntry 11 }

wtWebioEA2x2ERP-24VBinaryTcpClientApplicationMode OBJECT-TYPE
    SYNTAX OCTET STRING (SIZE (4))
    ACCESS read-write
    STATUS mandatory
    DESCRIPTION
        "Selection of the application mode:
        The OCTETS are interpreted bit-by-bit,
        Bit 0 corresponds to the LSB.
        OCTET 1: unused
        OCTET 2: unused
        OCTET 3: unused
        OCTET 4: Bit 3-7: unused
        	 Bit 2  : Box2Box Slave
        	 Bit 1  : Compatible 50xxx
        	 Bit 0  : Default"
    ::= { wtWebioEA2x2ERP-24VBinaryEntry 12 }

wtWebioEA2x2ERP-24VBinaryUdpPeerLocalPort OBJECT-TYPE
    SYNTAX INTEGER (1..65535)
    ACCESS read-write
    STATUS mandatory
    DESCRIPTION
        "Local UDP port for data exchange in this peer to peer mode.
        This port number must be unique within the device.
	Reserved port number must not be used (refere to the manual)."
    ::= { wtWebioEA2x2ERP-24VBinaryEntry 13 }

wtWebioEA2x2ERP-24VBinaryUdpPeerRemotePort OBJECT-TYPE
    SYNTAX INTEGER (1..65535)
    ACCESS read-write
    STATUS mandatory
    DESCRIPTION
        "Port number of the remote device. A complete set of port number, IP address
        and a valid input/output mask starts this mode.
        No data exchange take place when setting the remote port to zero."
    ::= { wtWebioEA2x2ERP-24VBinaryEntry 14 }

wtWebioEA2x2ERP-24VBinaryUdpPeerRemoteIpAddr OBJECT-TYPE
    SYNTAX OCTET STRING
    ACCESS read-write
    STATUS mandatory
    DESCRIPTION
        "Ip address of the remote device. A complete set of port number, IP address
        and a valid input/output mask starts this mode.
        No data exchange take place when setting the remote device IP address to 0.0.0.0."
    ::= { wtWebioEA2x2ERP-24VBinaryEntry 15 }

wtWebioEA2x2ERP-24VBinaryUdpPeerInputTrigger OBJECT-TYPE
    SYNTAX OCTET STRING (SIZE (4))
    ACCESS read-write
    STATUS mandatory
    DESCRIPTION
        "Every change on the inputs causes their state to be transmitted to the 
        remote device. To minimize data traffic, individual inputs may be exempted 
        from this rule. Nevertheless every transmission will contain all input bits.
        If a bit is set (1), a change of state on the corresponding input 
        triggers a transmission. If the bit is not set (0), no transmission 
        takes place.
        The OCTETS are interpreted bit-by-bit, with each bit corresponding to an input. 
        Bit 0 corresponds to the LSB.
        OCTET 1: unused
        OCTET 2: unused
        OCTET 3: unused
        OCTET 4, Bit 0-1: Digital inputs 0-1"
    ::= { wtWebioEA2x2ERP-24VBinaryEntry 16 }

wtWebioEA2x2ERP-24VBinaryUdpPeerInterval OBJECT-TYPE
    SYNTAX INTEGER (0..65535)
    ACCESS read-write
    STATUS mandatory
    DESCRIPTION
        "Configurable interval with a 100ms base, in which the Webio device sends
        data to the configured remote device. A interval of zero stopps the 
        periodical sending."
    ::= { wtWebioEA2x2ERP-24VBinaryEntry 17 }

wtWebioEA2x2ERP-24VBinaryUdpPeerApplicationMode OBJECT-TYPE
    SYNTAX OCTET STRING (SIZE (4))
    ACCESS read-write
    STATUS mandatory
    DESCRIPTION
        "Selection of the application mode:
        The OCTETS are interpreted bit-by-bit, with each bit corresponding to an output. 
        Bit 0 corresponds to the LSB.
        OCTET 1: unused
        OCTET 2: unused
        OCTET 3: unused
        OCTET 4: Bit 3-7: unused
        	 Bit 2  : Box2Box Slave
        	 Bit 1  : Compatible 50xxx
        	 Bit 0  : Default"
    ::= { wtWebioEA2x2ERP-24VBinaryEntry 18 }

wtWebioEA2x2ERP-24VBinaryConnectedPort OBJECT-TYPE
    SYNTAX INTEGER (1..65535)
    ACCESS read-only
    STATUS mandatory
    DESCRIPTION
        "Port number of the remote device, after connection has been established.
        In case of no connection or missing port informations a zero will be read."
    ::= { wtWebioEA2x2ERP-24VBinaryEntry 19 }

wtWebioEA2x2ERP-24VBinaryConnectedIpAddr OBJECT-TYPE
    SYNTAX IpAddress
    ACCESS read-only
    STATUS mandatory
    DESCRIPTION
        "IP address of the remote device, after connection has been established.
        In case of no connection or missing port informations 0.0.0.0 will be read."
    ::= { wtWebioEA2x2ERP-24VBinaryEntry 20 } 

wtWebioEA2x2ERP-24VBinaryTcpServerClientHttpPort OBJECT-TYPE
    SYNTAX INTEGER (1..65535)
    ACCESS read-write
    STATUS mandatory
    DESCRIPTION
        "HTTP port number of the remote device at TCP Server Mode. If an mailfunction occurs 
        status informations will be send to this port. 
        Not used at mode Compatible 50xxx."
    ::= { wtWebioEA2x2ERP-24VBinaryEntry 21 }
    
wtWebioEA2x2ERP-24VBinaryTcpClientServerHttpPort OBJECT-TYPE
    SYNTAX INTEGER (1..65535)
    ACCESS read-write
    STATUS mandatory
    DESCRIPTION
        "HTTP port number of the remote device at TCP Client Mode. In the operating mode
        Box2Box connection status informations will be exchanged through this port."
    ::= { wtWebioEA2x2ERP-24VBinaryEntry 22 }            
    
--  wtWebioEA2x2ERP-24VSyslog Group
--------------------------------
    
wtWebioEA2x2ERP-24VSyslogServerIP OBJECT-TYPE
    SYNTAX OCTET STRING 
    ACCESS read-write
    STATUS mandatory
    DESCRIPTION
        "Name or IP address of the Syslog server, which accepts the Syslog messgaes."
    ::= { wtWebioEA2x2ERP-24VSyslog 1 }
    
wtWebioEA2x2ERP-24VSyslogServerPort OBJECT-TYPE
    SYNTAX INTEGER
    ACCESS read-write
    STATUS mandatory
    DESCRIPTION
        "Portnumber of the Syslog servers, default 514."
    ::= { wtWebioEA2x2ERP-24VSyslog 2 }

wtWebioEA2x2ERP-24VSyslogSystemMessagesEnable OBJECT-TYPE
    SYNTAX OCTET STRING (SIZE(4))
    ACCESS read-write
    STATUS mandatory
    DESCRIPTION
        "Binary coded trigger conditions:
        Octet 1: unused
        Octet 2: unused
        Octet 3: unused
        Octet 4:
	        Bit 0:   ColdStart
	        Bit 1:   WarmStart
	        Bit 2:   Diag Messages
	        Bit 3-7: unused"
    ::= { wtWebioEA2x2ERP-24VSyslog 3 }    

wtWebioEA2x2ERP-24VSyslogEnable OBJECT-TYPE
    SYNTAX OCTET STRING 
    ACCESS read-write
    STATUS mandatory
    DESCRIPTION
        "Set bit 0to enable Syslog:
        Octet 1: unused
        Octet 2: unused
        Octet 3: unused
        Octet 4:
        	Bit 1-7: unused
                Bit 0  : Syslog enable"
    ::= { wtWebioEA2x2ERP-24VSyslog 4 }

--  wtWebioEA2x2ERP-24VFTP Group
--------------------------------

wtWebioEA2x2ERP-24VFTPServerIP OBJECT-TYPE
    SYNTAX OCTET STRING 
    ACCESS read-write
    STATUS mandatory
    DESCRIPTION
        "Name or IP address of the FTP server, which accepts the FTP messages."
    ::= { wtWebioEA2x2ERP-24VFTP 1 }
    
wtWebioEA2x2ERP-24VFTPServerControlPort OBJECT-TYPE
    SYNTAX INTEGER
    ACCESS read-write
    STATUS mandatory
    DESCRIPTION
        "Portnumber of the control port of the FTP server, default 21."
    ::= { wtWebioEA2x2ERP-24VFTP 2 }
    
wtWebioEA2x2ERP-24VFTPUserName OBJECT-TYPE
    SYNTAX OCTET STRING 
    ACCESS read-write
    STATUS mandatory
    DESCRIPTION
        "FTP Loggin: user name."
    ::= { wtWebioEA2x2ERP-24VFTP 3 }
    
wtWebioEA2x2ERP-24VFTPPassword OBJECT-TYPE
    SYNTAX OCTET STRING 
    ACCESS read-write
    STATUS mandatory
    DESCRIPTION
        "FTP Loggin: user password."
    ::= { wtWebioEA2x2ERP-24VFTP 4 }

wtWebioEA2x2ERP-24VFTPAccount OBJECT-TYPE
    SYNTAX OCTET STRING 
    ACCESS read-write
    STATUS mandatory
    DESCRIPTION
        "FTP Loggin: name of account."
    ::= { wtWebioEA2x2ERP-24VFTP 5 }

wtWebioEA2x2ERP-24VFTPOption OBJECT-TYPE
    SYNTAX OCTET STRING 
    ACCESS read-write
    STATUS mandatory
    DESCRIPTION
        "Bit 0 switches the FTP Server in Passiv-Mode,
        the Client controls the data connection on its own:
        Octet 1: unused
        Octet 2: unused
        Octet 3: unused
        Octet 4:
        	Bit 1-7: unused
                Bit 0  : PASV enable"
    ::= { wtWebioEA2x2ERP-24VFTP 6 }
    
wtWebioEA2x2ERP-24VFTPEnable OBJECT-TYPE
    SYNTAX OCTET STRING 
    ACCESS read-write
    STATUS mandatory
    DESCRIPTION
        "Set Bit 0 to enable FTP:
        Octet 1: unused
        Octet 2: unused
        Octet 3: unused
        Octet 4:
        	Bit 1-7: unused
                Bit 0  : FTP enable"
    ::= { wtWebioEA2x2ERP-24VFTP 7 }  

--  wtWebioEA2x2ERP-24VWayBack Group
--------------------------------

wtWebioEA2x2ERP-24VWayBackEnable OBJECT-TYPE
    SYNTAX OCTET STRING 
    ACCESS read-write
    STATUS mandatory
    DESCRIPTION
        "Set Bit 0 to enable WayBack:
        Octet 1: unused
        Octet 2: unused
        Octet 3: unused
        Octet 4:
        	Bit 1-7: unused
                Bit 0  : WayBack enable"
    ::= { wtWebioEA2x2ERP-24VWayBack 1 }    

wtWebioEA2x2ERP-24VWayBackServerControlPort OBJECT-TYPE
    SYNTAX INTEGER
    ACCESS read-write
    STATUS mandatory
    DESCRIPTION
        "Portnumber of the control port of the FTP server, default 21."
    ::= { wtWebioEA2x2ERP-24VWayBack 2 }
    
wtWebioEA2x2ERP-24VWayBackFTPPassword OBJECT-TYPE
    SYNTAX OCTET STRING 
    ACCESS read-write
    STATUS mandatory
    DESCRIPTION
        "WayBack FTP Loggin: Password of the user."
    ::= { wtWebioEA2x2ERP-24VWayBack 3 }    
    
wtWebioEA2x2ERP-24VWayBackFTPResponse OBJECT-TYPE
    SYNTAX OCTET STRING 
    ACCESS read-write
    STATUS mandatory
    DESCRIPTION
        "WayBack FTP response: return message after login."
    ::= { wtWebioEA2x2ERP-24VWayBack 4 }
    
wtWebioEA2x2ERP-24VWayBackFTPTimeOut OBJECT-TYPE
    SYNTAX OCTET STRING 
    ACCESS read-write
    STATUS mandatory
    DESCRIPTION
        "WayBack FTP Timeout: a request must be finished within this periode of time."
    ::= { wtWebioEA2x2ERP-24VWayBack 5 }    
    
--  wtWebioEA2x2ERP-24VOutputMode Group
--------------------------------

-- OutputMode Table

wtWebioEA2x2ERP-24VOutputModeTable OBJECT-TYPE
    SYNTAX SEQUENCE OF WtWebioEA2x2ERP-24VOutputModeEntry
    ACCESS not-accessible
    STATUS mandatory
    DESCRIPTION
        "Table of output mode configurations dependent on the output indices."
    ::= { wtWebioEA2x2ERP-24VOutputMode 1 }

wtWebioEA2x2ERP-24VOutputModeEntry OBJECT-TYPE
    SYNTAX WtWebioEA2x2ERP-24VOutputModeEntry
    ACCESS not-accessible
    STATUS mandatory
    DESCRIPTION
        "Output mode configurations of the individual outputs."
    INDEX  { wtWebioEA2x2ERP-24VOutputNo }
    ::= { wtWebioEA2x2ERP-24VOutputModeTable 1 }

WtWebioEA2x2ERP-24VOutputModeEntry ::= SEQUENCE {
    wtWebioEA2x2ERP-24VOutputModeBit	OCTET STRING
}

wtWebioEA2x2ERP-24VOutputModeBit OBJECT-TYPE
    SYNTAX OCTET STRING (SIZE (4))
    ACCESS read-write
    STATUS mandatory
    DESCRIPTION
        "This binary coded output mode defines the individual operation mode for any
        output. More than one mode must not be selected.
        The OCTETS are interpreted bit-by-bit, with each bit corresponding to an output. 
        Bit 0 corresponds to the LSB.
        OCTET 1: unused
        OCTET 2: unused
        OCTET 3: unused
        OCTET 4: Bit 6-7: unused
        	 Bit 5  : Logic
        	 Bit 4  : Binary 2
        	 Bit 3  : Binary 1
        	 Bit 2  : SNMP
        	 Bit 1  : UDP ASCII
        	 Bit 0  : HTTP"
    ::= { wtWebioEA2x2ERP-24VOutputModeEntry 1 }
    
wtWebioEA2x2ERP-24VSafetyTimeout OBJECT-TYPE
    SYNTAX INTEGER (0..65535)
    ACCESS read-write
    STATUS mandatory
    DESCRIPTION
        "After this period of time (multiple of 100ms) without receiving data
        outputs switch to their Safety States. For each output a independend safety state
        could be defined."
    ::= { wtWebioEA2x2ERP-24VOutputMode 2 }
 
 wtWebioEA2x2ERP-24VLoadControlEnable OBJECT-TYPE
    SYNTAX OCTET STRING 
    ACCESS read-write
    STATUS mandatory
    DESCRIPTION
        "Here the function of automatic load control can be enabled. All output were tested in 
        pairs (0-1). If an error occours at one output,
        both output of an pair will be switched of. For a properly function of the load control
        each output of a pair have to has a load. If there is no existing load, a pull down resistor
        can be used.
        Outputs with no load are automaticly detected and not part of the control function.
        The OCTETS are interpreted bit-by-bit, with each bit corresponding to an output. 
        Bit 0 corresponds to the LSB.
        Octet 1: unused
        Octet 2: unused
        Octet 3: unused
        Octet 4:
        	Bit 1-7: unused
                Bit 0  : Load Control enable"
    ::= { wtWebioEA2x2ERP-24VOutputMode 3 }
    
wtWebioEA2x2ERP-24VPowerSupplyEnable OBJECT-TYPE
    SYNTAX OCTET STRING 
    ACCESS read-write
    STATUS mandatory
    DESCRIPTION
        "Setting this enable bit turns on the intarnal 24V power supply of the outputs.
        All currents out must not exceed 150mA. At overcurrent condition the power supply will
        be shut down automatically. To reset the ocvercurrent protection circuit
        write 1 into wtWebioEA2x2DiagErrorClear.
        Internal power supply is a feature of 57638 only.
        
        Octet 1: unused
        Octet 2: unused
        Octet 3: unused
        Octet 4:
        	Bit 1-7: unused
                Bit 0  : Power Supply enable"
    ::= { wtWebioEA2x2ERP-24VOutputMode 4 }    
    
-- wtWebioEA2x2ERP-24VAlarm Group
----------------------------

wtWebioEA2x2ERP-24VAlarmCount OBJECT-TYPE
    SYNTAX INTEGER (1..4)
    ACCESS read-only
    STATUS mandatory
    DESCRIPTION
        "Number of independent alarms."
    ::= { wtWebioEA2x2ERP-24VAlarm 1 }
    
-- Alarm Interface Table

wtWebioEA2x2ERP-24VAlarmIfTable OBJECT-TYPE
    SYNTAX SEQUENCE OF WtWebioEA2x2ERP-24VAlarmIfEntry
    ACCESS not-accessible
    STATUS mandatory
    DESCRIPTION
        "List of alarm indices."
    ::= { wtWebioEA2x2ERP-24VAlarm 2 }

wtWebioEA2x2ERP-24VAlarmIfEntry OBJECT-TYPE
    SYNTAX WtWebioEA2x2ERP-24VAlarmIfEntry
    ACCESS not-accessible
    STATUS mandatory
    DESCRIPTION
        "Numbers of the alarms."
    INDEX  { wtWebioEA2x2ERP-24VAlarmNo }
    ::= { wtWebioEA2x2ERP-24VAlarmIfTable 1 }

WtWebioEA2x2ERP-24VAlarmIfEntry ::= SEQUENCE {
    wtWebioEA2x2ERP-24VAlarmNo INTEGER
}

wtWebioEA2x2ERP-24VAlarmNo OBJECT-TYPE
    SYNTAX INTEGER (1..4)
    ACCESS read-only
    STATUS mandatory
    DESCRIPTION
        "Numbers of the alarms."
    ::= { wtWebioEA2x2ERP-24VAlarmIfEntry 1 }

-- Alarm Table

wtWebioEA2x2ERP-24VAlarmTable OBJECT-TYPE
    SYNTAX SEQUENCE OF WtWebioEA2x2ERP-24VAlarmEntry
    ACCESS not-accessible
    STATUS mandatory
    DESCRIPTION
        "List of settings depending on the alarm number."
    ::= { wtWebioEA2x2ERP-24VAlarm 3 }

wtWebioEA2x2ERP-24VAlarmEntry OBJECT-TYPE
    SYNTAX WtWebioEA2x2ERP-24VAlarmEntry
    ACCESS not-accessible
    STATUS mandatory
    DESCRIPTION
        "Alarm parameters of the individual alarms."
    INDEX  { wtWebioEA2x2ERP-24VAlarmNo }
    ::= { wtWebioEA2x2ERP-24VAlarmTable 1 }

WtWebioEA2x2ERP-24VAlarmEntry ::= SEQUENCE {
    wtWebioEA2x2ERP-24VAlarmInputTrigger	OCTET STRING,
    wtWebioEA2x2ERP-24VAlarmOutputTrigger	OCTET STRING,
    wtWebioEA2x2ERP-24VAlarmSystemTrigger	OCTET STRING,
    wtWebioEA2x2ERP-24VAlarmMaxCounterValue	OCTET STRING,
    wtWebioEA2x2ERP-24VAlarmInterval		OCTET STRING,
    wtWebioEA2x2ERP-24VAlarmEnable		OCTET STRING,
    wtWebioEA2x2ERP-24VAlarmMailAddr		OCTET STRING,
    wtWebioEA2x2ERP-24VAlarmMailSubject		OCTET STRING,
    wtWebioEA2x2ERP-24VAlarmMailText		OCTET STRING,
    wtWebioEA2x2ERP-24VAlarmSnmpManagerIP	OCTET STRING,
    wtWebioEA2x2ERP-24VAlarmSnmpTrapText	OCTET STRING,
    wtWebioEA2x2ERP-24VAlarmUdpIpAddr		OCTET STRING,
    wtWebioEA2x2ERP-24VAlarmUdpPort		INTEGER,
    wtWebioEA2x2ERP-24VAlarmUdpText		OCTET STRING,
    wtWebioEA2x2ERP-24VAlarmTcpIpAddr		OCTET STRING,
    wtWebioEA2x2ERP-24VAlarmTcpPort		INTEGER,
    wtWebioEA2x2ERP-24VAlarmTcpText		OCTET STRING,    
    wtWebioEA2x2ERP-24VAlarmSyslogIpAddr	OCTET STRING,
    wtWebioEA2x2ERP-24VAlarmSyslogPort		INTEGER,
    wtWebioEA2x2ERP-24VAlarmSyslogText		OCTET STRING,
    wtWebioEA2x2ERP-24VAlarmFtpDataPort		OCTET STRING,
    wtWebioEA2x2ERP-24VAlarmFtpFileName		OCTET STRING,
    wtWebioEA2x2ERP-24VAlarmFtpText		OCTET STRING,
    wtWebioEA2x2ERP-24VAlarmFtpOption		OCTET STRING,
    wtWebioEA2x2ERP-24VAlarmTimerCron		OCTET STRING,

    wtWebioEA2x2ERP-24VAlarmMailReleaseSubject	OCTET STRING,
    wtWebioEA2x2ERP-24VAlarmMailReleaseText	OCTET STRING,
    wtWebioEA2x2ERP-24VAlarmSnmpTrapReleaseText	OCTET STRING,
    wtWebioEA2x2ERP-24VAlarmUdpReleaseText	OCTET STRING,
    wtWebioEA2x2ERP-24VAlarmTcpReleaseText	OCTET STRING,    
    wtWebioEA2x2ERP-24VAlarmSyslogReleaseText	OCTET STRING,
    wtWebioEA2x2ERP-24VAlarmFtpReleaseText	OCTET STRING    
    
}

wtWebioEA2x2ERP-24VAlarmInputTrigger OBJECT-TYPE
    SYNTAX OCTET STRING (SIZE(12))
    ACCESS read-write
    STATUS mandatory
    DESCRIPTION
        "This variable allows setting of individual input trigger conditions. 
        The OCTETS are interpreted bit-by-bit, with each bit corresponding to an input. 
        Bit 0 corresponds to the LSB.
	The first four OCTETS contain the mask which determines which of the inputs are to 
	be considered (corresponding bit = 1) and which inputs are to ignore 
	(corresponding bit = 0):
	OCTET 1 : unused
	OCTET 2 : unused
	OCTET 3 : unused
	OCTET 4, Bit 0-1: Mask for digital inputs 0-1
	
	OCTETS 5-8 contain the level (1=HIGH, 0=LOW) which the inputs 
	should assume:
	OCTET 5 : unused
	OCTET 6 : unused
	OCTET 7 : unused
        OCTET 8, Bit 0-1: Level of digital inputs 0-1
        
	OCTETS 9-12 contain the ANY bit (1=ON, 0=OFF). Inputs masked with the any bit trigger with any change 
	of the corresponding input bit. Settings in OCTET 5-9 are then unused:
	OCTET 9: unused
	OCTET 10: unused
	OCTET 11: unused
	OCTET 12, Bit 0-1: ANY bits of digital inputs 0-1"
        
    ::= { wtWebioEA2x2ERP-24VAlarmEntry 1 }

wtWebioEA2x2ERP-24VAlarmOutputTrigger OBJECT-TYPE
    SYNTAX OCTET STRING (SIZE(12))
    ACCESS read-write
    STATUS mandatory
    DESCRIPTION
        "This variable allows setting of individual output trigger conditions. 
        The OCTETS are interpreted bit-by-bit, with each bit corresponding to an output. 
        Bit 0 corresponds to the LSB.
	The first four OCTETS contain the mask which determines which of the outputs are to 
	be considered (corresponding bit = 1) and which outputs are to ignore 
	(corresponding bit = 0):
	OCTET 1 : unused
	OCTET 2 : unused
	OCTET 3 : unused
	OCTET 4, Bit 0-1: Mask for digital outputs 0-1
	
	OCTETS 5-8 contain the level (1=HIGH, 0=LOW) which the outputs 
	should assume:
	OCTET 5 : unused
	OCTET 6 : unused
	OCTET 7 : unused
        OCTET 8, Bit 0-1: Level of digital outputs 0-1

	OCTETS 9-12 contain the ANY bit (1=ON, 0=OFF). Outputs masked with the any bit trigger with any change 
	of the corresponding output bit. Settings in OCTET 5-9 are then unused:
	OCTET 9: unused
	OCTET 10: unused
	OCTET 11: unused
	OCTET 12, Bit 0-1: ANY bits of digital outputs 0-1"
        
    ::= { wtWebioEA2x2ERP-24VAlarmEntry 2 }
    
wtWebioEA2x2ERP-24VAlarmSystemTrigger OBJECT-TYPE
    SYNTAX OCTET STRING (SIZE(4))
    ACCESS read-write
    STATUS mandatory
    DESCRIPTION
        "Binary coded trigger conditions:
        The OCTETS are interpreted bit-by-bit.
        Bit 0 corresponds to the LSB.
        OCTET 1: unused
        OCTET 2: unused
        OCTET 3: unused
        OCTET 4, 
        	 Bit 4-7: unused
        	 Bit 3  : Warm Start
        	 Bit 2  : Cold Start
        	 Bit 1  : Timer
        	 Bit 0  : Load Control"
    ::= { wtWebioEA2x2ERP-24VAlarmEntry 3 }

wtWebioEA2x2ERP-24VAlarmMaxCounterValue OBJECT-TYPE
    SYNTAX OCTET STRING 
    ACCESS read-write
    STATUS mandatory
    DESCRIPTION
        "This variable configures a max. counter value. If an input counter value
        exceeds this max. value, the corresponding alarm is triggered. Input counters with
        its mask bit unset in wtWebioEA2x2ERP-24VAlarmInputTrigger are not considered."
    ::= { wtWebioEA2x2ERP-24VAlarmEntry 4 }

wtWebioEA2x2ERP-24VAlarmInterval OBJECT-TYPE
    SYNTAX OCTET STRING 
    ACCESS read-write
    STATUS mandatory
    DESCRIPTION
        "Send interval for alarm messages."
    ::= { wtWebioEA2x2ERP-24VAlarmEntry 5 }

wtWebioEA2x2ERP-24VAlarmEnable OBJECT-TYPE
    SYNTAX OCTET STRING (SIZE(4))
    ACCESS read-write
    STATUS mandatory
    DESCRIPTION
        "Binary coded alarm enable:
        Octet 1: unused
        Octet 2: unused
        Octet 3: unused
        Octet 4:
		Bit 0:	Mail Enable
        	Bit 1:	SNMP Trap enable
        	Bit 2:  UDP enable
        	Bit 3:  Send inputs to pending TCP connections
        	Bit 4:  TCP Client enable
        	Bit 5:	Syslog Messages enable
        	Bit 6-7: unused"
    ::= { wtWebioEA2x2ERP-24VAlarmEntry 6 }

wtWebioEA2x2ERP-24VAlarmMailAddr OBJECT-TYPE
    SYNTAX OCTET STRING 
    ACCESS read-write
    STATUS mandatory
    DESCRIPTION
        "E-Mail address for sending the alarm mail to."
    ::= { wtWebioEA2x2ERP-24VAlarmEntry 7 }

wtWebioEA2x2ERP-24VAlarmMailSubject OBJECT-TYPE
    SYNTAX OCTET STRING 
    ACCESS read-write
    STATUS mandatory
    DESCRIPTION
        "Subject line for alarm mail."
    ::= { wtWebioEA2x2ERP-24VAlarmEntry 8 }

wtWebioEA2x2ERP-24VAlarmMailText OBJECT-TYPE
    SYNTAX OCTET STRING 
    ACCESS read-write
    STATUS mandatory
    DESCRIPTION
        "Alarm mail text: 
        States of the Webio device can be included by using special tags.
        Please refer to the respective Webio manual"
    ::= { wtWebioEA2x2ERP-24VAlarmEntry 9 }

wtWebioEA2x2ERP-24VAlarmSnmpManagerIP OBJECT-TYPE
    SYNTAX OCTET STRING 
    ACCESS read-write
    STATUS mandatory
    DESCRIPTION
        "IP address of the SNMP Manager to which the Webio device should send SNMP traps."
    ::= { wtWebioEA2x2ERP-24VAlarmEntry 10 }

wtWebioEA2x2ERP-24VAlarmSnmpTrapText OBJECT-TYPE
    SYNTAX OCTET STRING 
    ACCESS read-write
    STATUS mandatory
    DESCRIPTION
        "This text appears in the trap body."
    ::= { wtWebioEA2x2ERP-24VAlarmEntry 11 }
    
wtWebioEA2x2ERP-24VAlarmUdpIpAddr OBJECT-TYPE
    SYNTAX OCTET STRING 
    ACCESS read-write
    STATUS mandatory
    DESCRIPTION
        "IP address of the UDP listener to which the Webio device should send UDP traps."
    ::= { wtWebioEA2x2ERP-24VAlarmEntry 12 }    

wtWebioEA2x2ERP-24VAlarmUdpPort OBJECT-TYPE
    SYNTAX INTEGER (1..65535) 
    ACCESS read-write
    STATUS mandatory
    DESCRIPTION
        "Port number of the UDP listener to which the Webio device should send UDP traps."
    ::= { wtWebioEA2x2ERP-24VAlarmEntry 13 }    

wtWebioEA2x2ERP-24VAlarmUdpText OBJECT-TYPE
    SYNTAX OCTET STRING 
    ACCESS read-write
    STATUS mandatory
    DESCRIPTION
        "This text appears in the UDP trap body."
    ::= { wtWebioEA2x2ERP-24VAlarmEntry 14 }
    
wtWebioEA2x2ERP-24VAlarmTcpIpAddr OBJECT-TYPE
    SYNTAX OCTET STRING
    ACCESS read-write
    STATUS mandatory
    DESCRIPTION
        "IP address of the TCP listener to which the Webio device should send TCP traps."
    ::= { wtWebioEA2x2ERP-24VAlarmEntry 15 }    

wtWebioEA2x2ERP-24VAlarmTcpPort OBJECT-TYPE
    SYNTAX INTEGER (1..65535) 
    ACCESS read-write
    STATUS mandatory
    DESCRIPTION
        "Port number of the TCP listener to which the Webio device should send TCP traps."
    ::= { wtWebioEA2x2ERP-24VAlarmEntry 16 }    

wtWebioEA2x2ERP-24VAlarmTcpText OBJECT-TYPE
    SYNTAX OCTET STRING 
    ACCESS read-write
    STATUS mandatory
    DESCRIPTION
        "This text appears in the TCP trap body."
    ::= { wtWebioEA2x2ERP-24VAlarmEntry 17 }

wtWebioEA2x2ERP-24VAlarmSyslogIpAddr OBJECT-TYPE
    SYNTAX OCTET STRING 
    ACCESS read-write
    STATUS mandatory
    DESCRIPTION
        "IP address of the syslog server to which the Webio device should send syslog messages."
    ::= { wtWebioEA2x2ERP-24VAlarmEntry 18 }    

wtWebioEA2x2ERP-24VAlarmSyslogPort OBJECT-TYPE
    SYNTAX INTEGER (1..65535) 
    ACCESS read-write
    STATUS mandatory
    DESCRIPTION
        "Port number of the syslog server to which the Webio device should send syslog messages."
    ::= { wtWebioEA2x2ERP-24VAlarmEntry 19 }    

wtWebioEA2x2ERP-24VAlarmSyslogText OBJECT-TYPE
    SYNTAX OCTET STRING 
    ACCESS read-write
    STATUS mandatory
    DESCRIPTION
        "Every message starts with the priority key, a time stamp and the host ip address, according RFC3164.
        This text appears in the following syslog message body."
    ::= { wtWebioEA2x2ERP-24VAlarmEntry 20 }    
    
wtWebioEA2x2ERP-24VAlarmFtpDataPort OBJECT-TYPE
    SYNTAX OCTET STRING 
    ACCESS read-write
    STATUS mandatory
    DESCRIPTION
        "Local data port: 1..65535 or AUTO: the next free port will be assigned."
    ::= { wtWebioEA2x2ERP-24VAlarmEntry 21 }
    
wtWebioEA2x2ERP-24VAlarmFtpFileName OBJECT-TYPE
    SYNTAX OCTET STRING 
    ACCESS read-write
    STATUS mandatory
    DESCRIPTION
        "Name of the file including path informations."
    ::= { wtWebioEA2x2ERP-24VAlarmEntry 22 }
    
wtWebioEA2x2ERP-24VAlarmFtpText OBJECT-TYPE
    SYNTAX OCTET STRING 
    ACCESS read-write
    STATUS mandatory
    DESCRIPTION
        "Message text to store on the FTP server."
    ::= { wtWebioEA2x2ERP-24VAlarmEntry 23 }

wtWebioEA2x2ERP-24VAlarmFtpOption OBJECT-TYPE
    SYNTAX OCTET STRING (SIZE(4))
    ACCESS read-write
    STATUS mandatory
    DESCRIPTION
        "Binary coded options, select only one option at the same time:
        STORE  = replace file
        APPEND = append message at the end of the file
        
        Octet 1: unused
        Octet 2: unused
        Octet 3: unused
        Octet 4:
		Bit 0  :	STORE
		Bit 1  :	APPEND
        	Bit 2-7:	unused"
    ::= { wtWebioEA2x2ERP-24VAlarmEntry 24 }      
    
wtWebioEA2x2ERP-24VAlarmTimerCron OBJECT-TYPE
    SYNTAX OCTET STRING
    ACCESS read-write
    STATUS mandatory
    DESCRIPTION
        "This entry contains 5 space or tab seperated text fields for time trigger definition.
        Each field must match with the actual time to trigger a message, weekday and day of month
        are interpreted separatley.
        1: Minutes	Range 0-59
        2. Hours	Range 0-23, 0 is midnight
        3: Day of month	Range 1-31
        4: Month	Range 1-12
        5: Weekday	Range 0-6, 0 is sunday
        
        Syntax for every field:
         - an asterix (*) enables every possible setting of a field
         - single numbers seperated by commas
         - a partition within the allowed range (1-5)
         - step size within an partition of the allowed range (0-59/2: every second minute)."
    ::= { wtWebioEA2x2ERP-24VAlarmEntry 25 }      

wtWebioEA2x2ERP-24VAlarmMailReleaseSubject OBJECT-TYPE
    SYNTAX OCTET STRING 
    ACCESS read-write
    STATUS mandatory
    DESCRIPTION
       "Subject line for alarm mail."
    ::= { wtWebioEA2x2ERP-24VAlarmEntry 26 }

wtWebioEA2x2ERP-24VAlarmMailReleaseText OBJECT-TYPE
    SYNTAX OCTET STRING 
    ACCESS read-write
    STATUS mandatory
    DESCRIPTION
        "Release Alarm mail text: 
        States of the Webio device can be included by using special tags.
        Please refer to the respective Webio manual"
    ::= { wtWebioEA2x2ERP-24VAlarmEntry 27 }    

wtWebioEA2x2ERP-24VAlarmSnmpTrapReleaseText OBJECT-TYPE
    SYNTAX OCTET STRING 
    ACCESS read-write
    STATUS mandatory
    DESCRIPTION
        "This text appears in the trap body."
    ::= { wtWebioEA2x2ERP-24VAlarmEntry 28 }

wtWebioEA2x2ERP-24VAlarmUdpReleaseText OBJECT-TYPE
    SYNTAX OCTET STRING 
    ACCESS read-write
    STATUS mandatory
    DESCRIPTION
        "This text appears in the UDP trap body."
    ::= { wtWebioEA2x2ERP-24VAlarmEntry 29 }

wtWebioEA2x2ERP-24VAlarmTcpReleaseText OBJECT-TYPE
    SYNTAX OCTET STRING 
    ACCESS read-write
    STATUS mandatory
    DESCRIPTION
        "This text appears in the TCP trap body."
    ::= { wtWebioEA2x2ERP-24VAlarmEntry 30 }

wtWebioEA2x2ERP-24VAlarmSyslogReleaseText OBJECT-TYPE
    SYNTAX OCTET STRING 
    ACCESS read-write
    STATUS mandatory
    DESCRIPTION
        "Every message starts with the priority key, a time stamp and the host ip address, according RFC3164.
        This text appears in the following syslog message body."
    ::= { wtWebioEA2x2ERP-24VAlarmEntry 31 }

wtWebioEA2x2ERP-24VAlarmFtpReleaseText OBJECT-TYPE
    SYNTAX OCTET STRING 
    ACCESS read-write
    STATUS mandatory
    DESCRIPTION
        "Message text to store on the FTP server."
    ::= { wtWebioEA2x2ERP-24VAlarmEntry 32 }

-- wtWebioEA2x2ERP-24VLoadControl
----------------------------

wtWebioEA2x2ERP-24VLoadControlView OBJECT-TYPE
    SYNTAX OCTET STRING (SIZE(4))
    ACCESS read-only
    STATUS mandatory
    DESCRIPTION
        "Here the result of automatic load control can be read. All output were tested in 
        pairs (0-1). If an error occours at one output,
        both output of an pair will be switched of. For a properly function of the load control
        each output of a pair have to has a load. If there is no existing load, a pull down resistor
        can be used.
        Outputs with no load are automaticly detected and not part of the control function.
        The OCTETS are interpreted bit-by-bit, with each bit corresponding to an output. 
        Bit 0 corresponds to the LSB.
        Octet 1: unused
        Octet 2: unused
        Octet 3: unused
        Octet 4: 
	        Bit 0-1: outputs 0-1."
    ::= { wtWebioEA2x2ERP-24VAlarm 4 }

wtWebioEA2x2ERP-24VLCShutDownView OBJECT-TYPE
    SYNTAX OCTET STRING (SIZE(4))
    ACCESS read-write
    STATUS mandatory
    DESCRIPTION
        "Here the result of the automatic load control shut down can be read. All outputs remain switched of,
        until a zero is written into this variable. But previously all loads should be inspected.
        High current (short circuit), a broken supply line or a defect load (i.e. lamp) may be a shut down reason.
        If no load is detected, the load control unit suspend automaticly the control of the corresponding output pair.
        All controlled output could be identified reading the variable wtWebioEA2x2ERP-24VLoadControlEnable.
        The OCTETS are interpreted bit-by-bit, with each bit corresponding to an ouput.
        Bit 0 corresponds to the LSB.
        
        Octet 1: unused
        Octet 2: unused
        Octet 3: unused
        Octet 4: Bit 0-1: outputs 0-1."
    ::= { wtWebioEA2x2ERP-24VAlarm 5 }

-- wtWebioEA2x2ERP-24VPorts Group
----------------------------

-- Input Port Table

wtWebioEA2x2ERP-24VInputPortTable OBJECT-TYPE
    SYNTAX SEQUENCE OF WtWebioEA2x2ERP-24VInputPortEntry
    ACCESS not-accessible
    STATUS mandatory
    DESCRIPTION
        "List of settings depending on the input number."
    ::= { wtWebioEA2x2ERP-24VPorts 1 }

wtWebioEA2x2ERP-24VInputPortEntry OBJECT-TYPE
    SYNTAX WtWebioEA2x2ERP-24VInputPortEntry
    ACCESS not-accessible
    STATUS mandatory
    DESCRIPTION
        "Input parameter for the individual inputs."
    INDEX  { wtWebioEA2x2ERP-24VInputNo }
    ::= { wtWebioEA2x2ERP-24VInputPortTable 1 }

WtWebioEA2x2ERP-24VInputPortEntry ::= SEQUENCE {
    wtWebioEA2x2ERP-24VPortInputName			OCTET STRING,
    wtWebioEA2x2ERP-24VPortInputText			OCTET STRING,
    wtWebioEA2x2ERP-24VPortInputMode			OCTET STRING,
    wtWebioEA2x2ERP-24VPortInputFilter			INTEGER,
    wtWebioEA2x2ERP-24VPortInputBicountPulsePolarity	OCTET STRING,
    wtWebioEA2x2ERP-24VPortInputBicountInactivTimeout	INTEGER
    
}

wtWebioEA2x2ERP-24VPortInputName OBJECT-TYPE
    SYNTAX OCTET STRING 
    ACCESS read-write
    STATUS mandatory
    DESCRIPTION
        "Name of the input."
    ::= { wtWebioEA2x2ERP-24VInputPortEntry 1 }

wtWebioEA2x2ERP-24VPortInputText OBJECT-TYPE
    SYNTAX OCTET STRING 
    ACCESS read-write
    STATUS mandatory
    DESCRIPTION
        "Description of the input."
    ::= { wtWebioEA2x2ERP-24VInputPortEntry 2 }

wtWebioEA2x2ERP-24VPortInputMode OBJECT-TYPE
    SYNTAX OCTET STRING (SIZE(4))
    ACCESS read-write
    STATUS mandatory
    DESCRIPTION
        "Binary coded modes:
        Selecting short pulse detection enable by setting the corresponding bit to 1 enables 
        interrupt support for counting. Only positive edges are accepted as trigger 
        source. The maximum counting frequenz equals 2000 Hz.
        This mode is available for inputs 0-3 only.
        Selecting counter clear on read by setting the corresponding bit to 1 enables
        the corresponding counter to be cleared automatically every time it is read,
        except HTTP reading with user rights.
        The OCTETS are interpreted bit-by-bit,
        Bit 0 corresponds to the LSB.
        Selection for input 0-1:
        OCTET 1: unused
        OCTET 2: unused
        OCTET 3: unused
        OCTET 4, Bit 4-7: unused
		 Bit 3	: Bidirectional counter enable
        	 Bit 2  : Counter clear on read
        	 Bit 1  : Change detection enable (default)
        	 Bit 0  : Short Pulse detection enable"
    ::= { wtWebioEA2x2ERP-24VInputPortEntry 3 }    
    
wtWebioEA2x2ERP-24VPortInputFilter OBJECT-TYPE
    SYNTAX INTEGER 
    ACCESS read-write
    STATUS mandatory
    DESCRIPTION
        "Pulses with a duration shorter than here specified (duration in 1/1000 sec),
	are ignored."
    ::= { wtWebioEA2x2ERP-24VInputPortEntry 4 }
    
wtWebioEA2x2ERP-24VPortInputBicountPulsePolarity OBJECT-TYPE
    SYNTAX OCTET STRING (SIZE (4))
    ACCESS read-write
    STATUS mandatory
    DESCRIPTION
        "This value defines the polarity of the input pulse.
        OCTET 1: unused
        OCTET 2: unused
        OCTET 3: unused
        	OCTET 4: 
        	 Bit 0   : negative polarity
        	 Bit 1   : positive polarity
        	 Bit 2-7 : unused"
    ::= { wtWebioEA2x2ERP-24VInputPortEntry 5 }

wtWebioEA2x2ERP-24VPortInputBicountInactivTimeout OBJECT-TYPE
    SYNTAX INTEGER 
    ACCESS read-write
    STATUS mandatory
    DESCRIPTION
        "Pulse chains with a duration shorter than here specified (in 1/10 sek),
	are ignored."
    ::= { wtWebioEA2x2ERP-24VInputPortEntry 6 }
        
-- Output Port Table

wtWebioEA2x2ERP-24VOutputPortTable OBJECT-TYPE
    SYNTAX SEQUENCE OF WtWebioEA2x2ERP-24VOutputPortEntry
    ACCESS not-accessible
    STATUS mandatory
    DESCRIPTION
        "List of settings depending on the output number."
    ::= { wtWebioEA2x2ERP-24VPorts 2 }

wtWebioEA2x2ERP-24VOutputPortEntry OBJECT-TYPE
    SYNTAX WtWebioEA2x2ERP-24VOutputPortEntry
    ACCESS not-accessible
    STATUS mandatory
    DESCRIPTION
        "Output parameters of the individual outputs."
    INDEX  { wtWebioEA2x2ERP-24VOutputNo }
    ::= { wtWebioEA2x2ERP-24VOutputPortTable 1 }

WtWebioEA2x2ERP-24VOutputPortEntry ::= SEQUENCE {
    wtWebioEA2x2ERP-24VPortOutputName		OCTET STRING,
    wtWebioEA2x2ERP-24VPortOutputText		OCTET STRING,
    wtWebioEA2x2ERP-24VPortOutputGroupMode	OCTET STRING,
    wtWebioEA2x2ERP-24VPortOutputSafetyState	OCTET STRING,
    wtWebioEA2x2ERP-24VPortLogicInputMask	OCTET STRING,
    wtWebioEA2x2ERP-24VPortLogicInputInverter	OCTET STRING,
    wtWebioEA2x2ERP-24VPortLogicFunction	OCTET STRING,
    wtWebioEA2x2ERP-24VPortLogicOutputInverter	OCTET STRING,
    wtWebioEA2x2ERP-24VPortPulseDuration	INTEGER,
    wtWebioEA2x2ERP-24VPortPulsePolarity	OCTET STRING
    
}

wtWebioEA2x2ERP-24VPortOutputName OBJECT-TYPE
    SYNTAX OCTET STRING 
    ACCESS read-write
    STATUS mandatory
    DESCRIPTION
        "Name of the output."
    ::= { wtWebioEA2x2ERP-24VOutputPortEntry 1 }

wtWebioEA2x2ERP-24VPortOutputText OBJECT-TYPE
    SYNTAX OCTET STRING 
    ACCESS read-write
    STATUS mandatory
    DESCRIPTION
        "Description of the output."
    ::= { wtWebioEA2x2ERP-24VOutputPortEntry 2 }

wtWebioEA2x2ERP-24VPortOutputGroupMode OBJECT-TYPE
    SYNTAX OCTET STRING 
    ACCESS read-write
    STATUS mandatory
    DESCRIPTION
        "It is possible to connect outputs together to increase the output current.
        This could be done by connecting 2 or 4 outputs in a group together. All bits
        of such a group has to be set all together in the same way. This variable
        configures this group scheme. If one ouput bit of a group is set, all other 
        output bits of the same group will be set in the same manner.
        More than one configuration must not be selected.
	Selection for ouputs 0-1:
        Octet 1: unused
        Octet 2: unused
        Octet 3: unused
        OCTET 4: Bit 0   : ouputs 0,1 disconnected (default)
        	 Bit 1   : ouputs 0+1 connected"
    ::= { wtWebioEA2x2ERP-24VOutputPortEntry 3 }

wtWebioEA2x2ERP-24VPortOutputSafetyState OBJECT-TYPE
    SYNTAX OCTET STRING 
    ACCESS read-write
    STATUS mandatory
    DESCRIPTION
        "This variable allows setting of individual digital outputs. The OCTETS are 
        interpreted bit-by-bit, with each bit corresponding to an output. Bit 0 corresponds 
        to the LSB.
        The first four OCTETS contain the mask which determines which of the outputs are to 
        be set (corresponding bit = 1) and which outputs are to remain unchanged 
        (corresponding bit = 0):
        OCTET 1		: unused
        OCTET 2		: unused
        OCTET 3		: unused
        OCTET 4, Bit 1-7: unused
        	 Bit 0	: Mask for digital output
        OCTETS 5-8 contain the level (1=HIGH, 0=LOW) which the outputs to be changed 
        should assume:
        OCTET 5		: unused
        OCTET 6		: unused
        OCTET 7		: unused
        OCTET 8, Bit 1-7: unused
        	 Bit 0  : Level of digital output"
    ::= { wtWebioEA2x2ERP-24VOutputPortEntry 4 }

wtWebioEA2x2ERP-24VPortLogicInputMask OBJECT-TYPE
    SYNTAX OCTET STRING (SIZE (4))
    ACCESS read-write
    STATUS mandatory
    DESCRIPTION
        "Selecting one of these inputs by setting the corresponding bit to 1 
        enables the logic function for the output identified by the index within 
        this table. The calculation take place in 4 steps:
        1. Selecting inputs				(wtWebioEA2x2ERP-24VPortLogicInputMask)
        2. Inverting inputs if necessary	(wtWebioEA2x2ERP-24VPortLogicInputInverter)
        3. Logical combination				(wtWebioEA2x2ERP-24VPortLogicFunction)
        4. Inverting the result if necessary	(wtWebioEA2x2ERP-24VPortLogicOutputInverter)
        OCTET 1: unused
        OCTET 2: unused
        OCTET 3: unused
        OCTET 4: Bit 0-1 : inputs 0-1"
    ::= { wtWebioEA2x2ERP-24VOutputPortEntry 5 }

wtWebioEA2x2ERP-24VPortLogicInputInverter OBJECT-TYPE
    SYNTAX OCTET STRING (SIZE (4))
    ACCESS read-write
    STATUS mandatory
    DESCRIPTION
        "Every input bit selected here will be inverted.
        OCTET 1: unused
        OCTET 2: unused
        OCTET 3: unused
        OCTET 4: Bit 0-1 : inputs 0-1"
    ::= { wtWebioEA2x2ERP-24VOutputPortEntry 6 }

wtWebioEA2x2ERP-24VPortLogicFunction OBJECT-TYPE
    SYNTAX OCTET STRING (SIZE (4))
    ACCESS read-write
    STATUS mandatory
    DESCRIPTION
        "This determines the logic function. No more than one function
        may be selected.
        OCTET 1: unused
        OCTET 2: unused
        OCTET 3: unused
        OCTET 4: 
        	 Bit 0   : logic function OR (default)
        	 Bit 1   : logic function AND
        	 Bit 2-7 : unused"
    ::= { wtWebioEA2x2ERP-24VOutputPortEntry 7 }

wtWebioEA2x2ERP-24VPortLogicOutputInverter OBJECT-TYPE
    SYNTAX OCTET STRING (SIZE (4))
    ACCESS read-write
    STATUS mandatory
    DESCRIPTION
        "The logical operation result could be inverteted by setting the corresponding
        bit to 1.
        OCTET 1: unused
        OCTET 2: unused
        OCTET 3: unused
        	OCTET 4: 
        	 Bit 0   : Output Inverter enable
        	 Bit 1-7 : unused"
    ::= { wtWebioEA2x2ERP-24VOutputPortEntry 8 }

wtWebioEA2x2ERP-24VPortPulseDuration OBJECT-TYPE
    SYNTAX INTEGER
    ACCESS read-write
    STATUS mandatory
    DESCRIPTION
        "Pulse length in 1/1000 sec. Setting this value to zero, disables the pulse output."
    ::= { wtWebioEA2x2ERP-24VOutputPortEntry 9 }

wtWebioEA2x2ERP-24VPortPulsePolarity OBJECT-TYPE
    SYNTAX OCTET STRING (SIZE (4))
    ACCESS read-write
    STATUS mandatory
    DESCRIPTION
        "This value defines the polarity of the output pulse, if wtWebioEA2x2ERP-24VPortPulseDuration is not set to zero.
        After the pulse is finished, the output switches back to the opposite state.
        OCTET 1: unused
        OCTET 2: unused
        OCTET 3: unused
        	OCTET 4: 
        	 Bit 0   : negative polarity
        	 Bit 1   : positive polarity
        	 Bit 2-7 : unused"
    ::= { wtWebioEA2x2ERP-24VOutputPortEntry 10 }

-- wtWebioEA2x2ERP-24VManufact Group
----------------------------

wtWebioEA2x2ERP-24VMfName OBJECT-TYPE
    SYNTAX OCTET STRING 
    ACCESS read-write
    STATUS mandatory
    DESCRIPTION
        "Manufacturer company name"
    ::= { wtWebioEA2x2ERP-24VManufact 1 }

wtWebioEA2x2ERP-24VMfAddr OBJECT-TYPE
    SYNTAX OCTET STRING 
    ACCESS read-write
    STATUS mandatory
    DESCRIPTION
        "Manufacturer address."
    ::= { wtWebioEA2x2ERP-24VManufact 2 }

wtWebioEA2x2ERP-24VMfHotline OBJECT-TYPE
    SYNTAX OCTET STRING 
    ACCESS read-write
    STATUS mandatory
    DESCRIPTION
        "Manufacturer hotline."
    ::= { wtWebioEA2x2ERP-24VManufact 3 }

wtWebioEA2x2ERP-24VMfInternet OBJECT-TYPE
    SYNTAX OCTET STRING 
    ACCESS read-write
    STATUS mandatory
    DESCRIPTION
        "Manufacturer Internet address."
    ::= { wtWebioEA2x2ERP-24VManufact 4 }

wtWebioEA2x2ERP-24VMfDeviceTyp OBJECT-TYPE
    SYNTAX OCTET STRING 
    ACCESS read-write
    STATUS mandatory
    DESCRIPTION
        "Manufacturer device name (model number)."
    ::= { wtWebioEA2x2ERP-24VManufact 5 }

-- wtWebioEA2x2ERP-24VDiag Group
----------------------------

wtWebioEA2x2ERP-24VDiagErrorCount OBJECT-TYPE
    SYNTAX INTEGER
    ACCESS read-only
    STATUS mandatory
    DESCRIPTION
        "Number of entries in the error memory."
    ::= { wtWebioEA2x2ERP-24VDiag 1 }

wtWebioEA2x2ERP-24VDiagBinaryError OBJECT-TYPE
    SYNTAX OCTET STRING 
    ACCESS read-only
    STATUS mandatory
    DESCRIPTION
        "Error causes coded bit-by-bit."
    ::= { wtWebioEA2x2ERP-24VDiag 2 }

wtWebioEA2x2ERP-24VDiagErrorIndex OBJECT-TYPE
    SYNTAX INTEGER
    ACCESS read-write
    STATUS mandatory
    DESCRIPTION
        "The value of this variable is used as an index to read 
        an error massege from wtWebioEA2x2ERP-24VDiagErrorMessage.
        Errors are numbered from 1 to wtWebioEA2x2ERP-24VDiagErrorCount.
        Writing a valid value into this variable, making the appropriate 
        message readable from wtWebioEA2x2ERP-24VDiagErrorMessage."
    ::= { wtWebioEA2x2ERP-24VDiag 3 }

wtWebioEA2x2ERP-24VDiagErrorMessage OBJECT-TYPE
    SYNTAX OCTET STRING 
    ACCESS read-only
    STATUS mandatory
    DESCRIPTION
        "Using wtWebioEA2x2ERP-24VDiagErrorIndex as an index, the appropriate message is available."
    ::= { wtWebioEA2x2ERP-24VDiag 4 }
    
wtWebioEA2x2ERP-24VDiagErrorClear OBJECT-TYPE
    SYNTAX INTEGER
    ACCESS write-only
    STATUS mandatory
    DESCRIPTION
        "Writing 1 into this variable clears all diagnosis messages."
    ::= { wtWebioEA2x2ERP-24VDiag 5 }


-- TRAP DEFINITIONS

-- Diese SNMP-Traps werden gesendet, wenn die Alarmtriggerbedingungen zutreffen 

wtWebioEA2x2ERP-24VAlert1 TRAP-TYPE
    ENTERPRISE  wtWebioEA2x2ERP-24V
    VARIABLES   { wtWebioEA2x2ERP-24VAlarmSnmpTrapText }
    DESCRIPTION
        "This SNMP trap is generated when Alarm 1 was triggered,
        SNMP trap enable is set and
        SNMP is enabled."
    -- NMS trap annotation
    --#TYPE "Webio Digital Alarm 1"
    --#SUMMARY "Alarm 1: %s"
    --#ARGUMENTS {0}
    --#SEVERITY INFORMATIONAL
    --#TIMEINDEX 99
    --#STATE OPERATIONAL    
    ::= 41

wtWebioEA2x2ERP-24VAlert2 TRAP-TYPE
    ENTERPRISE  wtWebioEA2x2ERP-24V
    VARIABLES   { wtWebioEA2x2ERP-24VAlarmSnmpTrapText }
    DESCRIPTION
        "This SNMP trap is generated when Alarm 2 was triggered,
        SNMP trap enable is set and
        SNMP is enabled."
    -- NMS trap annotation
    --#TYPE "Webio Digital Alarm 2"
    --#SUMMARY "Alarm 2: %s"
    --#ARGUMENTS {0}
    --#SEVERITY INFORMATIONAL
    --#TIMEINDEX 99
    --#STATE OPERATIONAL    
    ::= 42

wtWebioEA2x2ERP-24VAlert3 TRAP-TYPE
    ENTERPRISE  wtWebioEA2x2ERP-24V
    VARIABLES   { wtWebioEA2x2ERP-24VAlarmSnmpTrapText }
    DESCRIPTION
        "This SNMP trap is generated when Alarm 3 was triggered,
        SNMP trap enable is set and
        SNMP is enabled."
    -- NMS trap annotation
    --#TYPE "Webio Digital Alarm 3"
    --#SUMMARY "Alarm 3: %s"
    --#ARGUMENTS {0}
    --#SEVERITY INFORMATIONAL
    --#TIMEINDEX 99
    --#STATE OPERATIONAL    
    ::= 43

wtWebioEA2x2ERP-24VAlert4 TRAP-TYPE
    ENTERPRISE  wtWebioEA2x2ERP-24V
    VARIABLES   { wtWebioEA2x2ERP-24VAlarmSnmpTrapText }
    DESCRIPTION
        "This SNMP trap is generated when Alarm 4 was triggered,
        SNMP trap enable is set and
        SNMP is enabled."
    -- NMS trap annotation
    --#TYPE "Webio Digital Alarm 4"
    --#SUMMARY "Alarm 4: %s"
    --#ARGUMENTS {0}
    --#SEVERITY INFORMATIONAL
    --#TIMEINDEX 99
    --#STATE OPERATIONAL    
    ::= 44

wtWebioEA2x2ERP-24VAlert5 TRAP-TYPE
    ENTERPRISE  wtWebioEA2x2ERP-24V
    VARIABLES   { wtWebioEA2x2ERP-24VAlarmSnmpTrapText }
    DESCRIPTION
        "This SNMP trap is generated when Alarm 5 was triggered,
        SNMP trap enable is set and
        SNMP is enabled."
    -- NMS trap annotation
    --#TYPE "Webio Digital Alarm 5"
    --#SUMMARY "Alarm 5: %s"
    --#ARGUMENTS {0}
    --#SEVERITY INFORMATIONAL
    --#TIMEINDEX 99
    --#STATE OPERATIONAL    
    ::= 45

wtWebioEA2x2ERP-24VAlert6 TRAP-TYPE
    ENTERPRISE  wtWebioEA2x2ERP-24V
    VARIABLES   { wtWebioEA2x2ERP-24VAlarmSnmpTrapText }
    DESCRIPTION
        "This SNMP trap is generated when Alarm 6 was triggered,
        SNMP trap enable is set and
        SNMP is enabled."
    -- NMS trap annotation
    --#TYPE "Webio Digital Alarm 6"
    --#SUMMARY "Alarm 6: %s"
    --#ARGUMENTS {0}
    --#SEVERITY INFORMATIONAL
    --#TIMEINDEX 99
    --#STATE OPERATIONAL    
    ::= 46

wtWebioEA2x2ERP-24VAlert7 TRAP-TYPE
    ENTERPRISE  wtWebioEA2x2ERP-24V
    VARIABLES   { wtWebioEA2x2ERP-24VAlarmSnmpTrapText }
    DESCRIPTION
        "This SNMP trap is generated when Alarm 7 was triggered,
        SNMP trap enable is set and
        SNMP is enabled."
    -- NMS trap annotation
    --#TYPE "Webio Digital Alarm 7"
    --#SUMMARY "Alarm 7: %s"
    --#ARGUMENTS {0}
    --#SEVERITY INFORMATIONAL
    --#TIMEINDEX 99
    --#STATE OPERATIONAL    
    ::= 47

wtWebioEA2x2ERP-24VAlert8 TRAP-TYPE
    ENTERPRISE  wtWebioEA2x2ERP-24V
    VARIABLES   { wtWebioEA2x2ERP-24VAlarmSnmpTrapText }
    DESCRIPTION
        "This SNMP trap is generated when Alarm 8 was triggered,
        SNMP trap enable is set and
        SNMP is enabled."
    -- NMS trap annotation
    --#TYPE "Webio Digital Alarm 8"
    --#SUMMARY "Alarm 8: %s"
    --#ARGUMENTS {0}
    --#SEVERITY INFORMATIONAL
    --#TIMEINDEX 99
    --#STATE OPERATIONAL    
    ::= 48

wtWebioEA2x2ERP-24VAlert9 TRAP-TYPE
    ENTERPRISE  wtWebioEA2x2ERP-24V
    VARIABLES   { wtWebioEA2x2ERP-24VAlarmSnmpTrapText }
    DESCRIPTION
        "This SNMP trap is generated when Alarm 9 was triggered,
        SNMP trap enable is set and
        SNMP is enabled."
    -- NMS trap annotation
    --#TYPE "Webio Digital Alarm 9"
    --#SUMMARY "Alarm 9: %s"
    --#ARGUMENTS {0}
    --#SEVERITY INFORMATIONAL
    --#TIMEINDEX 99
    --#STATE OPERATIONAL    
    ::= 49

wtWebioEA2x2ERP-24VAlert10 TRAP-TYPE
    ENTERPRISE  wtWebioEA2x2ERP-24V
    VARIABLES   { wtWebioEA2x2ERP-24VAlarmSnmpTrapText }
    DESCRIPTION
        "This SNMP trap is generated when Alarm 10 was triggered,
        SNMP trap enable is set and
        SNMP is enabled."
    -- NMS trap annotation
    --#TYPE "Webio Digital Alarm 10"
    --#SUMMARY "Alarm 10: %s"
    --#ARGUMENTS {0}
    --#SEVERITY INFORMATIONAL
    --#TIMEINDEX 99
    --#STATE OPERATIONAL    
    ::= 50

wtWebioEA2x2ERP-24VAlert11 TRAP-TYPE
    ENTERPRISE  wtWebioEA2x2ERP-24V
    VARIABLES   { wtWebioEA2x2ERP-24VAlarmSnmpTrapText }
    DESCRIPTION
        "This SNMP trap is generated when Alarm 11 was triggered,
        SNMP trap enable is set and
        SNMP is enabled."
    -- NMS trap annotation
    --#TYPE "Webio Digital Alarm 11"
    --#SUMMARY "Alarm 11: %s"
    --#ARGUMENTS {0}
    --#SEVERITY INFORMATIONAL
    --#TIMEINDEX 99
    --#STATE OPERATIONAL    
    ::= 51

wtWebioEA2x2ERP-24VAlert12 TRAP-TYPE
    ENTERPRISE  wtWebioEA2x2ERP-24V
    VARIABLES   { wtWebioEA2x2ERP-24VAlarmSnmpTrapText }
    DESCRIPTION
        "This SNMP trap is generated when Alarm 12 was triggered,
        SNMP trap enable is set and
        SNMP is enabled."
    -- NMS trap annotation
    --#TYPE "Webio Digital Alarm 12"
    --#SUMMARY "Alarm 12: %s"
    --#ARGUMENTS {0}
    --#SEVERITY INFORMATIONAL
    --#TIMEINDEX 99
    --#STATE OPERATIONAL    
    ::= 52

wtWebioEA2x2ERP-24VAlert13 TRAP-TYPE
    ENTERPRISE  wtWebioEA2x2ERP-24V
    VARIABLES   { wtWebioEA2x2ERP-24VAlarmSnmpTrapReleaseText }
    DESCRIPTION
        "This SNMP trap is generated when Alarm 1 was released,
        SNMP trap enable is set and
        SNMP is enabled."
    -- NMS trap annotation
    --#TYPE "Webio Digital Release Alarm 1"
    --#SUMMARY "Release Alarm 1: %s"
    --#ARGUMENTS {0}
    --#SEVERITY INFORMATIONAL
    --#TIMEINDEX 99
    --#STATE OPERATIONAL    
    ::= 71

wtWebioEA2x2ERP-24VAlert14 TRAP-TYPE
    ENTERPRISE  wtWebioEA2x2ERP-24V
    VARIABLES   { wtWebioEA2x2ERP-24VAlarmSnmpTrapReleaseText }
    DESCRIPTION
        "This SNMP trap is generated when Alarm 2 was released,
        SNMP trap enable is set and
        SNMP is enabled."
    -- NMS trap annotation
    --#TYPE "Webio Digital Release Alarm 2"
    --#SUMMARY "Release Alarm 2: %s"
    --#ARGUMENTS {0}
    --#SEVERITY INFORMATIONAL
    --#TIMEINDEX 99
    --#STATE OPERATIONAL    
    ::= 72

wtWebioEA2x2ERP-24VAlert15 TRAP-TYPE
    ENTERPRISE  wtWebioEA2x2ERP-24V
    VARIABLES   { wtWebioEA2x2ERP-24VAlarmSnmpTrapReleaseText }
    DESCRIPTION
        "This SNMP trap is generated when Alarm 3 was released,
        SNMP trap enable is set and
        SNMP is enabled."
    -- NMS trap annotation
    --#TYPE "Webio Digital Release Alarm 3"
    --#SUMMARY "Release Alarm 3: %s"
    --#ARGUMENTS {0}
    --#SEVERITY INFORMATIONAL
    --#TIMEINDEX 99
    --#STATE OPERATIONAL    
    ::= 73

wtWebioEA2x2ERP-24VAlert16 TRAP-TYPE
    ENTERPRISE  wtWebioEA2x2ERP-24V
    VARIABLES   { wtWebioEA2x2ERP-24VAlarmSnmpTrapReleaseText }
    DESCRIPTION
        "This SNMP trap is generated when Alarm 4 was released,
        SNMP trap enable is set and
        SNMP is enabled."
    -- NMS trap annotation
    --#TYPE "Webio Digital Release Alarm 4"
    --#SUMMARY "Release Alarm 4: %s"
    --#ARGUMENTS {0}
    --#SEVERITY INFORMATIONAL
    --#TIMEINDEX 99
    --#STATE OPERATIONAL    
    ::= 74

wtWebioEA2x2ERP-24VAlert17 TRAP-TYPE
    ENTERPRISE  wtWebioEA2x2ERP-24V
    VARIABLES   { wtWebioEA2x2ERP-24VAlarmSnmpTrapReleaseText }
    DESCRIPTION
        "This SNMP trap is generated when Alarm 5 was released,
        SNMP trap enable is set and
        SNMP is enabled."
    -- NMS trap annotation
    --#TYPE "Webio Digital Release Alarm 5"
    --#SUMMARY "Release Alarm 5: %s"
    --#ARGUMENTS {0}
    --#SEVERITY INFORMATIONAL
    --#TIMEINDEX 99
    --#STATE OPERATIONAL    
    ::= 75

wtWebioEA2x2ERP-24VAlert18 TRAP-TYPE
    ENTERPRISE  wtWebioEA2x2ERP-24V
    VARIABLES   { wtWebioEA2x2ERP-24VAlarmSnmpTrapReleaseText }
    DESCRIPTION
        "This SNMP trap is generated when Alarm 6 was released,
        SNMP trap enable is set and
        SNMP is enabled."
    -- NMS trap annotation
    --#TYPE "Webio Digital Release Alarm 6"
    --#SUMMARY "Release Alarm 6: %s"
    --#ARGUMENTS {0}
    --#SEVERITY INFORMATIONAL
    --#TIMEINDEX 99
    --#STATE OPERATIONAL    
    ::= 76

wtWebioEA2x2ERP-24VAlert19 TRAP-TYPE
    ENTERPRISE  wtWebioEA2x2ERP-24V
    VARIABLES   { wtWebioEA2x2ERP-24VAlarmSnmpTrapReleaseText }
    DESCRIPTION
        "This SNMP trap is generated when Alarm 7 was released,
        SNMP trap enable is set and
        SNMP is enabled."
    -- NMS trap annotation
    --#TYPE "Webio Digital Release Alarm 7"
    --#SUMMARY "Release Alarm 7: %s"
    --#ARGUMENTS {0}
    --#SEVERITY INFORMATIONAL
    --#TIMEINDEX 99
    --#STATE OPERATIONAL    
    ::= 77

wtWebioEA2x2ERP-24VAlert20 TRAP-TYPE
    ENTERPRISE  wtWebioEA2x2ERP-24V
    VARIABLES   { wtWebioEA2x2ERP-24VAlarmSnmpTrapReleaseText }
    DESCRIPTION
        "This SNMP trap is generated when Alarm 8 was released,
        SNMP trap enable is set and
        SNMP is enabled."
    -- NMS trap annotation
    --#TYPE "Webio Digital Release Alarm 8"
    --#SUMMARY "Release Alarm 8: %s"
    --#ARGUMENTS {0}
    --#SEVERITY INFORMATIONAL
    --#TIMEINDEX 99
    --#STATE OPERATIONAL    
    ::= 78

wtWebioEA2x2ERP-24VAlert21 TRAP-TYPE
    ENTERPRISE  wtWebioEA2x2ERP-24V
    VARIABLES   { wtWebioEA2x2ERP-24VAlarmSnmpTrapReleaseText }
    DESCRIPTION
        "This SNMP trap is generated when Alarm 9 was released,
        SNMP trap enable is set and
        SNMP is enabled."
    -- NMS trap annotation
    --#TYPE "Webio Digital Release Alarm 9"
    --#SUMMARY "Release Alarm 9: %s"
    --#ARGUMENTS {0}
    --#SEVERITY INFORMATIONAL
    --#TIMEINDEX 99
    --#STATE OPERATIONAL    
    ::= 79

wtWebioEA2x2ERP-24VAlert22 TRAP-TYPE
    ENTERPRISE  wtWebioEA2x2ERP-24V
    VARIABLES   { wtWebioEA2x2ERP-24VAlarmSnmpTrapReleaseText }
    DESCRIPTION
        "This SNMP trap is generated when Alarm 10 was released,
        SNMP trap enable is set and
        SNMP is enabled."
    -- NMS trap annotation
    --#TYPE "Webio Digital Release Alarm 10"
    --#SUMMARY "Release Alarm 10: %s"
    --#ARGUMENTS {0}
    --#SEVERITY INFORMATIONAL
    --#TIMEINDEX 99
    --#STATE OPERATIONAL    
    ::= 80

wtWebioEA2x2ERP-24VAlert23 TRAP-TYPE
    ENTERPRISE  wtWebioEA2x2ERP-24V
    VARIABLES   { wtWebioEA2x2ERP-24VAlarmSnmpTrapReleaseText }
    DESCRIPTION
        "This SNMP trap is generated when Alarm 11 was released,
        SNMP trap enable is set and
        SNMP is enabled."
    -- NMS trap annotation
    --#TYPE "Webio Digital Release Alarm 11"
    --#SUMMARY "Release Alarm 11: %s"
    --#ARGUMENTS {0}
    --#SEVERITY INFORMATIONAL
    --#TIMEINDEX 99
    --#STATE OPERATIONAL    
    ::= 81

wtWebioEA2x2ERP-24VAlert24 TRAP-TYPE
    ENTERPRISE  wtWebioEA2x2ERP-24V
    VARIABLES   { wtWebioEA2x2ERP-24VAlarmSnmpTrapReleaseText }
    DESCRIPTION
        "This SNMP trap is generated when Alarm 12 was released,
        SNMP trap enable is set and
        SNMP is enabled."
    -- NMS trap annotation
    --#TYPE "Webio Digital Release Alarm 12"
    --#SUMMARY "Release Alarm 12: %s"
    --#ARGUMENTS {0}
    --#SEVERITY INFORMATIONAL
    --#TIMEINDEX 99
    --#STATE OPERATIONAL    
    ::= 82

wtWebioEA2x2ERP-24VAlertDiag TRAP-TYPE
    ENTERPRISE  wtWebioEA2x2ERP-24V
    VARIABLES   { 	
    		wtWebioEA2x2ERP-24VDiagErrorIndex,
    	  	wtWebioEA2x2ERP-24VDiagErrorMessage
    		}
    DESCRIPTION
        "This SNMP trap is generated when a diagnosis/error message was triggered,
        SNMP trap enable is set and
        SNMP is enabled."
    -- NMS trap annotation
    --#TYPE "Webio Digital Diagnose Error"
    --#SUMMARY "Diagnose error index: %d, Message: %s."
    --#ARGUMENTS {0,1}
    --#SEVERITY MAJOR
    --#TIMEINDEX 99
    --#STATE DEGRADED    
    ::= 110

--------------------------------------------------------------------------------
--------------------------------------------------------------------------------
--------------------------------------------------------------------------------

-- wtIpWatcher-24VInOut Group
------------------------

wtIpWatcher-24VInputs OBJECT-TYPE
    SYNTAX INTEGER (1..2)
    ACCESS read-only
    STATUS mandatory
    DESCRIPTION
        "Number of idependent inputs."
    ::= { wtIpWatcher-24VInOut 1 }

wtIpWatcher-24VOutputs OBJECT-TYPE
    SYNTAX INTEGER (1..2)
    ACCESS read-only
    STATUS mandatory
    DESCRIPTION
        "Number of idependent outputs."
    ::= { wtIpWatcher-24VInOut 2 }

-- Input Interface Table

wtIpWatcher-24VInputTable OBJECT-TYPE
    SYNTAX SEQUENCE OF WtIpWatcher-24VInputEntry
    ACCESS not-accessible
    STATUS mandatory
    DESCRIPTION
        "List of input indices."
    ::= { wtIpWatcher-24VInOut 3 }

wtIpWatcher-24VInputEntry OBJECT-TYPE
    SYNTAX WtIpWatcher-24VInputEntry
    ACCESS not-accessible
    STATUS mandatory
    DESCRIPTION
        "Number of the inputs."
    INDEX  { wtIpWatcher-24VInputNo }
    ::= { wtIpWatcher-24VInputTable 1 }

WtIpWatcher-24VInputEntry ::= SEQUENCE {
    wtIpWatcher-24VInputNo 		INTEGER,
    wtIpWatcher-24VInputCounter 	INTEGER,
    wtIpWatcher-24VInputCounterClear 	INTEGER,
    wtIpWatcher-24VInputState 		INTEGER
    
}

wtIpWatcher-24VInputNo OBJECT-TYPE
    SYNTAX INTEGER (1)
    ACCESS read-only
    STATUS mandatory
    DESCRIPTION
        "Index numbers of the inputs."
    ::= { wtIpWatcher-24VInputEntry 1 }

wtIpWatcher-24VInputCounter OBJECT-TYPE
    SYNTAX INTEGER (1)
    ACCESS read-only
    STATUS mandatory
    DESCRIPTION
        "Value of the input counter."
    ::= { wtIpWatcher-24VInputEntry 2 }
    
wtIpWatcher-24VInputCounterClear OBJECT-TYPE
    SYNTAX INTEGER
    ACCESS read-only
    STATUS mandatory
    DESCRIPTION
        "Clears the input counter after returning its value."
    ::= { wtIpWatcher-24VInputEntry 3 }
    
wtIpWatcher-24VInputState OBJECT-TYPE
    SYNTAX INTEGER{
    wtIpWatcher-24VInputState-OFF(0),
    wtIpWatcher-24VInputState-ON(1)
    }
    ACCESS read-only
    STATUS mandatory
    DESCRIPTION
        "Value of a single input bit."
    ::= { wtIpWatcher-24VInputEntry 4 }    
    
wtIpWatcher-24VInputValue OBJECT-TYPE
    SYNTAX INTEGER 
    ACCESS read-only
    STATUS mandatory
    DESCRIPTION
        "This variable is used to read the inputs of the digital I/O port.
        The OCTETS are interpreted bit-by-bit, with each bit corresponding to an output.
        Bit 0 corresponds to the LSB.
        OCTET 1: unused
        OCTET 2: unused
        OCTET 3: unused
        OCTET 4, Bit 0-1: Digital outputs 0-1"
    ::= { wtIpWatcher-24VInOut 4 }
    

-- Output Interface Table

wtIpWatcher-24VOutputTable OBJECT-TYPE
    SYNTAX SEQUENCE OF WtIpWatcher-24VOutputEntry
    ACCESS not-accessible
    STATUS mandatory
    DESCRIPTION
        "List of output indices."
    ::= { wtIpWatcher-24VInOut 5 }

wtIpWatcher-24VOutputEntry OBJECT-TYPE
    SYNTAX WtIpWatcher-24VOutputEntry
    ACCESS not-accessible
    STATUS mandatory
    DESCRIPTION
        "Number of the outputs."
    INDEX  { wtIpWatcher-24VOutputNo }
    ::= { wtIpWatcher-24VOutputTable 1 }

WtIpWatcher-24VOutputEntry ::= SEQUENCE {
    wtIpWatcher-24VOutputNo 	INTEGER,
    wtIpWatcher-24VOutputState 	INTEGER    
}

wtIpWatcher-24VOutputNo OBJECT-TYPE
    SYNTAX INTEGER (1)
    ACCESS read-only
    STATUS mandatory
    DESCRIPTION
        "Output number."
    ::= { wtIpWatcher-24VOutputEntry 1 }

wtIpWatcher-24VOutputState OBJECT-TYPE
    SYNTAX INTEGER{
    wtIpWatcher-24VOutputState-OFF(0),
    wtIpWatcher-24VOutputState-ON(1)
    }
    ACCESS read-write
    STATUS mandatory
    DESCRIPTION
        "Value of a single output bit."
    ::= { wtIpWatcher-24VOutputEntry 2 }
    

wtIpWatcher-24VOutputValue OBJECT-TYPE
    SYNTAX INTEGER
    ACCESS read-write
    STATUS mandatory
    DESCRIPTION
        "This variable is used to read and write the outputs of the digital I/O port. 
        The OCTETS are interpreted bit-by-bit, with each bit corresponding to an output. 
        Bit 0 corresponds to the LSB.
        OCTET 1: unused
        OCTET 2: unused
        OCTET 3: unused
        OCTET 4, Bit 0-1: Digital outputs 0-1
        	 Bit 2-7: ungenutzt"
    ::= { wtIpWatcher-24VInOut 6 }
    
wtIpWatcher-24VSetOutput OBJECT-TYPE
    SYNTAX OCTET STRING (SIZE (8))
    ACCESS read-write			-- write-only
    STATUS mandatory
    DESCRIPTION
        "This variable allows setting of individual digital outputs. The OCTETS are 
        interpreted bit-by-bit, with each bit corresponding to an output. Bit 0 corresponds 
        to the LSB.
        The first two OCTETS contain the mask which determines which of the outputs are to 
        be set (corresponding bit = 1) and which outputs are to remain unchanged 
        (corresponding bit = 0):
	OCTET 1 : unused
	OCTET 2 : unused
	OCTET 3 : unused
	OCTET 4, Bit 0-1: Mask for digital outputs 0-1
	
	OCTETS 5-8 contain the level (1=HIGH, 0=LOW) which the outputs 
	should assume:
	OCTET 5 : unused
	OCTET 6 : unused
	OCTET 7 : unused
        OCTET 8, Bit 0-1: Level of digital outputs 0-1"
    ::= { wtIpWatcher-24VInOut 7 }

-- Alarm Output Interface Table

wtIpWatcher-24VAlarmOutputTable OBJECT-TYPE
    SYNTAX SEQUENCE OF WtIpWatcher-24VAlarmOutputEntry
    ACCESS not-accessible
    STATUS mandatory
    DESCRIPTION
        "List of alarm indices.."
    ::= { wtIpWatcher-24VInOut 8 }

wtIpWatcher-24VAlarmOutputEntry OBJECT-TYPE
    SYNTAX WtIpWatcher-24VAlarmOutputEntry
    ACCESS not-accessible
    STATUS mandatory
    DESCRIPTION
        "Index reference."
    INDEX  { wtIpWatcher-24VAlarmNo }
    ::= { wtIpWatcher-24VAlarmOutputTable 1 }

WtIpWatcher-24VAlarmOutputEntry ::= SEQUENCE {
    wtIpWatcher-24VAlarmOutputState	INTEGER,
    wtIpWatcher-24VAlarmTriggerState	INTEGER
}

wtIpWatcher-24VAlarmOutputState OBJECT-TYPE
    SYNTAX INTEGER{
    wtIpWatcher-24VAlarmOutputState-OFF(0),
    wtIpWatcher-24VAlarmOutputState-ON(1)
    }
    ACCESS read-write
    STATUS mandatory
    DESCRIPTION
        "State of the alarm."
    ::= { wtIpWatcher-24VAlarmOutputEntry 1 }

wtIpWatcher-24VAlarmTriggerState OBJECT-TYPE
    SYNTAX INTEGER{
    wtIpWatcher-24VAlarmTriggerState-OFF(0),
    wtIpWatcher-24VAlarmTriggerState-ON(1)
    }
    ACCESS read-only
    STATUS mandatory
    DESCRIPTION
        "State of the trigger condition."
    ::= { wtIpWatcher-24VAlarmOutputEntry 2 }    
        
-- wtIpWatcher-24VSessCntrl Group
--------------------------------

wtIpWatcher-24VSessCntrlPassword OBJECT-TYPE
    SYNTAX OCTET STRING 
    ACCESS read-write
    STATUS mandatory
    DESCRIPTION
        "Entering this password opens a session which is ended by writing a 1 to 
        wtIpWatcher-24VSessCntrlLogout. When read this variable provides a string of
        length zero."
    ::= { wtIpWatcher-24VSessCntrl 1 }

wtIpWatcher-24VSessCntrlConfigMode OBJECT-TYPE
    SYNTAX INTEGER {
    wtIpWatcher-24VSessCntrl-NoSession(0),
    wtIpWatcher-24VSessCntrl-Session(1)
    }
    ACCESS read-only
    STATUS mandatory
    DESCRIPTION
        "When the device is in SNMP configuration mode, the value 1 is
        returned, otherwise 0. If the read value is 0 even though the password
        was written, the device is already in config mode and the variables
        can only be read."
    ::= { wtIpWatcher-24VSessCntrl 2 }

wtIpWatcher-24VSessCntrlLogout OBJECT-TYPE
    SYNTAX INTEGER 
    ACCESS read-write
    STATUS mandatory
    DESCRIPTION
        "If the device is in configuration mode and the session was opened by
        this SNMP Manager, writing a 1 to this variable will end the session 
        and all parameters are stored.
        Writing a 2 discards all entries again. When read this variable
        provides the value 0."
    ::= { wtIpWatcher-24VSessCntrl 3 }

wtIpWatcher-24VSessCntrlAdminPassword OBJECT-TYPE
    SYNTAX OCTET STRING 
    ACCESS read-write
    STATUS mandatory
    DESCRIPTION
        "This password protects access to the variables with administrator rights.
        It can only be changed by the administrator. If no password was assigned,
        the valid password is public."
    ::= { wtIpWatcher-24VSessCntrl 4 }

wtIpWatcher-24VSessCntrlConfigPassword OBJECT-TYPE
    SYNTAX OCTET STRING 
    ACCESS read-write
    STATUS mandatory
    DESCRIPTION
        "This password protects access to the variables with configurator rights. It can
        be changed by the administrator and by the configurator. If no password was assigned, 
        the valid password is public. When read this variable provides a null-pointer."
    ::= { wtIpWatcher-24VSessCntrl 5 }
    
-- wtIpWatcher-24VText Group
------------------------

wtIpWatcher-24VDeviceName OBJECT-TYPE
    SYNTAX OCTET STRING 
    ACCESS read-write
    STATUS mandatory
    DESCRIPTION
        "Name of the Webio, which is user definable."
    ::= { wtIpWatcher-24VText 1 }

wtIpWatcher-24VDeviceText OBJECT-TYPE
    SYNTAX OCTET STRING 
    ACCESS read-write
    STATUS mandatory
    DESCRIPTION
        "Description of the Webio, which is user definable."
    ::= { wtIpWatcher-24VText 2 }
    
wtIpWatcher-24VDeviceLocation OBJECT-TYPE
    SYNTAX OCTET STRING 
    ACCESS read-write
    STATUS mandatory
    DESCRIPTION
        "Description of the location of the Webio, which is user definable."
    ::= { wtIpWatcher-24VText 3 }

wtIpWatcher-24VDeviceContact OBJECT-TYPE
    SYNTAX OCTET STRING 
    ACCESS read-write
    STATUS mandatory
    DESCRIPTION
        "Contact address of the system operator of the Webio, which is user definable."
    ::= { wtIpWatcher-24VText 4 }    

-- wtIpWatcher-24VTimeZone Group
----------------------------

wtIpWatcher-24VTzOffsetHrs OBJECT-TYPE
    SYNTAX INTEGER 
    ACCESS read-write
    STATUS mandatory
    DESCRIPTION
        "Offset hours for the time zone (winter time) with respect to UTC."
    ::= { wtIpWatcher-24VTimeZone 1 }

wtIpWatcher-24VTzOffsetMin OBJECT-TYPE
    SYNTAX INTEGER 
    ACCESS read-write
    STATUS mandatory
    DESCRIPTION
        "Offset minutes for the time zone (winter time) with respect to UTC."
    ::= { wtIpWatcher-24VTimeZone 2 }

wtIpWatcher-24VTzEnable OBJECT-TYPE
    SYNTAX OCTET STRING (SIZE(4))
    ACCESS read-write
    STATUS mandatory
    DESCRIPTION
        "Binary coded conditions:
        Octet 1: unused
        Octet 2: unused
        Octet 3: unused
        Octet 4:
        	Bit 1-7: unused
	        Bit 0  : Apply Timezone"
    ::= { wtIpWatcher-24VTimeZone 3 }

wtIpWatcher-24VStTzOffsetHrs OBJECT-TYPE
    SYNTAX INTEGER 
    ACCESS read-write
    STATUS mandatory
    DESCRIPTION
        "Offset hours of the time zone (summer time) with respect to UTC."
    ::= { wtIpWatcher-24VTimeZone 4 }

wtIpWatcher-24VStTzOffsetMin OBJECT-TYPE
    SYNTAX INTEGER 
    ACCESS read-write
    STATUS mandatory
    DESCRIPTION
        "Offset minutes of the time zone (summer time) with respect to UTC."
    ::= { wtIpWatcher-24VTimeZone 5 }

wtIpWatcher-24VStTzEnable OBJECT-TYPE
    SYNTAX OCTET STRING (SIZE(4))
    ACCESS read-write
    STATUS mandatory
    DESCRIPTION
        "Binary coded conditions:
        Octet 1: unused
        Octet 2: unused
        Octet 3: unused
        Octet 4:
        	Bit 1-7: unused
	        Bit 0  : Apply Summertime"
    ::= { wtIpWatcher-24VTimeZone 6 }

wtIpWatcher-24VStTzStartMonth OBJECT-TYPE
    SYNTAX INTEGER {
    	wtIpWatcher-24VStartMonth-January(1),
    	wtIpWatcher-24VStartMonth-February(2),
    	wtIpWatcher-24VStartMonth-March(3),
    	wtIpWatcher-24VStartMonth-April(4),
    	wtIpWatcher-24VStartMonth-May(5),
    	wtIpWatcher-24VStartMonth-June(6),
    	wtIpWatcher-24VStartMonth-July(7),
    	wtIpWatcher-24VStartMonth-August(8),
    	wtIpWatcher-24VStartMonth-September(9),
    	wtIpWatcher-24VStartMonth-October(10),
    	wtIpWatcher-24VStartMonth-November(11),
    	wtIpWatcher-24VStartMonth-December(12)
    	}
    	
    ACCESS read-write
    STATUS mandatory
    DESCRIPTION
        "Month in which the change is made from winter time to summer time."
    ::= { wtIpWatcher-24VTimeZone 7 }

wtIpWatcher-24VStTzStartMode OBJECT-TYPE
    SYNTAX INTEGER {
    	wtIpWatcher-24VStartMode-first(1),
    	wtIpWatcher-24VStartMode-second(2),
    	wtIpWatcher-24VStartMode-third(3),
    	wtIpWatcher-24VStartMode-fourth(4),
    	wtIpWatcher-24VStartMode-last(5)
    	}
    	
    ACCESS read-write
    STATUS mandatory
    DESCRIPTION
        "Mode of the day of the week for which the change is made from winter time to summer time."
    ::= { wtIpWatcher-24VTimeZone 8 }

wtIpWatcher-24VStTzStartWday OBJECT-TYPE
    SYNTAX INTEGER {
    	wtIpWatcher-24VStartWday-Sunday(1),
    	wtIpWatcher-24VStartWday-Monday(2),
    	wtIpWatcher-24VStartWday-Tuesday(3),
    	wtIpWatcher-24VStartWday-Thursday(4),
    	wtIpWatcher-24VStartWday-Wednesday(5),
    	wtIpWatcher-24VStartWday-Friday(6),
    	wtIpWatcher-24VStartWday-Saturday(7)
    	}
    	
    ACCESS read-write
    STATUS mandatory
    DESCRIPTION
        "Day of the week on which the change is made from winter time to summer time"
    ::= { wtIpWatcher-24VTimeZone 9 }
    
wtIpWatcher-24VStTzStartHrs OBJECT-TYPE
    SYNTAX INTEGER 
    ACCESS read-write
    STATUS mandatory
    DESCRIPTION
        "Hour in which the time zone is changed from winter to summer time with
        respect to UTC."
    ::= { wtIpWatcher-24VTimeZone 10 }

wtIpWatcher-24VStTzStartMin OBJECT-TYPE
    SYNTAX INTEGER 
    ACCESS read-write
    STATUS mandatory
    DESCRIPTION
        "Minute in which the time zone is changed from winter to summer time with
        respect to UTC."
    ::= { wtIpWatcher-24VTimeZone 11 }
 
wtIpWatcher-24VStTzStopMonth OBJECT-TYPE
    SYNTAX INTEGER {
    	wtIpWatcher-24VStopMonth-January(1),
    	wtIpWatcher-24VStopMonth-February(2),
    	wtIpWatcher-24VStopMonth-March(3),
    	wtIpWatcher-24VStopMonth-April(4),
    	wtIpWatcher-24VStopMonth-May(5),
    	wtIpWatcher-24VStopMonth-June(6),
    	wtIpWatcher-24VStopMonth-July(7),
    	wtIpWatcher-24VStopMonth-August(8),
    	wtIpWatcher-24VStopMonth-September(9),
    	wtIpWatcher-24VStopMonth-October(10),
    	wtIpWatcher-24VStopMonth-November(11),
    	wtIpWatcher-24VStopMonth-December(12)
    	}
    ACCESS read-write
    STATUS mandatory
    DESCRIPTION
        "Month in which the change is made from summer time to winter time."
   ::= { wtIpWatcher-24VTimeZone 12 }

wtIpWatcher-24VStTzStopMode OBJECT-TYPE
    SYNTAX INTEGER {
    	wtIpWatcher-24VStopMode-first(1),
    	wtIpWatcher-24VStopMode-second(2),
    	wtIpWatcher-24VStopMode-third(3),
    	wtIpWatcher-24VStopMode-fourth(4),
    	wtIpWatcher-24VStopMode-last(5)
    	}
    ACCESS read-write
    STATUS mandatory
    DESCRIPTION
        "Mode of the week day on which the change is made from summer time to winter time."
    ::= { wtIpWatcher-24VTimeZone 13 }

wtIpWatcher-24VStTzStopWday OBJECT-TYPE
    SYNTAX INTEGER {
    	wtIpWatcher-24VStopWday-Sunday(1),
    	wtIpWatcher-24VStopWday-Monday(2),
    	wtIpWatcher-24VStopWday-Tuesday(3),
    	wtIpWatcher-24VStopWday-Thursday(4),
    	wtIpWatcher-24VStopWday-Wednesday(5),
    	wtIpWatcher-24VStopWday-Friday(6),
    	wtIpWatcher-24VStopWday-Saturday(7)
    	}
    ACCESS read-write
    STATUS mandatory
    DESCRIPTION
        "Day of the week on which the change is made from summer time to winter time."
    ::= { wtIpWatcher-24VTimeZone 14 }
    
wtIpWatcher-24VStTzStopHrs OBJECT-TYPE
    SYNTAX INTEGER 
    ACCESS read-write
    STATUS mandatory
    DESCRIPTION
        "Hour at which the time zone is changed from summer to winter time with
        respect to UTC."
    ::= { wtIpWatcher-24VTimeZone 15 }

wtIpWatcher-24VStTzStopMin OBJECT-TYPE
    SYNTAX INTEGER 
    ACCESS read-write
    STATUS mandatory
    DESCRIPTION
        "Minute at which the time zone is changed from summer to winter time with
        respect to UTC."
    ::= { wtIpWatcher-24VTimeZone 16 }

-- wtIpWatcher-24VTimeServer Group
----------------------------

wtIpWatcher-24VTimeServer1 OBJECT-TYPE
    SYNTAX OCTET STRING 
    ACCESS read-write
    STATUS mandatory
    DESCRIPTION
        "IP address or name of the 1st time server in ASCII"
    ::= { wtIpWatcher-24VTimeServer 1 }

wtIpWatcher-24VTimeServer2 OBJECT-TYPE
    SYNTAX OCTET STRING 
    ACCESS read-write
    STATUS mandatory
    DESCRIPTION
        "IP address or name of the 2nd time server in ASCII"
    ::= { wtIpWatcher-24VTimeServer 2 }

wtIpWatcher-24VTsEnable OBJECT-TYPE
    SYNTAX OCTET STRING (SIZE(4))
    ACCESS read-write
    STATUS mandatory
    DESCRIPTION
        "Binary coded conditions:
        Octet 1: unused
        Octet 2: unused
        Octet 3: unused
        Octet 4:
        	Bit 1-7: unused
	        Bit 0  : Apply Time Server"
    ::= { wtIpWatcher-24VTimeServer 3 }

wtIpWatcher-24VTsSyncTime OBJECT-TYPE
    SYNTAX INTEGER 
    ACCESS read-write
    STATUS mandatory
    DESCRIPTION
        "Daily synchronisation time with the time server (hour: 0-23)."
    ::= { wtIpWatcher-24VTimeServer 4 }
      
    
-- wtIpWatcher-24VDeviceClock Group
----------------------------

wtIpWatcher-24VClockHrs OBJECT-TYPE
    SYNTAX INTEGER (0..23)
    ACCESS read-write
    STATUS mandatory
    DESCRIPTION
        "Clock hours taking into account the time zone settings."
    ::= { wtIpWatcher-24VDeviceClock 1 }

wtIpWatcher-24VClockMin OBJECT-TYPE
    SYNTAX INTEGER (0..59)
    ACCESS read-write
    STATUS mandatory
    DESCRIPTION
        "Clock minutes taking into account the time zone settings."
    ::= { wtIpWatcher-24VDeviceClock 2 }

wtIpWatcher-24VClockDay OBJECT-TYPE
    SYNTAX INTEGER (1..31)
    ACCESS read-write
    STATUS mandatory
    DESCRIPTION
        "Date: Day of the month, taking into account the time zone settings."
    ::= { wtIpWatcher-24VDeviceClock 3 }

wtIpWatcher-24VClockMonth OBJECT-TYPE
   SYNTAX INTEGER {
    	wtIpWatcher-24VClockMonth-January(1),
    	wtIpWatcher-24VClockMonth-February(2),
    	wtIpWatcher-24VClockMonth-March(3),
    	wtIpWatcher-24VClockMonth-April(4),
    	wtIpWatcher-24VClockMonth-May(5),
    	wtIpWatcher-24VClockMonth-June(6),
    	wtIpWatcher-24VClockMonth-July(7),
    	wtIpWatcher-24VClockMonth-August(8),
    	wtIpWatcher-24VClockMonth-September(9),
    	wtIpWatcher-24VClockMonth-October(10),
    	wtIpWatcher-24VClockMonth-November(11),
    	wtIpWatcher-24VClockMonth-December(12)
    	}
    ACCESS read-write
    STATUS mandatory
    DESCRIPTION
        "Date: Month, taking into account the time zone settings."
    ::= { wtIpWatcher-24VDeviceClock 4 }

wtIpWatcher-24VClockYear OBJECT-TYPE
    SYNTAX INTEGER (0..65535)
    ACCESS read-write
    STATUS mandatory
    DESCRIPTION
        "Date: Year, taking into account the time zone settings."
    ::= { wtIpWatcher-24VDeviceClock 5 }

-- wtIpWatcher-24VNetwork Group
------------------------

wtIpWatcher-24VIpAddress OBJECT-TYPE
    SYNTAX IpAddress
    ACCESS read-write
    STATUS mandatory
    DESCRIPTION
        "IP address of the Webio"
    ::= { wtIpWatcher-24VNetwork 1 }

wtIpWatcher-24VSubnetMask OBJECT-TYPE
    SYNTAX IpAddress
    ACCESS read-write
    STATUS mandatory
    DESCRIPTION
        "Subnet mask of the Webio"
    ::= { wtIpWatcher-24VNetwork 2 }

wtIpWatcher-24VGateway OBJECT-TYPE
    SYNTAX IpAddress
    ACCESS read-write
    STATUS mandatory
    DESCRIPTION
        "Gateway of the Webio"
    ::= { wtIpWatcher-24VNetwork 3 }

wtIpWatcher-24VDnsServer1 OBJECT-TYPE
    SYNTAX OCTET STRING 
    ACCESS read-write
    STATUS mandatory
    DESCRIPTION
        "IP address of the 1st DNS server in ASCII"
    ::= { wtIpWatcher-24VNetwork 4 }

wtIpWatcher-24VDnsServer2 OBJECT-TYPE
    SYNTAX OCTET STRING 
    ACCESS read-write
    STATUS mandatory
    DESCRIPTION
        "IP address of the 2nd DNS server in ASCII"
    ::= { wtIpWatcher-24VNetwork 5 }

wtIpWatcher-24VAddConfig OBJECT-TYPE
    SYNTAX OCTET STRING 
    ACCESS read-write
    STATUS mandatory
    DESCRIPTION
        "Additional configuration (1=ON):
        Octet 1: unused
        Octet 2: unused
        Octet 3: unused
        Octet 4:
	        Bit 1: DHCP  enable
	        Bit 0: BOOTP enable"
    ::= { wtIpWatcher-24VNetwork 6 }

--  wtIpWatcher-24VHTTP Group
--------------------------------

wtIpWatcher-24VHttpPort OBJECT-TYPE
    SYNTAX INTEGER (1..65534)
    ACCESS read-write
    STATUS mandatory
    DESCRIPTION
       "Definition of the standard HTML port (Default: 80)."
    ::= { wtIpWatcher-24VHTTP 4 }        
    
    
-- wtIpWatcher-24VMail Group
--------------------------------

wtIpWatcher-24VMailAdName OBJECT-TYPE
    SYNTAX OCTET STRING 
    ACCESS read-write
    STATUS mandatory
    DESCRIPTION
        "Device name for mail administration."
    ::= { wtIpWatcher-24VMail 1 }
    
wtIpWatcher-24VMailReply OBJECT-TYPE
    SYNTAX OCTET STRING 
    ACCESS read-write
    STATUS mandatory
    DESCRIPTION
        "Reply address for the mail server."
    ::= { wtIpWatcher-24VMail 2 }
    
wtIpWatcher-24VMailServer OBJECT-TYPE
    SYNTAX OCTET STRING 
    ACCESS read-write
    STATUS mandatory
    DESCRIPTION
        "Name or IP address of the mail server."
    ::= { wtIpWatcher-24VMail 3 }
    
wtIpWatcher-24VMailEnable OBJECT-TYPE
    SYNTAX OCTET STRING 
    ACCESS read-write
    STATUS mandatory
    DESCRIPTION
        "Set this bit to enable the sending of mails:
        Octet 1: unused
        Octet 2: unused
        Octet 3: unused
        Octet 4:
        	Bit 1-7: unused
                Bit 0  : Mail enable"
    ::= { wtIpWatcher-24VMail 4 }

wtIpWatcher-24VMailAuthentication OBJECT-TYPE
    SYNTAX OCTET STRING (SIZE (4))
    ACCESS read-write
    STATUS mandatory
    DESCRIPTION
        "Selection of the authentication modi:
        The OCTETS are interpreted bit-by-bit,
        Bit 0 corresponds to the LSB.
        OCTET 1: unused
        OCTET 2: unused
        OCTET 3: unused
        OCTET 4: Bit 3-7: unused
        	 Bit 2  : POP3 before SMTP
        	 Bit 1  : ESMTP, authentication
        	 Bit 0  : SMTP, no authentication"
    ::= { wtIpWatcher-24VMail 5 }
    
wtIpWatcher-24VMailAuthUser OBJECT-TYPE
    SYNTAX OCTET STRING 
    ACCESS read-write
    STATUS mandatory
    DESCRIPTION
        "Name of the user to be authenticated."
    ::= { wtIpWatcher-24VMail 6 }    
    
wtIpWatcher-24VMailAuthPassword OBJECT-TYPE
    SYNTAX OCTET STRING 
    ACCESS read-write
    STATUS mandatory
    DESCRIPTION
        "Authentication password."
    ::= { wtIpWatcher-24VMail 7 }    
    
wtIpWatcher-24VMailPop3Server OBJECT-TYPE
    SYNTAX OCTET STRING 
    ACCESS read-write
    STATUS mandatory
    DESCRIPTION
        "Name or Ip-address of the POP3 Servers."
    ::= { wtIpWatcher-24VMail 8 }        
    

--  wtIpWatcher-24VSnmp Group
--------------------------------

wtIpWatcher-24VSnmpEnable OBJECT-TYPE
    SYNTAX OCTET STRING 
    ACCESS read-write
    STATUS mandatory
    DESCRIPTION
        "Set bit 0 to enable SNMP.
        If disabled, the device did not respond to any SNMP requests.
        Bit 1 decided wether the community string of read operations 
        is compared with the system password or not:
        Octet 1: unused
        Octet 2: unused
        Octet 3: unused
        Octet 4:
        	Bit 1-7: unused
        	Bit 0  : SNMP enable"
    ::= { wtIpWatcher-24VSNMP 1 }
    
wtIpWatcher-24VSnmpCommunityStringRead OBJECT-TYPE
    SYNTAX OCTET STRING
    ACCESS read-write
    STATUS mandatory
    DESCRIPTION
        "Community string read only"
    ::= { wtIpWatcher-24VSNMP 2 }

wtIpWatcher-24VSnmpCommunityStringReadWrite OBJECT-TYPE
    SYNTAX OCTET STRING
    ACCESS read-write
    STATUS mandatory
    DESCRIPTION
        "Community string read / write"
    ::= { wtIpWatcher-24VSNMP 3 }

wtIpWatcher-24VSnmpSystemTrapManagerIP OBJECT-TYPE
    SYNTAX OCTET STRING 
    ACCESS read-write
    STATUS mandatory
    DESCRIPTION
        "Name or IP address of the TCP server which accepts the system trap."
    ::= { wtIpWatcher-24VSNMP 4 }
    
wtIpWatcher-24VSnmpSystemTrapEnable OBJECT-TYPE
    SYNTAX OCTET STRING (SIZE(4))
    ACCESS read-write
    STATUS mandatory
    DESCRIPTION
        "Binary coded trigger conditions:
        Octet 1: unused
        Octet 2: unused
        Octet 3: unused
        Octet 4:
	        Bit 0:   ColdStart
	        Bit 1:   WarmStart
	        Bit 2:   Diag messages
	        Bit 3-7: unused"
    ::= { wtIpWatcher-24VSNMP 5 }    

-- wtIpWatcher-24VUDP Group
--------------------------------   

wtIpWatcher-24VUdpAdminPort OBJECT-TYPE
    SYNTAX INTEGER
    ACCESS read-write
    STATUS mandatory
    DESCRIPTION
        "Udp port to which the Udp queries ( short form GET requests) can be sent. This
        port number must be unique within the device."
    ::= { wtIpWatcher-24VUDP 1 }

wtIpWatcher-24VUdpEnable OBJECT-TYPE
    SYNTAX OCTET STRING 
    ACCESS read-write
    STATUS mandatory
    DESCRIPTION
        "Set this bit to enable UDP support:
        Octet 1: unused
        Octet 2: unused
        Octet 3: unused
        Octet 4:
        	Bit 1-7: unused
                Bit 0  : UDP enable"
    ::= { wtIpWatcher-24VUDP 2 }

wtIpWatcher-24VUdpRemotePort OBJECT-TYPE
    SYNTAX INTEGER
    ACCESS read-write
    STATUS mandatory
    DESCRIPTION
        "Udp remote port setting.
        If this value is set to zero, the source port read from a request will be used 
        as destination port for the answer.
        A non zero value forced the destination port to this value."
    ::= { wtIpWatcher-24VUDP 3 }
    
--  wtIpWatcher-24VSyslog Group
--------------------------------
    
wtIpWatcher-24VSyslogServerIP OBJECT-TYPE
    SYNTAX OCTET STRING 
    ACCESS read-write
    STATUS mandatory
    DESCRIPTION
        "Name or IP address of the Syslog server, which accepts the Syslog messgaes."
    ::= { wtIpWatcher-24VSyslog 1 }
    
wtIpWatcher-24VSyslogServerPort OBJECT-TYPE
    SYNTAX INTEGER
    ACCESS read-write
    STATUS mandatory
    DESCRIPTION
        "Portnumber of the Syslog servers, default 514."
    ::= { wtIpWatcher-24VSyslog 2 }

wtIpWatcher-24VSyslogSystemMessagesEnable OBJECT-TYPE
    SYNTAX OCTET STRING (SIZE(4))
    ACCESS read-write
    STATUS mandatory
    DESCRIPTION
        "Binary coded trigger conditions:
        Octet 1: unused
        Octet 2: unused
        Octet 3: unused
        Octet 4:
	        Bit 0:   ColdStart
	        Bit 1:   WarmStart
	        Bit 2:   Diag Messages
	        Bit 3-7: unused"
    ::= { wtIpWatcher-24VSyslog 3 }    

wtIpWatcher-24VSyslogEnable OBJECT-TYPE
    SYNTAX OCTET STRING 
    ACCESS read-write
    STATUS mandatory
    DESCRIPTION
        "Set bit 0to enable Syslog:
        Octet 1: unused
        Octet 2: unused
        Octet 3: unused
        Octet 4:
        	Bit 1-7: unused
                Bit 0  : Syslog enable"
    ::= { wtIpWatcher-24VSyslog 4 }

--  wtIpWatcher-24VFTP Group
--------------------------------

wtIpWatcher-24VFTPServerIP OBJECT-TYPE
    SYNTAX OCTET STRING 
    ACCESS read-write
    STATUS mandatory
    DESCRIPTION
        "Name or IP address of the FTP server, which accepts the FTP messages."
    ::= { wtIpWatcher-24VFTP 1 }
    
wtIpWatcher-24VFTPServerControlPort OBJECT-TYPE
    SYNTAX INTEGER
    ACCESS read-write
    STATUS mandatory
    DESCRIPTION
        "Portnumber of the control port of the FTP server, default 21."
    ::= { wtIpWatcher-24VFTP 2 }
    
wtIpWatcher-24VFTPUserName OBJECT-TYPE
    SYNTAX OCTET STRING 
    ACCESS read-write
    STATUS mandatory
    DESCRIPTION
        "FTP Loggin: user name."
    ::= { wtIpWatcher-24VFTP 3 }
    
wtIpWatcher-24VFTPPassword OBJECT-TYPE
    SYNTAX OCTET STRING 
    ACCESS read-write
    STATUS mandatory
    DESCRIPTION
        "FTP Loggin: user password."
    ::= { wtIpWatcher-24VFTP 4 }

wtIpWatcher-24VFTPAccount OBJECT-TYPE
    SYNTAX OCTET STRING 
    ACCESS read-write
    STATUS mandatory
    DESCRIPTION
        "FTP Loggin: name of account."
    ::= { wtIpWatcher-24VFTP 5 }

wtIpWatcher-24VFTPOption OBJECT-TYPE
    SYNTAX OCTET STRING 
    ACCESS read-write
    STATUS mandatory
    DESCRIPTION
        "Bit 0 switches the FTP Server in Passiv-Mode,
        the Client controls the data connection on its own:
        Octet 1: unused
        Octet 2: unused
        Octet 3: unused
        Octet 4:
        	Bit 1-7: unused
                Bit 0  : PASV enable"
    ::= { wtIpWatcher-24VFTP 6 }
    
wtIpWatcher-24VFTPEnable OBJECT-TYPE
    SYNTAX OCTET STRING 
    ACCESS read-write
    STATUS mandatory
    DESCRIPTION
        "Set Bit 0 to enable FTP:
        Octet 1: unused
        Octet 2: unused
        Octet 3: unused
        Octet 4:
        	Bit 1-7: unused
                Bit 0  : FTP enable"
    ::= { wtIpWatcher-24VFTP 7 }
    
-- wtIpWatcher-24VIpList Group
----------------------------

wtIpWatcher-24VIpListCount OBJECT-TYPE
    SYNTAX INTEGER
    ACCESS read-only
    STATUS mandatory
    DESCRIPTION
        "Number of Ip addresses."
    ::= { wtIpWatcher-24VIpList 1 }
    
-- IpList Interface Table

wtIpWatcher-24VIpListIfTable OBJECT-TYPE
    SYNTAX SEQUENCE OF WtIpWatcher-24VIpListIfEntry
    ACCESS not-accessible
    STATUS mandatory
    DESCRIPTION
        "Table of inices."
    ::= { wtIpWatcher-24VIpList 2 }

wtIpWatcher-24VIpListIfEntry OBJECT-TYPE
    SYNTAX WtIpWatcher-24VIpListIfEntry
    ACCESS not-accessible
    STATUS mandatory
    DESCRIPTION
        "Table entry."
    INDEX  { wtIpWatcher-24VIpListNo }
    ::= { wtIpWatcher-24VIpListIfTable 1 }

WtIpWatcher-24VIpListIfEntry ::= SEQUENCE {
    wtIpWatcher-24VIpListNo 	INTEGER
}

wtIpWatcher-24VIpListNo OBJECT-TYPE
    SYNTAX INTEGER (1..999)
    ACCESS read-only
    STATUS mandatory
    DESCRIPTION
        "List number of this entry."
    ::= { wtIpWatcher-24VIpListIfEntry 1 }

-- IpList Table

wtIpWatcher-24VIpListTable OBJECT-TYPE
    SYNTAX SEQUENCE OF WtIpWatcher-24VIpListEntry
    ACCESS not-accessible
    STATUS mandatory
    DESCRIPTION
        "List of ip addresses."
    ::= { wtIpWatcher-24VIpList 3 }

wtIpWatcher-24VIpListEntry OBJECT-TYPE
    SYNTAX WtIpWatcher-24VIpListEntry
    ACCESS not-accessible
    STATUS mandatory
    DESCRIPTION
        "List entry."
    INDEX  { wtIpWatcher-24VIpListNo }
    ::= { wtIpWatcher-24VIpListTable 1 }

WtIpWatcher-24VIpListEntry ::= SEQUENCE {
    wtIpWatcher-24VIpListName 		OCTET STRING,
    wtIpWatcher-24VIpListPort 		INTEGER,
    wtIpWatcher-24VIpListService	OCTET STRING,
    wtIpWatcher-24VIpListEnable 	OCTET STRING,
    wtIpWatcher-24VIpListAlias 		OCTET STRING
}

wtIpWatcher-24VIpListName OBJECT-TYPE
    SYNTAX OCTET STRING 
    ACCESS read-write
    STATUS mandatory
    DESCRIPTION
        "Name or IP address."
    ::= { wtIpWatcher-24VIpListEntry 1 }
    
wtIpWatcher-24VIpListPort OBJECT-TYPE
    SYNTAX INTEGER 
    ACCESS read-write
    STATUS mandatory
    DESCRIPTION
        "Port number, zero in the case of broadcast or Ping."
    ::= { wtIpWatcher-24VIpListEntry 2 }
    
wtIpWatcher-24VIpListService OBJECT-TYPE
    SYNTAX OCTET STRING 
    ACCESS read-write
    STATUS mandatory
    DESCRIPTION
        "Binary coded scan mode, only one mode can be selected at a particular time:
        Octet 1: unused
        Octet 2: unused
        Octet 3: unused
        Octet 4:
		Bit 0:	Ping enable
        	Bit 1-7: unused"
    ::= { wtIpWatcher-24VIpListEntry 3 }
    
wtIpWatcher-24VIpListEnable OBJECT-TYPE
    SYNTAX OCTET STRING 
    ACCESS read-write
    STATUS mandatory
    DESCRIPTION
        "Binary coded alarm enable:
        Octet 1: unused
        Octet 2: unused
        Octet 3: unused
        Octet 4:
		Bit 0:	enabled in Alarm 1
        	Bit 1:	enabled in Alarm 2
        	Bit 2:  enabled in Alarm 3
        	Bit 3:  enabled in Alarm 4
        	Bit 4-7: unused"
    ::= { wtIpWatcher-24VIpListEntry 4 }

wtIpWatcher-24VIpListAlias OBJECT-TYPE
    SYNTAX OCTET STRING 
    ACCESS read-write
    STATUS mandatory
    DESCRIPTION
        "Alias Name"
    ::= { wtIpWatcher-24VIpListEntry 5 }

 
-- wtIpWatcher-24VOutputMode Group
----------------------------    
    
wtIpWatcher-24VPowerSupplyEnable OBJECT-TYPE
    SYNTAX OCTET STRING 
    ACCESS read-write
    STATUS mandatory
    DESCRIPTION
        "Setting this enable bit turns on the intarnal 24V power supply of the outputs.
        All currents out must not exceed 150mA. At overcurrent condition the power supply will
        be shut down automatically. To reset the ocvercurrent protection circuit
        write 1 into wtIpWatcher-24VDiagErrorClear.
        Internal power supply is a feature of 57655 only.
        
        Octet 1: unused
        Octet 2: unused
        Octet 3: unused
        Octet 4:
        	Bit 1-7: unused
                Bit 0  : Power Supply enable"
    ::= { wtIpWatcher-24VOutputMode 4 }
     
    
-- wtIpWatcher-24VAlarm Group
----------------------------

wtIpWatcher-24VAlarmCount OBJECT-TYPE
    SYNTAX INTEGER (1..4)
    ACCESS read-only
    STATUS mandatory
    DESCRIPTION
        "Number of independent alarms."
    ::= { wtIpWatcher-24VAlarm 1 }
    
-- Alarm Interface Table

wtIpWatcher-24VAlarmIfTable OBJECT-TYPE
    SYNTAX SEQUENCE OF WtIpWatcher-24VAlarmIfEntry
    ACCESS not-accessible
    STATUS mandatory
    DESCRIPTION
        "List of alarm indices."
    ::= { wtIpWatcher-24VAlarm 2 }

wtIpWatcher-24VAlarmIfEntry OBJECT-TYPE
    SYNTAX WtIpWatcher-24VAlarmIfEntry
    ACCESS not-accessible
    STATUS mandatory
    DESCRIPTION
        "Numbers of the alarms."
    INDEX  { wtIpWatcher-24VAlarmNo }
    ::= { wtIpWatcher-24VAlarmIfTable 1 }

WtIpWatcher-24VAlarmIfEntry ::= SEQUENCE {
    wtIpWatcher-24VAlarmNo INTEGER
}

wtIpWatcher-24VAlarmNo OBJECT-TYPE
    SYNTAX INTEGER (1..4)
    ACCESS read-only
    STATUS mandatory
    DESCRIPTION
        "Numbers of the alarms."
    ::= { wtIpWatcher-24VAlarmIfEntry 1 }

-- Alarm Table

wtIpWatcher-24VAlarmTable OBJECT-TYPE
    SYNTAX SEQUENCE OF WtIpWatcher-24VAlarmEntry
    ACCESS not-accessible
    STATUS mandatory
    DESCRIPTION
        "List of settings depending on the alarm number."
    ::= { wtIpWatcher-24VAlarm 3 }

wtIpWatcher-24VAlarmEntry OBJECT-TYPE
    SYNTAX WtIpWatcher-24VAlarmEntry
    ACCESS not-accessible
    STATUS mandatory
    DESCRIPTION
        "Alarm parameters of the individual alarms."
    INDEX  { wtIpWatcher-24VAlarmNo }
    ::= { wtIpWatcher-24VAlarmTable 1 }

WtIpWatcher-24VAlarmEntry ::= SEQUENCE {
    wtIpWatcher-24VAlarmInterval		OCTET STRING,
    wtIpWatcher-24VAlarmEnable			OCTET STRING,
    wtIpWatcher-24VAlarmMailAddr		OCTET STRING,
    wtIpWatcher-24VAlarmMailSubject		OCTET STRING,
    wtIpWatcher-24VAlarmMailText		OCTET STRING,
    wtIpWatcher-24VAlarmSnmpManagerIP		OCTET STRING,
    wtIpWatcher-24VAlarmSnmpTrapText		OCTET STRING,
    wtIpWatcher-24VAlarmUdpIpAddr		OCTET STRING,
    wtIpWatcher-24VAlarmUdpPort			INTEGER,
    wtIpWatcher-24VAlarmUdpText			OCTET STRING,
    wtIpWatcher-24VAlarmTcpIpAddr		OCTET STRING,
    wtIpWatcher-24VAlarmTcpPort			INTEGER,
    wtIpWatcher-24VAlarmTcpText			OCTET STRING,    
    wtIpWatcher-24VAlarmSyslogIpAddr		OCTET STRING,
    wtIpWatcher-24VAlarmSyslogPort		INTEGER,
    wtIpWatcher-24VAlarmSyslogText		OCTET STRING,
    wtIpWatcher-24VAlarmFtpDataPort		OCTET STRING,
    wtIpWatcher-24VAlarmFtpFileName		OCTET STRING,
    wtIpWatcher-24VAlarmFtpText			OCTET STRING,
    wtIpWatcher-24VAlarmFtpOption		OCTET STRING,
    wtIpWatcher-24VAlarmTimerCron		OCTET STRING,

    wtIpWatcher-24VAlarmMailReleaseSubject	OCTET STRING,
    wtIpWatcher-24VAlarmMailReleaseText		OCTET STRING,
    wtIpWatcher-24VAlarmSnmpTrapReleaseText	OCTET STRING,
    wtIpWatcher-24VAlarmUdpReleaseText		OCTET STRING,
    wtIpWatcher-24VAlarmTcpReleaseText		OCTET STRING,    
    wtIpWatcher-24VAlarmSyslogReleaseText	OCTET STRING,
    wtIpWatcher-24VAlarmFtpReleaseText		OCTET STRING,

    wtIpWatcher-24VAlarmName			OCTET STRING,
    wtIpWatcher-24VAlarmGlobalEnable		OCTET STRING,
    wtIpWatcher-24VAlarmCounterClear		OCTET STRING,
    wtIpWatcher-24VAlarmAckEnable		OCTET STRING,
    wtIpWatcher-24VAlarmAckPort			INTEGER,
    wtIpWatcher-24VAlarmSetPort			INTEGER,

    wtIpWatcher-24VAlarmMailTrgClearSubject	OCTET STRING,
    wtIpWatcher-24VAlarmMailTrgClearText	OCTET STRING,
    wtIpWatcher-24VAlarmSnmpTrapTrgClearText	OCTET STRING,
    wtIpWatcher-24VAlarmUdpTrgClearText		OCTET STRING,
    wtIpWatcher-24VAlarmTcpTrgClearText		OCTET STRING,    
    wtIpWatcher-24VAlarmSyslogTrgClearText	OCTET STRING,
    wtIpWatcher-24VAlarmFtpTrgClearText		OCTET STRING,

    wtIpWatcher-24VAlarmMailTrapTxEnable	OCTET STRING,
    wtIpWatcher-24VAlarmSnmpTrapTrapTxEnable	OCTET STRING,
    wtIpWatcher-24VAlarmUdpTrapTxEnable		OCTET STRING,
    wtIpWatcher-24VAlarmTcpTrapTxEnable		OCTET STRING,    
    wtIpWatcher-24VAlarmSyslogTrapTxEnable	OCTET STRING,
    wtIpWatcher-24VAlarmFtpTrapTxEnable		OCTET STRING,
    
    wtIpWatcher-24VAlarmTriggerCount		INTEGER,
    wtIpWatcher-24VAlarmPollingRate		INTEGER
}

wtIpWatcher-24VAlarmInterval OBJECT-TYPE
    SYNTAX OCTET STRING 
    ACCESS read-write
    STATUS mandatory
    DESCRIPTION
        "Send interval for alarm messages."
    ::= { wtIpWatcher-24VAlarmEntry 5 }

wtIpWatcher-24VAlarmEnable OBJECT-TYPE
    SYNTAX OCTET STRING (SIZE(4))
    ACCESS read-write
    STATUS mandatory
    DESCRIPTION
        "Binary coded alarm enable:
        Octet 1: unused
        Octet 2: unused
        Octet 3: unused
        Octet 4:
		Bit 0:	Mail Enable
        	Bit 1:	SNMP Trap enable
        	Bit 2:  UDP enable
        	Bit 3:  Send inputs to pending TCP connections
        	Bit 4:  TCP Client enable
        	Bit 5:	Syslog Messages enable
        	Bit 6-7: unused"
    ::= { wtIpWatcher-24VAlarmEntry 6 }

wtIpWatcher-24VAlarmMailAddr OBJECT-TYPE
    SYNTAX OCTET STRING 
    ACCESS read-write
    STATUS mandatory
    DESCRIPTION
        "E-Mail address for sending the alarm mail to."
    ::= { wtIpWatcher-24VAlarmEntry 7 }

wtIpWatcher-24VAlarmMailSubject OBJECT-TYPE
    SYNTAX OCTET STRING 
    ACCESS read-write
    STATUS mandatory
    DESCRIPTION
        "Subject line for alarm mail."
    ::= { wtIpWatcher-24VAlarmEntry 8 }

wtIpWatcher-24VAlarmMailText OBJECT-TYPE
    SYNTAX OCTET STRING 
    ACCESS read-write
    STATUS mandatory
    DESCRIPTION
        "Alarm mail text: 
        States of the Webio device can be included by using special tags.
        Please refer to the respective Webio manual"
    ::= { wtIpWatcher-24VAlarmEntry 9 }

wtIpWatcher-24VAlarmSnmpManagerIP OBJECT-TYPE
    SYNTAX OCTET STRING 
    ACCESS read-write
    STATUS mandatory
    DESCRIPTION
        "IP address of the SNMP Manager to which the Webio device should send SNMP traps."
    ::= { wtIpWatcher-24VAlarmEntry 10 }

wtIpWatcher-24VAlarmSnmpTrapText OBJECT-TYPE
    SYNTAX OCTET STRING 
    ACCESS read-write
    STATUS mandatory
    DESCRIPTION
        "This text appears in the trap body."
    ::= { wtIpWatcher-24VAlarmEntry 11 }
    
wtIpWatcher-24VAlarmUdpIpAddr OBJECT-TYPE
    SYNTAX OCTET STRING 
    ACCESS read-write
    STATUS mandatory
    DESCRIPTION
        "IP address of the UDP listener to which the Webio device should send UDP traps."
    ::= { wtIpWatcher-24VAlarmEntry 12 }    

wtIpWatcher-24VAlarmUdpPort OBJECT-TYPE
    SYNTAX INTEGER (1..65535) 
    ACCESS read-write
    STATUS mandatory
    DESCRIPTION
        "Port number of the UDP listener to which the Webio device should send UDP traps."
    ::= { wtIpWatcher-24VAlarmEntry 13 }    

wtIpWatcher-24VAlarmUdpText OBJECT-TYPE
    SYNTAX OCTET STRING 
    ACCESS read-write
    STATUS mandatory
    DESCRIPTION
        "This text appears in the UDP trap body."
    ::= { wtIpWatcher-24VAlarmEntry 14 }
    
wtIpWatcher-24VAlarmTcpIpAddr OBJECT-TYPE
    SYNTAX OCTET STRING
    ACCESS read-write
    STATUS mandatory
    DESCRIPTION
        "IP address of the TCP listener to which the Webio device should send TCP traps."
    ::= { wtIpWatcher-24VAlarmEntry 15 }    

wtIpWatcher-24VAlarmTcpPort OBJECT-TYPE
    SYNTAX INTEGER (1..65535) 
    ACCESS read-write
    STATUS mandatory
    DESCRIPTION
        "Port number of the TCP listener to which the Webio device should send TCP traps."
    ::= { wtIpWatcher-24VAlarmEntry 16 }    

wtIpWatcher-24VAlarmTcpText OBJECT-TYPE
    SYNTAX OCTET STRING 
    ACCESS read-write
    STATUS mandatory
    DESCRIPTION
        "This text appears in the TCP trap body."
    ::= { wtIpWatcher-24VAlarmEntry 17 }

wtIpWatcher-24VAlarmSyslogIpAddr OBJECT-TYPE
    SYNTAX OCTET STRING 
    ACCESS read-write
    STATUS mandatory
    DESCRIPTION
        "IP address of the syslog server to which the Webio device should send syslog messages."
    ::= { wtIpWatcher-24VAlarmEntry 18 }    

wtIpWatcher-24VAlarmSyslogPort OBJECT-TYPE
    SYNTAX INTEGER (1..65535) 
    ACCESS read-write
    STATUS mandatory
    DESCRIPTION
        "Port number of the syslog server to which the Webio device should send syslog messages."
    ::= { wtIpWatcher-24VAlarmEntry 19 }    

wtIpWatcher-24VAlarmSyslogText OBJECT-TYPE
    SYNTAX OCTET STRING 
    ACCESS read-write
    STATUS mandatory
    DESCRIPTION
        "Every message starts with the priority key, a time stamp and the host ip address, according RFC3164.
        This text appears in the following syslog message body."
    ::= { wtIpWatcher-24VAlarmEntry 20 }    
    
wtIpWatcher-24VAlarmFtpDataPort OBJECT-TYPE
    SYNTAX OCTET STRING 
    ACCESS read-write
    STATUS mandatory
    DESCRIPTION
        "Local data port: 1..65535 or AUTO: the next free port will be assigned."
    ::= { wtIpWatcher-24VAlarmEntry 21 }
    
wtIpWatcher-24VAlarmFtpFileName OBJECT-TYPE
    SYNTAX OCTET STRING 
    ACCESS read-write
    STATUS mandatory
    DESCRIPTION
        "Name of the file including path informations."
    ::= { wtIpWatcher-24VAlarmEntry 22 }
    
wtIpWatcher-24VAlarmFtpText OBJECT-TYPE
    SYNTAX OCTET STRING 
    ACCESS read-write
    STATUS mandatory
    DESCRIPTION
        "Message text to store on the FTP server."
    ::= { wtIpWatcher-24VAlarmEntry 23 }

wtIpWatcher-24VAlarmFtpOption OBJECT-TYPE
    SYNTAX OCTET STRING (SIZE(4))
    ACCESS read-write
    STATUS mandatory
    DESCRIPTION
        "Binary coded options, select only one option at the same time:
        STORE  = replace file
        APPEND = append message at the end of the file
        
        Octet 1: unused
        Octet 2: unused
        Octet 3: unused
        Octet 4:
		Bit 0  :	STORE
		Bit 1  :	APPEND
        	Bit 2-7:	unused"
    ::= { wtIpWatcher-24VAlarmEntry 24 }      
    
wtIpWatcher-24VAlarmTimerCron OBJECT-TYPE
    SYNTAX OCTET STRING
    ACCESS read-write
    STATUS mandatory
    DESCRIPTION
        "This entry contains 5 space or tab seperated text fields for time trigger definition.
        Each field must match with the actual time to trigger a message, weekday and day of month
        are interpreted separatley.
        1: Minutes	Range 0-59
        2. Hours	Range 0-23, 0 is midnight
        3: Day of month	Range 1-31
        4: Month	Range 1-12
        5: Weekday	Range 0-6, 0 is sunday
        
        Syntax for every field:
         - an asterix (*) enables every possible setting of a field
         - single numbers seperated by commas
         - a partition within the allowed range (1-5)
         - step size within an partition of the allowed range (0-59/2: every second minute)."
    ::= { wtIpWatcher-24VAlarmEntry 25 }      

wtIpWatcher-24VAlarmMailReleaseSubject OBJECT-TYPE
    SYNTAX OCTET STRING 
    ACCESS read-write
    STATUS mandatory
    DESCRIPTION
       "Subject line for alarm mail."
    ::= { wtIpWatcher-24VAlarmEntry 26 }

wtIpWatcher-24VAlarmMailReleaseText OBJECT-TYPE
    SYNTAX OCTET STRING 
    ACCESS read-write
    STATUS mandatory
    DESCRIPTION
        "Release Alarm mail text: 
        States of the Webio device can be included by using special tags.
        Please refer to the respective Webio manual"
    ::= { wtIpWatcher-24VAlarmEntry 27 }    

wtIpWatcher-24VAlarmSnmpTrapReleaseText OBJECT-TYPE
    SYNTAX OCTET STRING 
    ACCESS read-write
    STATUS mandatory
    DESCRIPTION
        "This text appears in the trap body."
    ::= { wtIpWatcher-24VAlarmEntry 28 }

wtIpWatcher-24VAlarmUdpReleaseText OBJECT-TYPE
    SYNTAX OCTET STRING 
    ACCESS read-write
    STATUS mandatory
    DESCRIPTION
        "This text appears in the UDP trap body."
    ::= { wtIpWatcher-24VAlarmEntry 29 }

wtIpWatcher-24VAlarmTcpReleaseText OBJECT-TYPE
    SYNTAX OCTET STRING 
    ACCESS read-write
    STATUS mandatory
    DESCRIPTION
        "This text appears in the TCP trap body."
    ::= { wtIpWatcher-24VAlarmEntry 30 }

wtIpWatcher-24VAlarmSyslogReleaseText OBJECT-TYPE
    SYNTAX OCTET STRING 
    ACCESS read-write
    STATUS mandatory
    DESCRIPTION
        "Every message starts with the priority key, a time stamp and the host ip address, according RFC3164.
        This text appears in the following syslog message body."
    ::= { wtIpWatcher-24VAlarmEntry 31 }

wtIpWatcher-24VAlarmFtpReleaseText OBJECT-TYPE
    SYNTAX OCTET STRING 
    ACCESS read-write
    STATUS mandatory
    DESCRIPTION
        "Message text to store on the FTP server."
    ::= { wtIpWatcher-24VAlarmEntry 32 }

wtIpWatcher-24VAlarmName OBJECT-TYPE
    SYNTAX OCTET STRING 
    ACCESS read-write
    STATUS mandatory
    DESCRIPTION
        "Name of the alarm."
    ::= { wtIpWatcher-24VAlarmEntry 33 }    

wtIpWatcher-24VAlarmGlobalEnable OBJECT-TYPE
    SYNTAX OCTET STRING 
    ACCESS read-write
    STATUS mandatory
    DESCRIPTION
        "Binary coded alarm activation:
        Die OCTETS werden bitweise interpretiert.
        Bit 0 entspricht dem LSB.
        OCTET 1: unused
        OCTET 2: unused
        OCTET 3: unused
        OCTET 4, Bit 1-7: unused
        	 Bit 0  : Alarm enable"
    ::= { wtIpWatcher-24VAlarmEntry 34 }    

wtIpWatcher-24VAlarmCounterClear OBJECT-TYPE
    SYNTAX OCTET STRING 
    ACCESS read-write
    STATUS mandatory
    DESCRIPTION
        "Binary coded options:
        The OCTETS are interpreted bit-by-bit. 
        Bit 0 corresponds to the LSB.
        OCTET 1: unused
        OCTET 2: unused
        OCTET 3: unused
        OCTET 4, Bit 2-7: unused
        	 Bit 1  : Counter clear on Alarm acknowledge 
        	 Bit 0  : Counter clear on Alarm send"
    ::= { wtIpWatcher-24VAlarmEntry 35 }


    wtIpWatcher-24VAlarmAckEnable OBJECT-TYPE
    SYNTAX OCTET STRING 
    ACCESS read-write
    STATUS mandatory
    DESCRIPTION
        "Binary coded options:
        The OCTETS are interpreted bit-by-bit. 
        Bit 0 corresponds to the LSB.
        OCTET 1: unused
        OCTET 2: unused
        OCTET 3: unused
        OCTET 4, Bit 2-7: unused
        	 Bit 1  : Software acknowledge enable
        	 Bit 0  : Hardware acknowledge enable"
    ::= { wtIpWatcher-24VAlarmEntry 36 }


    wtIpWatcher-24VAlarmAckPort OBJECT-TYPE
    SYNTAX INTEGER 
    ACCESS read-write
    STATUS mandatory
    DESCRIPTION
        "Number of the input, which clears the alarm (1-6)."
    ::= { wtIpWatcher-24VAlarmEntry 37 }

    wtIpWatcher-24VAlarmSetPort OBJECT-TYPE
    SYNTAX INTEGER 
    ACCESS read-write
    STATUS mandatory
    DESCRIPTION
        "Number of the output, which will be set by this alarm (1-6).
        The configuration of pulse mode and polarity defined in the port output section is used."
    ::= { wtIpWatcher-24VAlarmEntry 38 }
    
wtIpWatcher-24VAlarmMailTrgClearSubject OBJECT-TYPE
    SYNTAX OCTET STRING 
    ACCESS read-write
    STATUS mandatory
    DESCRIPTION
        "Subject line for alarm mail."
    ::= { wtIpWatcher-24VAlarmEntry 39 }

wtIpWatcher-24VAlarmMailTrgClearText OBJECT-TYPE
    SYNTAX OCTET STRING 
    ACCESS read-write
    STATUS mandatory
    DESCRIPTION
        "Alarm mail text: 
        States of the Webio device can be included by using special tags.
        Please refer to the respective Webio manual"
    ::= { wtIpWatcher-24VAlarmEntry 40 }    

wtIpWatcher-24VAlarmSnmpTrapTrgClearText OBJECT-TYPE
    SYNTAX OCTET STRING 
    ACCESS read-write
    STATUS mandatory
    DESCRIPTION
        "This text appears in the trap body."
    ::= { wtIpWatcher-24VAlarmEntry 41 }

wtIpWatcher-24VAlarmUdpTrgClearText OBJECT-TYPE
    SYNTAX OCTET STRING 
    ACCESS read-write
    STATUS mandatory
    DESCRIPTION
        "This text appears in the UDP trap body."
    ::= { wtIpWatcher-24VAlarmEntry 42 }

wtIpWatcher-24VAlarmTcpTrgClearText OBJECT-TYPE
    SYNTAX OCTET STRING 
    ACCESS read-write
    STATUS mandatory
    DESCRIPTION
      "This text appears in the TCP trap body."
    ::= { wtIpWatcher-24VAlarmEntry 43 }

wtIpWatcher-24VAlarmSyslogTrgClearText OBJECT-TYPE
    SYNTAX OCTET STRING 
    ACCESS read-write
    STATUS mandatory
    DESCRIPTION
        "Every message starts with the priority key, a time stamp and the host ip address, according RFC3164.
        This text appears in the following syslog message body."
    ::= { wtIpWatcher-24VAlarmEntry 44 }

wtIpWatcher-24VAlarmFtpTrgClearText OBJECT-TYPE
    SYNTAX OCTET STRING 
    ACCESS read-write
    STATUS mandatory
    DESCRIPTION
        "Message text to store on the FTP server."
    ::= { wtIpWatcher-24VAlarmEntry 45 }     

    wtIpWatcher-24VAlarmMailTrapTxEnable OBJECT-TYPE
    SYNTAX OCTET STRING 
    ACCESS read-write
    STATUS mandatory
    DESCRIPTION
        "Binary coded options:
        The OCTETS are interpreted bit-by-bit. 
        Bit 0 corresponds to the LSB.
        OCTET 1: unused
        OCTET 2: unused
        OCTET 3: unused
        OCTET 4, Bit 4-7: unused
        	 Bit 3  : Alarm OFF message enable
        	 Bit 2  : Trigger OFF message enable
        	 Bit 1  : Re-Trigger message enable
        	 Bit 0  : Alarm ON message enable"
    ::= { wtIpWatcher-24VAlarmEntry 46 }

    wtIpWatcher-24VAlarmSnmpTrapTrapTxEnable OBJECT-TYPE
    SYNTAX OCTET STRING 
    ACCESS read-write
    STATUS mandatory
    DESCRIPTION
        "Binary coded options:
        The OCTETS are interpreted bit-by-bit. 
        Bit 0 corresponds to the LSB.
        OCTET 1: unused
        OCTET 2: unused
        OCTET 3: unused
        OCTET 4, Bit 4-7: unused
        	 Bit 3  : Alarm OFF message enable
        	 Bit 2  : Trigger OFF message enable
        	 Bit 1  : Re-Trigger message enable
        	 Bit 0  : Alarm ON message enable"
    ::= { wtIpWatcher-24VAlarmEntry 47 }

    wtIpWatcher-24VAlarmUdpTrapTxEnable OBJECT-TYPE
    SYNTAX OCTET STRING 
    ACCESS read-write
    STATUS mandatory
    DESCRIPTION
        "Binary coded options:
        The OCTETS are interpreted bit-by-bit. 
        Bit 0 corresponds to the LSB.
        OCTET 1: unused
        OCTET 2: unused
        OCTET 3: unused
        OCTET 4, Bit 4-7: unused
        	 Bit 3  : Alarm OFF message enable
        	 Bit 2  : Trigger OFF message enable
        	 Bit 1  : Re-Trigger message enable
        	 Bit 0  : Alarm ON message enable"
    ::= { wtIpWatcher-24VAlarmEntry 48 }

    wtIpWatcher-24VAlarmTcpTrapTxEnable OBJECT-TYPE
    SYNTAX OCTET STRING 
    ACCESS read-write
    STATUS mandatory
    DESCRIPTION
        "Binary coded options:
        The OCTETS are interpreted bit-by-bit. 
        Bit 0 corresponds to the LSB.
        OCTET 1: unused
        OCTET 2: unused
        OCTET 3: unused
        OCTET 4, Bit 4-7: unused
        	 Bit 3  : Alarm OFF message enable
        	 Bit 2  : Trigger OFF message enable
        	 Bit 1  : Re-Trigger message enable
        	 Bit 0  : Alarm ON message enable"
    ::= { wtIpWatcher-24VAlarmEntry 49 }

    wtIpWatcher-24VAlarmSyslogTrapTxEnable OBJECT-TYPE
    SYNTAX OCTET STRING 
    ACCESS read-write
    STATUS mandatory
    DESCRIPTION
        "Binary coded options:
        The OCTETS are interpreted bit-by-bit. 
        Bit 0 corresponds to the LSB.
        OCTET 1: unused
        OCTET 2: unused
        OCTET 3: unused
        OCTET 4, Bit 4-7: unused
        	 Bit 3  : Alarm OFF message enable
        	 Bit 2  : Trigger OFF message enable
        	 Bit 1  : Re-Trigger message enable
        	 Bit 0  : Alarm ON message enable"
    ::= { wtIpWatcher-24VAlarmEntry 50 }

    wtIpWatcher-24VAlarmFtpTrapTxEnable OBJECT-TYPE
    SYNTAX OCTET STRING 
    ACCESS read-write
    STATUS mandatory
    DESCRIPTION
        "Binary coded options:
        The OCTETS are interpreted bit-by-bit. 
        Bit 0 corresponds to the LSB.
        OCTET 1: unused
        OCTET 2: unused
        OCTET 3: unused
        OCTET 4, Bit 4-7: unused
        	 Bit 3  : Alarm OFF message enable
        	 Bit 2  : Trigger OFF message enable
        	 Bit 1  : Re-Trigger message enable
        	 Bit 0  : Alarm ON message enable"
    ::= { wtIpWatcher-24VAlarmEntry 51 }
    
    wtIpWatcher-24VAlarmTriggerCount OBJECT-TYPE
    SYNTAX INTEGER 
    ACCESS read-write
    STATUS mandatory
    DESCRIPTION
        "Alarm will be send if the trigger condition occours TriggerCount times."
    ::= { wtIpWatcher-24VAlarmEntry 52 }

    wtIpWatcher-24VAlarmPollingRate OBJECT-TYPE
    SYNTAX INTEGER 
    ACCESS read-write
    STATUS mandatory
    DESCRIPTION
        "Time in seconds."
    ::= { wtIpWatcher-24VAlarmEntry 53 }

-- wtIpWatcher-24VPorts Group
----------------------------

-- Input Port Table

wtIpWatcher-24VInputPortTable OBJECT-TYPE
    SYNTAX SEQUENCE OF WtIpWatcher-24VInputPortEntry
    ACCESS not-accessible
    STATUS mandatory
    DESCRIPTION
        "List of settings depending on the input number."
    ::= { wtIpWatcher-24VPorts 1 }

wtIpWatcher-24VInputPortEntry OBJECT-TYPE
    SYNTAX WtIpWatcher-24VInputPortEntry
    ACCESS not-accessible
    STATUS mandatory
    DESCRIPTION
        "Input parameter for the individual inputs."
    INDEX  { wtIpWatcher-24VInputNo }
    ::= { wtIpWatcher-24VInputPortTable 1 }

WtIpWatcher-24VInputPortEntry ::= SEQUENCE {
    wtIpWatcher-24VPortInputName	OCTET STRING,
    wtIpWatcher-24VPortInputText	OCTET STRING,
    wtIpWatcher-24VPortInputFilter	INTEGER    
    }

wtIpWatcher-24VPortInputName OBJECT-TYPE
    SYNTAX OCTET STRING 
    ACCESS read-write
    STATUS mandatory
    DESCRIPTION
        "Name of the input."
    ::= { wtIpWatcher-24VInputPortEntry 1 }

wtIpWatcher-24VPortInputText OBJECT-TYPE
    SYNTAX OCTET STRING 
    ACCESS read-write
    STATUS mandatory
    DESCRIPTION
        "Description of the input."
    ::= { wtIpWatcher-24VInputPortEntry 2 }

wtIpWatcher-24VPortInputFilter OBJECT-TYPE
    SYNTAX INTEGER 
    ACCESS read-write
    STATUS mandatory
    DESCRIPTION
        "Pulses with a duration shorter than here specified (duration in 1/1000 sec),
	are ignored."
    ::= { wtIpWatcher-24VInputPortEntry 4 }
    
-- Output Port Table

wtIpWatcher-24VOutputPortTable OBJECT-TYPE
    SYNTAX SEQUENCE OF WtIpWatcher-24VOutputPortEntry
    ACCESS not-accessible
    STATUS mandatory
    DESCRIPTION
        "List of settings depending on the output number."
    ::= { wtIpWatcher-24VPorts 2 }

wtIpWatcher-24VOutputPortEntry OBJECT-TYPE
    SYNTAX WtIpWatcher-24VOutputPortEntry
    ACCESS not-accessible
    STATUS mandatory
    DESCRIPTION
        "Output parameters of the individual outputs."
    INDEX  { wtIpWatcher-24VOutputNo }
    ::= { wtIpWatcher-24VOutputPortTable 1 }

WtIpWatcher-24VOutputPortEntry ::= SEQUENCE {
    wtIpWatcher-24VPortOutputName		OCTET STRING,
    wtIpWatcher-24VPortOutputText		OCTET STRING,
    wtIpWatcher-24VPortPulseDuration		INTEGER,
    wtIpWatcher-24VPortPulsePolarity		OCTET STRING
    
}

wtIpWatcher-24VPortOutputName OBJECT-TYPE
    SYNTAX OCTET STRING 
    ACCESS read-write
    STATUS mandatory
    DESCRIPTION
        "Name of the output."
    ::= { wtIpWatcher-24VOutputPortEntry 1 }

wtIpWatcher-24VPortOutputText OBJECT-TYPE
    SYNTAX OCTET STRING 
    ACCESS read-write
    STATUS mandatory
    DESCRIPTION
        "Description of the output."
    ::= { wtIpWatcher-24VOutputPortEntry 2 }

wtIpWatcher-24VPortPulseDuration OBJECT-TYPE
    SYNTAX INTEGER
    ACCESS read-write
    STATUS mandatory
    DESCRIPTION
        "Pulse length in 1/1000 sec. Setting this value to zero, disables the pulse output."
    ::= { wtIpWatcher-24VOutputPortEntry 9 }

wtIpWatcher-24VPortPulsePolarity OBJECT-TYPE
    SYNTAX OCTET STRING (SIZE (4))
    ACCESS read-write
    STATUS mandatory
    DESCRIPTION
        "This value defines the polarity of the output pulse, if wtIpWatcher-24VPortPulseDuration is not set to zero.
        After the pulse is finished, the output switches back to the opposite state.
        OCTET 1: unused
        OCTET 2: unused
        OCTET 3: unused
        	OCTET 4: 
        	 Bit 0   : negative polarity
        	 Bit 1   : positive polarity
        	 Bit 2-7 : unused"
    ::= { wtIpWatcher-24VOutputPortEntry 10 }

-- wtIpWatcher-24VManufact Group
----------------------------

wtIpWatcher-24VMfName OBJECT-TYPE
    SYNTAX OCTET STRING 
    ACCESS read-write
    STATUS mandatory
    DESCRIPTION
        "Manufacturer company name"
    ::= { wtIpWatcher-24VManufact 1 }

wtIpWatcher-24VMfAddr OBJECT-TYPE
    SYNTAX OCTET STRING 
    ACCESS read-write
    STATUS mandatory
    DESCRIPTION
        "Manufacturer address."
    ::= { wtIpWatcher-24VManufact 2 }

wtIpWatcher-24VMfHotline OBJECT-TYPE
    SYNTAX OCTET STRING 
    ACCESS read-write
    STATUS mandatory
    DESCRIPTION
        "Manufacturer hotline."
    ::= { wtIpWatcher-24VManufact 3 }

wtIpWatcher-24VMfInternet OBJECT-TYPE
    SYNTAX OCTET STRING 
    ACCESS read-write
    STATUS mandatory
    DESCRIPTION
        "Manufacturer Internet address."
    ::= { wtIpWatcher-24VManufact 4 }

wtIpWatcher-24VMfDeviceTyp OBJECT-TYPE
    SYNTAX OCTET STRING 
    ACCESS read-write
    STATUS mandatory
    DESCRIPTION
        "Manufacturer device name (model number)."
    ::= { wtIpWatcher-24VManufact 5 }

-- wtIpWatcher-24VDiag Group
----------------------------

wtIpWatcher-24VDiagErrorCount OBJECT-TYPE
    SYNTAX INTEGER
    ACCESS read-only
    STATUS mandatory
    DESCRIPTION
        "Number of entries in the error memory."
    ::= { wtIpWatcher-24VDiag 1 }

wtIpWatcher-24VDiagBinaryError OBJECT-TYPE
    SYNTAX OCTET STRING 
    ACCESS read-only
    STATUS mandatory
    DESCRIPTION
        "Error causes coded bit-by-bit."
    ::= { wtIpWatcher-24VDiag 2 }

wtIpWatcher-24VDiagErrorIndex OBJECT-TYPE
    SYNTAX INTEGER
    ACCESS read-write
    STATUS mandatory
    DESCRIPTION
        "The value of this variable is used as an index to read 
        an error massege from wtIpWatcher-24VDiagErrorMessage.
        Errors are numbered from 1 to wtIpWatcher-24VDiagErrorCount.
        Writing a valid value into this variable, making the appropriate 
        message readable from wtIpWatcher-24VDiagErrorMessage."
    ::= { wtIpWatcher-24VDiag 3 }

wtIpWatcher-24VDiagErrorMessage OBJECT-TYPE
    SYNTAX OCTET STRING 
    ACCESS read-only
    STATUS mandatory
    DESCRIPTION
        "Using wtIpWatcher-24VDiagErrorIndex as an index, the appropriate message is available."
    ::= { wtIpWatcher-24VDiag 4 }
    
wtIpWatcher-24VDiagErrorClear OBJECT-TYPE
    SYNTAX INTEGER
    ACCESS write-only
    STATUS mandatory
    DESCRIPTION
        "Writing 1 into this variable clears all diagnosis messages."
    ::= { wtIpWatcher-24VDiag 5 }


-- TRAP DEFINITIONS

-- Diese SNMP-Traps werden gesendet, wenn die Alarmtriggerbedingungen zutreffen 

wtIpWatcher-24VAlert1 TRAP-TYPE
    ENTERPRISE  wtIpWatcher-24V
    VARIABLES   { wtIpWatcher-24VAlarmSnmpTrapText }
    DESCRIPTION
        "This SNMP trap is generated when Alarm 1 was triggered,
        SNMP trap enable is set and
        SNMP is enabled."
    -- NMS trap annotation
    --#TYPE "IP Watcher Alarm 1"
    --#SUMMARY "Alarm 1: %s"
    --#ARGUMENTS {0}
    --#SEVERITY INFORMATIONAL
    --#TIMEINDEX 99
    --#STATE OPERATIONAL    
    ::= 41

wtIpWatcher-24VAlert2 TRAP-TYPE
    ENTERPRISE  wtIpWatcher-24V
    VARIABLES   { wtIpWatcher-24VAlarmSnmpTrapText }
    DESCRIPTION
        "This SNMP trap is generated when Alarm 2 was triggered,
        SNMP trap enable is set and
        SNMP is enabled."
    -- NMS trap annotation
    --#TYPE "IP Watcher Alarm 2"
    --#SUMMARY "Alarm 2: %s"
    --#ARGUMENTS {0}
    --#SEVERITY INFORMATIONAL
    --#TIMEINDEX 99
    --#STATE OPERATIONAL    
    ::= 42

wtIpWatcher-24VAlert3 TRAP-TYPE
    ENTERPRISE  wtIpWatcher-24V
    VARIABLES   { wtIpWatcher-24VAlarmSnmpTrapText }
    DESCRIPTION
        "This SNMP trap is generated when Alarm 3 was triggered,
        SNMP trap enable is set and
        SNMP is enabled."
    -- NMS trap annotation
    --#TYPE "IP Watcher Alarm 3"
    --#SUMMARY "Alarm 3: %s"
    --#ARGUMENTS {0}
    --#SEVERITY INFORMATIONAL
    --#TIMEINDEX 99
    --#STATE OPERATIONAL    
    ::= 43

wtIpWatcher-24VAlert4 TRAP-TYPE
    ENTERPRISE  wtIpWatcher-24V
    VARIABLES   { wtIpWatcher-24VAlarmSnmpTrapText }
    DESCRIPTION
        "This SNMP trap is generated when Alarm 4 was triggered,
        SNMP trap enable is set and
        SNMP is enabled."
    -- NMS trap annotation
    --#TYPE "IP Watcher Alarm 4"
    --#SUMMARY "Alarm 4: %s"
    --#ARGUMENTS {0}
    --#SEVERITY INFORMATIONAL
    --#TIMEINDEX 99
    --#STATE OPERATIONAL    
    ::= 44

wtIpWatcher-24VAlert5 TRAP-TYPE
    ENTERPRISE  wtIpWatcher-24V
    VARIABLES   { wtIpWatcher-24VAlarmSnmpTrapText }
    DESCRIPTION
        "This SNMP trap is generated when Alarm 5 was triggered,
        SNMP trap enable is set and
        SNMP is enabled."
    -- NMS trap annotation
    --#TYPE "IP Watcher Alarm 5"
    --#SUMMARY "Alarm 5: %s"
    --#ARGUMENTS {0}
    --#SEVERITY INFORMATIONAL
    --#TIMEINDEX 99
    --#STATE OPERATIONAL    
    ::= 45

wtIpWatcher-24VAlert6 TRAP-TYPE
    ENTERPRISE  wtIpWatcher-24V
    VARIABLES   { wtIpWatcher-24VAlarmSnmpTrapText }
    DESCRIPTION
        "This SNMP trap is generated when Alarm 6 was triggered,
        SNMP trap enable is set and
        SNMP is enabled."
    -- NMS trap annotation
    --#TYPE "IP Watcher Alarm 6"
    --#SUMMARY "Alarm 6: %s"
    --#ARGUMENTS {0}
    --#SEVERITY INFORMATIONAL
    --#TIMEINDEX 99
    --#STATE OPERATIONAL    
    ::= 46

wtIpWatcher-24VAlert7 TRAP-TYPE
    ENTERPRISE  wtIpWatcher-24V
    VARIABLES   { wtIpWatcher-24VAlarmSnmpTrapText }
    DESCRIPTION
        "This SNMP trap is generated when Alarm 7 was triggered,
        SNMP trap enable is set and
        SNMP is enabled."
    -- NMS trap annotation
    --#TYPE "IP Watcher Alarm 7"
    --#SUMMARY "Alarm 7: %s"
    --#ARGUMENTS {0}
    --#SEVERITY INFORMATIONAL
    --#TIMEINDEX 99
    --#STATE OPERATIONAL    
    ::= 47

wtIpWatcher-24VAlert8 TRAP-TYPE
    ENTERPRISE  wtIpWatcher-24V
    VARIABLES   { wtIpWatcher-24VAlarmSnmpTrapText }
    DESCRIPTION
        "This SNMP trap is generated when Alarm 8 was triggered,
        SNMP trap enable is set and
        SNMP is enabled."
    -- NMS trap annotation
    --#TYPE "IP Watcher Alarm 8"
    --#SUMMARY "Alarm 8: %s"
    --#ARGUMENTS {0}
    --#SEVERITY INFORMATIONAL
    --#TIMEINDEX 99
    --#STATE OPERATIONAL    
    ::= 48

wtIpWatcher-24VAlert9 TRAP-TYPE
    ENTERPRISE  wtIpWatcher-24V
    VARIABLES   { wtIpWatcher-24VAlarmSnmpTrapText }
    DESCRIPTION
        "This SNMP trap is generated when Alarm 9 was triggered,
        SNMP trap enable is set and
        SNMP is enabled."
    -- NMS trap annotation
    --#TYPE "IP Watcher Alarm 9"
    --#SUMMARY "Alarm 9: %s"
    --#ARGUMENTS {0}
    --#SEVERITY INFORMATIONAL
    --#TIMEINDEX 99
    --#STATE OPERATIONAL    
    ::= 49

wtIpWatcher-24VAlert10 TRAP-TYPE
    ENTERPRISE  wtIpWatcher-24V
    VARIABLES   { wtIpWatcher-24VAlarmSnmpTrapText }
    DESCRIPTION
        "This SNMP trap is generated when Alarm 10 was triggered,
        SNMP trap enable is set and
        SNMP is enabled."
    -- NMS trap annotation
    --#TYPE "IP Watcher Alarm 10"
    --#SUMMARY "Alarm 10: %s"
    --#ARGUMENTS {0}
    --#SEVERITY INFORMATIONAL
    --#TIMEINDEX 99
    --#STATE OPERATIONAL    
    ::= 50

wtIpWatcher-24VAlert11 TRAP-TYPE
    ENTERPRISE  wtIpWatcher-24V
    VARIABLES   { wtIpWatcher-24VAlarmSnmpTrapText }
    DESCRIPTION
        "This SNMP trap is generated when Alarm 11 was triggered,
        SNMP trap enable is set and
        SNMP is enabled."
    -- NMS trap annotation
    --#TYPE "IP Watcher Alarm 11"
    --#SUMMARY "Alarm 11: %s"
    --#ARGUMENTS {0}
    --#SEVERITY INFORMATIONAL
    --#TIMEINDEX 99
    --#STATE OPERATIONAL    
    ::= 51

wtIpWatcher-24VAlert12 TRAP-TYPE
    ENTERPRISE  wtIpWatcher-24V
    VARIABLES   { wtIpWatcher-24VAlarmSnmpTrapText }
    DESCRIPTION
        "This SNMP trap is generated when Alarm 12 was triggered,
        SNMP trap enable is set and
        SNMP is enabled."
    -- NMS trap annotation
    --#TYPE "IP Watcher Alarm 12"
    --#SUMMARY "Alarm 12: %s"
    --#ARGUMENTS {0}
    --#SEVERITY INFORMATIONAL
    --#TIMEINDEX 99
    --#STATE OPERATIONAL    
    ::= 52

wtIpWatcher-24VAlert13 TRAP-TYPE
    ENTERPRISE  wtIpWatcher-24V
    VARIABLES   { wtIpWatcher-24VAlarmSnmpTrapReleaseText }
    DESCRIPTION
        "This SNMP trap is generated when Alarm 1 was released,
        SNMP trap enable is set and
        SNMP is enabled."
    -- NMS trap annotation
    --#TYPE "IP Watcher Release Alarm 1"
    --#SUMMARY "Release Alarm 1: %s"
    --#ARGUMENTS {0}
    --#SEVERITY INFORMATIONAL
    --#TIMEINDEX 99
    --#STATE OPERATIONAL    
    ::= 71

wtIpWatcher-24VAlert14 TRAP-TYPE
    ENTERPRISE  wtIpWatcher-24V
    VARIABLES   { wtIpWatcher-24VAlarmSnmpTrapReleaseText }
    DESCRIPTION
        "This SNMP trap is generated when Alarm 2 was released,
        SNMP trap enable is set and
        SNMP is enabled."
    -- NMS trap annotation
    --#TYPE "IP Watcher Release Alarm 2"
    --#SUMMARY "Release Alarm 2: %s"
    --#ARGUMENTS {0}
    --#SEVERITY INFORMATIONAL
    --#TIMEINDEX 99
    --#STATE OPERATIONAL    
    ::= 72

wtIpWatcher-24VAlert15 TRAP-TYPE
    ENTERPRISE  wtIpWatcher-24V
    VARIABLES   { wtIpWatcher-24VAlarmSnmpTrapReleaseText }
    DESCRIPTION
        "This SNMP trap is generated when Alarm 3 was released,
        SNMP trap enable is set and
        SNMP is enabled."
    -- NMS trap annotation
    --#TYPE "IP Watcher Release Alarm 3"
    --#SUMMARY "Release Alarm 3: %s"
    --#ARGUMENTS {0}
    --#SEVERITY INFORMATIONAL
    --#TIMEINDEX 99
    --#STATE OPERATIONAL    
    ::= 73

wtIpWatcher-24VAlert16 TRAP-TYPE
    ENTERPRISE  wtIpWatcher-24V
    VARIABLES   { wtIpWatcher-24VAlarmSnmpTrapReleaseText }
    DESCRIPTION
        "This SNMP trap is generated when Alarm 4 was released,
        SNMP trap enable is set and
        SNMP is enabled."
    -- NMS trap annotation
    --#TYPE "IP Watcher Release Alarm 4"
    --#SUMMARY "Release Alarm 4: %s"
    --#ARGUMENTS {0}
    --#SEVERITY INFORMATIONAL
    --#TIMEINDEX 99
    --#STATE OPERATIONAL    
    ::= 74

wtIpWatcher-24VAlert17 TRAP-TYPE
    ENTERPRISE  wtIpWatcher-24V
    VARIABLES   { wtIpWatcher-24VAlarmSnmpTrapReleaseText }
    DESCRIPTION
        "This SNMP trap is generated when Alarm 5 was released,
        SNMP trap enable is set and
        SNMP is enabled."
    -- NMS trap annotation
    --#TYPE "IP Watcher Release Alarm 5"
    --#SUMMARY "Release Alarm 5: %s"
    --#ARGUMENTS {0}
    --#SEVERITY INFORMATIONAL
    --#TIMEINDEX 99
    --#STATE OPERATIONAL    
    ::= 75

wtIpWatcher-24VAlert18 TRAP-TYPE
    ENTERPRISE  wtIpWatcher-24V
    VARIABLES   { wtIpWatcher-24VAlarmSnmpTrapReleaseText }
    DESCRIPTION
        "This SNMP trap is generated when Alarm 6 was released,
        SNMP trap enable is set and
        SNMP is enabled."
    -- NMS trap annotation
    --#TYPE "IP Watcher Release Alarm 6"
    --#SUMMARY "Release Alarm 6: %s"
    --#ARGUMENTS {0}
    --#SEVERITY INFORMATIONAL
    --#TIMEINDEX 99
    --#STATE OPERATIONAL    
    ::= 76

wtIpWatcher-24VAlert19 TRAP-TYPE
    ENTERPRISE  wtIpWatcher-24V
    VARIABLES   { wtIpWatcher-24VAlarmSnmpTrapReleaseText }
    DESCRIPTION
        "This SNMP trap is generated when Alarm 7 was released,
        SNMP trap enable is set and
        SNMP is enabled."
    -- NMS trap annotation
    --#TYPE "IP Watcher Release Alarm 7"
    --#SUMMARY "Release Alarm 7: %s"
    --#ARGUMENTS {0}
    --#SEVERITY INFORMATIONAL
    --#TIMEINDEX 99
    --#STATE OPERATIONAL    
    ::= 77

wtIpWatcher-24VAlert20 TRAP-TYPE
    ENTERPRISE  wtIpWatcher-24V
    VARIABLES   { wtIpWatcher-24VAlarmSnmpTrapReleaseText }
    DESCRIPTION
        "This SNMP trap is generated when Alarm 8 was released,
        SNMP trap enable is set and
        SNMP is enabled."
    -- NMS trap annotation
    --#TYPE "IP Watcher Release Alarm 8"
    --#SUMMARY "Release Alarm 8: %s"
    --#ARGUMENTS {0}
    --#SEVERITY INFORMATIONAL
    --#TIMEINDEX 99
    --#STATE OPERATIONAL    
    ::= 78

wtIpWatcher-24VAlert21 TRAP-TYPE
    ENTERPRISE  wtIpWatcher-24V
    VARIABLES   { wtIpWatcher-24VAlarmSnmpTrapReleaseText }
    DESCRIPTION
        "This SNMP trap is generated when Alarm 9 was released,
        SNMP trap enable is set and
        SNMP is enabled."
    -- NMS trap annotation
    --#TYPE "IP Watcher Release Alarm 9"
    --#SUMMARY "Release Alarm 9: %s"
    --#ARGUMENTS {0}
    --#SEVERITY INFORMATIONAL
    --#TIMEINDEX 99
    --#STATE OPERATIONAL    
    ::= 79

wtIpWatcher-24VAlert22 TRAP-TYPE
    ENTERPRISE  wtIpWatcher-24V
    VARIABLES   { wtIpWatcher-24VAlarmSnmpTrapReleaseText }
    DESCRIPTION
        "This SNMP trap is generated when Alarm 10 was released,
        SNMP trap enable is set and
        SNMP is enabled."
    -- NMS trap annotation
    --#TYPE "IP Watcher Release Alarm 10"
    --#SUMMARY "Release Alarm 10: %s"
    --#ARGUMENTS {0}
    --#SEVERITY INFORMATIONAL
    --#TIMEINDEX 99
    --#STATE OPERATIONAL    
    ::= 80

wtIpWatcher-24VAlert23 TRAP-TYPE
    ENTERPRISE  wtIpWatcher-24V
    VARIABLES   { wtIpWatcher-24VAlarmSnmpTrapReleaseText }
    DESCRIPTION
        "This SNMP trap is generated when Alarm 11 was released,
        SNMP trap enable is set and
        SNMP is enabled."
    -- NMS trap annotation
    --#TYPE "IP Watcher Release Alarm 11"
    --#SUMMARY "Release Alarm 11: %s"
    --#ARGUMENTS {0}
    --#SEVERITY INFORMATIONAL
    --#TIMEINDEX 99
    --#STATE OPERATIONAL    
    ::= 81

wtIpWatcher-24VAlert24 TRAP-TYPE
    ENTERPRISE  wtIpWatcher-24V
    VARIABLES   { wtIpWatcher-24VAlarmSnmpTrapReleaseText }
    DESCRIPTION
        "This SNMP trap is generated when Alarm 12 was released,
        SNMP trap enable is set and
        SNMP is enabled."
    -- NMS trap annotation
    --#TYPE "IP Watcher Release Alarm 12"
    --#SUMMARY "Release Alarm 12: %s"
    --#ARGUMENTS {0}
    --#SEVERITY INFORMATIONAL
    --#TIMEINDEX 99
    --#STATE OPERATIONAL    
    ::= 82

wtIpWatcher-24VAlert25 TRAP-TYPE
    ENTERPRISE  wtIpWatcher-24V
    VARIABLES   { wtIpWatcher-24VAlarmSnmpTrapTrgClearText }
    DESCRIPTION
        "This SNMP trap is generated when the trigger of the Alarm 1 was released,
        SNMP trap enable is set and
        SNMP is enabled."
    -- NMS trap annotation
    --#TYPE "IP Watcher Alarm 1"
    --#SUMMARY "Alarm 1: %s"
    --#ARGUMENTS {0}
    --#SEVERITY INFORMATIONAL
    --#TIMEINDEX 99
    --#STATE OPERATIONAL    
    ::= 91

wtIpWatcher-24VAlert26 TRAP-TYPE
    ENTERPRISE  wtIpWatcher-24V
    VARIABLES   { wtIpWatcher-24VAlarmSnmpTrapTrgClearText }
    DESCRIPTION
        "This SNMP trap is generated when the trigger of the Alarm 2 was released,
        SNMP trap enable is set and
        SNMP is enabled."
    -- NMS trap annotation
    --#TYPE "IP Watcher Alarm 2"
    --#SUMMARY "Release Alarm 2: %s"
    --#ARGUMENTS {0}
    --#SEVERITY INFORMATIONAL
    --#TIMEINDEX 99
    --#STATE OPERATIONAL    
    ::= 92

wtIpWatcher-24VAlert27 TRAP-TYPE
    ENTERPRISE  wtIpWatcher-24V
    VARIABLES   { wtIpWatcher-24VAlarmSnmpTrapTrgClearText }
    DESCRIPTION
        "This SNMP trap is generated when the trigger of the Alarm 3 was released,
        SNMP trap enable is set and
        SNMP is enabled."
    -- NMS trap annotation
    --#TYPE "IP Watcher Alarm 3"
    --#SUMMARY "Release Alarm 3: %s"
    --#ARGUMENTS {0}
    --#SEVERITY INFORMATIONAL
    --#TIMEINDEX 99
    --#STATE OPERATIONAL    
    ::= 93

wtIpWatcher-24VAlert28 TRAP-TYPE
    ENTERPRISE  wtIpWatcher-24V
    VARIABLES   { wtIpWatcher-24VAlarmSnmpTrapTrgClearText }
    DESCRIPTION
        "This SNMP trap is generated when the trigger of the Alarm 4 was released,
        SNMP trap enable is set and
        SNMP is enabled."
    -- NMS trap annotation
    --#TYPE "IP Watcher Alarm 4"
    --#SUMMARY "Release Alarm 4: %s"
    --#ARGUMENTS {0}
    --#SEVERITY INFORMATIONAL
    --#TIMEINDEX 99
    --#STATE OPERATIONAL    
    ::= 94

wtIpWatcher-24VAlert29 TRAP-TYPE
    ENTERPRISE  wtIpWatcher-24V
    VARIABLES   { wtIpWatcher-24VAlarmSnmpTrapTrgClearText }
    DESCRIPTION
        "This SNMP trap is generated when the trigger of the Alarm 5 was released,
        SNMP trap enable is set and
        SNMP is enabled."
    -- NMS trap annotation
    --#TYPE "IP Watcher Alarm 5"
    --#SUMMARY "Release Alarm 5: %s"
    --#ARGUMENTS {0}
    --#SEVERITY INFORMATIONAL
    --#TIMEINDEX 99
    --#STATE OPERATIONAL    
    ::= 95

wtIpWatcher-24VAlert30 TRAP-TYPE
    ENTERPRISE  wtIpWatcher-24V
    VARIABLES   { wtIpWatcher-24VAlarmSnmpTrapTrgClearText }
    DESCRIPTION
        "This SNMP trap is generated when the trigger of the Alarm 6 was released,
        SNMP trap enable is set and
        SNMP is enabled."
    -- NMS trap annotation
    --#TYPE "IP Watcher Alarm 6"
    --#SUMMARY "Release Alarm 6: %s"
    --#ARGUMENTS {0}
    --#SEVERITY INFORMATIONAL
    --#TIMEINDEX 99
    --#STATE OPERATIONAL    
    ::= 96

wtIpWatcher-24VAlert31 TRAP-TYPE
    ENTERPRISE  wtIpWatcher-24V
    VARIABLES   { wtIpWatcher-24VAlarmSnmpTrapTrgClearText }
    DESCRIPTION
        "This SNMP trap is generated when the trigger of the Alarm 7 was released,
        SNMP trap enable is set and
        SNMP is enabled."
    -- NMS trap annotation
    --#TYPE "IP Watcher Alarm 7"
    --#SUMMARY "Release Alarm 7: %s"
    --#ARGUMENTS {0}
    --#SEVERITY INFORMATIONAL
    --#TIMEINDEX 99
    --#STATE OPERATIONAL    
    ::= 97

wtIpWatcher-24VAlert32 TRAP-TYPE
    ENTERPRISE  wtIpWatcher-24V
    VARIABLES   { wtIpWatcher-24VAlarmSnmpTrapTrgClearText }
    DESCRIPTION
        "This SNMP trap is generated when the trigger of the Alarm 8 was released,
        SNMP trap enable is set and
        SNMP is enabled."
    -- NMS trap annotation
    --#TYPE "IP Watcher Alarm 8"
    --#SUMMARY "Release Alarm 8: %s"
    --#ARGUMENTS {0}
    --#SEVERITY INFORMATIONAL
    --#TIMEINDEX 99
    --#STATE OPERATIONAL    
    ::= 98

wtIpWatcher-24VAlert33 TRAP-TYPE
    ENTERPRISE  wtIpWatcher-24V
    VARIABLES   { wtIpWatcher-24VAlarmSnmpTrapTrgClearText }
    DESCRIPTION
        "This SNMP trap is generated when the trigger of the Alarm 9 was released,
        SNMP trap enable is set and
        SNMP is enabled."
    -- NMS trap annotation
    --#TYPE "IP Watcher Alarm 9"
    --#SUMMARY "Release Alarm 9: %s"
    --#ARGUMENTS {0}
    --#SEVERITY INFORMATIONAL
    --#TIMEINDEX 99
    --#STATE OPERATIONAL    
    ::= 99

wtIpWatcher-24VAlert34 TRAP-TYPE
    ENTERPRISE  wtIpWatcher-24V
    VARIABLES   { wtIpWatcher-24VAlarmSnmpTrapTrgClearText }
    DESCRIPTION
        "This SNMP trap is generated when the trigger of the Alarm 10 was released,
        SNMP trap enable is set and
        SNMP is enabled."
    -- NMS trap annotation
    --#TYPE "IP Watcher Alarm 10"
    --#SUMMARY "Release Alarm 10: %s"
    --#ARGUMENTS {0}
    --#SEVERITY INFORMATIONAL
    --#TIMEINDEX 99
    --#STATE OPERATIONAL    
    ::= 100

wtIpWatcher-24VAlert35 TRAP-TYPE
    ENTERPRISE  wtIpWatcher-24V
    VARIABLES   { wtIpWatcher-24VAlarmSnmpTrapTrgClearText }
    DESCRIPTION
        "This SNMP trap is generated when the trigger of the Alarm 11 was released,
        SNMP trap enable is set and
        SNMP is enabled."
    -- NMS trap annotation
    --#TYPE "IP Watcher Alarm 11"
    --#SUMMARY "Release Alarm 11: %s"
    --#ARGUMENTS {0}
    --#SEVERITY INFORMATIONAL
    --#TIMEINDEX 99
    --#STATE OPERATIONAL    
    ::= 101

wtIpWatcher-24VAlert36 TRAP-TYPE
    ENTERPRISE  wtIpWatcher-24V
    VARIABLES   { wtIpWatcher-24VAlarmSnmpTrapTrgClearText }
    DESCRIPTION
        "This SNMP trap is generated when the trigger of the Alarm 12 was released,
        SNMP trap enable is set and
        SNMP is enabled."
    -- NMS trap annotation
    --#TYPE "IP Watcher Alarm 12"
    --#SUMMARY "Release Alarm 12: %s"
    --#ARGUMENTS {0}
    --#SEVERITY INFORMATIONAL
    --#TIMEINDEX 99
    --#STATE OPERATIONAL    
    ::= 102

wtIpWatcher-24VAlertDiag TRAP-TYPE
    ENTERPRISE  wtIpWatcher-24V
    VARIABLES   { 	
    		wtIpWatcher-24VDiagErrorIndex,
    	  	wtIpWatcher-24VDiagErrorMessage
    		}
    DESCRIPTION
        "This SNMP trap is generated when a diagnosis/error message was triggered,
        SNMP trap enable is set and
        SNMP is enabled."
    -- NMS trap annotation
    --#TYPE "IP Watcher Diagnose Error"
    --#SUMMARY "Diagnose error index: %d, Message: %s."
    --#ARGUMENTS {0,1}
    --#SEVERITY MAJOR
    --#TIMEINDEX 99
    --#STATE DEGRADED    
    ::= 110

--------------------------------------------------------------------------------
--------------------------------------------------------------------------------
--------------------------------------------------------------------------------

-- wtTrapReceiver2x2InOut Group
------------------------

wtTrapReceiver2x2Inputs OBJECT-TYPE
    SYNTAX INTEGER (1..2)
    ACCESS read-only
    STATUS mandatory
    DESCRIPTION
        "Number of idependent inputs."
    ::= { wtTrapReceiver2x2InOut 1 }

wtTrapReceiver2x2Outputs OBJECT-TYPE
    SYNTAX INTEGER (1..2)
    ACCESS read-only
    STATUS mandatory
    DESCRIPTION
        "Number of idependent outputs."
    ::= { wtTrapReceiver2x2InOut 2 }

-- Input Interface Table

wtTrapReceiver2x2InputTable OBJECT-TYPE
    SYNTAX SEQUENCE OF WtTrapReceiver2x2InputEntry
    ACCESS not-accessible
    STATUS mandatory
    DESCRIPTION
        "List of input indices."
    ::= { wtTrapReceiver2x2InOut 3 }

wtTrapReceiver2x2InputEntry OBJECT-TYPE
    SYNTAX WtTrapReceiver2x2InputEntry
    ACCESS not-accessible
    STATUS mandatory
    DESCRIPTION
        "Number of the inputs."
    INDEX  { wtTrapReceiver2x2InputNo }
    ::= { wtTrapReceiver2x2InputTable 1 }

WtTrapReceiver2x2InputEntry ::= SEQUENCE {
    wtTrapReceiver2x2InputNo 		INTEGER,
    wtTrapReceiver2x2InputState 	INTEGER
    
}

wtTrapReceiver2x2InputNo OBJECT-TYPE
    SYNTAX INTEGER (1)
    ACCESS read-only
    STATUS mandatory
    DESCRIPTION
        "Index numbers of the inputs."
    ::= { wtTrapReceiver2x2InputEntry 1 }

wtTrapReceiver2x2InputState OBJECT-TYPE
    SYNTAX INTEGER{
    wtTrapReceiver2x2InputState-OFF(0),
    wtTrapReceiver2x2InputState-ON(1)
    }
    ACCESS read-only
    STATUS mandatory
    DESCRIPTION
        "Value of a single input bit."
    ::= { wtTrapReceiver2x2InputEntry 4 }    
    
wtTrapReceiver2x2InputValue OBJECT-TYPE
    SYNTAX INTEGER 
    ACCESS read-only
    STATUS mandatory
    DESCRIPTION
        "This variable is used to read the inputs of the digital I/O port.
        The OCTETS are interpreted bit-by-bit, with each bit corresponding to an output.
        Bit 0 corresponds to the LSB.
        OCTET 1: unused
        OCTET 2: unused
        OCTET 3: unused
        OCTET 4, Bit 0-1: Digital outputs 0-1"
    ::= { wtTrapReceiver2x2InOut 4 }
    

-- Output Interface Table

wtTrapReceiver2x2OutputTable OBJECT-TYPE
    SYNTAX SEQUENCE OF WtTrapReceiver2x2OutputEntry
    ACCESS not-accessible
    STATUS mandatory
    DESCRIPTION
        "List of output indices."
    ::= { wtTrapReceiver2x2InOut 5 }

wtTrapReceiver2x2OutputEntry OBJECT-TYPE
    SYNTAX WtTrapReceiver2x2OutputEntry
    ACCESS not-accessible
    STATUS mandatory
    DESCRIPTION
        "Number of the outputs."
    INDEX  { wtTrapReceiver2x2OutputNo }
    ::= { wtTrapReceiver2x2OutputTable 1 }

WtTrapReceiver2x2OutputEntry ::= SEQUENCE {
    wtTrapReceiver2x2OutputNo 		INTEGER,
    wtTrapReceiver2x2OutputState 	INTEGER    
}

wtTrapReceiver2x2OutputNo OBJECT-TYPE
    SYNTAX INTEGER (1)
    ACCESS read-only
    STATUS mandatory
    DESCRIPTION
        "Output number."
    ::= { wtTrapReceiver2x2OutputEntry 1 }

wtTrapReceiver2x2OutputState OBJECT-TYPE
    SYNTAX INTEGER{
    wtTrapReceiver2x2OutputState-OFF(0),
    wtTrapReceiver2x2OutputState-ON(1)
    }
    ACCESS read-write
    STATUS mandatory
    DESCRIPTION
        "Value of a single output bit."
    ::= { wtTrapReceiver2x2OutputEntry 2 }
    

wtTrapReceiver2x2OutputValue OBJECT-TYPE
    SYNTAX INTEGER
    ACCESS read-only
    STATUS mandatory
    DESCRIPTION
        "This variable is used to read  the outputs of the digital I/O port. 
        The OCTETS are interpreted bit-by-bit, with each bit corresponding to an output. 
        Bit 0 corresponds to the LSB.
        OCTET 1: unused
        OCTET 2: unused
        OCTET 3: unused
        OCTET 4, Bit 0-1: Digital outputs 0-1
        	 Bit 2-7: ungenutzt"
    ::= { wtTrapReceiver2x2InOut 6 }
    
-- Action Output Interface Table

wtTrapReceiver2x2ActionOutputTable OBJECT-TYPE
    SYNTAX SEQUENCE OF WtTrapReceiver2x2ActionOutputEntry
    ACCESS not-accessible
    STATUS mandatory
    DESCRIPTION
        "List of alarm indices.."
    ::= { wtTrapReceiver2x2InOut 8 }

wtTrapReceiver2x2ActionOutputEntry OBJECT-TYPE
    SYNTAX WtTrapReceiver2x2ActionOutputEntry
    ACCESS not-accessible
    STATUS mandatory
    DESCRIPTION
        "Index reference."
    INDEX  { wtTrapReceiver2x2ActionNo }
    ::= { wtTrapReceiver2x2ActionOutputTable 1 }

WtTrapReceiver2x2ActionOutputEntry ::= SEQUENCE {
    wtTrapReceiver2x2ActionOutputState	INTEGER,
    wtTrapReceiver2x2ActionTriggerState	INTEGER
}

wtTrapReceiver2x2ActionOutputState OBJECT-TYPE
    SYNTAX INTEGER{
    wtTrapReceiver2x2ActionOutputState-OFF(0),
    wtTrapReceiver2x2ActionOutputState-ON(1)
    }
    ACCESS read-write
    STATUS mandatory
    DESCRIPTION
        "State of the alarm."
    ::= { wtTrapReceiver2x2ActionOutputEntry 1 }

wtTrapReceiver2x2ActionTriggerState OBJECT-TYPE
    SYNTAX INTEGER{
    wtTrapReceiver2x2ActionTriggerState-OFF(0),
    wtTrapReceiver2x2ActionTriggerState-ON(1)
    }
    ACCESS read-only
    STATUS mandatory
    DESCRIPTION
        "State of the trigger condition."
    ::= { wtTrapReceiver2x2ActionOutputEntry 2 }    
        
-- SystemTimer Interface Table

wtTrapReceiver2x2SystemTimerTable OBJECT-TYPE
    SYNTAX SEQUENCE OF WtTrapReceiver2x2SystemTimerEntry
    ACCESS not-accessible
    STATUS mandatory
    DESCRIPTION
        "List of system timer."
    ::= { wtTrapReceiver2x2InOut 9 }

wtTrapReceiver2x2SystemTimerEntry OBJECT-TYPE
    SYNTAX WtTrapReceiver2x2SystemTimerEntry
    ACCESS not-accessible
    STATUS mandatory
    DESCRIPTION
        "Number of the system timer."
    INDEX  { wtTrapReceiver2x2SystemTimerNo }
    ::= { wtTrapReceiver2x2SystemTimerTable 1 }

WtTrapReceiver2x2SystemTimerEntry ::= SEQUENCE {
    wtTrapReceiver2x2SystemTimerNo 			INTEGER
    
}

wtTrapReceiver2x2SystemTimerNo OBJECT-TYPE
    SYNTAX INTEGER
    ACCESS read-only
    STATUS mandatory
    DESCRIPTION
        "Index number of the system timer."
    ::= { wtTrapReceiver2x2SystemTimerEntry 1 }
        
-- Button Interface Table

wtTrapReceiver2x2ButtonTable OBJECT-TYPE
    SYNTAX SEQUENCE OF WtTrapReceiver2x2ButtonEntry
    ACCESS not-accessible
    STATUS mandatory
    DESCRIPTION
        "List of buttons."
    ::= { wtTrapReceiver2x2InOut 10 }

wtTrapReceiver2x2ButtonEntry OBJECT-TYPE
    SYNTAX WtTrapReceiver2x2ButtonEntry
    ACCESS not-accessible
    STATUS mandatory
    DESCRIPTION
        "Number of the button."
    INDEX  { wtTrapReceiver2x2ButtonNo }
    ::= { wtTrapReceiver2x2ButtonTable 1 }

WtTrapReceiver2x2ButtonEntry ::= SEQUENCE {
    wtTrapReceiver2x2ButtonNo 			INTEGER
    
}

wtTrapReceiver2x2ButtonNo OBJECT-TYPE
    SYNTAX INTEGER
    ACCESS read-only
    STATUS mandatory
    DESCRIPTION
        "Index numder of the button."
    ::= { wtTrapReceiver2x2ButtonEntry 1 }
            
        
-- wtTrapReceiver2x2SessCntrl Group
--------------------------------

wtTrapReceiver2x2SessCntrlPassword OBJECT-TYPE
    SYNTAX OCTET STRING 
    ACCESS read-write
    STATUS mandatory
    DESCRIPTION
        "Entering this password opens a session which is ended by writing a 1 to 
        wtTrapReceiver2x2SessCntrlLogout. When read this variable provides a string of
        length zero."
    ::= { wtTrapReceiver2x2SessCntrl 1 }

wtTrapReceiver2x2SessCntrlConfigMode OBJECT-TYPE
    SYNTAX INTEGER {
    wtTrapReceiver2x2SessCntrl-NoSession(0),
    wtTrapReceiver2x2SessCntrl-Session(1)
    }
    ACCESS read-only
    STATUS mandatory
    DESCRIPTION
        "When the device is in SNMP configuration mode, the value 1 is
        returned, otherwise 0. If the read value is 0 even though the password
        was written, the device is already in config mode and the variables
        can only be read."
    ::= { wtTrapReceiver2x2SessCntrl 2 }

wtTrapReceiver2x2SessCntrlLogout OBJECT-TYPE
    SYNTAX INTEGER 
    ACCESS read-write
    STATUS mandatory
    DESCRIPTION
        "If the device is in configuration mode and the session was opened by
        this SNMP Manager, writing a 1 to this variable will end the session 
        and all parameters are stored.
        Writing a 2 discards all entries again. When read this variable
        provides the value 0."
    ::= { wtTrapReceiver2x2SessCntrl 3 }

wtTrapReceiver2x2SessCntrlAdminPassword OBJECT-TYPE
    SYNTAX OCTET STRING 
    ACCESS read-write
    STATUS mandatory
    DESCRIPTION
        "This password protects access to the variables with administrator rights.
        It can only be changed by the administrator. If no password was assigned,
        the valid password is public."
    ::= { wtTrapReceiver2x2SessCntrl 4 }

wtTrapReceiver2x2SessCntrlConfigPassword OBJECT-TYPE
    SYNTAX OCTET STRING 
    ACCESS read-write
    STATUS mandatory
    DESCRIPTION
        "This password protects access to the variables with configurator rights. It can
        be changed by the administrator and by the configurator. If no password was assigned, 
        the valid password is public. When read this variable provides a null-pointer."
    ::= { wtTrapReceiver2x2SessCntrl 5 }
    
-- wtTrapReceiver2x2Text Group
------------------------

wtTrapReceiver2x2DeviceName OBJECT-TYPE
    SYNTAX OCTET STRING 
    ACCESS read-write
    STATUS mandatory
    DESCRIPTION
        "Name of the Webio, which is user definable."
    ::= { wtTrapReceiver2x2Text 1 }

wtTrapReceiver2x2DeviceText OBJECT-TYPE
    SYNTAX OCTET STRING 
    ACCESS read-write
    STATUS mandatory
    DESCRIPTION
        "Description of the Webio, which is user definable."
    ::= { wtTrapReceiver2x2Text 2 }
    
wtTrapReceiver2x2DeviceLocation OBJECT-TYPE
    SYNTAX OCTET STRING 
    ACCESS read-write
    STATUS mandatory
    DESCRIPTION
        "Description of the location of the Webio, which is user definable."
    ::= { wtTrapReceiver2x2Text 3 }

wtTrapReceiver2x2DeviceContact OBJECT-TYPE
    SYNTAX OCTET STRING 
    ACCESS read-write
    STATUS mandatory
    DESCRIPTION
        "Contact address of the system operator of the Webio, which is user definable."
    ::= { wtTrapReceiver2x2Text 4 }    

-- wtTrapReceiver2x2TimeZone Group
----------------------------

wtTrapReceiver2x2TzOffsetHrs OBJECT-TYPE
    SYNTAX INTEGER 
    ACCESS read-write
    STATUS mandatory
    DESCRIPTION
        "Offset hours for the time zone (winter time) with respect to UTC."
    ::= { wtTrapReceiver2x2TimeZone 1 }

wtTrapReceiver2x2TzOffsetMin OBJECT-TYPE
    SYNTAX INTEGER 
    ACCESS read-write
    STATUS mandatory
    DESCRIPTION
        "Offset minutes for the time zone (winter time) with respect to UTC."
    ::= { wtTrapReceiver2x2TimeZone 2 }

wtTrapReceiver2x2TzEnable OBJECT-TYPE
    SYNTAX OCTET STRING (SIZE(4))
    ACCESS read-write
    STATUS mandatory
    DESCRIPTION
        "Binary coded conditions:
        Octet 1: unused
        Octet 2: unused
        Octet 3: unused
        Octet 4:
        	Bit 1-7: unused
	        Bit 0  : Apply Timezone"
    ::= { wtTrapReceiver2x2TimeZone 3 }

wtTrapReceiver2x2StTzOffsetHrs OBJECT-TYPE
    SYNTAX INTEGER 
    ACCESS read-write
    STATUS mandatory
    DESCRIPTION
        "Offset hours of the time zone (summer time) with respect to UTC."
    ::= { wtTrapReceiver2x2TimeZone 4 }

wtTrapReceiver2x2StTzOffsetMin OBJECT-TYPE
    SYNTAX INTEGER 
    ACCESS read-write
    STATUS mandatory
    DESCRIPTION
        "Offset minutes of the time zone (summer time) with respect to UTC."
    ::= { wtTrapReceiver2x2TimeZone 5 }

wtTrapReceiver2x2StTzEnable OBJECT-TYPE
    SYNTAX OCTET STRING (SIZE(4))
    ACCESS read-write
    STATUS mandatory
    DESCRIPTION
        "Binary coded conditions:
        Octet 1: unused
        Octet 2: unused
        Octet 3: unused
        Octet 4:
        	Bit 1-7: unused
	        Bit 0  : Apply Summertime"
    ::= { wtTrapReceiver2x2TimeZone 6 }

wtTrapReceiver2x2StTzStartMonth OBJECT-TYPE
    SYNTAX INTEGER {
    	wtTrapReceiver2x2StartMonth-January(1),
    	wtTrapReceiver2x2StartMonth-February(2),
    	wtTrapReceiver2x2StartMonth-March(3),
    	wtTrapReceiver2x2StartMonth-April(4),
    	wtTrapReceiver2x2StartMonth-May(5),
    	wtTrapReceiver2x2StartMonth-June(6),
    	wtTrapReceiver2x2StartMonth-July(7),
    	wtTrapReceiver2x2StartMonth-August(8),
    	wtTrapReceiver2x2StartMonth-September(9),
    	wtTrapReceiver2x2StartMonth-October(10),
    	wtTrapReceiver2x2StartMonth-November(11),
    	wtTrapReceiver2x2StartMonth-December(12)
    	}
    	
    ACCESS read-write
    STATUS mandatory
    DESCRIPTION
        "Month in which the change is made from winter time to summer time."
    ::= { wtTrapReceiver2x2TimeZone 7 }

wtTrapReceiver2x2StTzStartMode OBJECT-TYPE
    SYNTAX INTEGER {
    	wtTrapReceiver2x2StartMode-first(1),
    	wtTrapReceiver2x2StartMode-second(2),
    	wtTrapReceiver2x2StartMode-third(3),
    	wtTrapReceiver2x2StartMode-fourth(4),
    	wtTrapReceiver2x2StartMode-last(5)
    	}
    	
    ACCESS read-write
    STATUS mandatory
    DESCRIPTION
        "Mode of the day of the week for which the change is made from winter time to summer time."
    ::= { wtTrapReceiver2x2TimeZone 8 }

wtTrapReceiver2x2StTzStartWday OBJECT-TYPE
    SYNTAX INTEGER {
    	wtTrapReceiver2x2StartWday-Sunday(1),
    	wtTrapReceiver2x2StartWday-Monday(2),
    	wtTrapReceiver2x2StartWday-Tuesday(3),
    	wtTrapReceiver2x2StartWday-Thursday(4),
    	wtTrapReceiver2x2StartWday-Wednesday(5),
    	wtTrapReceiver2x2StartWday-Friday(6),
    	wtTrapReceiver2x2StartWday-Saturday(7)
    	}
    	
    ACCESS read-write
    STATUS mandatory
    DESCRIPTION
        "Day of the week on which the change is made from winter time to summer time"
    ::= { wtTrapReceiver2x2TimeZone 9 }
    
wtTrapReceiver2x2StTzStartHrs OBJECT-TYPE
    SYNTAX INTEGER 
    ACCESS read-write
    STATUS mandatory
    DESCRIPTION
        "Hour in which the time zone is changed from winter to summer time with
        respect to UTC."
    ::= { wtTrapReceiver2x2TimeZone 10 }

wtTrapReceiver2x2StTzStartMin OBJECT-TYPE
    SYNTAX INTEGER 
    ACCESS read-write
    STATUS mandatory
    DESCRIPTION
        "Minute in which the time zone is changed from winter to summer time with
        respect to UTC."
    ::= { wtTrapReceiver2x2TimeZone 11 }
 
wtTrapReceiver2x2StTzStopMonth OBJECT-TYPE
    SYNTAX INTEGER {
    	wtTrapReceiver2x2StopMonth-January(1),
    	wtTrapReceiver2x2StopMonth-February(2),
    	wtTrapReceiver2x2StopMonth-March(3),
    	wtTrapReceiver2x2StopMonth-April(4),
    	wtTrapReceiver2x2StopMonth-May(5),
    	wtTrapReceiver2x2StopMonth-June(6),
    	wtTrapReceiver2x2StopMonth-July(7),
    	wtTrapReceiver2x2StopMonth-August(8),
    	wtTrapReceiver2x2StopMonth-September(9),
    	wtTrapReceiver2x2StopMonth-October(10),
    	wtTrapReceiver2x2StopMonth-November(11),
    	wtTrapReceiver2x2StopMonth-December(12)
    	}
    ACCESS read-write
    STATUS mandatory
    DESCRIPTION
        "Month in which the change is made from summer time to winter time."
   ::= { wtTrapReceiver2x2TimeZone 12 }

wtTrapReceiver2x2StTzStopMode OBJECT-TYPE
    SYNTAX INTEGER {
    	wtTrapReceiver2x2StopMode-first(1),
    	wtTrapReceiver2x2StopMode-second(2),
    	wtTrapReceiver2x2StopMode-third(3),
    	wtTrapReceiver2x2StopMode-fourth(4),
    	wtTrapReceiver2x2StopMode-last(5)
    	}
    ACCESS read-write
    STATUS mandatory
    DESCRIPTION
        "Mode of the week day on which the change is made from summer time to winter time."
    ::= { wtTrapReceiver2x2TimeZone 13 }

wtTrapReceiver2x2StTzStopWday OBJECT-TYPE
    SYNTAX INTEGER {
    	wtTrapReceiver2x2StopWday-Sunday(1),
    	wtTrapReceiver2x2StopWday-Monday(2),
    	wtTrapReceiver2x2StopWday-Tuesday(3),
    	wtTrapReceiver2x2StopWday-Thursday(4),
    	wtTrapReceiver2x2StopWday-Wednesday(5),
    	wtTrapReceiver2x2StopWday-Friday(6),
    	wtTrapReceiver2x2StopWday-Saturday(7)
    	}
    ACCESS read-write
    STATUS mandatory
    DESCRIPTION
        "Day of the week on which the change is made from summer time to winter time."
    ::= { wtTrapReceiver2x2TimeZone 14 }
    
wtTrapReceiver2x2StTzStopHrs OBJECT-TYPE
    SYNTAX INTEGER 
    ACCESS read-write
    STATUS mandatory
    DESCRIPTION
        "Hour at which the time zone is changed from summer to winter time with
        respect to UTC."
    ::= { wtTrapReceiver2x2TimeZone 15 }

wtTrapReceiver2x2StTzStopMin OBJECT-TYPE
    SYNTAX INTEGER 
    ACCESS read-write
    STATUS mandatory
    DESCRIPTION
        "Minute at which the time zone is changed from summer to winter time with
        respect to UTC."
    ::= { wtTrapReceiver2x2TimeZone 16 }

-- wtTrapReceiver2x2TimeServer Group
----------------------------

wtTrapReceiver2x2TimeServer1 OBJECT-TYPE
    SYNTAX OCTET STRING 
    ACCESS read-write
    STATUS mandatory
    DESCRIPTION
        "IP address or name of the 1st time server in ASCII"
    ::= { wtTrapReceiver2x2TimeServer 1 }

wtTrapReceiver2x2TimeServer2 OBJECT-TYPE
    SYNTAX OCTET STRING 
    ACCESS read-write
    STATUS mandatory
    DESCRIPTION
        "IP address or name of the 2nd time server in ASCII"
    ::= { wtTrapReceiver2x2TimeServer 2 }

wtTrapReceiver2x2TsEnable OBJECT-TYPE
    SYNTAX OCTET STRING (SIZE(4))
    ACCESS read-write
    STATUS mandatory
    DESCRIPTION
        "Binary coded conditions:
        Octet 1: unused
        Octet 2: unused
        Octet 3: unused
        Octet 4:
        	Bit 1-7: unused
	        Bit 0  : Apply Time Server"
    ::= { wtTrapReceiver2x2TimeServer 3 }

wtTrapReceiver2x2TsSyncTime OBJECT-TYPE
    SYNTAX INTEGER 
    ACCESS read-write
    STATUS mandatory
    DESCRIPTION
        "Daily synchronisation time with the time server (hour: 0-23)."
    ::= { wtTrapReceiver2x2TimeServer 4 }
      
    
-- wtTrapReceiver2x2DeviceClock Group
----------------------------

wtTrapReceiver2x2ClockHrs OBJECT-TYPE
    SYNTAX INTEGER (0..23)
    ACCESS read-write
    STATUS mandatory
    DESCRIPTION
        "Clock hours taking into account the time zone settings."
    ::= { wtTrapReceiver2x2DeviceClock 1 }

wtTrapReceiver2x2ClockMin OBJECT-TYPE
    SYNTAX INTEGER (0..59)
    ACCESS read-write
    STATUS mandatory
    DESCRIPTION
        "Clock minutes taking into account the time zone settings."
    ::= { wtTrapReceiver2x2DeviceClock 2 }

wtTrapReceiver2x2ClockDay OBJECT-TYPE
    SYNTAX INTEGER (1..31)
    ACCESS read-write
    STATUS mandatory
    DESCRIPTION
        "Date: Day of the month, taking into account the time zone settings."
    ::= { wtTrapReceiver2x2DeviceClock 3 }

wtTrapReceiver2x2ClockMonth OBJECT-TYPE
   SYNTAX INTEGER {
    	wtTrapReceiver2x2ClockMonth-January(1),
    	wtTrapReceiver2x2ClockMonth-February(2),
    	wtTrapReceiver2x2ClockMonth-March(3),
    	wtTrapReceiver2x2ClockMonth-April(4),
    	wtTrapReceiver2x2ClockMonth-May(5),
    	wtTrapReceiver2x2ClockMonth-June(6),
    	wtTrapReceiver2x2ClockMonth-July(7),
    	wtTrapReceiver2x2ClockMonth-August(8),
    	wtTrapReceiver2x2ClockMonth-September(9),
    	wtTrapReceiver2x2ClockMonth-October(10),
    	wtTrapReceiver2x2ClockMonth-November(11),
    	wtTrapReceiver2x2ClockMonth-December(12)
    	}
    ACCESS read-write
    STATUS mandatory
    DESCRIPTION
        "Date: Month, taking into account the time zone settings."
    ::= { wtTrapReceiver2x2DeviceClock 4 }

wtTrapReceiver2x2ClockYear OBJECT-TYPE
    SYNTAX INTEGER (0..65535)
    ACCESS read-write
    STATUS mandatory
    DESCRIPTION
        "Date: Year, taking into account the time zone settings."
    ::= { wtTrapReceiver2x2DeviceClock 5 }

-- wtTrapReceiver2x2Network Group
------------------------

wtTrapReceiver2x2IpAddress OBJECT-TYPE
    SYNTAX IpAddress
    ACCESS read-write
    STATUS mandatory
    DESCRIPTION
        "IP address of the Webio"
    ::= { wtTrapReceiver2x2Network 1 }

wtTrapReceiver2x2SubnetMask OBJECT-TYPE
    SYNTAX IpAddress
    ACCESS read-write
    STATUS mandatory
    DESCRIPTION
        "Subnet mask of the Webio"
    ::= { wtTrapReceiver2x2Network 2 }

wtTrapReceiver2x2Gateway OBJECT-TYPE
    SYNTAX IpAddress
    ACCESS read-write
    STATUS mandatory
    DESCRIPTION
        "Gateway of the Webio"
    ::= { wtTrapReceiver2x2Network 3 }

wtTrapReceiver2x2DnsServer1 OBJECT-TYPE
    SYNTAX OCTET STRING 
    ACCESS read-write
    STATUS mandatory
    DESCRIPTION
        "IP address of the 1st DNS server in ASCII"
    ::= { wtTrapReceiver2x2Network 4 }

wtTrapReceiver2x2DnsServer2 OBJECT-TYPE
    SYNTAX OCTET STRING 
    ACCESS read-write
    STATUS mandatory
    DESCRIPTION
        "IP address of the 2nd DNS server in ASCII"
    ::= { wtTrapReceiver2x2Network 5 }

wtTrapReceiver2x2AddConfig OBJECT-TYPE
    SYNTAX OCTET STRING 
    ACCESS read-write
    STATUS mandatory
    DESCRIPTION
        "Additional configuration (1=ON):
        Octet 1: unused
        Octet 2: unused
        Octet 3: unused
        Octet 4:
	        Bit 1: DHCP  enable
	        Bit 0: BOOTP enable"
    ::= { wtTrapReceiver2x2Network 6 }

--  wtTrapReceiver2x2HTTP Group
--------------------------------

wtTrapReceiver2x2HttpPort OBJECT-TYPE
    SYNTAX INTEGER (1..65534)
    ACCESS read-write
    STATUS mandatory
    DESCRIPTION
       "Definition of the standard HTML port (Default: 80)."
    ::= { wtTrapReceiver2x2HTTP 4 }        
    
    
-- wtTrapReceiver2x2Mail Group
--------------------------------

wtTrapReceiver2x2MailAdName OBJECT-TYPE
    SYNTAX OCTET STRING 
    ACCESS read-write
    STATUS mandatory
    DESCRIPTION
        "Device name for mail administration."
    ::= { wtTrapReceiver2x2Mail 1 }
    
wtTrapReceiver2x2MailReply OBJECT-TYPE
    SYNTAX OCTET STRING 
    ACCESS read-write
    STATUS mandatory
    DESCRIPTION
        "Reply address for the mail server."
    ::= { wtTrapReceiver2x2Mail 2 }
    
wtTrapReceiver2x2MailServer OBJECT-TYPE
    SYNTAX OCTET STRING 
    ACCESS read-write
    STATUS mandatory
    DESCRIPTION
        "Name or IP address of the mail server."
    ::= { wtTrapReceiver2x2Mail 3 }
    
wtTrapReceiver2x2MailEnable OBJECT-TYPE
    SYNTAX OCTET STRING 
    ACCESS read-write
    STATUS mandatory
    DESCRIPTION
        "Set this bit to enable the sending of mails:
        Octet 1: unused
        Octet 2: unused
        Octet 3: unused
        Octet 4:
        	Bit 1-7: unused
                Bit 0  : Mail enable"
    ::= { wtTrapReceiver2x2Mail 4 }

wtTrapReceiver2x2MailAuthentication OBJECT-TYPE
    SYNTAX OCTET STRING (SIZE (4))
    ACCESS read-write
    STATUS mandatory
    DESCRIPTION
        "Selection of the authentication modi:
        The OCTETS are interpreted bit-by-bit,
        Bit 0 corresponds to the LSB.
        OCTET 1: unused
        OCTET 2: unused
        OCTET 3: unused
        OCTET 4: Bit 3-7: unused
        	 Bit 2  : POP3 before SMTP
        	 Bit 1  : ESMTP, authentication
        	 Bit 0  : SMTP, no authentication"
    ::= { wtTrapReceiver2x2Mail 5 }
    
wtTrapReceiver2x2MailAuthUser OBJECT-TYPE
    SYNTAX OCTET STRING 
    ACCESS read-write
    STATUS mandatory
    DESCRIPTION
        "Name of the user to be authenticated."
    ::= { wtTrapReceiver2x2Mail 6 }    
    
wtTrapReceiver2x2MailAuthPassword OBJECT-TYPE
    SYNTAX OCTET STRING 
    ACCESS read-write
    STATUS mandatory
    DESCRIPTION
        "Authentication password."
    ::= { wtTrapReceiver2x2Mail 7 }    
    
wtTrapReceiver2x2MailPop3Server OBJECT-TYPE
    SYNTAX OCTET STRING 
    ACCESS read-write
    STATUS mandatory
    DESCRIPTION
        "Name or Ip-address of the POP3 Servers."
    ::= { wtTrapReceiver2x2Mail 8 }        
    

--  wtTrapReceiver2x2Snmp Group
--------------------------------

wtTrapReceiver2x2SnmpEnable OBJECT-TYPE
    SYNTAX OCTET STRING 
    ACCESS read-write
    STATUS mandatory
    DESCRIPTION
        "Set bit 0 to enable SNMP.
        If disabled, the device did not respond to any SNMP requests.
        Bit 1 decided wether the community string of read operations 
        is compared with the system password or not:
        Octet 1: unused
        Octet 2: unused
        Octet 3: unused
        Octet 4:
        	Bit 1-7: unused
        	Bit 0  : SNMP enable"
    ::= { wtTrapReceiver2x2SNMP 1 }
    
wtTrapReceiver2x2SnmpCommunityStringRead OBJECT-TYPE
    SYNTAX OCTET STRING
    ACCESS read-write
    STATUS mandatory
    DESCRIPTION
        "Community string read only"
    ::= { wtTrapReceiver2x2SNMP 2 }

wtTrapReceiver2x2SnmpCommunityStringReadWrite OBJECT-TYPE
    SYNTAX OCTET STRING
    ACCESS read-write
    STATUS mandatory
    DESCRIPTION
        "Community string read / write"
    ::= { wtTrapReceiver2x2SNMP 3 }

wtTrapReceiver2x2SnmpSystemTrapManagerIP OBJECT-TYPE
    SYNTAX OCTET STRING 
    ACCESS read-write
    STATUS mandatory
    DESCRIPTION
        "Name or IP address of the TCP server which accepts the system trap."
    ::= { wtTrapReceiver2x2SNMP 4 }
    
wtTrapReceiver2x2SnmpSystemTrapEnable OBJECT-TYPE
    SYNTAX OCTET STRING (SIZE(4))
    ACCESS read-write
    STATUS mandatory
    DESCRIPTION
        "Binary coded trigger conditions:
        Octet 1: unused
        Octet 2: unused
        Octet 3: unused
        Octet 4:
	        Bit 0:   ColdStart
	        Bit 1:   WarmStart
	        Bit 2:   Diag messages
	        Bit 3-7: unused"
    ::= { wtTrapReceiver2x2SNMP 5 }    

-- wtTrapReceiver2x2UDP Group
--------------------------------   

wtTrapReceiver2x2UdpAdminPort OBJECT-TYPE
    SYNTAX INTEGER
    ACCESS read-write
    STATUS mandatory
    DESCRIPTION
        "Udp port to which the Udp queries ( short form GET requests) can be sent. This
        port number must be unique within the device."
    ::= { wtTrapReceiver2x2UDP 1 }

wtTrapReceiver2x2UdpEnable OBJECT-TYPE
    SYNTAX OCTET STRING 
    ACCESS read-write
    STATUS mandatory
    DESCRIPTION
        "Set this bit to enable UDP support:
        Octet 1: unused
        Octet 2: unused
        Octet 3: unused
        Octet 4:
        	Bit 1-7: unused
                Bit 0  : UDP enable"
    ::= { wtTrapReceiver2x2UDP 2 }

wtTrapReceiver2x2UdpRemotePort OBJECT-TYPE
    SYNTAX INTEGER
    ACCESS read-write
    STATUS mandatory
    DESCRIPTION
        "Udp remote port setting.
        If this value is set to zero, the source port read from a request will be used 
        as destination port for the answer.
        A non zero value forced the destination port to this value."
    ::= { wtTrapReceiver2x2UDP 3 }
    
--  wtTrapReceiver2x2Syslog Group
--------------------------------
    
wtTrapReceiver2x2SyslogServerIP OBJECT-TYPE
    SYNTAX OCTET STRING 
    ACCESS read-write
    STATUS mandatory
    DESCRIPTION
        "Name or IP address of the Syslog server, which accepts the Syslog messgaes."
    ::= { wtTrapReceiver2x2Syslog 1 }
    
wtTrapReceiver2x2SyslogServerPort OBJECT-TYPE
    SYNTAX INTEGER
    ACCESS read-write
    STATUS mandatory
    DESCRIPTION
        "Portnumber of the Syslog servers, default 514."
    ::= { wtTrapReceiver2x2Syslog 2 }

wtTrapReceiver2x2SyslogSystemMessagesEnable OBJECT-TYPE
    SYNTAX OCTET STRING (SIZE(4))
    ACCESS read-write
    STATUS mandatory
    DESCRIPTION
        "Binary coded trigger conditions:
        Octet 1: unused
        Octet 2: unused
        Octet 3: unused
        Octet 4:
	        Bit 0:   ColdStart
	        Bit 1:   WarmStart
	        Bit 2:   Diag Messages
	        Bit 3-7: unused"
    ::= { wtTrapReceiver2x2Syslog 3 }    

wtTrapReceiver2x2SyslogEnable OBJECT-TYPE
    SYNTAX OCTET STRING 
    ACCESS read-write
    STATUS mandatory
    DESCRIPTION
        "Set bit 0to enable Syslog:
        Octet 1: unused
        Octet 2: unused
        Octet 3: unused
        Octet 4:
        	Bit 1-7: unused
                Bit 0  : Syslog enable"
    ::= { wtTrapReceiver2x2Syslog 4 }

--  wtTrapReceiver2x2FTP Group
--------------------------------

wtTrapReceiver2x2FTPServerIP OBJECT-TYPE
    SYNTAX OCTET STRING 
    ACCESS read-write
    STATUS mandatory
    DESCRIPTION
        "Name or IP address of the FTP server, which accepts the FTP messages."
    ::= { wtTrapReceiver2x2FTP 1 }
    
wtTrapReceiver2x2FTPServerControlPort OBJECT-TYPE
    SYNTAX INTEGER
    ACCESS read-write
    STATUS mandatory
    DESCRIPTION
        "Portnumber of the control port of the FTP server, default 21."
    ::= { wtTrapReceiver2x2FTP 2 }
    
wtTrapReceiver2x2FTPUserName OBJECT-TYPE
    SYNTAX OCTET STRING 
    ACCESS read-write
    STATUS mandatory
    DESCRIPTION
        "FTP Loggin: user name."
    ::= { wtTrapReceiver2x2FTP 3 }
    
wtTrapReceiver2x2FTPPassword OBJECT-TYPE
    SYNTAX OCTET STRING 
    ACCESS read-write
    STATUS mandatory
    DESCRIPTION
        "FTP Loggin: user password."
    ::= { wtTrapReceiver2x2FTP 4 }

wtTrapReceiver2x2FTPAccount OBJECT-TYPE
    SYNTAX OCTET STRING 
    ACCESS read-write
    STATUS mandatory
    DESCRIPTION
        "FTP Loggin: name of account."
    ::= { wtTrapReceiver2x2FTP 5 }

wtTrapReceiver2x2FTPOption OBJECT-TYPE
    SYNTAX OCTET STRING 
    ACCESS read-write
    STATUS mandatory
    DESCRIPTION
        "Bit 0 switches the FTP Server in Passiv-Mode,
        the Client controls the data connection on its own:
        Octet 1: unused
        Octet 2: unused
        Octet 3: unused
        Octet 4:
        	Bit 1-7: unused
                Bit 0  : PASV enable"
    ::= { wtTrapReceiver2x2FTP 6 }
    
wtTrapReceiver2x2FTPEnable OBJECT-TYPE
    SYNTAX OCTET STRING 
    ACCESS read-write
    STATUS mandatory
    DESCRIPTION
        "Set Bit 0 to enable FTP:
        Octet 1: unused
        Octet 2: unused
        Octet 3: unused
        Octet 4:
        	Bit 1-7: unused
                Bit 0  : FTP enable"
    ::= { wtTrapReceiver2x2FTP 7 }
    
-- wtTrapReceiver2x2WatchList Group
----------------------------

wtTrapReceiver2x2WatchListCount OBJECT-TYPE
    SYNTAX INTEGER
    ACCESS read-only
    STATUS mandatory
    DESCRIPTION
        "Number of Ip addresses."
    ::= { wtTrapReceiver2x2WatchList 1 }
    
-- WatchList Interface Table

wtTrapReceiver2x2WatchListIfTable OBJECT-TYPE
    SYNTAX SEQUENCE OF WtTrapReceiver2x2WatchListIfEntry
    ACCESS not-accessible
    STATUS mandatory
    DESCRIPTION
        "Table of inices."
    ::= { wtTrapReceiver2x2WatchList 2 }

wtTrapReceiver2x2WatchListIfEntry OBJECT-TYPE
    SYNTAX WtTrapReceiver2x2WatchListIfEntry
    ACCESS not-accessible
    STATUS mandatory
    DESCRIPTION
        "Table entry."
    INDEX  { wtTrapReceiver2x2WatchListNo }
    ::= { wtTrapReceiver2x2WatchListIfTable 1 }

WtTrapReceiver2x2WatchListIfEntry ::= SEQUENCE {
    wtTrapReceiver2x2WatchListNo 	INTEGER
}

wtTrapReceiver2x2WatchListNo OBJECT-TYPE
    SYNTAX INTEGER (1..999)
    ACCESS read-only
    STATUS mandatory
    DESCRIPTION
        "List number of this entry."
    ::= { wtTrapReceiver2x2WatchListIfEntry 1 }

-- WatchList Table

wtTrapReceiver2x2WatchListTable OBJECT-TYPE
    SYNTAX SEQUENCE OF WtTrapReceiver2x2WatchListEntry
    ACCESS not-accessible
    STATUS mandatory
    DESCRIPTION
        "List of ip addresses."
    ::= { wtTrapReceiver2x2WatchList 3 }

wtTrapReceiver2x2WatchListEntry OBJECT-TYPE
    SYNTAX WtTrapReceiver2x2WatchListEntry
    ACCESS not-accessible
    STATUS mandatory
    DESCRIPTION
        "List entry."
    INDEX  { wtTrapReceiver2x2WatchListNo }
    ::= { wtTrapReceiver2x2WatchListTable 1 }

WtTrapReceiver2x2WatchListEntry ::= SEQUENCE {
    wtTrapReceiver2x2WatchListName 		OCTET STRING,
    wtTrapReceiver2x2WatchListPort 		INTEGER,
    wtTrapReceiver2x2WatchListService 		OCTET STRING,
    wtTrapReceiver2x2WatchListEnable 		OCTET STRING,
    wtTrapReceiver2x2WatchListAlias 		OCTET STRING,
    wtTrapReceiver2x2WatchListTrapNo		INTEGER,
    wtTrapReceiver2x2WatchListSpecificNo	INTEGER,
    wtTrapReceiver2x2WatchListFacility		INTEGER,
    wtTrapReceiver2x2WatchListSeverity		INTEGER    
}

wtTrapReceiver2x2WatchListName OBJECT-TYPE
    SYNTAX OCTET STRING 
    ACCESS read-write
    STATUS mandatory
    DESCRIPTION
        "Name or IP address."
    ::= { wtTrapReceiver2x2WatchListEntry 1 }
    
wtTrapReceiver2x2WatchListPort OBJECT-TYPE
    SYNTAX INTEGER 
    ACCESS read-write
    STATUS mandatory
    DESCRIPTION
        "Port number, zero in the case of broadcast or Ping."
    ::= { wtTrapReceiver2x2WatchListEntry 2 }
    
wtTrapReceiver2x2WatchListService OBJECT-TYPE
    SYNTAX OCTET STRING 
    ACCESS read-write
    STATUS mandatory
    DESCRIPTION
        "Binary coded scan mode, only one mode can be selected at a particular time:
        Octet 1: unused
        Octet 2: unused
        Octet 3: unused
        Octet 4:
		Bit 0:	unused
		Bit 1:	unused
		Bit 2:	SNMP Trap reveive enable
		Bit 3:	Syslog receive enable
        	Bit 4-7: unused"
    ::= { wtTrapReceiver2x2WatchListEntry 3 }
    
wtTrapReceiver2x2WatchListEnable OBJECT-TYPE
    SYNTAX OCTET STRING 
    ACCESS read-write
    STATUS mandatory
    DESCRIPTION
        "Binary coded alarm enable:
        Octet 1: unused
        Octet 2: unused
        Octet 3: 
        	Bit 0:	enabled in Report 9
        	Bit 1:	enabled in Report 10
        	Bit 2:  enabled in Report 11
        	Bit 3:  enabled in Report 12
        	Bit 4-7: unused
        Octet 4:
		Bit 0:	enabled in Report 1
        	Bit 1:	enabled in Report 2
        	Bit 2:  enabled in Report 3
        	Bit 3:  enabled in Report 4
        	Bit 4:	enabled in Report 5
        	Bit 5:	enabled in Report 6
        	Bit 6:	enabled in Report 7
        	Bit 7:	enabled in Report 8"
    ::= { wtTrapReceiver2x2WatchListEntry 4 }

wtTrapReceiver2x2WatchListAlias OBJECT-TYPE
    SYNTAX OCTET STRING 
    ACCESS read-write
    STATUS mandatory
    DESCRIPTION
        "Alias Name"
    ::= { wtTrapReceiver2x2WatchListEntry 5 }

wtTrapReceiver2x2WatchListTrapNo OBJECT-TYPE
    SYNTAX INTEGER {
    wtTrapReceiver2x2WatchListTrapNo-ColdStart(0),
    wtTrapReceiver2x2WatchListTrapNo-WarmStart(1),
    wtTrapReceiver2x2WatchListTrapNo-LinkDown(2),
    wtTrapReceiver2x2WatchListTrapNo-LinkUp(3),
    wtTrapReceiver2x2WatchListTrapNo-AuthFailure(4),
    wtTrapReceiver2x2WatchListTrapNo-EPGneighborLoss(5),
    wtTrapReceiver2x2WatchListTrapNo-EnterpriseSpecific(6),
    wtTrapReceiver2x2WatchListTrapNo-WildCard(7)
    }    
    ACCESS read-write
    STATUS mandatory
    DESCRIPTION
        "SNMP Trap No: this filter is only active, if SNMP Trap reveive enable in
        wtTrapReceiver2x2WatchListService is set."
    ::= { wtTrapReceiver2x2WatchListEntry 6 }
    
wtTrapReceiver2x2WatchListSpecificNo OBJECT-TYPE
    SYNTAX INTEGER 
    ACCESS read-write
    STATUS mandatory
    DESCRIPTION
        "SNMP Specific No: this filter is only active, if SNMP Trap reveive enable in
        wtTrapReceiver2x2WatchListService is set."
    ::= { wtTrapReceiver2x2WatchListEntry 7 }
    
wtTrapReceiver2x2WatchListFacility OBJECT-TYPE
    SYNTAX INTEGER {
    wtTrapReceiver2x2WatchListFacility-Emergency(0),
    wtTrapReceiver2x2WatchListFacility-Alert(1),
    wtTrapReceiver2x2WatchListFacility-Critical(2),
    wtTrapReceiver2x2WatchListFacility-Error(3),
    wtTrapReceiver2x2WatchListFacility-Warning(4),
    wtTrapReceiver2x2WatchListFacility-Notice(5),
    wtTrapReceiver2x2WatchListFacility-Informational(6),
    wtTrapReceiver2x2WatchListFacility-Debug(7),
    wtTrapReceiver2x2WatchListFacility-WildCard(8)
    }
    ACCESS read-write
    STATUS mandatory
    DESCRIPTION
        "Syslog message level Facility: this filter is only active, if Syslog receive enable in
        wtTrapReceiver2x2WatchListService is set."
    ::= { wtTrapReceiver2x2WatchListEntry 8 }
    
wtTrapReceiver2x2WatchListSeverity OBJECT-TYPE
    SYNTAX INTEGER {
    wtTrapReceiver2x2WatchListSeverity-kernel-messages(0),
    wtTrapReceiver2x2WatchListSeverity-user-level-messages(1),
    wtTrapReceiver2x2WatchListSeverity-mail-system(2),
    wtTrapReceiver2x2WatchListSeverity-system-daemons(3),
    wtTrapReceiver2x2WatchListSeverity-security-authorization-messages(4),
    wtTrapReceiver2x2WatchListSeverity-messages-generated-internaly-by-syslogd(5),
    wtTrapReceiver2x2WatchListSeverity-line-printer-subsystem(6),
    wtTrapReceiver2x2WatchListSeverity-network-news-subsystem(7),
    wtTrapReceiver2x2WatchListSeverity-UUCP-subsystem(8),
    wtTrapReceiver2x2WatchListSeverity-clock-daemon(9),
    wtTrapReceiver2x2WatchListSeverity-security-authorization-messages-private(10),
    wtTrapReceiver2x2WatchListSeverity-FTP-daemon(11),
    wtTrapReceiver2x2WatchListSeverity-NTP-subsystem(12),
    wtTrapReceiver2x2WatchListSeverity-log-audit(13),
    wtTrapReceiver2x2WatchListSeverity-log-alert(14),
    wtTrapReceiver2x2WatchListSeverity-clock-daemon-15(15),
    wtTrapReceiver2x2WatchListSeverity-local0(16),
    wtTrapReceiver2x2WatchListSeverity-local1(17),
    wtTrapReceiver2x2WatchListSeverity-local2(18),
    wtTrapReceiver2x2WatchListSeverity-local3(19),
    wtTrapReceiver2x2WatchListSeverity-local4(20),
    wtTrapReceiver2x2WatchListSeverity-local5(21),
    wtTrapReceiver2x2WatchListSeverity-local6(22),
    wtTrapReceiver2x2WatchListSeverity-local7(23),
    wtTrapReceiver2x2WatchListSeverity-WildCard(24)
    }
    ACCESS read-write
    STATUS mandatory
    DESCRIPTION
        "Syslog message level Severity: this filter is only active, if Syslog receive enable in
        wtTrapReceiver2x2WatchListService is set."
    ::= { wtTrapReceiver2x2WatchListEntry 9 }     
 
-- wtTrapReceiver2x2OutputMode Group
----------------------------    
    
wtTrapReceiver2x2PowerSupplyEnable OBJECT-TYPE
    SYNTAX OCTET STRING 
    ACCESS read-write
    STATUS mandatory
    DESCRIPTION
        "Setting this enable bit turns on the intarnal 24V power supply of the outputs.
        All currents out must not exceed 150mA. At overcurrent condition the power supply will
        be shut down automatically. To reset the ocvercurrent protection circuit
        write 1 into wtTrapReceiver2x2DiagErrorClear.
        Internal power supply is a feature of 57655 only.
        
        Octet 1: unused
        Octet 2: unused
        Octet 3: unused
        Octet 4:
        	Bit 1-7: unused
                Bit 0  : Power Supply enable"
    ::= { wtTrapReceiver2x2OutputMode 4 }
     
    
-- wtTrapReceiver2x2Action Group
----------------------------

wtTrapReceiver2x2ActionCount OBJECT-TYPE
    SYNTAX INTEGER (1..4)
    ACCESS read-only
    STATUS mandatory
    DESCRIPTION
        "Number of independent alarms."
    ::= { wtTrapReceiver2x2Action 1 }
    
-- Action Interface Table

wtTrapReceiver2x2ActionIfTable OBJECT-TYPE
    SYNTAX SEQUENCE OF WtTrapReceiver2x2ActionIfEntry
    ACCESS not-accessible
    STATUS mandatory
    DESCRIPTION
        "List of alarm indices."
    ::= { wtTrapReceiver2x2Action 2 }

wtTrapReceiver2x2ActionIfEntry OBJECT-TYPE
    SYNTAX WtTrapReceiver2x2ActionIfEntry
    ACCESS not-accessible
    STATUS mandatory
    DESCRIPTION
        "Numbers of the alarms."
    INDEX  { wtTrapReceiver2x2ActionNo }
    ::= { wtTrapReceiver2x2ActionIfTable 1 }

WtTrapReceiver2x2ActionIfEntry ::= SEQUENCE {
    wtTrapReceiver2x2ActionNo INTEGER
}

wtTrapReceiver2x2ActionNo OBJECT-TYPE
    SYNTAX INTEGER (1..4)
    ACCESS read-only
    STATUS mandatory
    DESCRIPTION
        "Numbers of the alarms."
    ::= { wtTrapReceiver2x2ActionIfEntry 1 }

-- Action Table

wtTrapReceiver2x2ActionTable OBJECT-TYPE
    SYNTAX SEQUENCE OF WtTrapReceiver2x2ActionEntry
    ACCESS not-accessible
    STATUS mandatory
    DESCRIPTION
        "List of settings depending on the alarm number."
    ::= { wtTrapReceiver2x2Action 3 }

wtTrapReceiver2x2ActionEntry OBJECT-TYPE
    SYNTAX WtTrapReceiver2x2ActionEntry
    ACCESS not-accessible
    STATUS mandatory
    DESCRIPTION
        "Action parameters of the individual alarms."
    INDEX  { wtTrapReceiver2x2ActionNo }
    ::= { wtTrapReceiver2x2ActionTable 1 }

WtTrapReceiver2x2ActionEntry ::= SEQUENCE {
    wtTrapReceiver2x2ActionInputTrigger			OCTET STRING,
    wtTrapReceiver2x2ActionInterval			OCTET STRING,
    wtTrapReceiver2x2ActionEnable			OCTET STRING,
    wtTrapReceiver2x2ActionMailAddr			OCTET STRING,
    wtTrapReceiver2x2ActionMailSubject			OCTET STRING,
    wtTrapReceiver2x2ActionMailText			OCTET STRING,
    wtTrapReceiver2x2ActionSnmpManagerIP		OCTET STRING,
    wtTrapReceiver2x2ActionSnmpTrapText			OCTET STRING,
    wtTrapReceiver2x2ActionUdpIpAddr			OCTET STRING,
    wtTrapReceiver2x2ActionUdpPort			INTEGER,
    wtTrapReceiver2x2ActionUdpText			OCTET STRING,
    wtTrapReceiver2x2ActionTcpIpAddr			OCTET STRING,
    wtTrapReceiver2x2ActionTcpPort			INTEGER,
    wtTrapReceiver2x2ActionTcpText			OCTET STRING,    
    wtTrapReceiver2x2ActionSyslogIpAddr			OCTET STRING,
    wtTrapReceiver2x2ActionSyslogPort			INTEGER,
    wtTrapReceiver2x2ActionSyslogText			OCTET STRING,
    wtTrapReceiver2x2ActionFtpDataPort			OCTET STRING,
    wtTrapReceiver2x2ActionFtpFileName			OCTET STRING,
    wtTrapReceiver2x2ActionFtpText			OCTET STRING,
    wtTrapReceiver2x2ActionFtpOption			OCTET STRING,
    wtTrapReceiver2x2ActionTimerCron			OCTET STRING,

    wtTrapReceiver2x2ActionName				OCTET STRING,
    wtTrapReceiver2x2ActionGlobalEnable			OCTET STRING,
    
    wtTrapReceiver2x2ActionSystemTimerTrigger	OCTET STRING,
    wtTrapReceiver2x2ActionSystemButtonTrigger	OCTET STRING,
    wtTrapReceiver2x2ActionOutputAction			OCTET STRING
}

wtTrapReceiver2x2ActionInputTrigger OBJECT-TYPE
    SYNTAX OCTET STRING (SIZE(12))
    ACCESS read-write
    STATUS mandatory
    DESCRIPTION
        "This variable allows setting of individual input trigger conditions. 
        The OCTETS are interpreted bit-by-bit, with each bit corresponding to an input. 
        Bit 0 corresponds to the LSB.
	The four OCTETS contain the mask which determines which of the inputs are to 
	be considered (corresponding bit = 1) and which inputs are to ignore 
	(corresponding bit = 0):
	OCTET 1: unused
	OCTET 2: unused
	OCTET 3: unused
	OCTET 4:
		Bit 0: Input 0 falling edge 
		Bit 1: Input 0 rising edge 
		Bit 2: Input 1 falling edge 
		Bit 3: Input 1 rising edge 
		Bit 4-7: unused"        
    ::= { wtTrapReceiver2x2ActionEntry 1 }
    
wtTrapReceiver2x2ActionInterval OBJECT-TYPE
    SYNTAX OCTET STRING 
    ACCESS read-write
    STATUS mandatory
    DESCRIPTION
        "Send interval for alarm messages."
    ::= { wtTrapReceiver2x2ActionEntry 5 }

wtTrapReceiver2x2ActionEnable OBJECT-TYPE
    SYNTAX OCTET STRING (SIZE(4))
    ACCESS read-write
    STATUS mandatory
    DESCRIPTION
        "Binary coded alarm enable:
        Octet 1: unused
        Octet 2: unused
        Octet 3: unused
        Octet 4:
		Bit 0:	Mail Enable
        	Bit 1:	SNMP Trap enable
        	Bit 2:  UDP enable
        	Bit 3:  Send inputs to pending TCP connections
        	Bit 4:  TCP Client enable
        	Bit 5:	Syslog Messages enable
        	Bit 6-7: unused"
    ::= { wtTrapReceiver2x2ActionEntry 6 }

wtTrapReceiver2x2ActionMailAddr OBJECT-TYPE
    SYNTAX OCTET STRING 
    ACCESS read-write
    STATUS mandatory
    DESCRIPTION
        "E-Mail address for sending the alarm mail to."
    ::= { wtTrapReceiver2x2ActionEntry 7 }

wtTrapReceiver2x2ActionMailSubject OBJECT-TYPE
    SYNTAX OCTET STRING 
    ACCESS read-write
    STATUS mandatory
    DESCRIPTION
        "Subject line for alarm mail."
    ::= { wtTrapReceiver2x2ActionEntry 8 }

wtTrapReceiver2x2ActionMailText OBJECT-TYPE
    SYNTAX OCTET STRING 
    ACCESS read-write
    STATUS mandatory
    DESCRIPTION
        "Action mail text: 
        States of the Webio device can be included by using special tags.
        Please refer to the respective Webio manual"
    ::= { wtTrapReceiver2x2ActionEntry 9 }

wtTrapReceiver2x2ActionSnmpManagerIP OBJECT-TYPE
    SYNTAX OCTET STRING 
    ACCESS read-write
    STATUS mandatory
    DESCRIPTION
        "IP address of the SNMP Manager to which the Webio device should send SNMP traps."
    ::= { wtTrapReceiver2x2ActionEntry 10 }

wtTrapReceiver2x2ActionSnmpTrapText OBJECT-TYPE
    SYNTAX OCTET STRING 
    ACCESS read-write
    STATUS mandatory
    DESCRIPTION
        "This text appears in the trap body."
    ::= { wtTrapReceiver2x2ActionEntry 11 }
    
wtTrapReceiver2x2ActionUdpIpAddr OBJECT-TYPE
    SYNTAX OCTET STRING 
    ACCESS read-write
    STATUS mandatory
    DESCRIPTION
        "IP address of the UDP listener to which the Webio device should send UDP traps."
    ::= { wtTrapReceiver2x2ActionEntry 12 }    

wtTrapReceiver2x2ActionUdpPort OBJECT-TYPE
    SYNTAX INTEGER (1..65535) 
    ACCESS read-write
    STATUS mandatory
    DESCRIPTION
        "Port number of the UDP listener to which the Webio device should send UDP traps."
    ::= { wtTrapReceiver2x2ActionEntry 13 }    

wtTrapReceiver2x2ActionUdpText OBJECT-TYPE
    SYNTAX OCTET STRING 
    ACCESS read-write
    STATUS mandatory
    DESCRIPTION
        "This text appears in the UDP trap body."
    ::= { wtTrapReceiver2x2ActionEntry 14 }
    
wtTrapReceiver2x2ActionTcpIpAddr OBJECT-TYPE
    SYNTAX OCTET STRING
    ACCESS read-write
    STATUS mandatory
    DESCRIPTION
        "IP address of the TCP listener to which the Webio device should send TCP traps."
    ::= { wtTrapReceiver2x2ActionEntry 15 }    

wtTrapReceiver2x2ActionTcpPort OBJECT-TYPE
    SYNTAX INTEGER (1..65535) 
    ACCESS read-write
    STATUS mandatory
    DESCRIPTION
        "Port number of the TCP listener to which the Webio device should send TCP traps."
    ::= { wtTrapReceiver2x2ActionEntry 16 }    

wtTrapReceiver2x2ActionTcpText OBJECT-TYPE
    SYNTAX OCTET STRING 
    ACCESS read-write
    STATUS mandatory
    DESCRIPTION
        "This text appears in the TCP trap body."
    ::= { wtTrapReceiver2x2ActionEntry 17 }

wtTrapReceiver2x2ActionSyslogIpAddr OBJECT-TYPE
    SYNTAX OCTET STRING 
    ACCESS read-write
    STATUS mandatory
    DESCRIPTION
        "IP address of the syslog server to which the Webio device should send syslog messages."
    ::= { wtTrapReceiver2x2ActionEntry 18 }    

wtTrapReceiver2x2ActionSyslogPort OBJECT-TYPE
    SYNTAX INTEGER (1..65535) 
    ACCESS read-write
    STATUS mandatory
    DESCRIPTION
        "Port number of the syslog server to which the Webio device should send syslog messages."
    ::= { wtTrapReceiver2x2ActionEntry 19 }    

wtTrapReceiver2x2ActionSyslogText OBJECT-TYPE
    SYNTAX OCTET STRING 
    ACCESS read-write
    STATUS mandatory
    DESCRIPTION
        "Every message starts with the priority key, a time stamp and the host ip address, according RFC3164.
        This text appears in the following syslog message body."
    ::= { wtTrapReceiver2x2ActionEntry 20 }    
    
wtTrapReceiver2x2ActionFtpDataPort OBJECT-TYPE
    SYNTAX OCTET STRING 
    ACCESS read-write
    STATUS mandatory
    DESCRIPTION
        "Local data port: 1..65535 or AUTO: the next free port will be assigned."
    ::= { wtTrapReceiver2x2ActionEntry 21 }
    
wtTrapReceiver2x2ActionFtpFileName OBJECT-TYPE
    SYNTAX OCTET STRING 
    ACCESS read-write
    STATUS mandatory
    DESCRIPTION
        "Name of the file including path informations."
    ::= { wtTrapReceiver2x2ActionEntry 22 }
    
wtTrapReceiver2x2ActionFtpText OBJECT-TYPE
    SYNTAX OCTET STRING 
    ACCESS read-write
    STATUS mandatory
    DESCRIPTION
        "Message text to store on the FTP server."
    ::= { wtTrapReceiver2x2ActionEntry 23 }

wtTrapReceiver2x2ActionFtpOption OBJECT-TYPE
    SYNTAX OCTET STRING (SIZE(4))
    ACCESS read-write
    STATUS mandatory
    DESCRIPTION
        "Binary coded options, select only one option at the same time:
        STORE  = replace file
        APPEND = append message at the end of the file
        
        Octet 1: unused
        Octet 2: unused
        Octet 3: unused
        Octet 4:
		Bit 0  :	STORE
		Bit 1  :	APPEND
        	Bit 2-7:	unused"
    ::= { wtTrapReceiver2x2ActionEntry 24 }      
    
wtTrapReceiver2x2ActionTimerCron OBJECT-TYPE
    SYNTAX OCTET STRING
    ACCESS read-write
    STATUS mandatory
    DESCRIPTION
        "This entry contains 10 space or tab seperated text fields defining a time window for sending
        time triggered messages. 2 CRON time for start time and stop time are defined as follows:
        Start time:
        field
        1: Minutes	Range 0-59
        3. Hours	Range 0-23, 0 is midnight
        5: Day of month	Range 1-31
        7: Month	Range 1-12
        9: Weekday	Range 0-6, 0 is sunday
        
        Stop time:
        field
        2: Minutes	Range 0-59
        4. Hours	Range 0-23, 0 is midnight
        6: Day of month	Range 1-31
        8: Month	Range 1-12
        10: Weekday	Range 0-6, 0 is sunday

        Syntax for every field:
         - an asterix (*) enables every possible setting of a field
         - single numbers seperated by commas
         - a partition within the allowed range (1-5)
         - step size within an partition of the allowed range (0-59/2: every second minute)."
    ::= { wtTrapReceiver2x2ActionEntry 25 }      


wtTrapReceiver2x2ActionName OBJECT-TYPE
    SYNTAX OCTET STRING 
    ACCESS read-write
    STATUS mandatory
    DESCRIPTION
        "Name of the alarm."
    ::= { wtTrapReceiver2x2ActionEntry 33 }    

wtTrapReceiver2x2ActionGlobalEnable OBJECT-TYPE
    SYNTAX OCTET STRING 
    ACCESS read-write
    STATUS mandatory
    DESCRIPTION
        "Binary coded alarm activation:
        The OCTETS are interpreted bit-by-bit, with each bit corresponding to an input. 
        Bit 0 corresponds to the LSB.
        OCTET 1: unused
        OCTET 2: unused
        OCTET 3: unused
        OCTET 4, Bit 1-7: unused
        	 Bit 0  : Action enable"
    ::= { wtTrapReceiver2x2ActionEntry 34 }    

wtTrapReceiver2x2ActionSystemTimerTrigger OBJECT-TYPE
    SYNTAX OCTET STRING (SIZE(4))
    ACCESS read-write
    STATUS mandatory
    DESCRIPTION
        "Binary coded system timer activation:
        The OCTETS are interpreted bit-by-bit, with each bit corresponding to an input. 
        Bit 0 corresponds to the LSB.
	
	OCTET 1: unused
	OCTET 2: unused
	OCTET 3: unused
	OCTET 4:
		Bit 0: System Timer 1 enable
		Bit 1: System Timer 2 enable 
		Bit 2-7: unused"
    ::= { wtTrapReceiver2x2ActionEntry 55 }
    
wtTrapReceiver2x2ActionSystemButtonTrigger OBJECT-TYPE
    SYNTAX OCTET STRING (SIZE(4))
    ACCESS read-write
    STATUS mandatory
    DESCRIPTION
        "Binary coded button activation:
        The OCTETS are interpreted bit-by-bit, with each bit corresponding to an input. 
        Bit 0 corresponds to the LSB.
	
	OCTET 1: unused
	OCTET 2: unused
	OCTET 3: unused
	OCTET 4:
		Bit 0: Button 1 enable 
		Bit 1: Button 2 enable 
		Bit 2: Button 3 enable 
		Bit 3: Button 4 enable
		Bit 3: Button 5 enable
		Bit 3: Button 6 enable
		Bit 3: Button 7 enable
		Bit 3: Button 8 enable."
    ::= { wtTrapReceiver2x2ActionEntry 56 }

wtTrapReceiver2x2ActionOutputAction OBJECT-TYPE
    SYNTAX OCTET STRING (SIZE(12))
    ACCESS read-write
    STATUS mandatory
    DESCRIPTION
        "This variable allows setting of individual output. 
        The OCTETS are interpreted bit-by-bit, with each bit corresponding to an input. 
        Bit 0 corresponds to the LSB.
	The first four OCTETS contain the mask which determines which of the outputs are to 
	be considered (corresponding bit = 1) and which outputs are to ignore 
	(corresponding bit = 0):
	OCTET 1 : unused
	OCTET 2 : unused
	OCTET 3 : unused
	OCTET 4, Bit 0-1: Mask for digital outputs 0-1
	
	OCTETS 5-8 contain the level (1=HIGH, 0=LOW) which the outputs 
	should assume:
	OCTET 5 : unused
	OCTET 6 : unused
	OCTET 7 : unused
        OCTET 8, Bit 0-1: Level of digital outputs 0-1
        
	OCTETS 9-12 contain the TOOGLE bit (1=ON, 0=OFF). outputs masked with the TOGGLE bit trigger change 
	their state on every action. Settings in OCTET 5-9 are then unused:
	OCTET 9: unused
	OCTET 10: unused
	OCTET 11: unused
	OCTET 12, Bit 0-1: TOGGLE bits of digital outputs 0-1"
    ::= { wtTrapReceiver2x2ActionEntry 57 }

-- wtTrapReceiver2x2InEvSystemTimer Group
----------------------------

-- SystemTimer Table

wtTrapReceiver2x2SystemTimerPortTable OBJECT-TYPE
    SYNTAX SEQUENCE OF WtTrapReceiver2x2SystemTimerPortEntry
    ACCESS not-accessible
    STATUS mandatory
    DESCRIPTION
        "List of settings depending on the SystemTimer number."
    ::= { wtTrapReceiver2x2InEvSystemTimer 1 }

wtTrapReceiver2x2SystemTimerPortEntry OBJECT-TYPE
    SYNTAX WtTrapReceiver2x2SystemTimerPortEntry
    ACCESS not-accessible
    STATUS mandatory
    DESCRIPTION
        "SystemTimer parameter for the individual SystemTimer."
    INDEX  { wtTrapReceiver2x2SystemTimerNo }
    ::= { wtTrapReceiver2x2SystemTimerPortTable 1 }

WtTrapReceiver2x2SystemTimerPortEntry ::= SEQUENCE {
    wtTrapReceiver2x2PortSystemTimerEnable		OCTET STRING,
    wtTrapReceiver2x2PortSystemTimerName		OCTET STRING,
    wtTrapReceiver2x2PortSystemTimerCron		OCTET STRING
    
    }

wtTrapReceiver2x2PortSystemTimerEnable OBJECT-TYPE
    SYNTAX OCTET STRING 
    ACCESS read-write
    STATUS mandatory
    DESCRIPTION
        "Binary coded SystemTimer enable:
        The OCTETS are interpreted bit-by-bit, with each bit corresponding to an input. 
        Bit 0 corresponds to the LSB.
        OCTET 1: ungenutzt
        OCTET 2: ungenutzt
        OCTET 3: ungenutzt
        OCTET 4, Bit 1-7: ungenutzt
        	 Bit 0  : SystemTimer enable"
    ::= { wtTrapReceiver2x2SystemTimerPortEntry 1 }
    
wtTrapReceiver2x2PortSystemTimerName OBJECT-TYPE
    SYNTAX OCTET STRING 
    ACCESS read-write
    STATUS mandatory
    DESCRIPTION
        "Name of the SystemTimer."
    ::= { wtTrapReceiver2x2SystemTimerPortEntry 2 }

wtTrapReceiver2x2PortSystemTimerCron OBJECT-TYPE
    SYNTAX OCTET STRING 
    ACCESS read-write
    STATUS mandatory
    DESCRIPTION
        "This entry contains 5 space or tab seperated text fields for time trigger definition.
        Each field must match with the actual time to trigger a message, weekday and day of month
        are interpreted separatley.
        1: Minutes	Range 0-59
        2. Hours	Range 0-23, 0 is midnight
        3: Day of month	Range 1-31
        4: Month	Range 1-12
        5: Weekday	Range 0-6, 0 is sunday
        
        Syntax for every field:
         - an asterix (*) enables every possible setting of a field
         - single numbers seperated by commas
         - a partition within the allowed range (1-5)
         - step size within an partition of the allowed range (0-59/2: every second minute)."
    ::= { wtTrapReceiver2x2SystemTimerPortEntry 3 }

-- wtTrapReceiver2x2InEvButtons Group
----------------------------

-- Button Table

wtTrapReceiver2x2ButtonPortTable OBJECT-TYPE
    SYNTAX SEQUENCE OF WtTrapReceiver2x2ButtonPortEntry
    ACCESS not-accessible
    STATUS mandatory
    DESCRIPTION
        "List of settings depending on the button number."
    ::= { wtTrapReceiver2x2InEvButtons 1 }

wtTrapReceiver2x2ButtonPortEntry OBJECT-TYPE
    SYNTAX WtTrapReceiver2x2ButtonPortEntry
    ACCESS not-accessible
    STATUS mandatory
    DESCRIPTION
        "Button parameter for the individual buttons."
    INDEX  { wtTrapReceiver2x2ButtonNo }
    ::= { wtTrapReceiver2x2ButtonPortTable 1 }

WtTrapReceiver2x2ButtonPortEntry ::= SEQUENCE {
    wtTrapReceiver2x2PortButtonEnable		OCTET STRING,
    wtTrapReceiver2x2PortButtonName		OCTET STRING,
    wtTrapReceiver2x2PortButtonText		OCTET STRING,
    wtTrapReceiver2x2PortButtonAccess		OCTET STRING
    }

wtTrapReceiver2x2PortButtonEnable OBJECT-TYPE
    SYNTAX OCTET STRING 
    ACCESS read-write
    STATUS mandatory
    DESCRIPTION
        "Binary coded button enable:
        The OCTETS are interpreted bit-by-bit, with each bit corresponding to an input. 
        Bit 0 corresponds to the LSB.
        OCTET 1: ungenutzt
        OCTET 2: ungenutzt
        OCTET 3: ungenutzt
        OCTET 4, Bit 1-7: ungenutzt
        	 Bit 0  : Button enable"
    ::= { wtTrapReceiver2x2ButtonPortEntry 1 }
    
wtTrapReceiver2x2PortButtonName OBJECT-TYPE
    SYNTAX OCTET STRING 
    ACCESS read-write
    STATUS mandatory
    DESCRIPTION
        "Name of the button."
    ::= { wtTrapReceiver2x2ButtonPortEntry 2 }

wtTrapReceiver2x2PortButtonText OBJECT-TYPE
    SYNTAX OCTET STRING 
    ACCESS read-write
    STATUS mandatory
    DESCRIPTION
        "Description of the button."
    ::= { wtTrapReceiver2x2ButtonPortEntry 3 }

wtTrapReceiver2x2PortButtonAccess OBJECT-TYPE
    SYNTAX OCTET STRING 
    ACCESS read-write
    STATUS mandatory
    DESCRIPTION
        "Binary coded button access level:
        The OCTETS are interpreted bit-by-bit, with each bit corresponding to an input. 
        Bit 0 corresponds to the LSB.
        OCTET 1: unused
        OCTET 2: unused
        OCTET 3: unused
        OCTET 4, Bit 3-7: unused
        	 Bit 2  : For user administrator visible and operable
        	 Bit 1  : For user operator visible and operable
        	 Bit 0  : For user guest visible and operable"
    ::= { wtTrapReceiver2x2ButtonPortEntry 4 }
    

-- wtTrapReceiver2x2InEvInputs Group
----------------------------

-- Input Port Table


wtTrapReceiver2x2InputPortTable OBJECT-TYPE
    SYNTAX SEQUENCE OF WtTrapReceiver2x2InputPortEntry
    ACCESS not-accessible
    STATUS mandatory
    DESCRIPTION
        "List of settings depending on the input number."
    ::= { wtTrapReceiver2x2InEvInputs 1 }

wtTrapReceiver2x2InputPortEntry OBJECT-TYPE
    SYNTAX WtTrapReceiver2x2InputPortEntry
    ACCESS not-accessible
    STATUS mandatory
    DESCRIPTION
        "Input parameter for the individual inputs."
    INDEX  { wtTrapReceiver2x2InputNo }
    ::= { wtTrapReceiver2x2InputPortTable 1 }

WtTrapReceiver2x2InputPortEntry ::= SEQUENCE {
    wtTrapReceiver2x2PortInputName		OCTET STRING,
    wtTrapReceiver2x2PortInputText		OCTET STRING,
    wtTrapReceiver2x2PortInputFilter		INTEGER    
    }

wtTrapReceiver2x2PortInputName OBJECT-TYPE
    SYNTAX OCTET STRING 
    ACCESS read-write
    STATUS mandatory
    DESCRIPTION
        "Name of the input."
    ::= { wtTrapReceiver2x2InputPortEntry 1 }

wtTrapReceiver2x2PortInputText OBJECT-TYPE
    SYNTAX OCTET STRING 
    ACCESS read-write
    STATUS mandatory
    DESCRIPTION
        "Description of the input."
    ::= { wtTrapReceiver2x2InputPortEntry 2 }

wtTrapReceiver2x2PortInputFilter OBJECT-TYPE
    SYNTAX INTEGER 
    ACCESS read-write										       
    STATUS mandatory
    DESCRIPTION
        "Pulses with a duration shorter than here specified (duration in 1/1000 sec),
	are ignored."
    ::= { wtTrapReceiver2x2InputPortEntry 4 }
    
-- wtTrapReceiver2x2OutEvOutputs Group

wtTrapReceiver2x2OutputPortTable OBJECT-TYPE
    SYNTAX SEQUENCE OF WtTrapReceiver2x2OutputPortEntry
    ACCESS not-accessible
    STATUS mandatory
    DESCRIPTION
        "List of settings depending on the output number."
    ::= { wtTrapReceiver2x2OutEvOutputs 1 }

wtTrapReceiver2x2OutputPortEntry OBJECT-TYPE
    SYNTAX WtTrapReceiver2x2OutputPortEntry
    ACCESS not-accessible
    STATUS mandatory
    DESCRIPTION
        "Output parameters of the individual outputs."
    INDEX  { wtTrapReceiver2x2OutputNo }
    ::= { wtTrapReceiver2x2OutputPortTable 1 }

WtTrapReceiver2x2OutputPortEntry ::= SEQUENCE {
    wtTrapReceiver2x2PortOutputName		OCTET STRING,
    wtTrapReceiver2x2PortOutputText		OCTET STRING,
    wtTrapReceiver2x2PortPulseDuration		INTEGER,
    wtTrapReceiver2x2PortPulsePolarity		OCTET STRING
    
}

wtTrapReceiver2x2PortOutputName OBJECT-TYPE
    SYNTAX OCTET STRING 
    ACCESS read-write
    STATUS mandatory
    DESCRIPTION
        "Name of the output."
    ::= { wtTrapReceiver2x2OutputPortEntry 1 }

wtTrapReceiver2x2PortOutputText OBJECT-TYPE
    SYNTAX OCTET STRING 
    ACCESS read-write
    STATUS mandatory
    DESCRIPTION
        "Description of the output."
    ::= { wtTrapReceiver2x2OutputPortEntry 2 }

wtTrapReceiver2x2PortPulseDuration OBJECT-TYPE
    SYNTAX INTEGER
    ACCESS read-write
    STATUS mandatory
    DESCRIPTION
        "Pulse length in 1/1000 sec. Setting this value to zero, disables the pulse output."
    ::= { wtTrapReceiver2x2OutputPortEntry 9 }

wtTrapReceiver2x2PortPulsePolarity OBJECT-TYPE
    SYNTAX OCTET STRING (SIZE (4))
    ACCESS read-write
    STATUS mandatory
    DESCRIPTION
        "This value defines the polarity of the output pulse, if wtTrapReceiver2x2PortPulseDuration is not set to zero.
        After the pulse is finished, the output switches back to the opposite state.
        OCTET 1: unused
        OCTET 2: unused
        OCTET 3: unused
        	OCTET 4: 
        	 Bit 0   : negative polarity
        	 Bit 1   : positive polarity
        	 Bit 2-7 : unused"
    ::= { wtTrapReceiver2x2OutputPortEntry 10 }

-- wtTrapReceiver2x2Manufact Group
----------------------------

wtTrapReceiver2x2MfName OBJECT-TYPE
    SYNTAX OCTET STRING 
    ACCESS read-write
    STATUS mandatory
    DESCRIPTION
        "Manufacturer company name"
    ::= { wtTrapReceiver2x2Manufact 1 }

wtTrapReceiver2x2MfAddr OBJECT-TYPE
    SYNTAX OCTET STRING 
    ACCESS read-write
    STATUS mandatory
    DESCRIPTION
        "Manufacturer address."
    ::= { wtTrapReceiver2x2Manufact 2 }

wtTrapReceiver2x2MfHotline OBJECT-TYPE
    SYNTAX OCTET STRING 
    ACCESS read-write
    STATUS mandatory
    DESCRIPTION
        "Manufacturer hotline."
    ::= { wtTrapReceiver2x2Manufact 3 }

wtTrapReceiver2x2MfInternet OBJECT-TYPE
    SYNTAX OCTET STRING 
    ACCESS read-write
    STATUS mandatory
    DESCRIPTION
        "Manufacturer Internet address."
    ::= { wtTrapReceiver2x2Manufact 4 }

wtTrapReceiver2x2MfDeviceTyp OBJECT-TYPE
    SYNTAX OCTET STRING 
    ACCESS read-write
    STATUS mandatory
    DESCRIPTION
        "Manufacturer device name (model number)."
    ::= { wtTrapReceiver2x2Manufact 5 }

-- wtTrapReceiver2x2Diag Group
----------------------------

wtTrapReceiver2x2DiagErrorCount OBJECT-TYPE
    SYNTAX INTEGER
    ACCESS read-only
    STATUS mandatory
    DESCRIPTION
        "Number of entries in the error memory."
    ::= { wtTrapReceiver2x2Diag 1 }

wtTrapReceiver2x2DiagBinaryError OBJECT-TYPE
    SYNTAX OCTET STRING 
    ACCESS read-only
    STATUS mandatory
    DESCRIPTION
        "Error causes coded bit-by-bit."
    ::= { wtTrapReceiver2x2Diag 2 }

wtTrapReceiver2x2DiagErrorIndex OBJECT-TYPE
    SYNTAX INTEGER
    ACCESS read-write
    STATUS mandatory
    DESCRIPTION
        "The value of this variable is used as an index to read 
        an error massege from wtTrapReceiver2x2DiagErrorMessage.
        Errors are numbered from 1 to wtTrapReceiver2x2DiagErrorCount.
        Writing a valid value into this variable, making the appropriate 
        message readable from wtTrapReceiver2x2DiagErrorMessage."
    ::= { wtTrapReceiver2x2Diag 3 }

wtTrapReceiver2x2DiagErrorMessage OBJECT-TYPE
    SYNTAX OCTET STRING 
    ACCESS read-only
    STATUS mandatory
    DESCRIPTION
        "Using wtTrapReceiver2x2DiagErrorIndex as an index, the appropriate message is available."
    ::= { wtTrapReceiver2x2Diag 4 }
    
wtTrapReceiver2x2DiagErrorClear OBJECT-TYPE
    SYNTAX INTEGER
    ACCESS write-only
    STATUS mandatory
    DESCRIPTION
        "Writing 1 into this variable clears all diagnosis messages."
    ::= { wtTrapReceiver2x2Diag 5 }


-- TRAP DEFINITIONS

-- These SNMP traps will be send, if the appropriate trigger condition match

wtTrapReceiver2x2Alert1 TRAP-TYPE
    ENTERPRISE  wtTrapReceiver2x2
    VARIABLES   { wtTrapReceiver2x2ReportSnmpTrapText }
    DESCRIPTION
        "This SNMP trap is generated when Action 1 was triggered,
        SNMP trap enable is set and
        SNMP is enabled."
    -- NMS trap annotation
    --#TYPE "Trap-Receiver Action 1"
    --#SUMMARY "Action 1: %s"
    --#ARGUMENTS {0}
    --#SEVERITY INFORMATIONAL
    --#TIMEINDEX 99
    --#STATE OPERATIONAL    
    ::= 41

wtTrapReceiver2x2Alert2 TRAP-TYPE
    ENTERPRISE  wtTrapReceiver2x2
    VARIABLES   { wtTrapReceiver2x2ActionSnmpTrapText }
    DESCRIPTION
        "This SNMP trap is generated when Action 2 was triggered,
        SNMP trap enable is set and
        SNMP is enabled."
    -- NMS trap annotation
    --#TYPE "Trap-Receiver Action 2"
    --#SUMMARY "Action 2: %s"
    --#ARGUMENTS {0}
    --#SEVERITY INFORMATIONAL
    --#TIMEINDEX 99
    --#STATE OPERATIONAL    
    ::= 42

wtTrapReceiver2x2Alert3 TRAP-TYPE
    ENTERPRISE  wtTrapReceiver2x2
    VARIABLES   { wtTrapReceiver2x2ActionSnmpTrapText }
    DESCRIPTION
        "This SNMP trap is generated when Action 3 was triggered,
        SNMP trap enable is set and
        SNMP is enabled."
    -- NMS trap annotation
    --#TYPE "Trap-Receiver Action 3"
    --#SUMMARY "Action 3: %s"
    --#ARGUMENTS {0}
    --#SEVERITY INFORMATIONAL
    --#TIMEINDEX 99
    --#STATE OPERATIONAL    
    ::= 43

wtTrapReceiver2x2Alert4 TRAP-TYPE
    ENTERPRISE  wtTrapReceiver2x2
    VARIABLES   { wtTrapReceiver2x2ActionSnmpTrapText }
    DESCRIPTION
        "This SNMP trap is generated when Action 4 was triggered,
        SNMP trap enable is set and
        SNMP is enabled."
    -- NMS trap annotation
    --#TYPE "Trap-Receiver Action 4"
    --#SUMMARY "Action 4: %s"
    --#ARGUMENTS {0}
    --#SEVERITY INFORMATIONAL
    --#TIMEINDEX 99
    --#STATE OPERATIONAL    
    ::= 44

wtTrapReceiver2x2Alert5 TRAP-TYPE
    ENTERPRISE  wtTrapReceiver2x2
    VARIABLES   { wtTrapReceiver2x2ActionSnmpTrapText }
    DESCRIPTION
        "This SNMP trap is generated when Action 5 was triggered,
        SNMP trap enable is set and
        SNMP is enabled."
    -- NMS trap annotation
    --#TYPE "Trap-Receiver Action 5"
    --#SUMMARY "Action 5: %s"
    --#ARGUMENTS {0}
    --#SEVERITY INFORMATIONAL
    --#TIMEINDEX 99
    --#STATE OPERATIONAL    
    ::= 45

wtTrapReceiver2x2Alert6 TRAP-TYPE
    ENTERPRISE  wtTrapReceiver2x2
    VARIABLES   { wtTrapReceiver2x2ActionSnmpTrapText }
    DESCRIPTION
        "This SNMP trap is generated when Action 6 was triggered,
        SNMP trap enable is set and
        SNMP is enabled."
    -- NMS trap annotation
    --#TYPE "Trap-Receiver Action 6"
    --#SUMMARY "Action 6: %s"
    --#ARGUMENTS {0}
    --#SEVERITY INFORMATIONAL
    --#TIMEINDEX 99
    --#STATE OPERATIONAL    
    ::= 46

wtTrapReceiver2x2Alert7 TRAP-TYPE
    ENTERPRISE  wtTrapReceiver2x2
    VARIABLES   { wtTrapReceiver2x2ActionSnmpTrapText }
    DESCRIPTION
        "This SNMP trap is generated when Action 7 was triggered,
        SNMP trap enable is set and
        SNMP is enabled."
    -- NMS trap annotation
    --#TYPE "Trap-Receiver Action 7"
    --#SUMMARY "Action 7: %s"
    --#ARGUMENTS {0}
    --#SEVERITY INFORMATIONAL
    --#TIMEINDEX 99
    --#STATE OPERATIONAL    
    ::= 47

wtTrapReceiver2x2Alert8 TRAP-TYPE
    ENTERPRISE  wtTrapReceiver2x2
    VARIABLES   { wtTrapReceiver2x2ActionSnmpTrapText }
    DESCRIPTION
        "This SNMP trap is generated when Action 8 was triggered,
        SNMP trap enable is set and
        SNMP is enabled."
    -- NMS trap annotation
    --#TYPE "Trap-Receiver Action 8"
    --#SUMMARY "Action 8: %s"
    --#ARGUMENTS {0}
    --#SEVERITY INFORMATIONAL
    --#TIMEINDEX 99
    --#STATE OPERATIONAL    
    ::= 48

wtTrapReceiver2x2Alert9 TRAP-TYPE
    ENTERPRISE  wtTrapReceiver2x2
    VARIABLES   { wtTrapReceiver2x2ActionSnmpTrapText }
    DESCRIPTION
        "This SNMP trap is generated when Action 9 was triggered,
        SNMP trap enable is set and
        SNMP is enabled."
    -- NMS trap annotation
    --#TYPE "Trap-Receiver Action 9"
    --#SUMMARY "Action 9: %s"
    --#ARGUMENTS {0}
    --#SEVERITY INFORMATIONAL
    --#TIMEINDEX 99
    --#STATE OPERATIONAL    
    ::= 49

wtTrapReceiver2x2Alert10 TRAP-TYPE
    ENTERPRISE  wtTrapReceiver2x2
    VARIABLES   { wtTrapReceiver2x2ActionSnmpTrapText }
    DESCRIPTION
        "This SNMP trap is generated when Action 10 was triggered,
        SNMP trap enable is set and
        SNMP is enabled."
    -- NMS trap annotation
    --#TYPE "Trap-Receiver Action 10"
    --#SUMMARY "Action 10: %s"
    --#ARGUMENTS {0}
    --#SEVERITY INFORMATIONAL
    --#TIMEINDEX 99
    --#STATE OPERATIONAL    
    ::= 50

wtTrapReceiver2x2Alert11 TRAP-TYPE
    ENTERPRISE  wtTrapReceiver2x2
    VARIABLES   { wtTrapReceiver2x2ActionSnmpTrapText }
    DESCRIPTION
        "This SNMP trap is generated when Action 11 was triggered,
        SNMP trap enable is set and
        SNMP is enabled."
    -- NMS trap annotation
    --#TYPE "Trap-Receiver Action 11"
    --#SUMMARY "Action 11: %s"
    --#ARGUMENTS {0}
    --#SEVERITY INFORMATIONAL
    --#TIMEINDEX 99
    --#STATE OPERATIONAL    
    ::= 51

wtTrapReceiver2x2Alert12 TRAP-TYPE
    ENTERPRISE  wtTrapReceiver2x2
    VARIABLES   { wtTrapReceiver2x2ActionSnmpTrapText }
    DESCRIPTION
        "This SNMP trap is generated when Action 12 was triggered,
        SNMP trap enable is set and
        SNMP is enabled."
    -- NMS trap annotation
    --#TYPE "Trap-Receiver Action 12"
    --#SUMMARY "Action 12: %s"
    --#ARGUMENTS {0}
    --#SEVERITY INFORMATIONAL
    --#TIMEINDEX 99
    --#STATE OPERATIONAL    
    ::= 52



wtTrapReceiver2x2AlertDiag TRAP-TYPE
    ENTERPRISE  wtTrapReceiver2x2
    VARIABLES   { 	
    		wtTrapReceiver2x2DiagErrorIndex,
    	  	wtTrapReceiver2x2DiagErrorMessage
    		}
    DESCRIPTION
        "This SNMP trap is generated when a diagnosis/error message was triggered,
        SNMP trap enable is set and
        SNMP is enabled."
    -- NMS trap annotation
    --#TYPE "Trap-Receiver Diagnose Error"
    --#SUMMARY "Diagnose error index: %d, Message: %s."
    --#ARGUMENTS {0,1}
    --#SEVERITY MAJOR
    --#TIMEINDEX 99
    --#STATE DEGRADED    
    ::= 110


--------------------------------------------------------------------------------
--------------------------------------------------------------------------------
--------------------------------------------------------------------------------



END
