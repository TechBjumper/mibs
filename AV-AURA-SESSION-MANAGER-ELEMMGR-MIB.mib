-- Avaya Aura Session Manager MIB
-- Copyright (c) 2008-2009 by Avaya Inc. All rights reserved. 
-- MIB version 1.0.0 
-- Avaya Compas ID: NA

AV-AURA-SESSION-MANAGER-ELEMMGR-MIB DEFINITIONS ::= BEGIN

-- Add your MIB specific imports in the below import section.
IMPORTS 
MODULE-IDENTITY, OBJECT-TYPE, NOTIFICATION-TYPE, enterprises
    FROM SNMPv2-SMI
InetAddressIPv6
    FROM INET-ADDRESS-MIB
MODULE-COMPLIANCE, OBJECT-GROUP
    FROM SNMPv2-CONF
SnmpAdminString
    FROM SNMP-FRAMEWORK-MIB
DateAndTime
    FROM SNMPv2-TC;

        
--
-- The following are defined in Avaya Aura Session Manager-MIB
--
avaya              OBJECT IDENTIFIER ::= { enterprises 6889 }
products           OBJECT IDENTIFIER ::= { avaya 1 }
mibs               OBJECT IDENTIFIER ::= { avaya 2 }

avAuraSessMgrProd OBJECT IDENTIFIER ::= { products 36 }
avAuraSessMgrMibs MODULE-IDENTITY
       LAST-UPDATED "201301211353Z" -- 21 January 2013
       ORGANIZATION "Avaya, Inc."
       CONTACT-INFO "Avaya Customer Services

                     Postal: Avaya, Inc.
                             211 Mount Airy Rd
                             Basking Ridge. NJ 07920
                             USA
                             Tel: +1 908 953 6000
                             WWW: http://www.avaya.com"
       DESCRIPTION "This MIB module is for exposing Avaya Aura Session Manager inventory information via SNMP GET."
       
       REVISION 	"201301211353Z" -- 21 January 2013
       DESCRIPTION "MIB Version 1.0.0 - autobuild. Generated via the MIBTOOL."
             
       
       ::= { mibs 36 }

avAuraSessMgrMibNotifications OBJECT IDENTIFIER ::= { avAuraSessMgrMibs 0 }

avAuraSessMgrMibObjects OBJECT IDENTIFIER ::= { avAuraSessMgrMibs 1 }
avAuraSessMgrMibConformance OBJECT IDENTIFIER ::= { avAuraSessMgrMibs 2 }

-- Avaya Aura Session Manager Notifications (avAuraSessMgrMibNotifications) will be added here
-----------------------------------------------------------------------
-- According to RFC 2578 section 8.5, the next to last sub-identifier
-- in the name of any newly defined notification must have the value
-- zero. This is to achieve compatibility with SNMPv1 traps.
------------------------------------------------------------------------
-------------------NOTIFICATION OBJECTS *********************************START
avSessMgrTestAlarm NOTIFICATION-TYPE
	STATUS current
	DESCRIPTION
	"test alarm(Minor)"
	::= { avAuraSessMgrMibNotifications 211 }

avSessMgrTestClearAlarm NOTIFICATION-TYPE
	STATUS current
	DESCRIPTION
	"Clear alarm(Minor)"
	::= { avAuraSessMgrMibNotifications 212 }

avSessMgrMMTC20011 NOTIFICATION-TYPE
	STATUS current
	DESCRIPTION
	"Postgres database sanity check failed; the database is unaccessible(Major)"
	::= { avAuraSessMgrMibNotifications 221 }

avSessMgrMMTC20019 NOTIFICATION-TYPE
	STATUS current
	DESCRIPTION
	"SAL-Agent sanity check failed; alarms are not being processed(Minor)"
	::= { avAuraSessMgrMibNotifications 223 }

avSessMgrMMTC20033 NOTIFICATION-TYPE
	STATUS current
	DESCRIPTION
	"Management Instance check failed(Minor)"
	::= { avAuraSessMgrMibNotifications 225 }

avSessMgrMMTC20043 NOTIFICATION-TYPE
	STATUS current
	DESCRIPTION
	"Management BSM Instance check failed(Minor)"
	::= { avAuraSessMgrMibNotifications 227 }

avSessMgrMMTC20045 NOTIFICATION-TYPE
	STATUS current
	DESCRIPTION
	"SM/BSM host name resolution failed(Minor)"
	::= { avAuraSessMgrMibNotifications 229 }

avSessMgrMPER20226 NOTIFICATION-TYPE
	STATUS current
	DESCRIPTION
	"Performance Management disk usage threshold warning(Minor)"
	::= { avAuraSessMgrMibNotifications 231 }

avSessMgrMPER20227 NOTIFICATION-TYPE
	STATUS current
	DESCRIPTION
	"Performance Management disk usage limit and collection disabled(Major)"
	::= { avAuraSessMgrMibNotifications 233 }

avSessMgrMPER20228 NOTIFICATION-TYPE
	STATUS current
	DESCRIPTION
	"NFS server used for performance data storage not accessible(Minor)"
	::= { avAuraSessMgrMibNotifications 235 }

avSessMgrMPER20229 NOTIFICATION-TYPE
	STATUS current
	DESCRIPTION
	"NFS server used for performance data storage not accessible(Major)"
	::= { avAuraSessMgrMibNotifications 237 }

avSessMgrLIC20251 NOTIFICATION-TYPE
	STATUS current
	DESCRIPTION
	"SIP session counts exceeded the licensed number(Warning)"
	::= { avAuraSessMgrMibNotifications 239 }

-------------------NOTIFICATION OBJECTS*******************************************END
END
