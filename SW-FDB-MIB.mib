-- Revision 1.0.0
-- Copyright 1999 D-Link, Inc.
-- All rights reserved.

SW-FDB-MIB      DEFINITIONS ::= BEGIN
    IMPORTS
        OBJECT-TYPE     FROM RFC-1212
        enterprises     FROM RFC1155-SMI;        

    MacAddress  ::= OCTET STRING(SIZE(6))
    PortList    ::= OCTET STRING(SIZE(4))
    
    marconi     OBJECT IDENTIFIER ::= { enterprises 326 }
    systems     OBJECT IDENTIFIER ::= { marconi 2 }
    external    OBJECT IDENTIFIER ::= { systems 20 }
    dlink       OBJECT IDENTIFIER ::= { external 1 }

    dlinkcommon OBJECT IDENTIFIER ::= { dlink 1 }

    golf        OBJECT IDENTIFIER ::= { dlink 2 }
    golfproducts        OBJECT IDENTIFIER ::= { golf 1 }
    es2000              OBJECT IDENTIFIER ::= { golfproducts 3 }

    golfcommon          OBJECT IDENTIFIER ::= { golf 2 }

    marconi-mgmt    OBJECT IDENTIFIER ::= { golfcommon 2 }    

    es2000Mgmt      OBJECT IDENTIFIER ::= { marconi-mgmt 28 }

    swL2Mgmt        OBJECT IDENTIFIER ::= { es2000Mgmt 2 }

    swFDB           OBJECT IDENTIFIER ::= { swL2Mgmt 9 }

    endOfMIB OBJECT-TYPE
        SYNTAX  INTEGER
        ACCESS  read-only
        STATUS  optional
DESCRIPTION ""
        ::= { es2000Mgmt 9999 }

-- *****************************************************************************
--  swFdbStaticTable
-- *****************************************************************************
    swFdbStaticTable OBJECT-TYPE
        SYNTAX  SEQUENCE OF SwFdbStaticEntry
        ACCESS  not-accessible
        STATUS  mandatory
        DESCRIPTION
            "This table defines for frames with specific destincation MAC address,
             the set of ports that the frame will be forwarded to. Note that if a MAC
             address appears in this table also appears in the filter table, the filter
             table has higher priority over than this table. See swFdbFilterTable description."
        ::= { swFDB 1 }

    swFdbStaticEntry OBJECT-TYPE
        SYNTAX  SwFdbStaticEntry
        ACCESS  not-accessible
        STATUS  mandatory
        DESCRIPTION
            "A list of information specifies which ports the frames with specific
             destination MAC address to go."
        INDEX   { swFdbStaticVid , swFdbStaticAddress }
        ::= { swFdbStaticTable 1 }

    SwFdbStaticEntry ::=
        SEQUENCE {
            swFdbStaticVid
                INTEGER,
            swFdbStaticAddress
                MacAddress,
            swFdbStaticPortMap
                PortList,
            swFdbStaticState
                INTEGER,
            swFdbStaticStatus
                INTEGER
        }

    swFdbStaticVid OBJECT-TYPE
        SYNTAX  INTEGER
        ACCESS  read-only
        STATUS  mandatory
        DESCRIPTION
            "This object indicates the VLAN-ID. If the swVlanInfoStatus is
             port-base mode, the object ranges from 1 to 12. If VLAN is in
             mac-based mode or disabled, the object indicates the default
             VLAN-ID(0)."
        ::= { swFdbStaticEntry 1 }

    swFdbStaticAddress OBJECT-TYPE
        SYNTAX  MacAddress
        ACCESS  read-only
        STATUS  mandatory
        DESCRIPTION
            "The MAC address which this forwarding entry applied.
             It can be an unicast address or a multicast address."
        ::= { swFdbStaticEntry 2 }

    swFdbStaticPortMap OBJECT-TYPE
        SYNTAX  PortList
        ACCESS  read-write
        STATUS  mandatory
        DESCRIPTION
            "The set of ports to which frames received containing the value of
             swFdbStaticAddress as the DA, are allowed to be forwarded. Each
             octet within the value of this object specifies a set of eight ports,
             with the first octet specifying ports 1 through 8, the second octet
             specifying ports 9 through 16, etc. Within each octet, the most
             significant bit represents the lowest numbered port, and the least
             significant bit represents the highest numbered port. Thus, each port
             of the bridge is represented by a single bit within the value of this
             object. If that bit has a value of '1' then that port is included in
             the set of ports; the port is not included if its bit has a value of
             '0'.(Note that the setting of the bit corresponding to the port from
             which a frame is received is irrelevant.)"
        ::= { swFdbStaticEntry 3 }

    swFdbStaticState OBJECT-TYPE
        SYNTAX  INTEGER {
            other(1),
            invalid(2),
            valid(3)
        }
        ACCESS  read-write
        STATUS  mandatory
        DESCRIPTION
            "This object indicates the status of this entry.
             other(1) - This entry is currently in use but the conditions under
                        which it will remain so are different from each of the
                        following values.
             invalid(2) - Writing this value to the object, and then the
                          corresponding entry will be removed from the table.
             valid(3) - This entry is reside in the table."
        ::= { swFdbStaticEntry 4 }

    swFdbStaticStatus OBJECT-TYPE
        SYNTAX  INTEGER {
            other(1),
            apply(2),
            not-apply(3)
        }
        ACCESS  read-only
        STATUS  mandatory
        DESCRIPTION
            "This object indicates the status of this entry.
             other(1) - This entry is currently in use but the conditions under
                        which it will remain so are different from each of the
                        following values.
             apply(2) - This entry is currently in use and reside in the table.
             not-apply(3) - This entry is reside in the table but currently not
                            in use due to conflict with filter table."
        ::= { swFdbStaticEntry 5 }

-- *****************************************************************************
--  swFdbStaticMemberTable
-- *****************************************************************************
    swFdbStaticMemberTable OBJECT-TYPE
        SYNTAX  SEQUENCE OF SwFdbStaticMemberEntry
        ACCESS  not-accessible
        STATUS  mandatory
        DESCRIPTION
            "A list of information provide a different view for those ports
             where packets from the given Vlan need to be forwarded to."
        ::= { swFDB 2 }

    swFdbStaticMemberEntry OBJECT-TYPE
        SYNTAX  SwFdbStaticMemberEntry
        ACCESS  not-accessible
        STATUS  mandatory
        DESCRIPTION
            "A list of MIB capability entries supported by this forwarding static table."
        INDEX   { swFdbStaticMemberVid, swFdbStaticMemberAddress ,
                  swFdbStaticMemberUnitIndex, swFdbStaticMemberModuleIndex,
                  swFdbStaticMemberPortIndex }
        ::= { swFdbStaticMemberTable 1 }

    SwFdbStaticMemberEntry ::=
        SEQUENCE {
            swFdbStaticMemberVid
                INTEGER,
            swFdbStaticMemberAddress
                MacAddress,
            swFdbStaticMemberUnitIndex
                INTEGER,
            swFdbStaticMemberModuleIndex
                INTEGER,
            swFdbStaticMemberPortIndex
                INTEGER
        }

    swFdbStaticMemberVid OBJECT-TYPE
        SYNTAX  INTEGER
        ACCESS  read-only
        STATUS  mandatory
        DESCRIPTION
            "This object indicates the VLAN-ID. If the swVlanInfoStatus is
             port-base mode, the object ranges from 1 to 12. If VLAN is in
             mac-based mode or disabled, the object indicates the default
             VLAN-ID(0)."
        ::= { swFdbStaticMemberEntry 1 }

    swFdbStaticMemberAddress OBJECT-TYPE
        SYNTAX  MacAddress
        ACCESS  read-only
        STATUS  mandatory
        DESCRIPTION
            "The MAC address which this forwarding entry applied.
             It can be an unicast address or a multicast address."
        ::= { swFdbStaticMemberEntry 2 }

    swFdbStaticMemberUnitIndex OBJECT-TYPE
        SYNTAX  INTEGER
        ACCESS  read-only
        STATUS  mandatory
        DESCRIPTION
            "Specifies the unit ID where the port is located."
        ::= { swFdbStaticMemberEntry 3 }

    swFdbStaticMemberModuleIndex OBJECT-TYPE
        SYNTAX  INTEGER
        ACCESS  read-only
        STATUS  mandatory
        DESCRIPTION
            "Specifies the module ID where the port is located."
        ::= { swFdbStaticMemberEntry 4 }

    swFdbStaticMemberPortIndex OBJECT-TYPE
        SYNTAX  INTEGER
        ACCESS  read-only
        STATUS  mandatory
        DESCRIPTION
            "Specifies the port index relative to the module."
        ::= { swFdbStaticMemberEntry 5 }

-- *****************************************************************************
--  swFdbFilterTable
-- *****************************************************************************
    swFdbFilterTable OBJECT-TYPE
        SYNTAX  SEQUENCE OF SwFdbFilterEntry
        ACCESS  not-accessible
        STATUS  mandatory
        DESCRIPTION
            "This table defines information for the device to filter packets
             with specific MAC address (either as the DA or as the SA). The MAC
             address can be a unicast address or a multicast address. This table
             has higher priority than both static FDB table and IGMP table.
             It means that if a MAC address appears on this table also appears
             on the static FDB table, the device will use the information
             provide by this table to process the packet."
        ::= { swFDB 3 }

    swFdbFilterEntry OBJECT-TYPE
        SYNTAX  SwFdbFilterEntry
        ACCESS  not-accessible
        STATUS  mandatory
        DESCRIPTION
            "A list of information about a specific unicast/multicast MAC
             address for which the switch has filtering information."
        INDEX   { swFdbFilterVid, swFdbFilterAddress }
        ::= { swFdbFilterTable 1 }

    SwFdbFilterEntry ::=
        SEQUENCE {
            swFdbFilterVid
                INTEGER,
            swFdbFilterAddress
                MacAddress,
            swFdbFilterState
                INTEGER
        }

    swFdbFilterVid OBJECT-TYPE
        SYNTAX  INTEGER
        ACCESS  read-only
        STATUS  mandatory
        DESCRIPTION
            "This object indicates the VLAN-ID. If the swVlanInfoStatus is
             port-base mode, the object ranges from 1 to 12. If VLAN is in
             mac-based mode or disabled, the object indicates the default
             VLAN-ID(0)."
        ::= { swFdbFilterEntry 1 }

    swFdbFilterAddress OBJECT-TYPE
        SYNTAX  MacAddress
        ACCESS  read-only
        STATUS  mandatory
        DESCRIPTION
            "This object indicates a unicast/multicast MAC address for which
             the bridge has filtering information."
        ::= { swFdbFilterEntry 2 }

    swFdbFilterState OBJECT-TYPE
        SYNTAX  INTEGER {
            other(1),
            invalid(2),
            valid(3),
            dst-src-addr(4)
        }
        ACCESS  read-write
        STATUS  mandatory
        DESCRIPTION
            "This object indicates the status of this entry.
             other(1) - This entry is currently in use but the conditions under
                        which it will remain so are different from each of the
                        following values.
             invalid(2) - Writing this value to the object, and then the
                          corresponding entry will be removed from the table.
             valid(3) - Writing this value to the object, and then the
                        corresponding entry will be added into the table.
             dst-src-addr(4) - Recieved frames's destination address or source
                               address are currently used to be filtered as it
                               meets with the MAC address entry of the table."
        ::= { swFdbFilterEntry 3 }

END
