-- file automatically created


TELDAT-TRAP-IPSF-MIB DEFINITIONS ::= BEGIN


IMPORTS
	MODULE-IDENTITY,OBJECT-TYPE,OBJECT-IDENTITY,NOTIFICATION-TYPE,Integer32,IpAddress
		FROM SNMPv2-SMI
	DisplayString
		FROM SNMPv2-TC
	telEventTraps
		FROM TELDAT-MIB;


ipsfTrapsMIB MODULE-IDENTITY
    LAST-UPDATED "201401200930Z"
    ORGANIZATION "Teldat, S.A."
    CONTACT-INFO 
        "Teldat, S.A.
        Customer Service

        Postal: Parque Tecnologico de Madrid
                Tres Cantos 28760
                Madrid, SPAIN

        Tel.: +34 918 076 565

        http://www.teldat.com"
    DESCRIPTION
        "This Module Information Base file is defined for managing received
        SNMP notifications generated by the IPSF event subsystem."
    REVISION "201401200930Z"
    DESCRIPTION "Initial implementation"
        ::= { telEventTraps 230 }


ipsfEventsGroup	OBJECT IDENTIFIER	::= { ipsfTrapsMIB 1 }

ipsfNotifications	OBJECT IDENTIFIER	::= { ipsfTrapsMIB 2 }
ipsfNotificationsPrefix	OBJECT IDENTIFIER	::= { ipsfNotifications 0 }

ipsfEventObjects1 OBJECT-IDENTITY
    STATUS current
    DESCRIPTION
        "Event IPSF.1
        Generic abnormal internal error message."
    ::= { ipsfEventsGroup 1 }

ipsf1-message OBJECT-TYPE
    SYNTAX DisplayString
    MAX-ACCESS accessible-for-notify
    STATUS current
    DESCRIPTION
        "Parameter 'message' in event IPSF.1"
    ::= { ipsfEventObjects1 1 }

ipsfEventObjects2 OBJECT-IDENTITY
    STATUS current
    DESCRIPTION
        "Event IPSF.2
        Generic usual internal error message."
    ::= { ipsfEventsGroup 2 }

ipsf2-message OBJECT-TYPE
    SYNTAX DisplayString
    MAX-ACCESS accessible-for-notify
    STATUS current
    DESCRIPTION
        "Parameter 'message' in event IPSF.2"
    ::= { ipsfEventObjects2 1 }

ipsfEventObjects3 OBJECT-IDENTITY
    STATUS current
    DESCRIPTION
        "Event IPSF.3
        Generic abnormal external error message."
    ::= { ipsfEventsGroup 3 }

ipsf3-message OBJECT-TYPE
    SYNTAX DisplayString
    MAX-ACCESS accessible-for-notify
    STATUS current
    DESCRIPTION
        "Parameter 'message' in event IPSF.3"
    ::= { ipsfEventObjects3 1 }

ipsfEventObjects4 OBJECT-IDENTITY
    STATUS current
    DESCRIPTION
        "Event IPSF.4
        Generic usual external error message."
    ::= { ipsfEventsGroup 4 }

ipsf4-message OBJECT-TYPE
    SYNTAX DisplayString
    MAX-ACCESS accessible-for-notify
    STATUS current
    DESCRIPTION
        "Parameter 'message' in event IPSF.4"
    ::= { ipsfEventObjects4 1 }

ipsfEventObjects5 OBJECT-IDENTITY
    STATUS current
    DESCRIPTION
        "Event IPSF.5
        Generic comment on abnormal information message."
    ::= { ipsfEventsGroup 5 }

ipsf5-message OBJECT-TYPE
    SYNTAX DisplayString
    MAX-ACCESS accessible-for-notify
    STATUS current
    DESCRIPTION
        "Parameter 'message' in event IPSF.5"
    ::= { ipsfEventObjects5 1 }

ipsfEventObjects6 OBJECT-IDENTITY
    STATUS current
    DESCRIPTION
        "Event IPSF.6
        Generic comment on usual information message."
    ::= { ipsfEventsGroup 6 }

ipsf6-message OBJECT-TYPE
    SYNTAX DisplayString
    MAX-ACCESS accessible-for-notify
    STATUS current
    DESCRIPTION
        "Parameter 'message' in event IPSF.6"
    ::= { ipsfEventObjects6 1 }

ipsfEventObjects7 OBJECT-IDENTITY
    STATUS current
    DESCRIPTION
        "Event IPSF.7
        Generic packet trace message."
    ::= { ipsfEventsGroup 7 }

ipsf7-message OBJECT-TYPE
    SYNTAX DisplayString
    MAX-ACCESS accessible-for-notify
    STATUS current
    DESCRIPTION
        "Parameter 'message' in event IPSF.7"
    ::= { ipsfEventObjects7 1 }

ipsfEventObjects8 OBJECT-IDENTITY
    STATUS current
    DESCRIPTION
        "Event IPSF.8
        Generic abnormal operation trace message."
    ::= { ipsfEventsGroup 8 }

ipsf8-message OBJECT-TYPE
    SYNTAX DisplayString
    MAX-ACCESS accessible-for-notify
    STATUS current
    DESCRIPTION
        "Parameter 'message' in event IPSF.8"
    ::= { ipsfEventObjects8 1 }

ipsfEventObjects9 OBJECT-IDENTITY
    STATUS current
    DESCRIPTION
        "Event IPSF.9
        Generic usual operation trace message."
    ::= { ipsfEventsGroup 9 }

ipsf9-message OBJECT-TYPE
    SYNTAX DisplayString
    MAX-ACCESS accessible-for-notify
    STATUS current
    DESCRIPTION
        "Parameter 'message' in event IPSF.9"
    ::= { ipsfEventObjects9 1 }

ipsfEventObjects10 OBJECT-IDENTITY
    STATUS current
    DESCRIPTION
        "Event IPSF.10
        The generic event level is wrong."
    ::= { ipsfEventsGroup 10 }

ipsf10-event-level OBJECT-TYPE
    SYNTAX Integer32
    MAX-ACCESS accessible-for-notify
    STATUS current
    DESCRIPTION
        "Parameter 'event-level' in event IPSF.10"
    ::= { ipsfEventObjects10 1 }

ipsf10-message OBJECT-TYPE
    SYNTAX DisplayString
    MAX-ACCESS accessible-for-notify
    STATUS current
    DESCRIPTION
        "Parameter 'message' in event IPSF.10"
    ::= { ipsfEventObjects10 2 }

ipsfEventObjects11 OBJECT-IDENTITY
    STATUS current
    DESCRIPTION
        "Event IPSF.11
        A new peer has been added to the session list."
    ::= { ipsfEventsGroup 11 }

ipsf11-peerID OBJECT-TYPE
    SYNTAX Integer32
    MAX-ACCESS accessible-for-notify
    STATUS current
    DESCRIPTION
        "Parameter 'peerID' in event IPSF.11"
    ::= { ipsfEventObjects11 1 }

ipsf11-SID OBJECT-TYPE
    SYNTAX DisplayString
    MAX-ACCESS accessible-for-notify
    STATUS current
    DESCRIPTION
        "Parameter 'SID' in event IPSF.11"
    ::= { ipsfEventObjects11 2 }

ipsf11-SID-value OBJECT-TYPE
    SYNTAX Integer32
    MAX-ACCESS accessible-for-notify
    STATUS current
    DESCRIPTION
        "Parameter 'SID-value' in event IPSF.11"
    ::= { ipsfEventObjects11 3 }

ipsfEventObjects12 OBJECT-IDENTITY
    STATUS current
    DESCRIPTION
        "Event IPSF.12
        A peer has been deleted from the session list."
    ::= { ipsfEventsGroup 12 }

ipsf12-peerID OBJECT-TYPE
    SYNTAX Integer32
    MAX-ACCESS accessible-for-notify
    STATUS current
    DESCRIPTION
        "Parameter 'peerID' in event IPSF.12"
    ::= { ipsfEventObjects12 1 }

ipsf12-SID OBJECT-TYPE
    SYNTAX DisplayString
    MAX-ACCESS accessible-for-notify
    STATUS current
    DESCRIPTION
        "Parameter 'SID' in event IPSF.12"
    ::= { ipsfEventObjects12 2 }

ipsf12-SID-value OBJECT-TYPE
    SYNTAX Integer32
    MAX-ACCESS accessible-for-notify
    STATUS current
    DESCRIPTION
        "Parameter 'SID-value' in event IPSF.12"
    ::= { ipsfEventObjects12 3 }

ipsfEventObjects13 OBJECT-IDENTITY
    STATUS current
    DESCRIPTION
        "Event IPSF.13
        The specified message could not be sent to IPSecFT queue."
    ::= { ipsfEventsGroup 13 }

ipsf13-type OBJECT-TYPE
    SYNTAX DisplayString
    MAX-ACCESS accessible-for-notify
    STATUS current
    DESCRIPTION
        "Parameter 'type' in event IPSF.13"
    ::= { ipsfEventObjects13 1 }

ipsf13-reason OBJECT-TYPE
    SYNTAX DisplayString
    MAX-ACCESS accessible-for-notify
    STATUS current
    DESCRIPTION
        "Parameter 'reason' in event IPSF.13"
    ::= { ipsfEventObjects13 2 }

ipsfEventObjects14 OBJECT-IDENTITY
    STATUS current
    DESCRIPTION
        "Event IPSF.14
        The specified message has been sent to IPSecFT queue."
    ::= { ipsfEventsGroup 14 }

ipsf14-type OBJECT-TYPE
    SYNTAX DisplayString
    MAX-ACCESS accessible-for-notify
    STATUS current
    DESCRIPTION
        "Parameter 'type' in event IPSF.14"
    ::= { ipsfEventObjects14 1 }

ipsfEventObjects15 OBJECT-IDENTITY
    STATUS current
    DESCRIPTION
        "Event IPSF.15
        The specified task has been created."
    ::= { ipsfEventsGroup 15 }

ipsf15-task-name OBJECT-TYPE
    SYNTAX DisplayString
    MAX-ACCESS accessible-for-notify
    STATUS current
    DESCRIPTION
        "Parameter 'task-name' in event IPSF.15"
    ::= { ipsfEventObjects15 1 }

ipsfEventObjects16 OBJECT-IDENTITY
    STATUS current
    DESCRIPTION
        "Event IPSF.16
        The specified session has change its state."
    ::= { ipsfEventsGroup 16 }

ipsf16-current-state OBJECT-TYPE
    SYNTAX DisplayString
    MAX-ACCESS accessible-for-notify
    STATUS current
    DESCRIPTION
        "Parameter 'current-state' in event IPSF.16"
    ::= { ipsfEventObjects16 1 }

ipsf16-new-state OBJECT-TYPE
    SYNTAX DisplayString
    MAX-ACCESS accessible-for-notify
    STATUS current
    DESCRIPTION
        "Parameter 'new-state' in event IPSF.16"
    ::= { ipsfEventObjects16 2 }

ipsf16-SID OBJECT-TYPE
    SYNTAX DisplayString
    MAX-ACCESS accessible-for-notify
    STATUS current
    DESCRIPTION
        "Parameter 'SID' in event IPSF.16"
    ::= { ipsfEventObjects16 3 }

ipsf16-SID-value OBJECT-TYPE
    SYNTAX Integer32
    MAX-ACCESS accessible-for-notify
    STATUS current
    DESCRIPTION
        "Parameter 'SID-value' in event IPSF.16"
    ::= { ipsfEventObjects16 4 }

ipsfEventObjects17 OBJECT-IDENTITY
    STATUS current
    DESCRIPTION
        "Event IPSF.17
        The specified session will change its state."
    ::= { ipsfEventsGroup 17 }

ipsf17-timeout OBJECT-TYPE
    SYNTAX Integer32
    MAX-ACCESS accessible-for-notify
    STATUS current
    DESCRIPTION
        "Parameter 'timeout' in event IPSF.17"
    ::= { ipsfEventObjects17 1 }

ipsf17-current-state OBJECT-TYPE
    SYNTAX DisplayString
    MAX-ACCESS accessible-for-notify
    STATUS current
    DESCRIPTION
        "Parameter 'current-state' in event IPSF.17"
    ::= { ipsfEventObjects17 2 }

ipsf17-new-state OBJECT-TYPE
    SYNTAX DisplayString
    MAX-ACCESS accessible-for-notify
    STATUS current
    DESCRIPTION
        "Parameter 'new-state' in event IPSF.17"
    ::= { ipsfEventObjects17 3 }

ipsf17-SID OBJECT-TYPE
    SYNTAX DisplayString
    MAX-ACCESS accessible-for-notify
    STATUS current
    DESCRIPTION
        "Parameter 'SID' in event IPSF.17"
    ::= { ipsfEventObjects17 4 }

ipsf17-SID-value OBJECT-TYPE
    SYNTAX Integer32
    MAX-ACCESS accessible-for-notify
    STATUS current
    DESCRIPTION
        "Parameter 'SID-value' in event IPSF.17"
    ::= { ipsfEventObjects17 5 }

ipsfEventObjects18 OBJECT-IDENTITY
    STATUS current
    DESCRIPTION
        "Event IPSF.18
        The specified session is connecting."
    ::= { ipsfEventsGroup 18 }

ipsf18-src-addr OBJECT-TYPE
    SYNTAX IpAddress
    MAX-ACCESS accessible-for-notify
    STATUS current
    DESCRIPTION
        "Parameter 'src-addr' in event IPSF.18"
    ::= { ipsfEventObjects18 1 }

ipsf18-src-port OBJECT-TYPE
    SYNTAX Integer32
    MAX-ACCESS accessible-for-notify
    STATUS current
    DESCRIPTION
        "Parameter 'src-port' in event IPSF.18"
    ::= { ipsfEventObjects18 2 }

ipsf18-dst-addr OBJECT-TYPE
    SYNTAX IpAddress
    MAX-ACCESS accessible-for-notify
    STATUS current
    DESCRIPTION
        "Parameter 'dst-addr' in event IPSF.18"
    ::= { ipsfEventObjects18 3 }

ipsf18-dst-port OBJECT-TYPE
    SYNTAX Integer32
    MAX-ACCESS accessible-for-notify
    STATUS current
    DESCRIPTION
        "Parameter 'dst-port' in event IPSF.18"
    ::= { ipsfEventObjects18 4 }

ipsf18-timeout OBJECT-TYPE
    SYNTAX Integer32
    MAX-ACCESS accessible-for-notify
    STATUS current
    DESCRIPTION
        "Parameter 'timeout' in event IPSF.18"
    ::= { ipsfEventObjects18 5 }

ipsf18-SID OBJECT-TYPE
    SYNTAX DisplayString
    MAX-ACCESS accessible-for-notify
    STATUS current
    DESCRIPTION
        "Parameter 'SID' in event IPSF.18"
    ::= { ipsfEventObjects18 6 }

ipsf18-SID-value OBJECT-TYPE
    SYNTAX Integer32
    MAX-ACCESS accessible-for-notify
    STATUS current
    DESCRIPTION
        "Parameter 'SID-value' in event IPSF.18"
    ::= { ipsfEventObjects18 7 }

ipsfEventObjects19 OBJECT-IDENTITY
    STATUS current
    DESCRIPTION
        "Event IPSF.19
        IPSecFT has been started as specified type."
    ::= { ipsfEventsGroup 19 }

ipsf19-type OBJECT-TYPE
    SYNTAX DisplayString
    MAX-ACCESS accessible-for-notify
    STATUS current
    DESCRIPTION
        "Parameter 'type' in event IPSF.19"
    ::= { ipsfEventObjects19 1 }

ipsfEventObjects20 OBJECT-IDENTITY
    STATUS current
    DESCRIPTION
        "Event IPSF.20
        The specified process is being restarted."
    ::= { ipsfEventsGroup 20 }

ipsf20-process OBJECT-TYPE
    SYNTAX DisplayString
    MAX-ACCESS accessible-for-notify
    STATUS current
    DESCRIPTION
        "Parameter 'process' in event IPSF.20"
    ::= { ipsfEventObjects20 1 }

ipsfEventObjects21 OBJECT-IDENTITY
    STATUS current
    DESCRIPTION
        "Event IPSF.21
        The TCP connection has been established."
    ::= { ipsfEventsGroup 21 }

ipsf21-SID-value OBJECT-TYPE
    SYNTAX Integer32
    MAX-ACCESS accessible-for-notify
    STATUS current
    DESCRIPTION
        "Parameter 'SID-value' in event IPSF.21"
    ::= { ipsfEventObjects21 1 }

ipsfEventObjects22 OBJECT-IDENTITY
    STATUS current
    DESCRIPTION
        "Event IPSF.22
        The specified event has been received."
    ::= { ipsfEventsGroup 22 }

ipsf22-event OBJECT-TYPE
    SYNTAX DisplayString
    MAX-ACCESS accessible-for-notify
    STATUS current
    DESCRIPTION
        "Parameter 'event' in event IPSF.22"
    ::= { ipsfEventObjects22 1 }

ipsf22-current-state OBJECT-TYPE
    SYNTAX DisplayString
    MAX-ACCESS accessible-for-notify
    STATUS current
    DESCRIPTION
        "Parameter 'current-state' in event IPSF.22"
    ::= { ipsfEventObjects22 2 }

ipsf22-SID OBJECT-TYPE
    SYNTAX DisplayString
    MAX-ACCESS accessible-for-notify
    STATUS current
    DESCRIPTION
        "Parameter 'SID' in event IPSF.22"
    ::= { ipsfEventObjects22 3 }

ipsf22-SID-value OBJECT-TYPE
    SYNTAX Integer32
    MAX-ACCESS accessible-for-notify
    STATUS current
    DESCRIPTION
        "Parameter 'SID-value' in event IPSF.22"
    ::= { ipsfEventObjects22 4 }

ipsfEventObjects23 OBJECT-IDENTITY
    STATUS current
    DESCRIPTION
        "Event IPSF.23
        The specified packet has been sent."
    ::= { ipsfEventsGroup 23 }

ipsf23-packet-type OBJECT-TYPE
    SYNTAX DisplayString
    MAX-ACCESS accessible-for-notify
    STATUS current
    DESCRIPTION
        "Parameter 'packet-type' in event IPSF.23"
    ::= { ipsfEventObjects23 1 }

ipsf23-len OBJECT-TYPE
    SYNTAX Integer32
    MAX-ACCESS accessible-for-notify
    STATUS current
    DESCRIPTION
        "Parameter 'len' in event IPSF.23"
    ::= { ipsfEventObjects23 2 }

ipsf23-SID OBJECT-TYPE
    SYNTAX DisplayString
    MAX-ACCESS accessible-for-notify
    STATUS current
    DESCRIPTION
        "Parameter 'SID' in event IPSF.23"
    ::= { ipsfEventObjects23 3 }

ipsf23-SID-value OBJECT-TYPE
    SYNTAX Integer32
    MAX-ACCESS accessible-for-notify
    STATUS current
    DESCRIPTION
        "Parameter 'SID-value' in event IPSF.23"
    ::= { ipsfEventObjects23 4 }

ipsfEventObjects24 OBJECT-IDENTITY
    STATUS current
    DESCRIPTION
        "Event IPSF.24
        IPSecFT is listening for incoming data."
    ::= { ipsfEventsGroup 24 }

ipsf24-timeout OBJECT-TYPE
    SYNTAX Integer32
    MAX-ACCESS accessible-for-notify
    STATUS current
    DESCRIPTION
        "Parameter 'timeout' in event IPSF.24"
    ::= { ipsfEventObjects24 1 }

ipsf24-interval OBJECT-TYPE
    SYNTAX DisplayString
    MAX-ACCESS accessible-for-notify
    STATUS current
    DESCRIPTION
        "Parameter 'interval' in event IPSF.24"
    ::= { ipsfEventObjects24 2 }

ipsf24-SID OBJECT-TYPE
    SYNTAX DisplayString
    MAX-ACCESS accessible-for-notify
    STATUS current
    DESCRIPTION
        "Parameter 'SID' in event IPSF.24"
    ::= { ipsfEventObjects24 3 }

ipsf24-SID-value OBJECT-TYPE
    SYNTAX Integer32
    MAX-ACCESS accessible-for-notify
    STATUS current
    DESCRIPTION
        "Parameter 'SID-value' in event IPSF.24"
    ::= { ipsfEventObjects24 4 }

ipsfEventObjects25 OBJECT-IDENTITY
    STATUS current
    DESCRIPTION
        "Event IPSF.25
        The ACK is wrong."
    ::= { ipsfEventsGroup 25 }

ipsf25-reason OBJECT-TYPE
    SYNTAX DisplayString
    MAX-ACCESS accessible-for-notify
    STATUS current
    DESCRIPTION
        "Parameter 'reason' in event IPSF.25"
    ::= { ipsfEventObjects25 1 }

ipsf25-SID OBJECT-TYPE
    SYNTAX DisplayString
    MAX-ACCESS accessible-for-notify
    STATUS current
    DESCRIPTION
        "Parameter 'SID' in event IPSF.25"
    ::= { ipsfEventObjects25 2 }

ipsf25-SID-value OBJECT-TYPE
    SYNTAX Integer32
    MAX-ACCESS accessible-for-notify
    STATUS current
    DESCRIPTION
        "Parameter 'SID-value' in event IPSF.25"
    ::= { ipsfEventObjects25 3 }

ipsfEventObjects26 OBJECT-IDENTITY
    STATUS current
    DESCRIPTION
        "Event IPSF.26
        The specified IP has been inherited."
    ::= { ipsfEventsGroup 26 }

ipsf26-IP OBJECT-TYPE
    SYNTAX IpAddress
    MAX-ACCESS accessible-for-notify
    STATUS current
    DESCRIPTION
        "Parameter 'IP' in event IPSF.26"
    ::= { ipsfEventObjects26 1 }

ipsf26-SID OBJECT-TYPE
    SYNTAX DisplayString
    MAX-ACCESS accessible-for-notify
    STATUS current
    DESCRIPTION
        "Parameter 'SID' in event IPSF.26"
    ::= { ipsfEventObjects26 2 }

ipsf26-SID-value OBJECT-TYPE
    SYNTAX Integer32
    MAX-ACCESS accessible-for-notify
    STATUS current
    DESCRIPTION
        "Parameter 'SID-value' in event IPSF.26"
    ::= { ipsfEventObjects26 3 }

ipsfEventObjects27 OBJECT-IDENTITY
    STATUS current
    DESCRIPTION
        "Event IPSF.27
        Keepalive packet will be sent at the specified time."
    ::= { ipsfEventsGroup 27 }

ipsf27-timer OBJECT-TYPE
    SYNTAX Integer32
    MAX-ACCESS accessible-for-notify
    STATUS current
    DESCRIPTION
        "Parameter 'timer' in event IPSF.27"
    ::= { ipsfEventObjects27 1 }

ipsf27-SID OBJECT-TYPE
    SYNTAX DisplayString
    MAX-ACCESS accessible-for-notify
    STATUS current
    DESCRIPTION
        "Parameter 'SID' in event IPSF.27"
    ::= { ipsfEventObjects27 2 }

ipsf27-SID-value OBJECT-TYPE
    SYNTAX Integer32
    MAX-ACCESS accessible-for-notify
    STATUS current
    DESCRIPTION
        "Parameter 'SID-value' in event IPSF.27"
    ::= { ipsfEventObjects27 3 }

ipsfEventObjects28 OBJECT-IDENTITY
    STATUS current
    DESCRIPTION
        "Event IPSF.28
        IPSecFT is retrieving queued elements."
    ::= { ipsfEventsGroup 28 }

ipsf28-SID OBJECT-TYPE
    SYNTAX DisplayString
    MAX-ACCESS accessible-for-notify
    STATUS current
    DESCRIPTION
        "Parameter 'SID' in event IPSF.28"
    ::= { ipsfEventObjects28 1 }

ipsf28-SID-value OBJECT-TYPE
    SYNTAX Integer32
    MAX-ACCESS accessible-for-notify
    STATUS current
    DESCRIPTION
        "Parameter 'SID-value' in event IPSF.28"
    ::= { ipsfEventObjects28 2 }

ipsfEventObjects29 OBJECT-IDENTITY
    STATUS current
    DESCRIPTION
        "Event IPSF.29
        The specified session has been established."
    ::= { ipsfEventsGroup 29 }

ipsf29-SID OBJECT-TYPE
    SYNTAX DisplayString
    MAX-ACCESS accessible-for-notify
    STATUS current
    DESCRIPTION
        "Parameter 'SID' in event IPSF.29"
    ::= { ipsfEventObjects29 1 }

ipsf29-SID-value OBJECT-TYPE
    SYNTAX Integer32
    MAX-ACCESS accessible-for-notify
    STATUS current
    DESCRIPTION
        "Parameter 'SID-value' in event IPSF.29"
    ::= { ipsfEventObjects29 2 }

ipsfEventObjects30 OBJECT-IDENTITY
    STATUS current
    DESCRIPTION
        "Event IPSF.30
        IPSecFT is waiting for incoming connections."
    ::= { ipsfEventsGroup 30 }

ipsf30-local-addr OBJECT-TYPE
    SYNTAX IpAddress
    MAX-ACCESS accessible-for-notify
    STATUS current
    DESCRIPTION
        "Parameter 'local-addr' in event IPSF.30"
    ::= { ipsfEventObjects30 1 }

ipsf30-local-port OBJECT-TYPE
    SYNTAX Integer32
    MAX-ACCESS accessible-for-notify
    STATUS current
    DESCRIPTION
        "Parameter 'local-port' in event IPSF.30"
    ::= { ipsfEventObjects30 2 }

ipsfEventObjects31 OBJECT-IDENTITY
    STATUS current
    DESCRIPTION
        "Event IPSF.31
        A TCP connection has been accepted."
    ::= { ipsfEventsGroup 31 }

ipsf31-remote-addr OBJECT-TYPE
    SYNTAX IpAddress
    MAX-ACCESS accessible-for-notify
    STATUS current
    DESCRIPTION
        "Parameter 'remote-addr' in event IPSF.31"
    ::= { ipsfEventObjects31 1 }

ipsf31-remote-port OBJECT-TYPE
    SYNTAX Integer32
    MAX-ACCESS accessible-for-notify
    STATUS current
    DESCRIPTION
        "Parameter 'remote-port' in event IPSF.31"
    ::= { ipsfEventObjects31 2 }

ipsf31-local-addr OBJECT-TYPE
    SYNTAX IpAddress
    MAX-ACCESS accessible-for-notify
    STATUS current
    DESCRIPTION
        "Parameter 'local-addr' in event IPSF.31"
    ::= { ipsfEventObjects31 3 }

ipsf31-local-port OBJECT-TYPE
    SYNTAX Integer32
    MAX-ACCESS accessible-for-notify
    STATUS current
    DESCRIPTION
        "Parameter 'local-port' in event IPSF.31"
    ::= { ipsfEventObjects31 4 }

ipsf31-internalID OBJECT-TYPE
    SYNTAX DisplayString
    MAX-ACCESS accessible-for-notify
    STATUS current
    DESCRIPTION
        "Parameter 'internalID' in event IPSF.31"
    ::= { ipsfEventObjects31 5 }

ipsf31-internalID-value OBJECT-TYPE
    SYNTAX Integer32
    MAX-ACCESS accessible-for-notify
    STATUS current
    DESCRIPTION
        "Parameter 'internalID-value' in event IPSF.31"
    ::= { ipsfEventObjects31 6 }

ipsfEventObjects32 OBJECT-IDENTITY
    STATUS current
    DESCRIPTION
        "Event IPSF.32
        A TCP connection has been closed."
    ::= { ipsfEventsGroup 32 }

ipsf32-source-addr OBJECT-TYPE
    SYNTAX IpAddress
    MAX-ACCESS accessible-for-notify
    STATUS current
    DESCRIPTION
        "Parameter 'source-addr' in event IPSF.32"
    ::= { ipsfEventObjects32 1 }

ipsf32-source-port OBJECT-TYPE
    SYNTAX Integer32
    MAX-ACCESS accessible-for-notify
    STATUS current
    DESCRIPTION
        "Parameter 'source-port' in event IPSF.32"
    ::= { ipsfEventObjects32 2 }

ipsf32-destination-addr OBJECT-TYPE
    SYNTAX IpAddress
    MAX-ACCESS accessible-for-notify
    STATUS current
    DESCRIPTION
        "Parameter 'destination-addr' in event IPSF.32"
    ::= { ipsfEventObjects32 3 }

ipsf32-destination-port OBJECT-TYPE
    SYNTAX Integer32
    MAX-ACCESS accessible-for-notify
    STATUS current
    DESCRIPTION
        "Parameter 'destination-port' in event IPSF.32"
    ::= { ipsfEventObjects32 4 }

ipsf32-SID OBJECT-TYPE
    SYNTAX DisplayString
    MAX-ACCESS accessible-for-notify
    STATUS current
    DESCRIPTION
        "Parameter 'SID' in event IPSF.32"
    ::= { ipsfEventObjects32 5 }

ipsf32-SID-value OBJECT-TYPE
    SYNTAX Integer32
    MAX-ACCESS accessible-for-notify
    STATUS current
    DESCRIPTION
        "Parameter 'SID-value' in event IPSF.32"
    ::= { ipsfEventObjects32 6 }

ipsfEventObjects33 OBJECT-IDENTITY
    STATUS current
    DESCRIPTION
        "Event IPSF.33
        The specified data length has been received."
    ::= { ipsfEventsGroup 33 }

ipsf33-length OBJECT-TYPE
    SYNTAX Integer32
    MAX-ACCESS accessible-for-notify
    STATUS current
    DESCRIPTION
        "Parameter 'length' in event IPSF.33"
    ::= { ipsfEventObjects33 1 }

ipsf33-SID OBJECT-TYPE
    SYNTAX DisplayString
    MAX-ACCESS accessible-for-notify
    STATUS current
    DESCRIPTION
        "Parameter 'SID' in event IPSF.33"
    ::= { ipsfEventObjects33 2 }

ipsf33-SID-value OBJECT-TYPE
    SYNTAX Integer32
    MAX-ACCESS accessible-for-notify
    STATUS current
    DESCRIPTION
        "Parameter 'SID-value' in event IPSF.33"
    ::= { ipsfEventObjects33 3 }

ipsfEventObjects34 OBJECT-IDENTITY
    STATUS current
    DESCRIPTION
        "Event IPSF.34
        The specified packet has been received."
    ::= { ipsfEventsGroup 34 }

ipsf34-packet-type OBJECT-TYPE
    SYNTAX DisplayString
    MAX-ACCESS accessible-for-notify
    STATUS current
    DESCRIPTION
        "Parameter 'packet-type' in event IPSF.34"
    ::= { ipsfEventObjects34 1 }

ipsf34-SID OBJECT-TYPE
    SYNTAX DisplayString
    MAX-ACCESS accessible-for-notify
    STATUS current
    DESCRIPTION
        "Parameter 'SID' in event IPSF.34"
    ::= { ipsfEventObjects34 2 }

ipsf34-SID-value OBJECT-TYPE
    SYNTAX Integer32
    MAX-ACCESS accessible-for-notify
    STATUS current
    DESCRIPTION
        "Parameter 'SID-value' in event IPSF.34"
    ::= { ipsfEventObjects34 3 }

ipsfEventObjects35 OBJECT-IDENTITY
    STATUS current
    DESCRIPTION
        "Event IPSF.35
        The callback for writing was successful."
    ::= { ipsfEventsGroup 35 }

ipsf35-length OBJECT-TYPE
    SYNTAX Integer32
    MAX-ACCESS accessible-for-notify
    STATUS current
    DESCRIPTION
        "Parameter 'length' in event IPSF.35"
    ::= { ipsfEventObjects35 1 }

ipsf35-SID OBJECT-TYPE
    SYNTAX DisplayString
    MAX-ACCESS accessible-for-notify
    STATUS current
    DESCRIPTION
        "Parameter 'SID' in event IPSF.35"
    ::= { ipsfEventObjects35 2 }

ipsf35-SID-value OBJECT-TYPE
    SYNTAX Integer32
    MAX-ACCESS accessible-for-notify
    STATUS current
    DESCRIPTION
        "Parameter 'SID-value' in event IPSF.35"
    ::= { ipsfEventObjects35 3 }

ipsfEventObjects36 OBJECT-IDENTITY
    STATUS current
    DESCRIPTION
        "Event IPSF.36
        IPSecFT as backup server has inherited the tunnels."
    ::= { ipsfEventsGroup 36 }

ipsf36-tunnels OBJECT-TYPE
    SYNTAX Integer32
    MAX-ACCESS accessible-for-notify
    STATUS current
    DESCRIPTION
        "Parameter 'tunnels' in event IPSF.36"
    ::= { ipsfEventObjects36 1 }

ipsf36-SID OBJECT-TYPE
    SYNTAX DisplayString
    MAX-ACCESS accessible-for-notify
    STATUS current
    DESCRIPTION
        "Parameter 'SID' in event IPSF.36"
    ::= { ipsfEventObjects36 2 }

ipsf36-SID-value OBJECT-TYPE
    SYNTAX Integer32
    MAX-ACCESS accessible-for-notify
    STATUS current
    DESCRIPTION
        "Parameter 'SID-value' in event IPSF.36"
    ::= { ipsfEventObjects36 3 }

ipsfEventObjects37 OBJECT-IDENTITY
    STATUS current
    DESCRIPTION
        "Event IPSF.37
        The specified session will be finished."
    ::= { ipsfEventsGroup 37 }

ipsf37-internalID OBJECT-TYPE
    SYNTAX DisplayString
    MAX-ACCESS accessible-for-notify
    STATUS current
    DESCRIPTION
        "Parameter 'internalID' in event IPSF.37"
    ::= { ipsfEventObjects37 1 }

ipsf37-internalID-value OBJECT-TYPE
    SYNTAX Integer32
    MAX-ACCESS accessible-for-notify
    STATUS current
    DESCRIPTION
        "Parameter 'internalID-value' in event IPSF.37"
    ::= { ipsfEventObjects37 2 }

ipsf37-SID OBJECT-TYPE
    SYNTAX DisplayString
    MAX-ACCESS accessible-for-notify
    STATUS current
    DESCRIPTION
        "Parameter 'SID' in event IPSF.37"
    ::= { ipsfEventObjects37 3 }

ipsf37-SID-value OBJECT-TYPE
    SYNTAX Integer32
    MAX-ACCESS accessible-for-notify
    STATUS current
    DESCRIPTION
        "Parameter 'SID-value' in event IPSF.37"
    ::= { ipsfEventObjects37 4 }

ipsfEventObjects38 OBJECT-IDENTITY
    STATUS current
    DESCRIPTION
        "Event IPSF.38
        Timeout in keepalive timer."
    ::= { ipsfEventsGroup 38 }

ipsf38-SID OBJECT-TYPE
    SYNTAX DisplayString
    MAX-ACCESS accessible-for-notify
    STATUS current
    DESCRIPTION
        "Parameter 'SID' in event IPSF.38"
    ::= { ipsfEventObjects38 1 }

ipsf38-SID-value OBJECT-TYPE
    SYNTAX Integer32
    MAX-ACCESS accessible-for-notify
    STATUS current
    DESCRIPTION
        "Parameter 'SID-value' in event IPSF.38"
    ::= { ipsfEventObjects38 2 }

ipsfEventObjects39 OBJECT-IDENTITY
    STATUS current
    DESCRIPTION
        "Event IPSF.39
        The timer for keepalive transmission has been deleted."
    ::= { ipsfEventsGroup 39 }

ipsf39-SID OBJECT-TYPE
    SYNTAX DisplayString
    MAX-ACCESS accessible-for-notify
    STATUS current
    DESCRIPTION
        "Parameter 'SID' in event IPSF.39"
    ::= { ipsfEventObjects39 1 }

ipsf39-SID-value OBJECT-TYPE
    SYNTAX Integer32
    MAX-ACCESS accessible-for-notify
    STATUS current
    DESCRIPTION
        "Parameter 'SID-value' in event IPSF.39"
    ::= { ipsfEventObjects39 2 }

ipsfEventObjects40 OBJECT-IDENTITY
    STATUS current
    DESCRIPTION
        "Event IPSF.40
        The configuration has changed."
    ::= { ipsfEventsGroup 40 }

ipsf40-current-state OBJECT-TYPE
    SYNTAX DisplayString
    MAX-ACCESS accessible-for-notify
    STATUS current
    DESCRIPTION
        "Parameter 'current-state' in event IPSF.40"
    ::= { ipsfEventObjects40 1 }

ipsf40-event OBJECT-TYPE
    SYNTAX DisplayString
    MAX-ACCESS accessible-for-notify
    STATUS current
    DESCRIPTION
        "Parameter 'event' in event IPSF.40"
    ::= { ipsfEventObjects40 2 }

ipsf40-SID OBJECT-TYPE
    SYNTAX DisplayString
    MAX-ACCESS accessible-for-notify
    STATUS current
    DESCRIPTION
        "Parameter 'SID' in event IPSF.40"
    ::= { ipsfEventObjects40 3 }

ipsf40-SID-value OBJECT-TYPE
    SYNTAX Integer32
    MAX-ACCESS accessible-for-notify
    STATUS current
    DESCRIPTION
        "Parameter 'SID-value' in event IPSF.40"
    ::= { ipsfEventObjects40 4 }

ipsfEventObjects41 OBJECT-IDENTITY
    STATUS current
    DESCRIPTION
        "Event IPSF.41
        An innocuous event has been received."
    ::= { ipsfEventsGroup 41 }

ipsf41-current-state OBJECT-TYPE
    SYNTAX DisplayString
    MAX-ACCESS accessible-for-notify
    STATUS current
    DESCRIPTION
        "Parameter 'current-state' in event IPSF.41"
    ::= { ipsfEventObjects41 1 }

ipsf41-event OBJECT-TYPE
    SYNTAX DisplayString
    MAX-ACCESS accessible-for-notify
    STATUS current
    DESCRIPTION
        "Parameter 'event' in event IPSF.41"
    ::= { ipsfEventObjects41 2 }

ipsf41-SID OBJECT-TYPE
    SYNTAX DisplayString
    MAX-ACCESS accessible-for-notify
    STATUS current
    DESCRIPTION
        "Parameter 'SID' in event IPSF.41"
    ::= { ipsfEventObjects41 3 }

ipsf41-SID-value OBJECT-TYPE
    SYNTAX Integer32
    MAX-ACCESS accessible-for-notify
    STATUS current
    DESCRIPTION
        "Parameter 'SID-value' in event IPSF.41"
    ::= { ipsfEventObjects41 4 }

ipsfEventObjects42 OBJECT-IDENTITY
    STATUS current
    DESCRIPTION
        "Event IPSF.42
        The specified task has been suspended."
    ::= { ipsfEventsGroup 42 }

ipsf42-task-name OBJECT-TYPE
    SYNTAX DisplayString
    MAX-ACCESS accessible-for-notify
    STATUS current
    DESCRIPTION
        "Parameter 'task-name' in event IPSF.42"
    ::= { ipsfEventObjects42 1 }

ipsfEventObjects43 OBJECT-IDENTITY
    STATUS current
    DESCRIPTION
        "Event IPSF.43
        The specified task has been resumed."
    ::= { ipsfEventsGroup 43 }

ipsf43-task-name OBJECT-TYPE
    SYNTAX DisplayString
    MAX-ACCESS accessible-for-notify
    STATUS current
    DESCRIPTION
        "Parameter 'task-name' in event IPSF.43"
    ::= { ipsfEventObjects43 1 }

ipsfEventObjects44 OBJECT-IDENTITY
    STATUS current
    DESCRIPTION
        "Event IPSF.44
        Sending signal to IPSec to inherit the specified tunnel."
    ::= { ipsfEventsGroup 44 }

ipsf44-peerID OBJECT-TYPE
    SYNTAX Integer32
    MAX-ACCESS accessible-for-notify
    STATUS current
    DESCRIPTION
        "Parameter 'peerID' in event IPSF.44"
    ::= { ipsfEventObjects44 1 }

ipsf44-ep-dest OBJECT-TYPE
    SYNTAX IpAddress
    MAX-ACCESS accessible-for-notify
    STATUS current
    DESCRIPTION
        "Parameter 'ep-dest' in event IPSF.44"
    ::= { ipsfEventObjects44 2 }

ipsf44-client-dest OBJECT-TYPE
    SYNTAX IpAddress
    MAX-ACCESS accessible-for-notify
    STATUS current
    DESCRIPTION
        "Parameter 'client-dest' in event IPSF.44"
    ::= { ipsfEventObjects44 3 }

ipsf44-SID OBJECT-TYPE
    SYNTAX DisplayString
    MAX-ACCESS accessible-for-notify
    STATUS current
    DESCRIPTION
        "Parameter 'SID' in event IPSF.44"
    ::= { ipsfEventObjects44 4 }

ipsf44-SID-value OBJECT-TYPE
    SYNTAX Integer32
    MAX-ACCESS accessible-for-notify
    STATUS current
    DESCRIPTION
        "Parameter 'SID-value' in event IPSF.44"
    ::= { ipsfEventObjects44 5 }

ipsfEventObjects45 OBJECT-IDENTITY
    STATUS current
    DESCRIPTION
        "Event IPSF.45
        Event delete list has been received."
    ::= { ipsfEventsGroup 45 }

ipsf45-current-state OBJECT-TYPE
    SYNTAX DisplayString
    MAX-ACCESS accessible-for-notify
    STATUS current
    DESCRIPTION
        "Parameter 'current-state' in event IPSF.45"
    ::= { ipsfEventObjects45 1 }

ipsf45-event OBJECT-TYPE
    SYNTAX DisplayString
    MAX-ACCESS accessible-for-notify
    STATUS current
    DESCRIPTION
        "Parameter 'event' in event IPSF.45"
    ::= { ipsfEventObjects45 2 }

ipsf45-SID OBJECT-TYPE
    SYNTAX DisplayString
    MAX-ACCESS accessible-for-notify
    STATUS current
    DESCRIPTION
        "Parameter 'SID' in event IPSF.45"
    ::= { ipsfEventObjects45 3 }

ipsf45-SID-value OBJECT-TYPE
    SYNTAX Integer32
    MAX-ACCESS accessible-for-notify
    STATUS current
    DESCRIPTION
        "Parameter 'SID-value' in event IPSF.45"
    ::= { ipsfEventObjects45 4 }

ipsfEventObjects46 OBJECT-IDENTITY
    STATUS current
    DESCRIPTION
        "Event IPSF.46
        Deleting IPSec sessions with the specified source IP address."
    ::= { ipsfEventsGroup 46 }

ipsf46-IP OBJECT-TYPE
    SYNTAX IpAddress
    MAX-ACCESS accessible-for-notify
    STATUS current
    DESCRIPTION
        "Parameter 'IP' in event IPSF.46"
    ::= { ipsfEventObjects46 1 }

ipsf46-SID OBJECT-TYPE
    SYNTAX DisplayString
    MAX-ACCESS accessible-for-notify
    STATUS current
    DESCRIPTION
        "Parameter 'SID' in event IPSF.46"
    ::= { ipsfEventObjects46 2 }

ipsf46-SID-value OBJECT-TYPE
    SYNTAX Integer32
    MAX-ACCESS accessible-for-notify
    STATUS current
    DESCRIPTION
        "Parameter 'SID-value' in event IPSF.46"
    ::= { ipsfEventObjects46 3 }

ipsfEventObjects47 OBJECT-IDENTITY
    STATUS current
    DESCRIPTION
        "Event IPSF.47
        The specified list has been initilized."
    ::= { ipsfEventsGroup 47 }

ipsf47-list OBJECT-TYPE
    SYNTAX DisplayString
    MAX-ACCESS accessible-for-notify
    STATUS current
    DESCRIPTION
        "Parameter 'list' in event IPSF.47"
    ::= { ipsfEventObjects47 1 }

ipsf47-n-of-peers OBJECT-TYPE
    SYNTAX Integer32
    MAX-ACCESS accessible-for-notify
    STATUS current
    DESCRIPTION
        "Parameter 'n-of-peers' in event IPSF.47"
    ::= { ipsfEventObjects47 2 }

ipsfEventObjects48 OBJECT-IDENTITY
    STATUS current
    DESCRIPTION
        "Event IPSF.48
        The specified session has been removed."
    ::= { ipsfEventsGroup 48 }

ipsf48-internalID-value OBJECT-TYPE
    SYNTAX Integer32
    MAX-ACCESS accessible-for-notify
    STATUS current
    DESCRIPTION
        "Parameter 'internalID-value' in event IPSF.48"
    ::= { ipsfEventObjects48 1 }

ipsfEventObjects49 OBJECT-IDENTITY
    STATUS current
    DESCRIPTION
        "Event IPSF.49
        There are no peers to inherit."
    ::= { ipsfEventsGroup 49 }

ipsf49-SID OBJECT-TYPE
    SYNTAX DisplayString
    MAX-ACCESS accessible-for-notify
    STATUS current
    DESCRIPTION
        "Parameter 'SID' in event IPSF.49"
    ::= { ipsfEventObjects49 1 }

ipsf49-SID-value OBJECT-TYPE
    SYNTAX Integer32
    MAX-ACCESS accessible-for-notify
    STATUS current
    DESCRIPTION
        "Parameter 'SID-value' in event IPSF.49"
    ::= { ipsfEventObjects49 2 }

ipsfEventObjects50 OBJECT-IDENTITY
    STATUS current
    DESCRIPTION
        "Event IPSF.50
        The inherit task has finished."
    ::= { ipsfEventsGroup 50 }

ipsf50-peers-inherited OBJECT-TYPE
    SYNTAX Integer32
    MAX-ACCESS accessible-for-notify
    STATUS current
    DESCRIPTION
        "Parameter 'peers-inherited' in event IPSF.50"
    ::= { ipsfEventObjects50 1 }

ipsf50-SID OBJECT-TYPE
    SYNTAX DisplayString
    MAX-ACCESS accessible-for-notify
    STATUS current
    DESCRIPTION
        "Parameter 'SID' in event IPSF.50"
    ::= { ipsfEventObjects50 2 }

ipsf50-SID-value OBJECT-TYPE
    SYNTAX Integer32
    MAX-ACCESS accessible-for-notify
    STATUS current
    DESCRIPTION
        "Parameter 'SID-value' in event IPSF.50"
    ::= { ipsfEventObjects50 3 }

ipsfEventObjects51 OBJECT-IDENTITY
    STATUS current
    DESCRIPTION
        "Event IPSF.51
        The specified peer has been found."
    ::= { ipsfEventsGroup 51 }

ipsf51-place OBJECT-TYPE
    SYNTAX DisplayString
    MAX-ACCESS accessible-for-notify
    STATUS current
    DESCRIPTION
        "Parameter 'place' in event IPSF.51"
    ::= { ipsfEventObjects51 1 }

ipsf51-peerID OBJECT-TYPE
    SYNTAX Integer32
    MAX-ACCESS accessible-for-notify
    STATUS current
    DESCRIPTION
        "Parameter 'peerID' in event IPSF.51"
    ::= { ipsfEventObjects51 2 }

ipsf51-ep-dest OBJECT-TYPE
    SYNTAX IpAddress
    MAX-ACCESS accessible-for-notify
    STATUS current
    DESCRIPTION
        "Parameter 'ep-dest' in event IPSF.51"
    ::= { ipsfEventObjects51 3 }

ipsf51-client-dest OBJECT-TYPE
    SYNTAX IpAddress
    MAX-ACCESS accessible-for-notify
    STATUS current
    DESCRIPTION
        "Parameter 'client-dest' in event IPSF.51"
    ::= { ipsfEventObjects51 4 }

ipsf51-SID OBJECT-TYPE
    SYNTAX DisplayString
    MAX-ACCESS accessible-for-notify
    STATUS current
    DESCRIPTION
        "Parameter 'SID' in event IPSF.51"
    ::= { ipsfEventObjects51 5 }

ipsf51-SID-value OBJECT-TYPE
    SYNTAX Integer32
    MAX-ACCESS accessible-for-notify
    STATUS current
    DESCRIPTION
        "Parameter 'SID-value' in event IPSF.51"
    ::= { ipsfEventObjects51 6 }


ipsfNotification1 NOTIFICATION-TYPE
    OBJECTS { 
              ipsf1-message 
            }
    STATUS current
    DESCRIPTION
        "Notification of Event IPSF.1

        Message: '$1'

        Parameters list:
              $1: ipsf1-message

        Generic abnormal internal error message."
    ::= { ipsfNotificationsPrefix 1 }

ipsfNotification2 NOTIFICATION-TYPE
    OBJECTS { 
              ipsf2-message 
            }
    STATUS current
    DESCRIPTION
        "Notification of Event IPSF.2

        Message: '$1'

        Parameters list:
              $1: ipsf2-message

        Generic usual internal error message."
    ::= { ipsfNotificationsPrefix 2 }

ipsfNotification3 NOTIFICATION-TYPE
    OBJECTS { 
              ipsf3-message 
            }
    STATUS current
    DESCRIPTION
        "Notification of Event IPSF.3

        Message: '$1'

        Parameters list:
              $1: ipsf3-message

        Generic abnormal external error message."
    ::= { ipsfNotificationsPrefix 3 }

ipsfNotification4 NOTIFICATION-TYPE
    OBJECTS { 
              ipsf4-message 
            }
    STATUS current
    DESCRIPTION
        "Notification of Event IPSF.4

        Message: '$1'

        Parameters list:
              $1: ipsf4-message

        Generic usual external error message."
    ::= { ipsfNotificationsPrefix 4 }

ipsfNotification5 NOTIFICATION-TYPE
    OBJECTS { 
              ipsf5-message 
            }
    STATUS current
    DESCRIPTION
        "Notification of Event IPSF.5

        Message: '$1'

        Parameters list:
              $1: ipsf5-message

        Generic comment on abnormal information message."
    ::= { ipsfNotificationsPrefix 5 }

ipsfNotification6 NOTIFICATION-TYPE
    OBJECTS { 
              ipsf6-message 
            }
    STATUS current
    DESCRIPTION
        "Notification of Event IPSF.6

        Message: '$1'

        Parameters list:
              $1: ipsf6-message

        Generic comment on usual information message."
    ::= { ipsfNotificationsPrefix 6 }

ipsfNotification7 NOTIFICATION-TYPE
    OBJECTS { 
              ipsf7-message 
            }
    STATUS current
    DESCRIPTION
        "Notification of Event IPSF.7

        Message: '$1'

        Parameters list:
              $1: ipsf7-message

        Generic packet trace message."
    ::= { ipsfNotificationsPrefix 7 }

ipsfNotification8 NOTIFICATION-TYPE
    OBJECTS { 
              ipsf8-message 
            }
    STATUS current
    DESCRIPTION
        "Notification of Event IPSF.8

        Message: '$1'

        Parameters list:
              $1: ipsf8-message

        Generic abnormal operation trace message."
    ::= { ipsfNotificationsPrefix 8 }

ipsfNotification9 NOTIFICATION-TYPE
    OBJECTS { 
              ipsf9-message 
            }
    STATUS current
    DESCRIPTION
        "Notification of Event IPSF.9

        Message: '$1'

        Parameters list:
              $1: ipsf9-message

        Generic usual operation trace message."
    ::= { ipsfNotificationsPrefix 9 }

ipsfNotification10 NOTIFICATION-TYPE
    OBJECTS { 
              ipsf10-event-level, 
              ipsf10-message 
            }
    STATUS current
    DESCRIPTION
        "Notification of Event IPSF.10

        Message: 'Bad generic event level ($1) ($2)'

        Parameters list:
              $1: ipsf10-event-level
              $2: ipsf10-message

        The generic event level is wrong."
    ::= { ipsfNotificationsPrefix 10 }

ipsfNotification11 NOTIFICATION-TYPE
    OBJECTS { 
              ipsf11-peerID, 
              ipsf11-SID,
              ipsf11-SID-value 
            }
    STATUS current
    DESCRIPTION
        "Notification of Event IPSF.11

        Message: 'Peer 0x$1 added to session list [$2 0x$3]'

        Parameters list:
              $1: ipsf11-peerID
              $2: ipsf11-SID
              $3: ipsf11-SID-value

        A new peer has been added to the session list."
    ::= { ipsfNotificationsPrefix 11 }

ipsfNotification12 NOTIFICATION-TYPE
    OBJECTS { 
              ipsf12-peerID, 
              ipsf12-SID,
              ipsf12-SID-value 
            }
    STATUS current
    DESCRIPTION
        "Notification of Event IPSF.12

        Message: 'Peer 0x$1 deleted from session list [$2 0x$3]'

        Parameters list:
              $1: ipsf12-peerID
              $2: ipsf12-SID
              $3: ipsf12-SID-value

        A peer has been deleted from the session list."
    ::= { ipsfNotificationsPrefix 12 }

ipsfNotification13 NOTIFICATION-TYPE
    OBJECTS { 
              ipsf13-type, 
              ipsf13-reason 
            }
    STATUS current
    DESCRIPTION
        "Notification of Event IPSF.13

        Message: 'Message $1 could not be sent to queue: $2'

        Parameters list:
              $1: ipsf13-type
              $2: ipsf13-reason

        The specified message could not be sent to IPSecFT queue."
    ::= { ipsfNotificationsPrefix 13 }

ipsfNotification14 NOTIFICATION-TYPE
    OBJECTS { 
              ipsf14-type 
            }
    STATUS current
    DESCRIPTION
        "Notification of Event IPSF.14

        Message: 'Message $1 has been sent to queue'

        Parameters list:
              $1: ipsf14-type

        The specified message has been sent to IPSecFT queue."
    ::= { ipsfNotificationsPrefix 14 }

ipsfNotification15 NOTIFICATION-TYPE
    OBJECTS { 
              ipsf15-task-name 
            }
    STATUS current
    DESCRIPTION
        "Notification of Event IPSF.15

        Message: '$1 task created'

        Parameters list:
              $1: ipsf15-task-name

        The specified task has been created."
    ::= { ipsfNotificationsPrefix 15 }

ipsfNotification16 NOTIFICATION-TYPE
    OBJECTS { 
              ipsf16-current-state, 
              ipsf16-new-state,
              ipsf16-SID,
              ipsf16-SID-value 
            }
    STATUS current
    DESCRIPTION
        "Notification of Event IPSF.16

        Message: 'Changing state ($1->$2) [$3 0x$4]'

        Parameters list:
              $1: ipsf16-current-state
              $2: ipsf16-new-state
              $3: ipsf16-SID
              $4: ipsf16-SID-value

        The specified session has change its state."
    ::= { ipsfNotificationsPrefix 16 }

ipsfNotification17 NOTIFICATION-TYPE
    OBJECTS { 
              ipsf17-timeout, 
              ipsf17-current-state,
              ipsf17-new-state,
              ipsf17-SID,
              ipsf17-SID-value 
            }
    STATUS current
    DESCRIPTION
        "Notification of Event IPSF.17

        Message: 'Changing state in $1 second[s] ($2->$3) [$4 0x$5]'

        Parameters list:
              $1: ipsf17-timeout
              $2: ipsf17-current-state
              $3: ipsf17-new-state
              $4: ipsf17-SID
              $5: ipsf17-SID-value

        The specified session will change its state."
    ::= { ipsfNotificationsPrefix 17 }

ipsfNotification18 NOTIFICATION-TYPE
    OBJECTS { 
              ipsf18-src-addr, 
              ipsf18-src-port,
              ipsf18-dst-addr,
              ipsf18-dst-port,
              ipsf18-timeout,
              ipsf18-SID,
              ipsf18-SID-value 
            }
    STATUS current
    DESCRIPTION
        "Notification of Event IPSF.18

        Message: 'Connecting ($1:$2->$3:$4). Timeout in $5 second[s] [$6 0x$7]'

        Parameters list:
              $1: ipsf18-src-addr
              $2: ipsf18-src-port
              $3: ipsf18-dst-addr
              $4: ipsf18-dst-port
              $5: ipsf18-timeout
              $6: ipsf18-SID
              $7: ipsf18-SID-value

        The specified session is connecting."
    ::= { ipsfNotificationsPrefix 18 }

ipsfNotification19 NOTIFICATION-TYPE
    OBJECTS { 
              ipsf19-type 
            }
    STATUS current
    DESCRIPTION
        "Notification of Event IPSF.19

        Message: 'IPSecFT has been started as $1 server'

        Parameters list:
              $1: ipsf19-type

        IPSecFT has been started as specified type."
    ::= { ipsfNotificationsPrefix 19 }

ipsfNotification20 NOTIFICATION-TYPE
    OBJECTS { 
              ipsf20-process 
            }
    STATUS current
    DESCRIPTION
        "Notification of Event IPSF.20

        Message: '$1 is being restarted'

        Parameters list:
              $1: ipsf20-process

        The specified process is being restarted."
    ::= { ipsfNotificationsPrefix 20 }

ipsfNotification21 NOTIFICATION-TYPE
    OBJECTS { 
              ipsf21-SID-value 
            }
    STATUS current
    DESCRIPTION
        "Notification of Event IPSF.21

        Message: 'TCP connect OK [MSID 0x$1]'

        Parameters list:
              $1: ipsf21-SID-value

        The TCP connection has been established."
    ::= { ipsfNotificationsPrefix 21 }

ipsfNotification22 NOTIFICATION-TYPE
    OBJECTS { 
              ipsf22-event, 
              ipsf22-current-state,
              ipsf22-SID,
              ipsf22-SID-value 
            }
    STATUS current
    DESCRIPTION
        "Notification of Event IPSF.22

        Message: 'Event $1 received (state $2) [$3 0x$4]'

        Parameters list:
              $1: ipsf22-event
              $2: ipsf22-current-state
              $3: ipsf22-SID
              $4: ipsf22-SID-value

        The specified event has been received."
    ::= { ipsfNotificationsPrefix 22 }

ipsfNotification23 NOTIFICATION-TYPE
    OBJECTS { 
              ipsf23-packet-type, 
              ipsf23-len,
              ipsf23-SID,
              ipsf23-SID-value 
            }
    STATUS current
    DESCRIPTION
        "Notification of Event IPSF.23

        Message: '$1 packet has been sent ($2 bytes) [$3 0x$4]'

        Parameters list:
              $1: ipsf23-packet-type
              $2: ipsf23-len
              $3: ipsf23-SID
              $4: ipsf23-SID-value

        The specified packet has been sent."
    ::= { ipsfNotificationsPrefix 23 }

ipsfNotification24 NOTIFICATION-TYPE
    OBJECTS { 
              ipsf24-timeout, 
              ipsf24-interval,
              ipsf24-SID,
              ipsf24-SID-value 
            }
    STATUS current
    DESCRIPTION
        "Notification of Event IPSF.24

        Message: 'Listen for incoming data. Timeout in $1 $2 [$3 0x$4]'

        Parameters list:
              $1: ipsf24-timeout
              $2: ipsf24-interval
              $3: ipsf24-SID
              $4: ipsf24-SID-value

        IPSecFT is listening for incoming data."
    ::= { ipsfNotificationsPrefix 24 }

ipsfNotification25 NOTIFICATION-TYPE
    OBJECTS { 
              ipsf25-reason, 
              ipsf25-SID,
              ipsf25-SID-value 
            }
    STATUS current
    DESCRIPTION
        "Notification of Event IPSF.25

        Message: 'Wrong ACK: $1 [$2 0x$3]'

        Parameters list:
              $1: ipsf25-reason
              $2: ipsf25-SID
              $3: ipsf25-SID-value

        The ACK is wrong."
    ::= { ipsfNotificationsPrefix 25 }

ipsfNotification26 NOTIFICATION-TYPE
    OBJECTS { 
              ipsf26-IP, 
              ipsf26-SID,
              ipsf26-SID-value 
            }
    STATUS current
    DESCRIPTION
        "Notification of Event IPSF.26

        Message: 'IP address $1 has been inherited [$2 0x$3]'

        Parameters list:
              $1: ipsf26-IP
              $2: ipsf26-SID
              $3: ipsf26-SID-value

        The specified IP has been inherited."
    ::= { ipsfNotificationsPrefix 26 }

ipsfNotification27 NOTIFICATION-TYPE
    OBJECTS { 
              ipsf27-timer, 
              ipsf27-SID,
              ipsf27-SID-value 
            }
    STATUS current
    DESCRIPTION
        "Notification of Event IPSF.27

        Message: 'Added timer for keepalive transmission. Timeout in $1 millisecond[s] [$2 0x$3]'

        Parameters list:
              $1: ipsf27-timer
              $2: ipsf27-SID
              $3: ipsf27-SID-value

        Keepalive packet will be sent at the specified time."
    ::= { ipsfNotificationsPrefix 27 }

ipsfNotification28 NOTIFICATION-TYPE
    OBJECTS { 
              ipsf28-SID, 
              ipsf28-SID-value 
            }
    STATUS current
    DESCRIPTION
        "Notification of Event IPSF.28

        Message: 'Retrieving queued elements [$1 0x$2]'

        Parameters list:
              $1: ipsf28-SID
              $2: ipsf28-SID-value

        IPSecFT is retrieving queued elements."
    ::= { ipsfNotificationsPrefix 28 }

ipsfNotification29 NOTIFICATION-TYPE
    OBJECTS { 
              ipsf29-SID, 
              ipsf29-SID-value 
            }
    STATUS current
    DESCRIPTION
        "Notification of Event IPSF.29

        Message: 'Session established [$1 0x$2]'

        Parameters list:
              $1: ipsf29-SID
              $2: ipsf29-SID-value

        The specified session has been established."
    ::= { ipsfNotificationsPrefix 29 }

ipsfNotification30 NOTIFICATION-TYPE
    OBJECTS { 
              ipsf30-local-addr, 
              ipsf30-local-port 
            }
    STATUS current
    DESCRIPTION
        "Notification of Event IPSF.30

        Message: 'Waiting for incoming connections ($1:$2)'

        Parameters list:
              $1: ipsf30-local-addr
              $2: ipsf30-local-port

        IPSecFT is waiting for incoming connections."
    ::= { ipsfNotificationsPrefix 30 }

ipsfNotification31 NOTIFICATION-TYPE
    OBJECTS { 
              ipsf31-remote-addr, 
              ipsf31-remote-port,
              ipsf31-local-addr,
              ipsf31-local-port,
              ipsf31-internalID,
              ipsf31-internalID-value 
            }
    STATUS current
    DESCRIPTION
        "Notification of Event IPSF.31

        Message: 'TCP connection accepted ($1:$2->$3:$4) [$5 0x$6]'

        Parameters list:
              $1: ipsf31-remote-addr
              $2: ipsf31-remote-port
              $3: ipsf31-local-addr
              $4: ipsf31-local-port
              $5: ipsf31-internalID
              $6: ipsf31-internalID-value

        A TCP connection has been accepted."
    ::= { ipsfNotificationsPrefix 31 }

ipsfNotification32 NOTIFICATION-TYPE
    OBJECTS { 
              ipsf32-source-addr, 
              ipsf32-source-port,
              ipsf32-destination-addr,
              ipsf32-destination-port,
              ipsf32-SID,
              ipsf32-SID-value 
            }
    STATUS current
    DESCRIPTION
        "Notification of Event IPSF.32

        Message: 'Closing connection ($1:$2->$3:$4) [$5 0x$6]'

        Parameters list:
              $1: ipsf32-source-addr
              $2: ipsf32-source-port
              $3: ipsf32-destination-addr
              $4: ipsf32-destination-port
              $5: ipsf32-SID
              $6: ipsf32-SID-value

        A TCP connection has been closed."
    ::= { ipsfNotificationsPrefix 32 }

ipsfNotification33 NOTIFICATION-TYPE
    OBJECTS { 
              ipsf33-length, 
              ipsf33-SID,
              ipsf33-SID-value 
            }
    STATUS current
    DESCRIPTION
        "Notification of Event IPSF.33

        Message: 'Read complete ($1 bytes) [$2 0x$3]'

        Parameters list:
              $1: ipsf33-length
              $2: ipsf33-SID
              $3: ipsf33-SID-value

        The specified data length has been received."
    ::= { ipsfNotificationsPrefix 33 }

ipsfNotification34 NOTIFICATION-TYPE
    OBJECTS { 
              ipsf34-packet-type, 
              ipsf34-SID,
              ipsf34-SID-value 
            }
    STATUS current
    DESCRIPTION
        "Notification of Event IPSF.34

        Message: '$1 packet received [$2 0x$3]'

        Parameters list:
              $1: ipsf34-packet-type
              $2: ipsf34-SID
              $3: ipsf34-SID-value

        The specified packet has been received."
    ::= { ipsfNotificationsPrefix 34 }

ipsfNotification35 NOTIFICATION-TYPE
    OBJECTS { 
              ipsf35-length, 
              ipsf35-SID,
              ipsf35-SID-value 
            }
    STATUS current
    DESCRIPTION
        "Notification of Event IPSF.35

        Message: 'Write callback OK ($1 bytes) [$2 0x$3]'

        Parameters list:
              $1: ipsf35-length
              $2: ipsf35-SID
              $3: ipsf35-SID-value

        The callback for writing was successful."
    ::= { ipsfNotificationsPrefix 35 }

ipsfNotification36 NOTIFICATION-TYPE
    OBJECTS { 
              ipsf36-tunnels, 
              ipsf36-SID,
              ipsf36-SID-value 
            }
    STATUS current
    DESCRIPTION
        "Notification of Event IPSF.36

        Message: '$1 tunnels have been inherited [$2 0x$3]'

        Parameters list:
              $1: ipsf36-tunnels
              $2: ipsf36-SID
              $3: ipsf36-SID-value

        IPSecFT as backup server has inherited the tunnels."
    ::= { ipsfNotificationsPrefix 36 }

ipsfNotification37 NOTIFICATION-TYPE
    OBJECTS { 
              ipsf37-internalID, 
              ipsf37-internalID-value,
              ipsf37-SID,
              ipsf37-SID-value 
            }
    STATUS current
    DESCRIPTION
        "Notification of Event IPSF.37

        Message: 'Finishing session [$1 0x$2, $3 0x$4]'

        Parameters list:
              $1: ipsf37-internalID
              $2: ipsf37-internalID-value
              $3: ipsf37-SID
              $4: ipsf37-SID-value

        The specified session will be finished."
    ::= { ipsfNotificationsPrefix 37 }

ipsfNotification38 NOTIFICATION-TYPE
    OBJECTS { 
              ipsf38-SID, 
              ipsf38-SID-value 
            }
    STATUS current
    DESCRIPTION
        "Notification of Event IPSF.38

        Message: 'Timeout in keepalive timer [$1 0x$2]'

        Parameters list:
              $1: ipsf38-SID
              $2: ipsf38-SID-value

        Timeout in keepalive timer."
    ::= { ipsfNotificationsPrefix 38 }

ipsfNotification39 NOTIFICATION-TYPE
    OBJECTS { 
              ipsf39-SID, 
              ipsf39-SID-value 
            }
    STATUS current
    DESCRIPTION
        "Notification of Event IPSF.39

        Message: 'Deleting timer for keepalive transmission [$1 0x$2]'

        Parameters list:
              $1: ipsf39-SID
              $2: ipsf39-SID-value

        The timer for keepalive transmission has been deleted."
    ::= { ipsfNotificationsPrefix 39 }

ipsfNotification40 NOTIFICATION-TYPE
    OBJECTS { 
              ipsf40-current-state, 
              ipsf40-event,
              ipsf40-SID,
              ipsf40-SID-value 
            }
    STATUS current
    DESCRIPTION
        "Notification of Event IPSF.40

        Message: 'Configuration has changed (state $1, event $2) [$3 0x$4]'

        Parameters list:
              $1: ipsf40-current-state
              $2: ipsf40-event
              $3: ipsf40-SID
              $4: ipsf40-SID-value

        The configuration has changed."
    ::= { ipsfNotificationsPrefix 40 }

ipsfNotification41 NOTIFICATION-TYPE
    OBJECTS { 
              ipsf41-current-state, 
              ipsf41-event,
              ipsf41-SID,
              ipsf41-SID-value 
            }
    STATUS current
    DESCRIPTION
        "Notification of Event IPSF.41

        Message: 'Innocuous event (state $1, event $2) [$3 0x$4]'

        Parameters list:
              $1: ipsf41-current-state
              $2: ipsf41-event
              $3: ipsf41-SID
              $4: ipsf41-SID-value

        An innocuous event has been received."
    ::= { ipsfNotificationsPrefix 41 }

ipsfNotification42 NOTIFICATION-TYPE
    OBJECTS { 
              ipsf42-task-name 
            }
    STATUS current
    DESCRIPTION
        "Notification of Event IPSF.42

        Message: 'Task $1 has been suspended'

        Parameters list:
              $1: ipsf42-task-name

        The specified task has been suspended."
    ::= { ipsfNotificationsPrefix 42 }

ipsfNotification43 NOTIFICATION-TYPE
    OBJECTS { 
              ipsf43-task-name 
            }
    STATUS current
    DESCRIPTION
        "Notification of Event IPSF.43

        Message: 'Task $1 has been resumed'

        Parameters list:
              $1: ipsf43-task-name

        The specified task has been resumed."
    ::= { ipsfNotificationsPrefix 43 }

ipsfNotification44 NOTIFICATION-TYPE
    OBJECTS { 
              ipsf44-peerID, 
              ipsf44-ep-dest,
              ipsf44-client-dest,
              ipsf44-SID,
              ipsf44-SID-value 
            }
    STATUS current
    DESCRIPTION
        "Notification of Event IPSF.44

        Message: 'Sending signal to IPSec to inherit tunnel 0x$1: ep-dest $2, client-dest $3 [$4 0x$5]'

        Parameters list:
              $1: ipsf44-peerID
              $2: ipsf44-ep-dest
              $3: ipsf44-client-dest
              $4: ipsf44-SID
              $5: ipsf44-SID-value

        Sending signal to IPSec to inherit the specified tunnel."
    ::= { ipsfNotificationsPrefix 44 }

ipsfNotification45 NOTIFICATION-TYPE
    OBJECTS { 
              ipsf45-current-state, 
              ipsf45-event,
              ipsf45-SID,
              ipsf45-SID-value 
            }
    STATUS current
    DESCRIPTION
        "Notification of Event IPSF.45

        Message: 'Delete list received (state $1, event $2) [$3 0x$4]'

        Parameters list:
              $1: ipsf45-current-state
              $2: ipsf45-event
              $3: ipsf45-SID
              $4: ipsf45-SID-value

        Event delete list has been received."
    ::= { ipsfNotificationsPrefix 45 }

ipsfNotification46 NOTIFICATION-TYPE
    OBJECTS { 
              ipsf46-IP, 
              ipsf46-SID,
              ipsf46-SID-value 
            }
    STATUS current
    DESCRIPTION
        "Notification of Event IPSF.46

        Message: 'Deleting IPSec sessions with source IP address $1 [$2 0x$3]'

        Parameters list:
              $1: ipsf46-IP
              $2: ipsf46-SID
              $3: ipsf46-SID-value

        Deleting IPSec sessions with the specified source IP address."
    ::= { ipsfNotificationsPrefix 46 }

ipsfNotification47 NOTIFICATION-TYPE
    OBJECTS { 
              ipsf47-list, 
              ipsf47-n-of-peers 
            }
    STATUS current
    DESCRIPTION
        "Notification of Event IPSF.47

        Message: '$1 list has been initialized with $2 peers'

        Parameters list:
              $1: ipsf47-list
              $2: ipsf47-n-of-peers

        The specified list has been initilized."
    ::= { ipsfNotificationsPrefix 47 }

ipsfNotification48 NOTIFICATION-TYPE
    OBJECTS { 
              ipsf48-internalID-value 
            }
    STATUS current
    DESCRIPTION
        "Notification of Event IPSF.48

        Message: 'Backup session has already been removed [IBSID 0x$1]'

        Parameters list:
              $1: ipsf48-internalID-value

        The specified session has been removed."
    ::= { ipsfNotificationsPrefix 48 }

ipsfNotification49 NOTIFICATION-TYPE
    OBJECTS { 
              ipsf49-SID, 
              ipsf49-SID-value 
            }
    STATUS current
    DESCRIPTION
        "Notification of Event IPSF.49

        Message: 'No peers to inherit [$1 0x$2]'

        Parameters list:
              $1: ipsf49-SID
              $2: ipsf49-SID-value

        There are no peers to inherit."
    ::= { ipsfNotificationsPrefix 49 }

ipsfNotification50 NOTIFICATION-TYPE
    OBJECTS { 
              ipsf50-peers-inherited, 
              ipsf50-SID,
              ipsf50-SID-value 
            }
    STATUS current
    DESCRIPTION
        "Notification of Event IPSF.50

        Message: 'Inherit task finished with $1 peers [$2 0x$3]'

        Parameters list:
              $1: ipsf50-peers-inherited
              $2: ipsf50-SID
              $3: ipsf50-SID-value

        The inherit task has finished."
    ::= { ipsfNotificationsPrefix 50 }

ipsfNotification51 NOTIFICATION-TYPE
    OBJECTS { 
              ipsf51-place, 
              ipsf51-peerID,
              ipsf51-ep-dest,
              ipsf51-client-dest,
              ipsf51-SID,
              ipsf51-SID-value 
            }
    STATUS current
    DESCRIPTION
        "Notification of Event IPSF.51

        Message: 'Peer found in $1 for fast inheriting, 0x$2: ep-dest $3, client-dest $4 [$5 0x$6]'

        Parameters list:
              $1: ipsf51-place
              $2: ipsf51-peerID
              $3: ipsf51-ep-dest
              $4: ipsf51-client-dest
              $5: ipsf51-SID
              $6: ipsf51-SID-value

        The specified peer has been found."
    ::= { ipsfNotificationsPrefix 51 }


END
