GatewayServer-MIB DEFINITIONS ::= BEGIN

        IMPORTS
                enterprises,
                OBJECT-TYPE,
                Counter
                        FROM RFC1155-SMI
                internetServer
                        FROM InternetServer-MIB;

--      microsoft       OBJECT IDENTIFIER ::= { enterprises 311 }
--      software        OBJECT IDENTIFIER ::= { microsoft 1 }
--      InternetServer  OBJECT IDENTIFIER ::= { software 7 }
        gatewayServer      OBJECT IDENTIFIER ::= { internetServer 5 }
        gatewayStatistics  OBJECT IDENTIFIER ::= { gatewayServer 1 }

-- Gateway Server Statistics

        totalBytesSent-HighWord OBJECT-TYPE
                SYNTAX  Counter
                ACCESS  read-only
                STATUS  mandatory
                DESCRIPTION
                        "This is the high 32-bits of the total number of
                        of BYTEs sent by the Gateway Server"
                ::= { gatewayStatistics 1 }

        totalBytesSent-LowWord OBJECT-TYPE
                SYNTAX  Counter
                ACCESS  read-only
                STATUS  mandatory
                DESCRIPTION
                        "This is the low 32-bits of the total number of
                        of BYTEs sent by the Gateway Server"
                ::= { gatewayStatistics 2 }

        totalBytesReceived-HighWord OBJECT-TYPE
                SYNTAX  Counter
                ACCESS  read-only
                STATUS  mandatory
                DESCRIPTION
                        "This is the high 32-bits of the total number of
                        of BYTEs received by the Gateway Server"
                ::= { gatewayStatistics 3 }

        totalBytesReceived-LowWord OBJECT-TYPE
                SYNTAX  Counter
                ACCESS  read-only
                STATUS  mandatory
                DESCRIPTION
                        "This is the low 32-bits of the total number of
                        of BYTEs received by the Gateway Server"
                ::= { gatewayStatistics 4 }

        totalFilesSent OBJECT-TYPE
                SYNTAX  Counter
                ACCESS  read-only
                STATUS  mandatory
                DESCRIPTION
                        "This is the total number of files sent by this
                        Gateway Server"
                ::= { gatewayStatistics 5 }

        totalFilesReceived OBJECT-TYPE
                SYNTAX  Counter
                ACCESS  read-only
                STATUS  mandatory
                DESCRIPTION
                        "This is the total number of files received by this
                        Gateway Server"
                ::= { gatewayStatistics 6 }

        currentUsers OBJECT-TYPE
                SYNTAX  INTEGER
                ACCESS  read-only
                STATUS  mandatory
                DESCRIPTION
                        "This is the number of users currently connected
                        to the Gateway Server"
                ::= { gatewayStatistics 7 }

        totalUsers OBJECT-TYPE
                SYNTAX  Counter
                ACCESS  read-only
                STATUS  mandatory
                DESCRIPTION
                        "This is the total number of users that have
                        ever connected to the Gateway Server"
                ::= { gatewayStatistics 8  }

        maxUsers OBJECT-TYPE
                SYNTAX  Counter
                ACCESS  read-only
                STATUS  mandatory
                DESCRIPTION
                        "This is the maximum number of users
                        simultaneously connected to the Gateway Server"
                ::= { gatewayStatistics 9 }

        currentConnections OBJECT-TYPE
                SYNTAX  INTEGER
                ACCESS  read-only
                STATUS  mandatory
                DESCRIPTION
                        "This is the current number of connections to the
                        Gateway Server"
                ::= { gatewayStatistics 10 }

        maxConnections OBJECT-TYPE
                SYNTAX  Counter
                ACCESS  read-only
                STATUS  mandatory
                DESCRIPTION
                        "This is the maximum number of simultaneous
                        connections to the Gateway Server"
                ::= { gatewayStatistics 11 }

        connectionAttempts OBJECT-TYPE
                SYNTAX  Counter
                ACCESS  read-only
                STATUS  mandatory
                DESCRIPTION
                        "This is the number of connection attempts that
                        have been made to the Gateway Server"
                ::= { gatewayStatistics 12 }

        ftpRequests OBJECT-TYPE
                SYNTAX  Counter
                ACCESS  read-only
                STATUS  mandatory
                DESCRIPTION
                        "This is the number of Ftp requests that have
                        been made to this Gateway Server"
                ::= { gatewayStatistics 13 }

        gopherRequests OBJECT-TYPE
                SYNTAX  Counter
                ACCESS  read-only
                STATUS  mandatory
                DESCRIPTION
                        "This is the number of Gopher requests that have
                        been made to this Gateway Server"
                ::= { gatewayStatistics 14 }

        httpRequests OBJECT-TYPE
                SYNTAX  Counter
                ACCESS  read-only
                STATUS  mandatory
                DESCRIPTION
                        "This is the number of Http requests that have
                        been made to this Gateway Server"
                ::= { gatewayStatistics 15 }

        totalInternetRequests OBJECT-TYPE
                SYNTAX  Counter
                ACCESS  read-only
                STATUS  mandatory
                DESCRIPTION
                        "This is the number of requests using the GET method
                        that have been made to this Gateway Server"
                ::= { gatewayStatistics 16 }

        totalInternetFetches OBJECT-TYPE
                SYNTAX  Counter
                ACCESS  read-only
                STATUS  mandatory
                DESCRIPTION
                        "This is the number of Internet fetches for the Internet
                        requests that have been made to this Gateway Server"
                ::= { gatewayStatistics 17 }

        totalCacheFetches OBJECT-TYPE
                SYNTAX  Counter
                ACCESS  read-only
                STATUS  mandatory
                DESCRIPTION
                        "This is the number of Cache fetches for the Internet 
                        requests that have been made to this Gateway Server"
                ::= { gatewayStatistics 18 }

END
