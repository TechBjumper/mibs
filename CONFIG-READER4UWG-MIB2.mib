CONFIG-READER4UWG-MIB2 DEFINITIONS ::= BEGIN

IMPORTS
    enterprises, MODULE-IDENTITY, Integer32
        FROM SNMPv2-SMI;

reader4uwg MODULE-IDENTITY
    LAST-UPDATED "0609201255Z"
    ORGANIZATION "Sun Microsystems Inc."
    CONTACT-INFO
        "        Sun Microsystems Inc.
       Customer Support
            Postal: 901 San Antonio Road 
       Palo Alto, CA-94303-4900
    USA
                         Tel: 650-960-1300
                E-mail: service@sun.com"
    DESCRIPTION
        ""
    ::= { config 3 }
config	OBJECT IDENTIFIER ::= { hardware 1 }

hardware	OBJECT IDENTIFIER ::= { modules 1 }

modules	OBJECT IDENTIFIER ::= { agent 2 }

agent	OBJECT IDENTIFIER ::= { sunsymon 2 }

sunsymon	OBJECT IDENTIFIER ::= { prod 12 }

prod	OBJECT IDENTIFIER ::= { sun 2 }

sun	OBJECT IDENTIFIER ::= { enterprises 42 }


picld	OBJECT IDENTIFIER ::= { reader4uwg 1 }

DisplayString ::= TEXTUAL-CONVENTION
    DISPLAY-HINT "255a"
    STATUS       current
    DESCRIPTION
            "Represents textual information taken from the NVT ASCII
            character set, as defined in pages 4, 10-11 of RFC 854.

            To summarize RFC 854, the NVT ASCII repertoire specifies:

              - the use of character codes 0-127 (decimal)

              - the graphics characters (32-126) are interpreted as
                US ASCII

              - NUL, LF, CR, BEL, BS, HT, VT and FF have the special
                meanings specified in RFC 854

              - the other 25 codes have no standard interpretation

              - the sequence 'CR LF' means newline

              - the sequence 'CR NUL' means carriage-return

              - an 'LF' not preceded by a 'CR' means moving to the
                same column on the next line.

              - the sequence 'CR x' for any x other than LF or NUL is
                illegal.  (Note that this also means that a string may
                end with either 'CR LF' or 'CR NUL', but not with CR.)

            Any object defined using this syntax may not exceed 255
            characters in length."
    SYNTAX       OCTET STRING (SIZE (0..255))

picldStatus OBJECT-TYPE
    SYNTAX      Integer32
    MAX-ACCESS  read-only
    STATUS      current
    DESCRIPTION
                "Integer value"
    ::= { picld 1 }

system	OBJECT IDENTIFIER ::= { reader4uwg 2 }

systemsunSmTreeProp OBJECT-TYPE
    SYNTAX      DisplayString
    MAX-ACCESS  read-only
    STATUS      current
    DESCRIPTION
                "Character string value"
    ::= { system 1 }

systemsunSmNodeName OBJECT-TYPE
    SYNTAX      DisplayString
    MAX-ACCESS  read-only
    STATUS      current
    DESCRIPTION
                "Character string value"
    ::= { system 2 }

os OBJECT-TYPE
    SYNTAX      DisplayString
    MAX-ACCESS  read-only
    STATUS      current
    DESCRIPTION
                "Character string value"
    ::= { system 3 }

oSversion OBJECT-TYPE
    SYNTAX      DisplayString
    MAX-ACCESS  read-only
    STATUS      current
    DESCRIPTION
                "Character string value"
    ::= { system 4 }

systemclockfrequency OBJECT-TYPE
    SYNTAX      DisplayString
    MAX-ACCESS  read-only
    STATUS      current
    DESCRIPTION
                "Character string value"
    ::= { system 5 }

architecture OBJECT-TYPE
    SYNTAX      DisplayString
    MAX-ACCESS  read-only
    STATUS      current
    DESCRIPTION
                "Character string value"
    ::= { system 6 }

hostname OBJECT-TYPE
    SYNTAX      DisplayString
    MAX-ACCESS  read-only
    STATUS      current
    DESCRIPTION
                "Character string value"
    ::= { system 7 }

machine OBJECT-TYPE
    SYNTAX      DisplayString
    MAX-ACCESS  read-only
    STATUS      current
    DESCRIPTION
                "Character string value"
    ::= { system 8 }

platform OBJECT-TYPE
    SYNTAX      DisplayString
    MAX-ACCESS  read-only
    STATUS      current
    DESCRIPTION
                "Character string value"
    ::= { system 9 }

sample OBJECT-TYPE
    SYNTAX      DisplayString
    MAX-ACCESS  read-only
    STATUS      current
    DESCRIPTION
                "Character string value"
    ::= { system 10 }

serialnumber OBJECT-TYPE
    SYNTAX      DisplayString
    MAX-ACCESS  read-only
    STATUS      current
    DESCRIPTION
                "Character string value"
    ::= { system 11 }

timestamp OBJECT-TYPE
    SYNTAX      DisplayString
    MAX-ACCESS  read-only
    STATUS      current
    DESCRIPTION
                "Character string value"
    ::= { system 12 }

timestampraw OBJECT-TYPE
    SYNTAX      DisplayString
    MAX-ACCESS  read-only
    STATUS      current
    DESCRIPTION
                "Character string value"
    ::= { system 13 }

totaldisks OBJECT-TYPE
    SYNTAX      DisplayString
    MAX-ACCESS  read-only
    STATUS      current
    DESCRIPTION
                "Character string value"
    ::= { system 14 }

totalmemory OBJECT-TYPE
    SYNTAX      DisplayString
    MAX-ACCESS  read-only
    STATUS      current
    DESCRIPTION
                "Character string value"
    ::= { system 15 }

totalprocessors OBJECT-TYPE
    SYNTAX      DisplayString
    MAX-ACCESS  read-only
    STATUS      current
    DESCRIPTION
                "Character string value"
    ::= { system 16 }

totaltapedevices OBJECT-TYPE
    SYNTAX      DisplayString
    MAX-ACCESS  read-only
    STATUS      current
    DESCRIPTION
                "Character string value"
    ::= { system 17 }

totalmodelchanges OBJECT-TYPE
    SYNTAX      Integer32
    MAX-ACCESS  read-only
    STATUS      current
    DESCRIPTION
                "Integer value"
    ::= { system 18 }

totalconfigchanges OBJECT-TYPE
    SYNTAX      Integer32
    MAX-ACCESS  read-only
    STATUS      current
    DESCRIPTION
                "Integer value"
    ::= { system 19 }

systemboard	OBJECT IDENTIFIER ::= { reader4uwg 3 }

systemboardsunSmTreeProp OBJECT-TYPE
    SYNTAX      DisplayString
    MAX-ACCESS  read-only
    STATUS      current
    DESCRIPTION
                "Character string value"
    ::= { systemboard 1 }

systemboardsunSmNodeName OBJECT-TYPE
    SYNTAX      DisplayString
    MAX-ACCESS  read-only
    STATUS      current
    DESCRIPTION
                "Character string value"
    ::= { systemboard 2 }

systemboardfru OBJECT-TYPE
    SYNTAX      DisplayString
    MAX-ACCESS  read-only
    STATUS      current
    DESCRIPTION
                "Character string value"
    ::= { systemboard 3 }

systemboardstate OBJECT-TYPE
    SYNTAX      DisplayString
    MAX-ACCESS  read-only
    STATUS      current
    DESCRIPTION
                "Character string value"
    ::= { systemboard 4 }

sUNWUltra1	OBJECT IDENTIFIER ::= { reader4uwg 4 }

sUNWUltra1sunSmTreeProp OBJECT-TYPE
    SYNTAX      DisplayString
    MAX-ACCESS  read-only
    STATUS      current
    DESCRIPTION
                "Character string value"
    ::= { sUNWUltra1 1 }

sUNWUltra1sunSmNodeName OBJECT-TYPE
    SYNTAX      DisplayString
    MAX-ACCESS  read-only
    STATUS      current
    DESCRIPTION
                "Character string value"
    ::= { sUNWUltra1 2 }

sUNWUltra2	OBJECT IDENTIFIER ::= { reader4uwg 5 }

sUNWUltra2sunSmTreeProp OBJECT-TYPE
    SYNTAX      DisplayString
    MAX-ACCESS  read-only
    STATUS      current
    DESCRIPTION
                "Character string value"
    ::= { sUNWUltra2 1 }

sUNWUltra2sunSmNodeName OBJECT-TYPE
    SYNTAX      DisplayString
    MAX-ACCESS  read-only
    STATUS      current
    DESCRIPTION
                "Character string value"
    ::= { sUNWUltra2 2 }

sUNWUltra5	OBJECT IDENTIFIER ::= { reader4uwg 6 }

sUNWUltra5sunSmTreeProp OBJECT-TYPE
    SYNTAX      DisplayString
    MAX-ACCESS  read-only
    STATUS      current
    DESCRIPTION
                "Character string value"
    ::= { sUNWUltra5 1 }

sUNWUltra5sunSmNodeName OBJECT-TYPE
    SYNTAX      DisplayString
    MAX-ACCESS  read-only
    STATUS      current
    DESCRIPTION
                "Character string value"
    ::= { sUNWUltra5 2 }

sUNWUltra10	OBJECT IDENTIFIER ::= { reader4uwg 7 }

sUNWUltra10sunSmTreeProp OBJECT-TYPE
    SYNTAX      DisplayString
    MAX-ACCESS  read-only
    STATUS      current
    DESCRIPTION
                "Character string value"
    ::= { sUNWUltra10 1 }

sUNWUltra10sunSmNodeName OBJECT-TYPE
    SYNTAX      DisplayString
    MAX-ACCESS  read-only
    STATUS      current
    DESCRIPTION
                "Character string value"
    ::= { sUNWUltra10 2 }

sUNWUltra510	OBJECT IDENTIFIER ::= { reader4uwg 8 }

sUNWUltra510sunSmTreeProp OBJECT-TYPE
    SYNTAX      DisplayString
    MAX-ACCESS  read-only
    STATUS      current
    DESCRIPTION
                "Character string value"
    ::= { sUNWUltra510 1 }

sUNWUltra510sunSmNodeName OBJECT-TYPE
    SYNTAX      DisplayString
    MAX-ACCESS  read-only
    STATUS      current
    DESCRIPTION
                "Character string value"
    ::= { sUNWUltra510 2 }

sUNWUltra250	OBJECT IDENTIFIER ::= { reader4uwg 9 }

sUNWUltra250sunSmTreeProp OBJECT-TYPE
    SYNTAX      DisplayString
    MAX-ACCESS  read-only
    STATUS      current
    DESCRIPTION
                "Character string value"
    ::= { sUNWUltra250 1 }

sUNWUltra250sunSmNodeName OBJECT-TYPE
    SYNTAX      DisplayString
    MAX-ACCESS  read-only
    STATUS      current
    DESCRIPTION
                "Character string value"
    ::= { sUNWUltra250 2 }

sUNWUltra60	OBJECT IDENTIFIER ::= { reader4uwg 10 }

sUNWUltra60sunSmTreeProp OBJECT-TYPE
    SYNTAX      DisplayString
    MAX-ACCESS  read-only
    STATUS      current
    DESCRIPTION
                "Character string value"
    ::= { sUNWUltra60 1 }

sUNWUltra60sunSmNodeName OBJECT-TYPE
    SYNTAX      DisplayString
    MAX-ACCESS  read-only
    STATUS      current
    DESCRIPTION
                "Character string value"
    ::= { sUNWUltra60 2 }

sUNWUltra80	OBJECT IDENTIFIER ::= { reader4uwg 11 }

sUNWUltra80sunSmTreeProp OBJECT-TYPE
    SYNTAX      DisplayString
    MAX-ACCESS  read-only
    STATUS      current
    DESCRIPTION
                "Character string value"
    ::= { sUNWUltra80 1 }

sUNWUltra80sunSmNodeName OBJECT-TYPE
    SYNTAX      DisplayString
    MAX-ACCESS  read-only
    STATUS      current
    DESCRIPTION
                "Character string value"
    ::= { sUNWUltra80 2 }

sUNWUltra4	OBJECT IDENTIFIER ::= { reader4uwg 12 }

sUNWUltra4sunSmTreeProp OBJECT-TYPE
    SYNTAX      DisplayString
    MAX-ACCESS  read-only
    STATUS      current
    DESCRIPTION
                "Character string value"
    ::= { sUNWUltra4 1 }

sUNWUltra4sunSmNodeName OBJECT-TYPE
    SYNTAX      DisplayString
    MAX-ACCESS  read-only
    STATUS      current
    DESCRIPTION
                "Character string value"
    ::= { sUNWUltra4 2 }

cpuunit	OBJECT IDENTIFIER ::= { reader4uwg 15 }

cpuunitTbl OBJECT-TYPE
    SYNTAX      SEQUENCE OF Cpuunitentry
    MAX-ACCESS  not-accessible
    STATUS      current
    DESCRIPTION
                "MIB tree branch"
    ::= { cpuunit 1 }

cpuunitentry OBJECT-TYPE
    SYNTAX      Cpuunitentry
    MAX-ACCESS  not-accessible
    STATUS      current
    DESCRIPTION
                "MIB tree branch"
    INDEX  { cpuunitentryentryno }
    ::= { cpuunitTbl 1 }

Cpuunitentry ::=
    SEQUENCE {
        cpuunitentrysunSmTreeProp
            DisplayString,
        cpuunitentrysunSmNodeName
            DisplayString,
        cpuunitentryentryno
            Integer32,
        clockfrequency
            DisplayString,
        cputype
            DisplayString,
        dcachesize
            DisplayString,
        cpuunitentrydevicetype
            DisplayString,
        ecachesize
            DisplayString,
        cpuunitentryfru
            DisplayString,
        icachesize
            DisplayString,
        cpuunitentrymodel
            DisplayString,
        cpuunitentrypathnameelement
            DisplayString,
        processorid
            DisplayString,
        cpuunitentryStatus
            DisplayString,
        cpuunitentryunit
            DisplayString,
        temperature
            DisplayString,
        cpuunitentryupaportid
            DisplayString
    }

cpuunitentrysunSmTreeProp OBJECT-TYPE
    SYNTAX      DisplayString
    MAX-ACCESS  read-only
    STATUS      current
    DESCRIPTION
                "Character string value"
    ::= { cpuunitentry 1 }

cpuunitentrysunSmNodeName OBJECT-TYPE
    SYNTAX      DisplayString
    MAX-ACCESS  read-only
    STATUS      current
    DESCRIPTION
                "Character string value"
    ::= { cpuunitentry 2 }

cpuunitentryentryno OBJECT-TYPE
    SYNTAX      Integer32
    MAX-ACCESS  read-only
    STATUS      current
    DESCRIPTION
                "Integer value"
    ::= { cpuunitentry 3 }

cpuunitentryclockfrequency OBJECT-TYPE
    SYNTAX      DisplayString
    MAX-ACCESS  read-only
    STATUS      current
    DESCRIPTION
                "Character string value"
    ::= { cpuunitentry 4 }

cputype OBJECT-TYPE
    SYNTAX      DisplayString
    MAX-ACCESS  read-only
    STATUS      current
    DESCRIPTION
                "Character string value"
    ::= { cpuunitentry 5 }

dcachesize OBJECT-TYPE
    SYNTAX      DisplayString
    MAX-ACCESS  read-only
    STATUS      current
    DESCRIPTION
                "Character string value"
    ::= { cpuunitentry 6 }

cpuunitentrydevicetype OBJECT-TYPE
    SYNTAX      DisplayString
    MAX-ACCESS  read-only
    STATUS      current
    DESCRIPTION
                "Character string value"
    ::= { cpuunitentry 7 }

ecachesize OBJECT-TYPE
    SYNTAX      DisplayString
    MAX-ACCESS  read-only
    STATUS      current
    DESCRIPTION
                "Character string value"
    ::= { cpuunitentry 8 }

cpuunitentryfru OBJECT-TYPE
    SYNTAX      DisplayString
    MAX-ACCESS  read-only
    STATUS      current
    DESCRIPTION
                "Character string value"
    ::= { cpuunitentry 9 }

icachesize OBJECT-TYPE
    SYNTAX      DisplayString
    MAX-ACCESS  read-only
    STATUS      current
    DESCRIPTION
                "Character string value"
    ::= { cpuunitentry 10 }

cpuunitentrymodel OBJECT-TYPE
    SYNTAX      DisplayString
    MAX-ACCESS  read-only
    STATUS      current
    DESCRIPTION
                "Character string value"
    ::= { cpuunitentry 11 }

cpuunitentrypathnameelement OBJECT-TYPE
    SYNTAX      DisplayString
    MAX-ACCESS  read-only
    STATUS      current
    DESCRIPTION
                "Character string value"
    ::= { cpuunitentry 12 }

processorid OBJECT-TYPE
    SYNTAX      DisplayString
    MAX-ACCESS  read-only
    STATUS      current
    DESCRIPTION
                "Character string value"
    ::= { cpuunitentry 13 }

cpuunitentryStatus OBJECT-TYPE
    SYNTAX      DisplayString
    MAX-ACCESS  read-only
    STATUS      current
    DESCRIPTION
                "Character string value"
    ::= { cpuunitentry 14 }

cpuunitentryunitunit OBJECT-TYPE
    SYNTAX      DisplayString
    MAX-ACCESS  read-only
    STATUS      current
    DESCRIPTION
                "Character string value"
    ::= { cpuunitentry 15 }

temperature OBJECT-TYPE
    SYNTAX      DisplayString
    MAX-ACCESS  read-only
    STATUS      current
    DESCRIPTION
                "Character string value"
    ::= { cpuunitentry 16 }

cpuunitentryupaportid OBJECT-TYPE
    SYNTAX      DisplayString
    MAX-ACCESS  read-only
    STATUS      current
    DESCRIPTION
                "Character string value"
    ::= { cpuunitentry 17 }

mc	OBJECT IDENTIFIER ::= { reader4uwg 17 }

mcTbl OBJECT-TYPE
    SYNTAX      SEQUENCE OF Mcentry
    MAX-ACCESS  not-accessible
    STATUS      current
    DESCRIPTION
                "MIB tree branch"
    ::= { mc 1 }

mcentry OBJECT-TYPE
    SYNTAX      Mcentry
    MAX-ACCESS  not-accessible
    STATUS      current
    DESCRIPTION
                "MIB tree branch"
    INDEX  { mcentryno }
    ::= { mcTbl 1 }

Mcentry ::=
    SEQUENCE {
        mcentrysunSmTreeProp
            DisplayString,
        mcentrysunSmNodeName
            DisplayString,
        mcentryno
            Integer32,
        mcentrydevicetype
            DisplayString,
        mcentryfrudevice
            DisplayString
    }

mcentrysunSmTreeProp OBJECT-TYPE
    SYNTAX      DisplayString
    MAX-ACCESS  read-only
    STATUS      current
    DESCRIPTION
                "Character string value"
    ::= { mcentry 1 }

mcentrysunSmNodeName OBJECT-TYPE
    SYNTAX      DisplayString
    MAX-ACCESS  read-only
    STATUS      current
    DESCRIPTION
                "Character string value"
    ::= { mcentry 2 }

mcentryno OBJECT-TYPE
    SYNTAX      Integer32
    MAX-ACCESS  read-only
    STATUS      current
    DESCRIPTION
                "Integer value"
    ::= { mcentry 3 }

mcentrydevicetype OBJECT-TYPE
    SYNTAX      DisplayString
    MAX-ACCESS  read-only
    STATUS      current
    DESCRIPTION
                "Character string value"
    ::= { mcentry 4 }

mcentryfrudevice OBJECT-TYPE
    SYNTAX      DisplayString
    MAX-ACCESS  read-only
    STATUS      current
    DESCRIPTION
                "Character string value"
    ::= { mcentry 5 }

bank	OBJECT IDENTIFIER ::= { reader4uwg 18 }

bankTbl OBJECT-TYPE
    SYNTAX      SEQUENCE OF Bankentry
    MAX-ACCESS  not-accessible
    STATUS      current
    DESCRIPTION
                "MIB tree branch"
    ::= { bank 1 }

bankentry OBJECT-TYPE
    SYNTAX      Bankentry
    MAX-ACCESS  not-accessible
    STATUS      current
    DESCRIPTION
                "MIB tree branch"
    INDEX  { bankentryno }
    ::= { bankTbl 1 }

Bankentry ::=
    SEQUENCE {
        bankentrysunSmTreeProp
            DisplayString,
        bankentrysunSmNodeName
            DisplayString,
        bankentryno
            Integer32,
        banksize
            DisplayString,
        bankentrydevicetype
            DisplayString,
        bankentryfrudevice
            DisplayString,
        bankentryStatus
            DisplayString
    }

bankentrysunSmTreeProp OBJECT-TYPE
    SYNTAX      DisplayString
    MAX-ACCESS  read-only
    STATUS      current
    DESCRIPTION
                "Character string value"
    ::= { bankentry 1 }

bankentrysunSmNodeName OBJECT-TYPE
    SYNTAX      DisplayString
    MAX-ACCESS  read-only
    STATUS      current
    DESCRIPTION
                "Character string value"
    ::= { bankentry 2 }

bankentryno OBJECT-TYPE
    SYNTAX      Integer32
    MAX-ACCESS  read-only
    STATUS      current
    DESCRIPTION
                "Integer value"
    ::= { bankentry 3 }

banksize OBJECT-TYPE
    SYNTAX      DisplayString
    MAX-ACCESS  read-only
    STATUS      current
    DESCRIPTION
                "Character string value"
    ::= { bankentry 4 }

bankentrydevicetype OBJECT-TYPE
    SYNTAX      DisplayString
    MAX-ACCESS  read-only
    STATUS      current
    DESCRIPTION
                "Character string value"
    ::= { bankentry 5 }

bankentryfrudevice OBJECT-TYPE
    SYNTAX      DisplayString
    MAX-ACCESS  read-only
    STATUS      current
    DESCRIPTION
                "Character string value"
    ::= { bankentry 6 }

bankentryStatus OBJECT-TYPE
    SYNTAX      DisplayString
    MAX-ACCESS  read-only
    STATUS      current
    DESCRIPTION
                "Character string value"
    ::= { bankentry 7 }

dimm	OBJECT IDENTIFIER ::= { reader4uwg 19 }

dimmTbl OBJECT-TYPE
    SYNTAX      SEQUENCE OF Dimmentry
    MAX-ACCESS  not-accessible
    STATUS      current
    DESCRIPTION
                "MIB tree branch"
    ::= { dimm 1 }

dimmentry OBJECT-TYPE
    SYNTAX      Dimmentry
    MAX-ACCESS  not-accessible
    STATUS      current
    DESCRIPTION
                "MIB tree branch"
    INDEX  { dimmentryno }
    ::= { dimmTbl 1 }

Dimmentry ::=
    SEQUENCE {
        dimmentrysunSmTreeProp
            DisplayString,
        dimmentrysunSmNodeName
            DisplayString,
        dimmentryno
            Integer32,
        dimmentrydevicetype
            DisplayString,
        dimmentryfru
            DisplayString,
        dimmentryfrudevice
            DisplayString,
        modulesize
            DisplayString,
        dimmentryerrorcount
            Integer32,
        socketname
            DisplayString,
        dimmentryStatus
            DisplayString
    }

dimmentrysunSmTreeProp OBJECT-TYPE
    SYNTAX      DisplayString
    MAX-ACCESS  read-only
    STATUS      current
    DESCRIPTION
                "Character string value"
    ::= { dimmentry 1 }

dimmentrysunSmNodeName OBJECT-TYPE
    SYNTAX      DisplayString
    MAX-ACCESS  read-only
    STATUS      current
    DESCRIPTION
                "Character string value"
    ::= { dimmentry 2 }

dimmentryno OBJECT-TYPE
    SYNTAX      Integer32
    MAX-ACCESS  read-only
    STATUS      current
    DESCRIPTION
                "Integer value"
    ::= { dimmentry 3 }

dimmentrydevicetype OBJECT-TYPE
    SYNTAX      DisplayString
    MAX-ACCESS  read-only
    STATUS      current
    DESCRIPTION
                "Character string value"
    ::= { dimmentry 4 }

dimmentryfru OBJECT-TYPE
    SYNTAX      DisplayString
    MAX-ACCESS  read-only
    STATUS      current
    DESCRIPTION
                "Character string value"
    ::= { dimmentry 5 }

dimmentryfrudevice OBJECT-TYPE
    SYNTAX      DisplayString
    MAX-ACCESS  read-only
    STATUS      current
    DESCRIPTION
                "Character string value"
    ::= { dimmentry 6 }

modulesize OBJECT-TYPE
    SYNTAX      DisplayString
    MAX-ACCESS  read-only
    STATUS      current
    DESCRIPTION
                "Character string value"
    ::= { dimmentry 7 }

dimmentryerrorcount OBJECT-TYPE
    SYNTAX      Integer32
    MAX-ACCESS  read-only
    STATUS      current
    DESCRIPTION
                "Integer value"
    ::= { dimmentry 19 }

socketname OBJECT-TYPE
    SYNTAX      DisplayString
    MAX-ACCESS  read-only
    STATUS      current
    DESCRIPTION
                "Character string value"
    ::= { dimmentry 8 }

dimmentryStatus OBJECT-TYPE
    SYNTAX      DisplayString
    MAX-ACCESS  read-only
    STATUS      current
    DESCRIPTION
                "Character string value"
    ::= { dimmentry 9 }

memory OBJECT-TYPE
    SYNTAX      SEQUENCE OF Memoryentry
    MAX-ACCESS  not-accessible
    STATUS      current
    DESCRIPTION
                "MIB tree branch"
    ::= { reader4uwg 20 }

memoryentry OBJECT-TYPE
    SYNTAX      Memoryentry
    MAX-ACCESS  not-accessible
    STATUS      current
    DESCRIPTION
                "MIB tree branch"
    INDEX  { memoryentryno }
    ::= { memory 1 }

Memoryentry ::=
    SEQUENCE {
        memoryentrysunSmTreeProp
            DisplayString,
        memoryentrysunSmNodeName
            DisplayString,
        memoryentryno
            Integer32,
        memoryentrypathnameelement
            DisplayString
    }

memoryentrysunSmTreeProp OBJECT-TYPE
    SYNTAX      DisplayString
    MAX-ACCESS  read-only
    STATUS      current
    DESCRIPTION
                "Character string value"
    ::= { memoryentry 1 }

memoryentrysunSmNodeName OBJECT-TYPE
    SYNTAX      DisplayString
    MAX-ACCESS  read-only
    STATUS      current
    DESCRIPTION
                "Character string value"
    ::= { memoryentry 2 }

memoryentryno OBJECT-TYPE
    SYNTAX      Integer32
    MAX-ACCESS  read-only
    STATUS      current
    DESCRIPTION
                "Integer value"
    ::= { memoryentry 3 }

memoryentrypathnameelement OBJECT-TYPE
    SYNTAX      DisplayString
    MAX-ACCESS  read-only
    STATUS      current
    DESCRIPTION
                "Character string value"
    ::= { memoryentry 4 }

simm	OBJECT IDENTIFIER ::= { reader4uwg 21 }

simmTbl OBJECT-TYPE
    SYNTAX      SEQUENCE OF Simmentry
    MAX-ACCESS  not-accessible
    STATUS      current
    DESCRIPTION
                "MIB tree branch"
    ::= { simm 1 }

simmentry OBJECT-TYPE
    SYNTAX      Simmentry
    MAX-ACCESS  not-accessible
    STATUS      current
    DESCRIPTION
                "MIB tree branch"
    INDEX  { simmentryno }
    ::= { simmTbl 1 }

Simmentry ::=
    SEQUENCE {
        simmentrysunSmTreeProp
            DisplayString,
        simmentrysunSmNodeName
            DisplayString,
        simmentryno
            Integer32,
        boardreferencenumber
            DisplayString,
        simmentryerrorcount
            Integer32,
        simmentryfru
            DisplayString,
        size
            DisplayString,
        slot
            DisplayString,
        type
            DisplayString
    }

simmentrysunSmTreeProp OBJECT-TYPE
    SYNTAX      DisplayString
    MAX-ACCESS  read-only
    STATUS      current
    DESCRIPTION
                "Character string value"
    ::= { simmentry 1 }

simmentrysunSmNodeName OBJECT-TYPE
    SYNTAX      DisplayString
    MAX-ACCESS  read-only
    STATUS      current
    DESCRIPTION
                "Character string value"
    ::= { simmentry 2 }

simmentryno OBJECT-TYPE
    SYNTAX      Integer32
    MAX-ACCESS  read-only
    STATUS      current
    DESCRIPTION
                "Integer value"
    ::= { simmentry 3 }

boardreferencenumber OBJECT-TYPE
    SYNTAX      DisplayString
    MAX-ACCESS  read-only
    STATUS      current
    DESCRIPTION
                "Character string value"
    ::= { simmentry 4 }

simmentryerrorcount OBJECT-TYPE
    SYNTAX      Integer32
    MAX-ACCESS  read-only
    STATUS      current
    DESCRIPTION
                "Integer value"
    ::= { simmentry 21 }

simmentryfru OBJECT-TYPE
    SYNTAX      DisplayString
    MAX-ACCESS  read-only
    STATUS      current
    DESCRIPTION
                "Character string value"
    ::= { simmentry 5 }

size OBJECT-TYPE
    SYNTAX      DisplayString
    MAX-ACCESS  read-only
    STATUS      current
    DESCRIPTION
                "Character string value"
    ::= { simmentry 6 }

slot OBJECT-TYPE
    SYNTAX      DisplayString
    MAX-ACCESS  read-only
    STATUS      current
    DESCRIPTION
                "Character string value"
    ::= { simmentry 7 }

type OBJECT-TYPE
    SYNTAX      DisplayString
    MAX-ACCESS  read-only
    STATUS      current
    DESCRIPTION
                "Character string value"
    ::= { simmentry 8 }

powersupply	OBJECT IDENTIFIER ::= { reader4uwg 22 }

powersupplyTbl OBJECT-TYPE
    SYNTAX      SEQUENCE OF Powersupplyentry
    MAX-ACCESS  not-accessible
    STATUS      current
    DESCRIPTION
                "MIB tree branch"
    ::= { powersupply 1 }

powersupplyentry OBJECT-TYPE
    SYNTAX      Powersupplyentry
    MAX-ACCESS  not-accessible
    STATUS      current
    DESCRIPTION
                "MIB tree branch"
    INDEX  { powersupplyentryno }
    ::= { powersupplyTbl 1 }

Powersupplyentry ::=
    SEQUENCE {
        powersupplyentrysunSmTreeProp
            DisplayString,
        powersupplyentrysunSmNodeName
            DisplayString,
        powersupplyentryno
            Integer32,
        powersupplyentryfru
            DisplayString,
        powersupplyentrystate
            DisplayString
    }

sunSmTreeProp OBJECT-TYPE
    SYNTAX      DisplayString
    MAX-ACCESS  read-only
    STATUS      current
    DESCRIPTION
                "Character string value"
    ::= { powersupplyentry 1 }

powersupplyentrysunSmNodeName OBJECT-TYPE
    SYNTAX      DisplayString
    MAX-ACCESS  read-only
    STATUS      current
    DESCRIPTION
                "Character string value"
    ::= { powersupplyentry 2 }

powersupplyentryno OBJECT-TYPE
    SYNTAX      Integer32
    MAX-ACCESS  read-only
    STATUS      current
    DESCRIPTION
                "Integer value"
    ::= { powersupplyentry 3 }

powersupplyentryfru OBJECT-TYPE
    SYNTAX      DisplayString
    MAX-ACCESS  read-only
    STATUS      current
    DESCRIPTION
                "Character string value"
    ::= { powersupplyentry 4 }

powersupplyentrystate OBJECT-TYPE
    SYNTAX      DisplayString
    MAX-ACCESS  read-only
    STATUS      current
    DESCRIPTION
                "Character string value"
    ::= { powersupplyentry 5 }

cpufans	OBJECT IDENTIFIER ::= { reader4uwg 24 }

cpufansTbl OBJECT-TYPE
    SYNTAX      SEQUENCE OF Cpufanentry
    MAX-ACCESS  not-accessible
    STATUS      current
    DESCRIPTION
                "MIB tree branch"
    ::= { cpufans 1 }

cpufanentry OBJECT-TYPE
    SYNTAX      Cpufanentry
    MAX-ACCESS  not-accessible
    STATUS      current
    DESCRIPTION
                "MIB tree branch"
    INDEX  { cpufansTblentryno }
    ::= { cpufansTbl 1 }

Cpufanentry ::=
    SEQUENCE {
        cpufansTblsunSmTreeProp
            DisplayString,
        cpufansTblsunSmNodeName
            DisplayString,
        cpufansTblentryno
            Integer32,
        cpufansTblfanentryStatus
            DisplayString,
        cpufansTblspeed
            Integer32
    }

cpufansTblsunSmTreeProp OBJECT-TYPE
    SYNTAX      DisplayString
    MAX-ACCESS  read-only
    STATUS      current
    DESCRIPTION
                "Character string value"
    ::= { cpufanentry 1 }

cpufansTblsunSmNodeName OBJECT-TYPE
    SYNTAX      DisplayString
    MAX-ACCESS  read-only
    STATUS      current
    DESCRIPTION
                "Character string value"
    ::= { cpufanentry 2 }

cpufansTblentryno OBJECT-TYPE
    SYNTAX      Integer32
    MAX-ACCESS  read-only
    STATUS      current
    DESCRIPTION
                "Integer value"
    ::= { cpufanentry 3 }

cpufansTblfanentryStatus OBJECT-TYPE
    SYNTAX      DisplayString
    MAX-ACCESS  read-only
    STATUS      current
    DESCRIPTION
                "Character string value"
    ::= { cpufanentry 4 }

cpufansTblspeed OBJECT-TYPE
    SYNTAX      Integer32
    MAX-ACCESS  read-only
    STATUS      current
    DESCRIPTION
                "Integer value"
    ::= { cpufanentry 5 }

powersupplyfans	OBJECT IDENTIFIER ::= { reader4uwg 25 }

powersupplyfansTbl OBJECT-TYPE
    SYNTAX      SEQUENCE OF Psfanentry
    MAX-ACCESS  not-accessible
    STATUS      current
    DESCRIPTION
                "MIB tree branch"
    ::= { powersupplyfans 1 }

psfanentry OBJECT-TYPE
    SYNTAX      Psfanentry
    MAX-ACCESS  not-accessible
    STATUS      current
    DESCRIPTION
                "MIB tree branch"
    INDEX  { psfanentryno }
    ::= { powersupplyfansTbl 1 }

Psfanentry ::=
    SEQUENCE {
        psfanentrysunSmTreeProp
            DisplayString,
        psfanentrysunSmNodeName
            DisplayString,
        psfanentryno
            Integer32,
        psfanentryStatus
            DisplayString
    }

psfanentrysunSmTreeProp OBJECT-TYPE
    SYNTAX      DisplayString
    MAX-ACCESS  read-only
    STATUS      current
    DESCRIPTION
                "Character string value"
    ::= { psfanentry 1 }

psfanentrysunSmNodeName OBJECT-TYPE
    SYNTAX      DisplayString
    MAX-ACCESS  read-only
    STATUS      current
    DESCRIPTION
                "Character string value"
    ::= { psfanentry 2 }

psfanentryno OBJECT-TYPE
    SYNTAX      Integer32
    MAX-ACCESS  read-only
    STATUS      current
    DESCRIPTION
                "Integer value"
    ::= { psfanentry 3 }

 psfanentryStatus OBJECT-TYPE
    SYNTAX      DisplayString
    MAX-ACCESS  read-only
    STATUS      current
    DESCRIPTION
                "Character string value"
    ::= { psfanentry 4 }

fan OBJECT-TYPE
    SYNTAX      SEQUENCE OF Fanentry
    MAX-ACCESS  not-accessible
    STATUS      current
    DESCRIPTION
                "MIB tree branch"
    ::= { reader4uwg 26 }

fanentry OBJECT-TYPE
    SYNTAX      Fanentry
    MAX-ACCESS  not-accessible
    STATUS      current
    DESCRIPTION
                "MIB tree branch"
    INDEX  { fanentryno }
    ::= { fan 1 }

Fanentry ::=
    SEQUENCE {
        fanentrysunSmTreeProp
            DisplayString,
        fanentrysunSmNodeName
            DisplayString,
       fanentryno
            Integer32,
       fantblfanentryStatus
            DisplayString
    }

fanentrysunSmTreeProp OBJECT-TYPE
    SYNTAX      DisplayString
    MAX-ACCESS  read-only
    STATUS      current
    DESCRIPTION
                "Character string value"
    ::= { fanentry 1 }

fanentrysunSmNodeName OBJECT-TYPE
    SYNTAX      DisplayString
    MAX-ACCESS  read-only
    STATUS      current
    DESCRIPTION
                "Character string value"
    ::= { fanentry 2 }

fanentryno OBJECT-TYPE
    SYNTAX      Integer32
    MAX-ACCESS  read-only
    STATUS      current
    DESCRIPTION
                "Integer value"
    ::= { fanentry 3 }

fantblfanentryStatus OBJECT-TYPE
    SYNTAX      DisplayString
    MAX-ACCESS  read-only
    STATUS      current
    DESCRIPTION
                "Character string value"
    ::= { fanentry 4 }

ffb OBJECT-TYPE
    SYNTAX      SEQUENCE OF Ffbentry
    MAX-ACCESS  not-accessible
    STATUS      current
    DESCRIPTION
                "MIB tree branch"
    ::= { reader4uwg 27 }

ffbentry OBJECT-TYPE
    SYNTAX      Ffbentry
    MAX-ACCESS  not-accessible
    STATUS      current
    DESCRIPTION
                "MIB tree branch"
    INDEX  { ffbentryno }
    ::= { ffb 1 }

Ffbentry ::=
    SEQUENCE {
        ffbentrysunSmTreeProp
            DisplayString,
        ffbentrysunSmNodeName
            DisplayString,
        ffbentryno
            Integer32,
        ffbentrybuffer
            DisplayString,
        ffbentrydevicetype
            DisplayString,
        ffbentrymodel
            DisplayString,
        ffbentrypathnameelement
            DisplayString
    }

ffbentrysunSmTreeProp OBJECT-TYPE
    SYNTAX      DisplayString
    MAX-ACCESS  read-only
    STATUS      current
    DESCRIPTION
                "Character string value"
    ::= { ffbentry 1 }

ffbentrysunSmNodeName OBJECT-TYPE
    SYNTAX      DisplayString
    MAX-ACCESS  read-only
    STATUS      current
    DESCRIPTION
                "Character string value"
    ::= { ffbentry 2 }

ffbentryno OBJECT-TYPE
    SYNTAX      Integer32
    MAX-ACCESS  read-only
    STATUS      current
    DESCRIPTION
                "Integer value"
    ::= { ffbentry 3 }

ffbentrybuffer OBJECT-TYPE
    SYNTAX      DisplayString
    MAX-ACCESS  read-only
    STATUS      current
    DESCRIPTION
                "Character string value"
    ::= { ffbentry 4 }

ffbentrydevicetype OBJECT-TYPE
    SYNTAX      DisplayString
    MAX-ACCESS  read-only
    STATUS      current
    DESCRIPTION
                "Character string value"
    ::= { ffbentry 5 }

ffbentrymodel OBJECT-TYPE
    SYNTAX      DisplayString
    MAX-ACCESS  read-only
    STATUS      current
    DESCRIPTION
                "Character string value"
    ::= { ffbentry 6 }

ffbentrypathnameelement OBJECT-TYPE
    SYNTAX      DisplayString
    MAX-ACCESS  read-only
    STATUS      current
    DESCRIPTION
                "Character string value"
    ::= { ffbentry 7 }

afb OBJECT-TYPE
    SYNTAX      SEQUENCE OF Afbentry
    MAX-ACCESS  not-accessible
    STATUS      current
    DESCRIPTION
                "MIB tree branch"
    ::= { reader4uwg 28 }

afbentry OBJECT-TYPE
    SYNTAX      Afbentry
    MAX-ACCESS  not-accessible
    STATUS      current
    DESCRIPTION
                "MIB tree branch"
    INDEX  { afbentryno }
    ::= { afb 1 }

Afbentry ::=
    SEQUENCE {
        afbentrysunSmTreeProp
            DisplayString,
        afbentrysunSmNodeName
            DisplayString,
        afbentryno
            Integer32,
        afbentrybuffer
            DisplayString,
        afbentrydevicetype
            DisplayString,
        afbentrymodel
            DisplayString,
        afbentrypathnameelement
            DisplayString
    }

afbentrysunSmTreeProp OBJECT-TYPE
    SYNTAX      DisplayString
    MAX-ACCESS  read-only
    STATUS      current
    DESCRIPTION
                "Character string value"
    ::= { afbentry 1 }

afbentrysunSmNodeName OBJECT-TYPE
    SYNTAX      DisplayString
    MAX-ACCESS  read-only
    STATUS      current
    DESCRIPTION
                "Character string value"
    ::= { afbentry 2 }

afbentryno OBJECT-TYPE
    SYNTAX      Integer32
    MAX-ACCESS  read-only
    STATUS      current
    DESCRIPTION
                "Integer value"
    ::= { afbentry 3 }

afbentrybuffer OBJECT-TYPE
    SYNTAX      DisplayString
    MAX-ACCESS  read-only
    STATUS      current
    DESCRIPTION
                "Character string value"
    ::= { afbentry 4 }

afbentrydevicetype OBJECT-TYPE
    SYNTAX      DisplayString
    MAX-ACCESS  read-only
    STATUS      current
    DESCRIPTION
                "Character string value"
    ::= { afbentry 5 }

afbentrymodel OBJECT-TYPE
    SYNTAX      DisplayString
    MAX-ACCESS  read-only
    STATUS      current
    DESCRIPTION
                "Character string value"
    ::= { afbentry 6 }

afbentrypathnameelement OBJECT-TYPE
    SYNTAX      DisplayString
    MAX-ACCESS  read-only
    STATUS      current
    DESCRIPTION
                "Character string value"
    ::= { afbentry 7 }

sUNWffb OBJECT-TYPE
    SYNTAX      SEQUENCE OF SUNWffbentry
    MAX-ACCESS  not-accessible
    STATUS      current
    DESCRIPTION
                "MIB tree branch"
    ::= { reader4uwg 29 }

sUNWffbentry OBJECT-TYPE
    SYNTAX      SUNWffbentry
    MAX-ACCESS  not-accessible
    STATUS      current
    DESCRIPTION
                "MIB tree branch"
    INDEX  { sUNWffbentryno }
    ::= { sUNWffb 1 }

SUNWffbentry ::=
    SEQUENCE {
        sUNWffbentrysunSmTreeProp
            DisplayString,
        sUNWffbentrysunSmNodeName
            DisplayString,
        sUNWffbentryno
            Integer32,
        xDRAM
            DisplayString,
        dAC
            DisplayString,
        fBCversion
            DisplayString,
        boardtype
            DisplayString,
        sUNWffbentrybuffer
            DisplayString,
        sUNWffbentrydevicetype
            DisplayString,
        height
            DisplayString,
        sUNWffbentrymodel
            DisplayString,
        revision
            DisplayString,
        sUNWffbentryupaportid
            DisplayString,
        width
            DisplayString
    }

sUNWffbentrysunSmTreeProp OBJECT-TYPE
    SYNTAX      DisplayString
    MAX-ACCESS  read-only
    STATUS      current
    DESCRIPTION
                "Character string value"
    ::= { sUNWffbentry 1 }

sUNWffbentrysunSmNodeName OBJECT-TYPE
    SYNTAX      DisplayString
    MAX-ACCESS  read-only
    STATUS      current
    DESCRIPTION
                "Character string value"
    ::= { sUNWffbentry 2 }

sUNWffbentryno OBJECT-TYPE
    SYNTAX      Integer32
    MAX-ACCESS  read-only
    STATUS      current
    DESCRIPTION
                "Integer value"
    ::= { sUNWffbentry 3 }

xDRAM OBJECT-TYPE
    SYNTAX      DisplayString
    MAX-ACCESS  read-only
    STATUS      current
    DESCRIPTION
                "Character string value"
    ::= { sUNWffbentry 4 }

dAC OBJECT-TYPE
    SYNTAX      DisplayString
    MAX-ACCESS  read-only
    STATUS      current
    DESCRIPTION
                "Character string value"
    ::= { sUNWffbentry 5 }

fBCversion OBJECT-TYPE
    SYNTAX      DisplayString
    MAX-ACCESS  read-only
    STATUS      current
    DESCRIPTION
                "Character string value"
    ::= { sUNWffbentry 6 }

boardtype OBJECT-TYPE
    SYNTAX      DisplayString
    MAX-ACCESS  read-only
    STATUS      current
    DESCRIPTION
                "Character string value"
    ::= { sUNWffbentry 7 }

sUNWffbentrybuffer OBJECT-TYPE
    SYNTAX      DisplayString
    MAX-ACCESS  read-only
    STATUS      current
    DESCRIPTION
                "Character string value"
    ::= { sUNWffbentry 8 }

sUNWffbentrydevicetype OBJECT-TYPE
    SYNTAX      DisplayString
    MAX-ACCESS  read-only
    STATUS      current
    DESCRIPTION
                "Character string value"
    ::= { sUNWffbentry 9 }

height OBJECT-TYPE
    SYNTAX      DisplayString
    MAX-ACCESS  read-only
    STATUS      current
    DESCRIPTION
                "Character string value"
    ::= { sUNWffbentry 10 }

sUNWffbentrymodel OBJECT-TYPE
    SYNTAX      DisplayString
    MAX-ACCESS  read-only
    STATUS      current
    DESCRIPTION
                "Character string value"
    ::= { sUNWffbentry 11 }

revision OBJECT-TYPE
    SYNTAX      DisplayString
    MAX-ACCESS  read-only
    STATUS      current
    DESCRIPTION
                "Character string value"
    ::= { sUNWffbentry 12 }

sUNWffbentryupaportid OBJECT-TYPE
    SYNTAX      DisplayString
    MAX-ACCESS  read-only
    STATUS      current
    DESCRIPTION
                "Character string value"
    ::= { sUNWffbentry 13 }

width OBJECT-TYPE
    SYNTAX      DisplayString
    MAX-ACCESS  read-only
    STATUS      current
    DESCRIPTION
                "Character string value"
    ::= { sUNWffbentry 14 }

keyswitch	OBJECT IDENTIFIER ::= { reader4uwg 30 }

keyswitchsunSmTreeProp OBJECT-TYPE
    SYNTAX      DisplayString
    MAX-ACCESS  read-only
    STATUS      current
    DESCRIPTION
                "Character string value"
    ::= { keyswitch 1 }

keyswitchsunSmNodeName OBJECT-TYPE
    SYNTAX      DisplayString
    MAX-ACCESS  read-only
    STATUS      current
    DESCRIPTION
                "Character string value"
    ::= { keyswitch 2 }

position OBJECT-TYPE
    SYNTAX      DisplayString
    MAX-ACCESS  read-only
    STATUS      current
    DESCRIPTION
                "Character string value"
    ::= { keyswitch 3 }

activeled	OBJECT IDENTIFIER ::= { reader4uwg 31 }

activeledsunSmTreeProp OBJECT-TYPE
    SYNTAX      DisplayString
    MAX-ACCESS  read-only
    STATUS      current
    DESCRIPTION
                "Character string value"
    ::= { activeled 1 }

activeledsunSmNodeName OBJECT-TYPE
    SYNTAX      DisplayString
    MAX-ACCESS  read-only
    STATUS      current
    DESCRIPTION
                "Character string value"
    ::= { activeled 2 }

activeledstate OBJECT-TYPE
    SYNTAX      DisplayString
    MAX-ACCESS  read-only
    STATUS      current
    DESCRIPTION
                "Character string value"
    ::= { activeled 3 }

diskerrorled	OBJECT IDENTIFIER ::= { reader4uwg 32 }

diskerrorledsunSmTreeProp OBJECT-TYPE
    SYNTAX      DisplayString
    MAX-ACCESS  read-only
    STATUS      current
    DESCRIPTION
                "Character string value"
    ::= { diskerrorled 1 }

diskerrorledsunSmNodeName OBJECT-TYPE
    SYNTAX      DisplayString
    MAX-ACCESS  read-only
    STATUS      current
    DESCRIPTION
                "Character string value"
    ::= { diskerrorled 2 }

diskerrorledstate OBJECT-TYPE
    SYNTAX      DisplayString
    MAX-ACCESS  read-only
    STATUS      current
    DESCRIPTION
                "Character string value"
    ::= { diskerrorled 3 }

generrorled	OBJECT IDENTIFIER ::= { reader4uwg 33 }

generrorledsunSmTreeProp OBJECT-TYPE
    SYNTAX      DisplayString
    MAX-ACCESS  read-only
    STATUS      current
    DESCRIPTION
                "Character string value"
    ::= { generrorled 1 }

generrorledsunSmNodeName OBJECT-TYPE
    SYNTAX      DisplayString
    MAX-ACCESS  read-only
    STATUS      current
    DESCRIPTION
                "Character string value"
    ::= { generrorled 2 }

generrorledstate OBJECT-TYPE
    SYNTAX      DisplayString
    MAX-ACCESS  read-only
    STATUS      current
    DESCRIPTION
                "Character string value"
    ::= { generrorled 3 }

powerled	OBJECT IDENTIFIER ::= { reader4uwg 34 }

powerledsunSmTreeProp OBJECT-TYPE
    SYNTAX      DisplayString
    MAX-ACCESS  read-only
    STATUS      current
    DESCRIPTION
                "Character string value"
    ::= { powerled 1 }

powerledsunSmNodeName OBJECT-TYPE
    SYNTAX      DisplayString
    MAX-ACCESS  read-only
    STATUS      current
    DESCRIPTION
                "Character string value"
    ::= { powerled 2 }

powerledstate OBJECT-TYPE
    SYNTAX      DisplayString
    MAX-ACCESS  read-only
    STATUS      current
    DESCRIPTION
                "Character string value"
    ::= { powerled 3 }

pserrorled	OBJECT IDENTIFIER ::= { reader4uwg 35 }

pserrorledsunSmTreeProp OBJECT-TYPE
    SYNTAX      DisplayString
    MAX-ACCESS  read-only
    STATUS      current
    DESCRIPTION
                "Character string value"
    ::= { pserrorled 1 }

pserrorledsunSmNodeName OBJECT-TYPE
    SYNTAX      DisplayString
    MAX-ACCESS  read-only
    STATUS      current
    DESCRIPTION
                "Character string value"
    ::= { pserrorled 2 }

pserrorledstate OBJECT-TYPE
    SYNTAX      DisplayString
    MAX-ACCESS  read-only
    STATUS      current
    DESCRIPTION
                "Character string value"
    ::= { pserrorled 3 }

temperrorled	OBJECT IDENTIFIER ::= { reader4uwg 36 }

temperrorledsunSmTreeProp OBJECT-TYPE
    SYNTAX      DisplayString
    MAX-ACCESS  read-only
    STATUS      current
    DESCRIPTION
                "Character string value"
    ::= { temperrorled 1 }

temperrorledsunSmNodeName OBJECT-TYPE
    SYNTAX      DisplayString
    MAX-ACCESS  read-only
    STATUS      current
    DESCRIPTION
                "Character string value"
    ::= { temperrorled 2 }

temperrorledstate OBJECT-TYPE
    SYNTAX      DisplayString
    MAX-ACCESS  read-only
    STATUS      current
    DESCRIPTION
                "Character string value"
    ::= { temperrorled 3 }

systemstatuspanel OBJECT-TYPE
    SYNTAX      SEQUENCE OF Sspentry
    MAX-ACCESS  not-accessible
    STATUS      current
    DESCRIPTION
                "MIB tree branch"
    ::= { reader4uwg 37 }

sspentry OBJECT-TYPE
    SYNTAX      Sspentry
    MAX-ACCESS  not-accessible
    STATUS      current
    DESCRIPTION
                "MIB tree branch"
    INDEX  { sspentryno }
    ::= { systemstatuspanel 1 }

Sspentry ::=
    SEQUENCE {
        sspentrysunSmTreeProp
            DisplayString,
        sspentrysunSmNodeName
            DisplayString,
        sspentryno
            Integer32
    }

sspentrysunSmTreeProp OBJECT-TYPE
    SYNTAX      DisplayString
    MAX-ACCESS  read-only
    STATUS      current
    DESCRIPTION
                "Character string value"
    ::= { sspentry 1 }

sspentrysunSmNodeName OBJECT-TYPE
    SYNTAX      DisplayString
    MAX-ACCESS  read-only
    STATUS      current
    DESCRIPTION
                "Character string value"
    ::= { sspentry 2 }

sspentryno OBJECT-TYPE
    SYNTAX      Integer32
    MAX-ACCESS  read-only
    STATUS      current
    DESCRIPTION
                "Integer value"
    ::= { sspentry 3 }

diskstatusleds OBJECT-TYPE
    SYNTAX      SEQUENCE OF Diskstatusledsentry
    MAX-ACCESS  not-accessible
    STATUS      current
    DESCRIPTION
                "MIB tree branch"
    ::= { reader4uwg 38 }

diskstatusledsentry OBJECT-TYPE
    SYNTAX      Diskstatusledsentry
    MAX-ACCESS  not-accessible
    STATUS      current
    DESCRIPTION
                "MIB tree branch"
    INDEX  { diskstatusledsentryno }
    ::= { diskstatusleds 1 }

Diskstatusledsentry ::=
    SEQUENCE {
        diskstatusledssunSmTreeProp
            DisplayString,
        diskstatusledssunSmNodeName
            DisplayString,
        diskstatusledsentryno
            Integer32
    }

diskstatusledssunSmTreeProp OBJECT-TYPE
    SYNTAX      DisplayString
    MAX-ACCESS  read-only
    STATUS      current
    DESCRIPTION
                "Character string value"
    ::= { diskstatusledsentry 1 }

diskstatusledssunSmNodeName OBJECT-TYPE
    SYNTAX      DisplayString
    MAX-ACCESS  read-only
    STATUS      current
    DESCRIPTION
                "Character string value"
    ::= { diskstatusledsentry 2 }

diskstatusledsentryno OBJECT-TYPE
    SYNTAX      Integer32
    MAX-ACCESS  read-only
    STATUS      current
    DESCRIPTION
                "Integer value"
    ::= { diskstatusledsentry 3 }

rsc	OBJECT IDENTIFIER ::= { reader4uwg 46 }

rscsunSmTreeProp OBJECT-TYPE
    SYNTAX      DisplayString
    MAX-ACCESS  read-only
    STATUS      current
    DESCRIPTION
                "Character string value"
    ::= { rsc 1 }

rscsunSmNodeName OBJECT-TYPE
    SYNTAX      DisplayString
    MAX-ACCESS  read-only
    STATUS      current
    DESCRIPTION
                "Character string value"
    ::= { rsc 2 }

rscdevicetype OBJECT-TYPE
    SYNTAX      DisplayString
    MAX-ACCESS  read-only
    STATUS      current
    DESCRIPTION
                "Character string value"
    ::= { rsc 3 }

rscfrudevice OBJECT-TYPE
    SYNTAX      DisplayString
    MAX-ACCESS  read-only
    STATUS      current
    DESCRIPTION
                "Character string value"
    ::= { rsc 4 }

rscname OBJECT-TYPE
    SYNTAX      DisplayString
    MAX-ACCESS  read-only
    STATUS      current
    DESCRIPTION
                "Character string value"
    ::= { rsc 5 }

rschostname OBJECT-TYPE
    SYNTAX      DisplayString
    MAX-ACCESS  read-only
    STATUS      current
    DESCRIPTION
                "Character string value"
    ::= { rsc 6 }

hardwarerules	OBJECT IDENTIFIER ::= { reader4uwg 47 }

rcr4u209 OBJECT-TYPE
    SYNTAX      DisplayString
    MAX-ACCESS  read-only
    STATUS      current
    DESCRIPTION
                "No Data Value"
    ::= { hardwarerules 1 }

rcr4u290 OBJECT-TYPE
    SYNTAX      DisplayString
    MAX-ACCESS  read-only
    STATUS      current
    DESCRIPTION
                "No Data Value"
    ::= { hardwarerules 2 }

addremTbl OBJECT-TYPE
    SYNTAX      SEQUENCE OF AddremTblEntry
    MAX-ACCESS  not-accessible
    STATUS      current
    DESCRIPTION
                "MIB tree branch"
    ::= { hardwarerules 14 }

addremTblEntry OBJECT-TYPE
    SYNTAX      AddremTblEntry
    MAX-ACCESS  not-accessible
    STATUS      current
    DESCRIPTION
                "MIB tree branch"
    INDEX  { addremTblentryno }
    ::= { addremTbl 1 }

AddremTblEntry ::=
    SEQUENCE {
        addremTblentryno
            Integer32,
        uniqueid
            DisplayString,
        nodename
            DisplayString,
        addrem
            DisplayString
    }

addremTblentryno OBJECT-TYPE
    SYNTAX      Integer32
    MAX-ACCESS  read-only
    STATUS      current
    DESCRIPTION
                "Integer value"
    ::= { addremTblEntry 1 }

uniqueid OBJECT-TYPE
    SYNTAX      DisplayString
    MAX-ACCESS  read-only
    STATUS      current
    DESCRIPTION
                "Character string value"
    ::= { addremTblEntry 2 }

nodename OBJECT-TYPE
    SYNTAX      DisplayString
    MAX-ACCESS  read-only
    STATUS      current
    DESCRIPTION
                "Character string value"
    ::= { addremTblEntry 3 }

addrem OBJECT-TYPE
    SYNTAX      DisplayString
    MAX-ACCESS  read-only
    STATUS      current
    DESCRIPTION
                "Character string value"
    ::= { addremTblEntry 4 }

iocontroller	OBJECT IDENTIFIER ::= { reader4uwg 49 }

iocontrollerTbl OBJECT-TYPE
    SYNTAX      SEQUENCE OF IocontrollerTblEntry
    MAX-ACCESS  not-accessible
    STATUS      current
    DESCRIPTION
                "MIB tree branch"
    ::= { iocontroller 1 }

iocontrollerTblEntry OBJECT-TYPE
    SYNTAX      IocontrollerTblEntry
    MAX-ACCESS  not-accessible
    STATUS      current
    DESCRIPTION
                "MIB tree branch"
    INDEX  { iocontrollerTblentryno }
    ::= { iocontrollerTbl 1 }

IocontrollerTblEntry ::=
    SEQUENCE {
        iocontrollerTblsunSmTreeProp
            DisplayString,
        iocontrollerTblsunSmNodeName
            DisplayString,
        iocontrollerTblentryno
            Integer32,
        iocontrollerTblboardnum
            DisplayString,
        iocontrollerTblclockfrequency
            DisplayString,
        iocontrollerTbldevicetype
            DisplayString,
        iocontrollerTblfru
            DisplayString,
        iocontrollerTblinstance
            DisplayString,
        iocontrollerTblmodel
            DisplayString,
        iocontrollerTblreg
            DisplayString,
        upamid
            DisplayString,
        iocontrollerTblupaportid
            DisplayString,
        versionno
            DisplayString
    }

iocontrollerTblsunSmTreeProp OBJECT-TYPE
    SYNTAX      DisplayString
    MAX-ACCESS  read-only
    STATUS      current
    DESCRIPTION
                "Character string value"
    ::= { iocontrollerTblEntry 1 }

iocontrollerTblsunSmNodeName OBJECT-TYPE
    SYNTAX      DisplayString
    MAX-ACCESS  read-only
    STATUS      current
    DESCRIPTION
                "Character string value"
    ::= { iocontrollerTblEntry 2 }

iocontrollerTblentryno OBJECT-TYPE
    SYNTAX      Integer32
    MAX-ACCESS  read-only
    STATUS      current
    DESCRIPTION
                "Integer value"
    ::= { iocontrollerTblEntry 3 }

iocontrollerTblboardnum OBJECT-TYPE
    SYNTAX      DisplayString
    MAX-ACCESS  read-only
    STATUS      current
    DESCRIPTION
                "Character string value"
    ::= { iocontrollerTblEntry 4 }

iocontrollerTblclockfrequency OBJECT-TYPE
    SYNTAX      DisplayString
    MAX-ACCESS  read-only
    STATUS      current
    DESCRIPTION
                "Character string value"
    ::= { iocontrollerTblEntry 5 }

iocontrollerTbldevicetype OBJECT-TYPE
    SYNTAX      DisplayString
    MAX-ACCESS  read-only
    STATUS      current
    DESCRIPTION
                "Character string value"
    ::= { iocontrollerTblEntry 6 }

iocontrollerTblfru OBJECT-TYPE
    SYNTAX      DisplayString
    MAX-ACCESS  read-only
    STATUS      current
    DESCRIPTION
                "Character string value"
    ::= { iocontrollerTblEntry 13 }

iocontrollerTblinstance OBJECT-TYPE
    SYNTAX      DisplayString
    MAX-ACCESS  read-only
    STATUS      current
    DESCRIPTION
                "Character string value"
    ::= { iocontrollerTblEntry 7 }

iocontrollerTblmodel OBJECT-TYPE
    SYNTAX      DisplayString
    MAX-ACCESS  read-only
    STATUS      current
    DESCRIPTION
                "Character string value"
    ::= { iocontrollerTblEntry 8 }

iocontrollerTblreg OBJECT-TYPE
    SYNTAX      DisplayString
    MAX-ACCESS  read-only
    STATUS      current
    DESCRIPTION
                "Character string value"
    ::= { iocontrollerTblEntry 9 }

upamid OBJECT-TYPE
    SYNTAX      DisplayString
    MAX-ACCESS  read-only
    STATUS      current
    DESCRIPTION
                "Character string value"
    ::= { iocontrollerTblEntry 10 }

iocontrollerTblupaportid OBJECT-TYPE
    SYNTAX      DisplayString
    MAX-ACCESS  read-only
    STATUS      current
    DESCRIPTION
                "Character string value"
    ::= { iocontrollerTblEntry 11 }

versionno OBJECT-TYPE
    SYNTAX      DisplayString
    MAX-ACCESS  read-only
    STATUS      current
    DESCRIPTION
                "Character string value"
    ::= { iocontrollerTblEntry 12 }

iodevice	OBJECT IDENTIFIER ::= { reader4uwg 50 }

iodeviceTbl OBJECT-TYPE
    SYNTAX      SEQUENCE OF IodeviceEntry
    MAX-ACCESS  not-accessible
    STATUS      current
    DESCRIPTION
                "MIB tree branch"
    ::= { iodevice 1 }

iodeviceEntry OBJECT-TYPE
    SYNTAX      IodeviceEntry
    MAX-ACCESS  not-accessible
    STATUS      current
    DESCRIPTION
                "MIB tree branch"
    INDEX  { iodeviceTblentryno }
    ::= { iodeviceTbl 1 }

IodeviceEntry ::=
    SEQUENCE {
        iodeviceTblsunSmTreeProp
            DisplayString,
        iodeviceTblsunSmNodeName
            DisplayString,
        iodeviceTblentryno
            Integer32,
        iodeviceTbldevicetype
            DisplayString,
        iodeviceTblfru
            DisplayString,
        diskcount
            DisplayString,
        iodeviceTblinstance
            DisplayString,
        iodeviceTblmodel
            DisplayString,
        iodeviceTblnodehierarchy
            DisplayString,
        networkcount
            DisplayString,
        iodeviceTblreg
            DisplayString,
        tapecount
            DisplayString
    }

iodeviceTblsunSmTreeProp OBJECT-TYPE
    SYNTAX      DisplayString
    MAX-ACCESS  read-only
    STATUS      current
    DESCRIPTION
                "Character string value"
    ::= { iodeviceEntry 1 }

iodeviceTblsunSmNodeName OBJECT-TYPE
    SYNTAX      DisplayString
    MAX-ACCESS  read-only
    STATUS      current
    DESCRIPTION
                "Character string value"
    ::= { iodeviceEntry 2 }

iodeviceTblentryno OBJECT-TYPE
    SYNTAX      Integer32
    MAX-ACCESS  read-only
    STATUS      current
    DESCRIPTION
                "Integer value"
    ::= { iodeviceEntry 3 }

iodeviceTbldevicetype OBJECT-TYPE
    SYNTAX      DisplayString
    MAX-ACCESS  read-only
    STATUS      current
    DESCRIPTION
                "Character string value"
    ::= { iodeviceEntry 4 }

iodeviceTblfru OBJECT-TYPE
    SYNTAX      DisplayString
    MAX-ACCESS  read-only
    STATUS      current
    DESCRIPTION
                "Character string value"
    ::= { iodeviceEntry 12 }

diskcount OBJECT-TYPE
    SYNTAX      DisplayString
    MAX-ACCESS  read-only
    STATUS      current
    DESCRIPTION
                "Character string value"
    ::= { iodeviceEntry 5 }

iodeviceTblinstance OBJECT-TYPE
    SYNTAX      DisplayString
    MAX-ACCESS  read-only
    STATUS      current
    DESCRIPTION
                "Character string value"
    ::= { iodeviceEntry 6 }

iodeviceTblmodel OBJECT-TYPE
    SYNTAX      DisplayString
    MAX-ACCESS  read-only
    STATUS      current
    DESCRIPTION
                "Character string value"
    ::= { iodeviceEntry 7 }

iodeviceTblnodehierarchy OBJECT-TYPE
    SYNTAX      DisplayString
    MAX-ACCESS  read-only
    STATUS      current
    DESCRIPTION
                "Character string value"
    ::= { iodeviceEntry 8 }

networkcount OBJECT-TYPE
    SYNTAX      DisplayString
    MAX-ACCESS  read-only
    STATUS      current
    DESCRIPTION
                "Character string value"
    ::= { iodeviceEntry 9 }

iodeviceTblreg OBJECT-TYPE
    SYNTAX      DisplayString
    MAX-ACCESS  read-only
    STATUS      current
    DESCRIPTION
                "Character string value"
    ::= { iodeviceEntry 10 }

tapecount OBJECT-TYPE
    SYNTAX      DisplayString
    MAX-ACCESS  read-only
    STATUS      current
    DESCRIPTION
                "Character string value"
    ::= { iodeviceEntry 11 }

disk	OBJECT IDENTIFIER ::= { reader4uwg 51 }

diskTbl OBJECT-TYPE
    SYNTAX      SEQUENCE OF DiskEntry
    MAX-ACCESS  not-accessible
    STATUS      current
    DESCRIPTION
                "MIB tree branch"
    ::= { disk 1 }

diskEntry OBJECT-TYPE
    SYNTAX      DiskEntry
    MAX-ACCESS  not-accessible
    STATUS      current
    DESCRIPTION
                "MIB tree branch"
    INDEX  { diskTblentryno }
    ::= { diskTbl 1 }

DiskEntry ::=
    SEQUENCE {
        diskTblsunSmTreeProp
            DisplayString,
        diskTblsunSmNodeName
            DisplayString,
        diskTblentryno
            Integer32,
        diskTbldevicetype
            DisplayString,
        diskname
            DisplayString,
        diskTblfru
            DisplayString,
        diskTblinstance
            DisplayString,
        diskTblnodehierarchy
            DisplayString,
        diskTbltarget
            DisplayString,
        diskTblsofterrors
            Integer32,
        diskTblharderrors
            Integer32,
        diskTbltransporterrors
            Integer32
    }

diskTblsunSmTreeProp OBJECT-TYPE
    SYNTAX      DisplayString
    MAX-ACCESS  read-only
    STATUS      current
    DESCRIPTION
                "Character string value"
    ::= { diskEntry 1 }

diskTblsunSmNodeName OBJECT-TYPE
    SYNTAX      DisplayString
    MAX-ACCESS  read-only
    STATUS      current
    DESCRIPTION
                "Character string value"
    ::= { diskEntry 2 }

diskTblentryno OBJECT-TYPE
    SYNTAX      Integer32
    MAX-ACCESS  read-only
    STATUS      current
    DESCRIPTION
                "Integer value"
    ::= { diskEntry 3 }

diskTbldevicetype OBJECT-TYPE
    SYNTAX      DisplayString
    MAX-ACCESS  read-only
    STATUS      current
    DESCRIPTION
                "Character string value"
    ::= { diskEntry 4 }

diskname OBJECT-TYPE
    SYNTAX      DisplayString
    MAX-ACCESS  read-only
    STATUS      current
    DESCRIPTION
                "Character string value"
    ::= { diskEntry 5 }

diskTblfru OBJECT-TYPE
    SYNTAX      DisplayString
    MAX-ACCESS  read-only
    STATUS      current
    DESCRIPTION
                "Character string value"
    ::= { diskEntry 6 }

diskTblinstance OBJECT-TYPE
    SYNTAX      DisplayString
    MAX-ACCESS  read-only
    STATUS      current
    DESCRIPTION
                "Character string value"
    ::= { diskEntry 7 }

diskTblnodehierarchy OBJECT-TYPE
    SYNTAX      DisplayString
    MAX-ACCESS  read-only
    STATUS      current
    DESCRIPTION
                "Character string value"
    ::= { diskEntry 8 }

diskTbltarget OBJECT-TYPE
    SYNTAX      DisplayString
    MAX-ACCESS  read-only
    STATUS      current
    DESCRIPTION
                "Character string value"
    ::= { diskEntry 9 }

diskTblsofterrors OBJECT-TYPE
    SYNTAX      Integer32
    MAX-ACCESS  read-only
    STATUS      current
    DESCRIPTION
                "Integer value"
    ::= { diskEntry 10 }

diskTblharderrors OBJECT-TYPE
    SYNTAX      Integer32
    MAX-ACCESS  read-only
    STATUS      current
    DESCRIPTION
                "Integer value"
    ::= { diskEntry 11 }

diskTbltransporterrors OBJECT-TYPE
    SYNTAX      Integer32
    MAX-ACCESS  read-only
    STATUS      current
    DESCRIPTION
                "Integer value"
    ::= { diskEntry 12 }

tape	OBJECT IDENTIFIER ::= { reader4uwg 52 }

tapeTbl OBJECT-TYPE
    SYNTAX      SEQUENCE OF TapeEntry
    MAX-ACCESS  not-accessible
    STATUS      current
    DESCRIPTION
                "MIB tree branch"
    ::= { tape 1 }

tapeEntry OBJECT-TYPE
    SYNTAX      TapeEntry
    MAX-ACCESS  not-accessible
    STATUS      current
    DESCRIPTION
                "MIB tree branch"
    INDEX  { tapeTblentryno }
    ::= { tapeTbl 1 }

TapeEntry ::=
    SEQUENCE {
        tapeTblsunSmTreeProp
            DisplayString,
        tapeTblsunSmNodeName
            DisplayString,
        tapeTblentryno
            Integer32,
        tapeTbldevicetype
            DisplayString,
        tapeTblfru
            DisplayString,
        tapeTblinstance
            DisplayString,
        tapeTblmodel
            DisplayString,
        tapeTblnodehierarchy
            DisplayString,
        tapeTbltapename
            DisplayString,
        tapeEntryStatus
            DisplayString,
        tapeTbltarget
            DisplayString,
        tapeTblsofterrors
            Integer32,
        tapeTblharderrors
            Integer32,
        tapeTbltransporterrors
            Integer32
    }

tapeTblsunSmTreeProp OBJECT-TYPE
    SYNTAX      DisplayString
    MAX-ACCESS  read-only
    STATUS      current
    DESCRIPTION
                "Character string value"
    ::= { tapeEntry 1 }

tapeTblsunSmNodeName OBJECT-TYPE
    SYNTAX      DisplayString
    MAX-ACCESS  read-only
    STATUS      current
    DESCRIPTION
                "Character string value"
    ::= { tapeEntry 2 }

tapeTblentryno OBJECT-TYPE
    SYNTAX      Integer32
    MAX-ACCESS  read-only
    STATUS      current
    DESCRIPTION
                "Integer value"
    ::= { tapeEntry 3 }

tapeTbldevicetype OBJECT-TYPE
    SYNTAX      DisplayString
    MAX-ACCESS  read-only
    STATUS      current
    DESCRIPTION
                "Character string value"
    ::= { tapeEntry 4 }

tapeTblfru OBJECT-TYPE
    SYNTAX      DisplayString
    MAX-ACCESS  read-only
    STATUS      current
    DESCRIPTION
                "Character string value"
    ::= { tapeEntry 5 }

tapeTblinstance OBJECT-TYPE
    SYNTAX      DisplayString
    MAX-ACCESS  read-only
    STATUS      current
    DESCRIPTION
                "Character string value"
    ::= { tapeEntry 6 }

tapeTblmodel OBJECT-TYPE
    SYNTAX      DisplayString
    MAX-ACCESS  read-only
    STATUS      current
    DESCRIPTION
                "Character string value"
    ::= { tapeEntry 7 }

tapeTblnodehierarchy OBJECT-TYPE
    SYNTAX      DisplayString
    MAX-ACCESS  read-only
    STATUS      current
    DESCRIPTION
                "Character string value"
    ::= { tapeEntry 8 }

tapename OBJECT-TYPE
    SYNTAX      DisplayString
    MAX-ACCESS  read-only
    STATUS      current
    DESCRIPTION
                "Character string value"
    ::= { tapeEntry 9 }

tapeEntryStatus OBJECT-TYPE
    SYNTAX      DisplayString
    MAX-ACCESS  read-only
    STATUS      current
    DESCRIPTION
                "Character string value"
    ::= { tapeEntry 10 }

tapeTbltarget OBJECT-TYPE
    SYNTAX      DisplayString
    MAX-ACCESS  read-only
    STATUS      current
    DESCRIPTION
                "Character string value"
    ::= { tapeEntry 11 }

tapeTblsofterrors OBJECT-TYPE
    SYNTAX      Integer32
    MAX-ACCESS  read-only
    STATUS      current
    DESCRIPTION
                "Integer value"
    ::= { tapeEntry 12 }

tapeTblharderrors OBJECT-TYPE
    SYNTAX      Integer32
    MAX-ACCESS  read-only
    STATUS      current
    DESCRIPTION
                "Integer value"
    ::= { tapeEntry 13 }

tapeTbltransporterrors OBJECT-TYPE
    SYNTAX      Integer32
    MAX-ACCESS  read-only
    STATUS      current
    DESCRIPTION
                "Integer value"
    ::= { tapeEntry 14 }

network 	OBJECT IDENTIFIER ::= { reader4uwg 53 }

networkTbl OBJECT-TYPE
    SYNTAX      SEQUENCE OF NetworkEntry
    MAX-ACCESS  not-accessible
    STATUS      current
    DESCRIPTION
                "MIB tree branch"
    ::= { network 1 }

networkEntry OBJECT-TYPE
    SYNTAX      NetworkEntry
    MAX-ACCESS  not-accessible
    STATUS      current
    DESCRIPTION
                "MIB tree branch"
    INDEX  { networkTblentryno }
    ::= { networkTbl 1 }

NetworkEntry ::=
    SEQUENCE {
        networkTblsunSmTreeProp
            DisplayString,
        networkTblsunSmNodeName
            DisplayString,
        networkTblentryno
            Integer32,
        networkTbldevicetype
            DisplayString,
        networkTblfru
            DisplayString,
        ether
            DisplayString,
        inet
            DisplayString,
        interfacename
            DisplayString,
        networkTblnodehierarchy
            DisplayString,
        symbolicname
            DisplayString,
        networkTblreg
            DisplayString,
        inputerrors
            Integer32,
        outputerrors
            Integer32
    }

networkTblsunSmTreeProp OBJECT-TYPE
    SYNTAX      DisplayString
    MAX-ACCESS  read-only
    STATUS      current
    DESCRIPTION
                "Character string value"
    ::= { networkEntry 1 }

networkTblsunSmNodeName OBJECT-TYPE
    SYNTAX      DisplayString
    MAX-ACCESS  read-only
    STATUS      current
    DESCRIPTION
                "Character string value"
    ::= { networkEntry 2 }

networkTblentryno OBJECT-TYPE
    SYNTAX      Integer32
    MAX-ACCESS  read-only
    STATUS      current
    DESCRIPTION
                "Integer value"
    ::= { networkEntry 3 }

networkTbldevicetype OBJECT-TYPE
    SYNTAX      DisplayString
    MAX-ACCESS  read-only
    STATUS      current
    DESCRIPTION
                "Character string value"
    ::= { networkEntry 4 }

networkTblfru OBJECT-TYPE
    SYNTAX      DisplayString
    MAX-ACCESS  read-only
    STATUS      current
    DESCRIPTION
                "Character string value"
    ::= { networkEntry 5 }

ether OBJECT-TYPE
    SYNTAX      DisplayString
    MAX-ACCESS  read-only
    STATUS      current
    DESCRIPTION
                "Character string value"
    ::= { networkEntry 6 }

inet OBJECT-TYPE
    SYNTAX      DisplayString
    MAX-ACCESS  read-only
    STATUS      current
    DESCRIPTION
                "Character string value"
    ::= { networkEntry 7 }

interfacename OBJECT-TYPE
    SYNTAX      DisplayString
    MAX-ACCESS  read-only
    STATUS      current
    DESCRIPTION
                "Character string value"
    ::= { networkEntry 8 }

networkTblnodehierarchy OBJECT-TYPE
    SYNTAX      DisplayString
    MAX-ACCESS  read-only
    STATUS      current
    DESCRIPTION
                "Character string value"
    ::= { networkEntry 9 }

symbolicname OBJECT-TYPE
    SYNTAX      DisplayString
    MAX-ACCESS  read-only
    STATUS      current
    DESCRIPTION
                "Character string value"
    ::= { networkEntry 10 }

networkTblreg OBJECT-TYPE
    SYNTAX      DisplayString
    MAX-ACCESS  read-only
    STATUS      current
    DESCRIPTION
                "Character string value"
    ::= { networkEntry 11 }

inputerrors OBJECT-TYPE
    SYNTAX      Integer32
    MAX-ACCESS  read-only
    STATUS      current
    DESCRIPTION
                "Integer value"
    ::= { networkEntry 12 }

outputerrors OBJECT-TYPE
    SYNTAX      Integer32
    MAX-ACCESS  read-only
    STATUS      current
    DESCRIPTION
                "Integer value"
    ::= { networkEntry 13 }

iounit OBJECT-TYPE
    SYNTAX      SEQUENCE OF IounitEntry
    MAX-ACCESS  not-accessible
    STATUS      current
    DESCRIPTION
                "MIB tree branch"
    ::= { reader4uwg 54 }

iounitEntry OBJECT-TYPE
    SYNTAX      IounitEntry
    MAX-ACCESS  not-accessible
    STATUS      current
    DESCRIPTION
                "MIB tree branch"
    INDEX  { iounitentryno }
    ::= { iounit 1 }

IounitEntry ::=
    SEQUENCE {
        iounitsunSmTreeProp
            DisplayString,
        iounitsunSmNodeName
            DisplayString,
        iounitentryno
            Integer32,
        iounitboardnum
            DisplayString,
        iounitdeviceid
            DisplayString,
        iounitinstance
            DisplayString,
        iounitreg
            DisplayString
    }

iounitsunSmTreeProp OBJECT-TYPE
    SYNTAX      DisplayString
    MAX-ACCESS  read-only
    STATUS      current
    DESCRIPTION
                "Character string value"
    ::= { iounitEntry 1 }

iounitsunSmNodeName OBJECT-TYPE
    SYNTAX      DisplayString
    MAX-ACCESS  read-only
    STATUS      current
    DESCRIPTION
                "Character string value"
    ::= { iounitEntry 2 }

iounitentryno OBJECT-TYPE
    SYNTAX      Integer32
    MAX-ACCESS  read-only
    STATUS      current
    DESCRIPTION
                "Integer value"
    ::= { iounitEntry 3 }

iounitboardnum OBJECT-TYPE
    SYNTAX      DisplayString
    MAX-ACCESS  read-only
    STATUS      current
    DESCRIPTION
                "Character string value"
    ::= { iounitEntry 4 }

iounitdeviceid OBJECT-TYPE
    SYNTAX      DisplayString
    MAX-ACCESS  read-only
    STATUS      current
    DESCRIPTION
                "Character string value"
    ::= { iounitEntry 5 }

iounitinstance OBJECT-TYPE
    SYNTAX      DisplayString
    MAX-ACCESS  read-only
    STATUS      current
    DESCRIPTION
                "Character string value"
    ::= { iounitEntry 6 }

iounitreg OBJECT-TYPE
    SYNTAX      DisplayString
    MAX-ACCESS  read-only
    STATUS      current
    DESCRIPTION
                "Character string value"
    ::= { iounitEntry 7 }

genericdevice	OBJECT IDENTIFIER ::= { reader4uwg 55 }

genericdeviceTbl OBJECT-TYPE
    SYNTAX      SEQUENCE OF Genericdeviceentry
    MAX-ACCESS  not-accessible
    STATUS      current
    DESCRIPTION
                "MIB tree branch"
    ::= { genericdevice 1 }

genericdeviceentry OBJECT-TYPE
    SYNTAX      Genericdeviceentry
    MAX-ACCESS  not-accessible
    STATUS      current
    DESCRIPTION
                "MIB tree branch"
    INDEX  { genericdeviceTblentryno }
    ::= { genericdeviceTbl 1 }

Genericdeviceentry ::=
    SEQUENCE {
        genericdeviceTblsunSmTreeProp
            DisplayString,
        genericdeviceTblsunSmNodeName
            DisplayString,
        genericdeviceTblentryno
            Integer32,
        genericdeviceTblpathnameelement
            DisplayString
    }

genericdeviceTblsunSmTreeProp OBJECT-TYPE
    SYNTAX      DisplayString
    MAX-ACCESS  read-only
    STATUS      current
    DESCRIPTION
                "Character string value"
    ::= { genericdeviceentry 1 }

genericdeviceTblsunSmNodeName OBJECT-TYPE
    SYNTAX      DisplayString
    MAX-ACCESS  read-only
    STATUS      current
    DESCRIPTION
                "Character string value"
    ::= { genericdeviceentry 2 }

genericdeviceTblentryno OBJECT-TYPE
    SYNTAX      Integer32
    MAX-ACCESS  read-only
    STATUS      current
    DESCRIPTION
                "Integer value"
    ::= { genericdeviceentry 3 }

genericdeviceTblpathnameelement OBJECT-TYPE
    SYNTAX      DisplayString
    MAX-ACCESS  read-only
    STATUS      current
    DESCRIPTION
                "Character string value"
    ::= { genericdeviceentry 4 }
END
