-- *****************************************************************
-- CISCO-RFC1213-CAPABILITY.my:  Cisco's RFC 1213 (MIB-II) AGENT-CAPABILITIES
--
-- August 1994, Jeffrey T. Johnson
-- October 2003, Jayakumar Kadirvelu
--
-- Copyright (c) 1994-2003 by cisco Systems, Inc.
-- All rights reserved.
-- 
-- *****************************************************************
--

CISCO-RFC1213-CAPABILITY DEFINITIONS ::= BEGIN

IMPORTS
        MODULE-IDENTITY
                FROM SNMPv2-SMI
        AGENT-CAPABILITIES
                FROM SNMPv2-CONF
			DisplayString
					FROM SNMPv2-TC
        ciscoAgentCapability
                FROM CISCO-SMI;

ciscoRFC1213Capability MODULE-IDENTITY
        LAST-UPDATED    "200310271600Z"
        ORGANIZATION    "Cisco Systems, Inc."
        CONTACT-INFO
                "       Cisco Systems
                        Customer Service
                       
                Postal: 170 West Tasman Drive
                        San Jose, CA  95134
                        USA
                    
                   Tel: +1 800 553-NETS
                        
                E-mail: cs-snmp@cisco.com
                        cs-lan-switch-snmp@cisco.com"
        DESCRIPTION
                "Agent capabilities for the RFC1213-MIB (MIB-II)"
        REVISION        "200310271600Z"
        DESCRIPTION
                "Added ciscoRFC1213CapCatOSV08R0101."

        REVISION        "200109081600Z"
        DESCRIPTION
                "Zero length for sysName disallowed."
        REVISION        "9408180000Z"
        DESCRIPTION
                "Initial version of this MIB module."
        ::= { ciscoAgentCapability 101 }

ciscoRFC1213CapabilityV10R02 AGENT-CAPABILITIES

PRODUCT-RELEASE "Cisco IOS 10.2"
STATUS          current
DESCRIPTION     "RFC 1213 (MIB II) capabilities"

SUPPORTS        RFC1213-MIB
INCLUDES        { systemGroup, interfacesGroup, atGroup, ipGroup, icmpGroup,
                  tcpGroup, udpGroup, egpGroup, snmpGroup }

VARIATION       ifAdminStatus
SYNTAX          INTEGER { up(1), down(2) }
DESCRIPTION     "Unable to set test mode"

VARIATION       ifOperStatus
SYNTAX          INTEGER { up(1), down(2), unknown(4), dormant(5) }
DESCRIPTION     "testing(3) not available, but unknown(4) and dormant(5)
                as defined by RFC 1573 are available"

VARIATION       atIfIndex
ACCESS          read-only
DESCRIPTION     "Unable to create or modify atTable entries"

VARIATION       atPhysAddress
ACCESS          read-only
DESCRIPTION     "Unable to create or modify atTable entries"

VARIATION       atNetAddress
ACCESS          read-only
DESCRIPTION     "Unable to create or modify atTable entries"

-- ip group still under modification, so capabilities aren't defined
-- currently, only entry deletion is supported(no creation/modification)

VARIATION       egpNeighEventTrigger
ACCESS          read-only
DESCRIPTION     "Unable to initiate triggers via snmp"

        ::= { ciscoRFC1213Capability 1 }

ciscoRFC1213CapabilityV12R02 AGENT-CAPABILITIES

PRODUCT-RELEASE "Cisco IOS 12.2"
STATUS          current
DESCRIPTION     "RFC 1213 (MIB II) capabilities"

SUPPORTS        RFC1213-MIB
INCLUDES        { systemGroup, interfacesGroup, atGroup, ipGroup, 
                  icmpGroup, tcpGroup, udpGroup, egpGroup, snmpGroup }

VARIATION       ifAdminStatus
SYNTAX          INTEGER { up(1), down(2) }
DESCRIPTION     "Unable to set test mode"

VARIATION       ifOperStatus
SYNTAX          INTEGER { up(1), down(2), unknown(4), dormant(5) }
DESCRIPTION     "testing(3) not available, but unknown(4) and dormant(5)
                as defined by RFC 1573 are available"

VARIATION       atIfIndex
ACCESS          read-only
DESCRIPTION     "Unable to create or modify atTable entries"

VARIATION       atPhysAddress
ACCESS          read-only
DESCRIPTION     "Unable to create or modify atTable entries"

VARIATION       atNetAddress
ACCESS          read-only
DESCRIPTION     "Unable to create or modify atTable entries"

-- ip group still under modification, so capabilities aren't defined
-- currently, only entry deletion is supported(no creation/modification)

VARIATION       ipNetToMediaType
ACCESS          read-write
DESCRIPTION     "Unable to create or modify ipNetToMediaTable
                entries. Only entry deletion is supported by 
                setting this object to invalid(2)"

VARIATION       egpNeighEventTrigger
ACCESS          read-only
DESCRIPTION     "Unable to initiate triggers via snmp"

VARIATION       sysName
SYNTAX          DisplayString (SIZE (1..255))
DESCRIPTION     "Changing SIZE to 1..255 from 0..255, to disallow
                zero length sysName strings."

        ::= { ciscoRFC1213Capability 2 }

ciscoRFC1213CapabilityV12R00S AGENT-CAPABILITIES

PRODUCT-RELEASE "Cisco IOS 12.0S"
STATUS          current
DESCRIPTION     "RFC 1213 (MIB II) capabilities"

SUPPORTS        RFC1213-MIB
INCLUDES        { systemGroup, interfacesGroup, atGroup, ipGroup, 
                  icmpGroup, tcpGroup, udpGroup, egpGroup, snmpGroup }

VARIATION       ifAdminStatus
SYNTAX          INTEGER { up(1), down(2) }
DESCRIPTION     "Unable to set test mode"

VARIATION       ifOperStatus
SYNTAX          INTEGER { up(1), down(2), unknown(4), dormant(5) }
DESCRIPTION     "testing(3) not available, but unknown(4) and dormant(5)
                as defined by RFC 1573 are available"

VARIATION       atIfIndex
ACCESS          read-only
DESCRIPTION     "Unable to create or modify atTable entries"

VARIATION       atPhysAddress
ACCESS          read-only
DESCRIPTION     "Unable to create or modify atTable entries"

VARIATION       atNetAddress
ACCESS          read-only
DESCRIPTION     "Unable to create or modify atTable entries"

-- ip group still under modification, so capabilities aren't defined
-- currently, only entry deletion is supported(no creation/modification)

VARIATION       ipNetToMediaType
ACCESS          read-write
DESCRIPTION     "Unable to create or modify ipNetToMediaTable
                entries. Only entry deletion is supported by 
                setting this object to invalid(2)"

VARIATION       egpNeighEventTrigger
ACCESS          read-only
DESCRIPTION     "Unable to initiate triggers via snmp"

VARIATION       sysName
SYNTAX          DisplayString (SIZE (1..255))
DESCRIPTION     "Changing SIZE to 1..255 from 0..255, to disallow
                zero length sysName strings."

        ::= { ciscoRFC1213Capability 3 }

ciscoRFC1213CapabilityV12R01 AGENT-CAPABILITIES

PRODUCT-RELEASE "Cisco IOS 12.1"
STATUS          current
DESCRIPTION     "RFC 1213 (MIB II) capabilities"

SUPPORTS        RFC1213-MIB
INCLUDES        { systemGroup, interfacesGroup, atGroup, ipGroup, 
                  icmpGroup, tcpGroup, udpGroup, egpGroup, snmpGroup }

VARIATION       ifAdminStatus
SYNTAX          INTEGER { up(1), down(2) }
DESCRIPTION     "Unable to set test mode"

VARIATION       ifOperStatus
SYNTAX          INTEGER { up(1), down(2), unknown(4), dormant(5) }
DESCRIPTION     "testing(3) not available, but unknown(4) and dormant(5)
                as defined by RFC 1573 are available"

VARIATION       atIfIndex
ACCESS          read-only
DESCRIPTION     "Unable to create or modify atTable entries"

VARIATION       atPhysAddress
ACCESS          read-only
DESCRIPTION     "Unable to create or modify atTable entries"

VARIATION       atNetAddress
ACCESS          read-only
DESCRIPTION     "Unable to create or modify atTable entries"

-- ip group still under modification, so capabilities aren't defined
-- currently, only entry deletion is supported(no creation/modification)

VARIATION       ipNetToMediaType
ACCESS          read-write
DESCRIPTION     "Unable to create or modify ipNetToMediaTable
                entries. Only entry deletion is supported by 
                setting this object to invalid(2)"

VARIATION       egpNeighEventTrigger
ACCESS          read-only
DESCRIPTION     "Unable to initiate triggers via snmp"

VARIATION       sysName
SYNTAX          DisplayString (SIZE (1..255))
DESCRIPTION     "Changing SIZE to 1..255 from 0..255, to disallow
                zero length sysName strings."

        ::= { ciscoRFC1213Capability 4 }

ciscoRFC1213CapCatOSV08R0101 AGENT-CAPABILITIES

PRODUCT-RELEASE "Cisco CatOS 8.1(1)."
STATUS          current
DESCRIPTION     "RFC1213-MIB agent capabilities."

SUPPORTS        RFC1213-MIB
INCLUDES        { systemGroup, interfacesGroup, atGroup, 
                  ipGroup, icmpGroup, tcpGroup, udpGroup, 
                  snmpGroup }

VARIATION       sysServices
DESCRIPTION     "Always returns 2 (datalink/subnetwork layer)."

VARIATION       ipInUnknownProtos
DESCRIPTION     "Always returns 0."

VARIATION       ipInDiscards
DESCRIPTION     "Always returns 0."

VARIATION       ipOutRequests
DESCRIPTION     "Always returns 0."

VARIATION       ipOutDiscards
DESCRIPTION     "Always returns 0."

VARIATION       ipFragOKs
DESCRIPTION     "Always returns 0."

VARIATION       ipFragFails
DESCRIPTION     "Always returns 0."

VARIATION       ipFragCreates
DESCRIPTION     "Always returns 0."

VARIATION       ipRoutingDiscards
DESCRIPTION     "Always returns 0."

VARIATION       ipAdEntReasmMaxSize
DESCRIPTION     "Always returns 65535."

VARIATION       ipRouteMetric2
DESCRIPTION     "Always returns -1."

VARIATION       ipRouteMetric3
DESCRIPTION     "Always returns -1."

VARIATION       ipRouteMetric4
DESCRIPTION     "Always returns -1."

VARIATION       ipRouteProto 
SYNTAX          INTEGER { local(2), netmgmt(3), icmp(4) }
DESCRIPTION     "Only supports local(2), netmgmt(3), icmp(4)."

VARIATION       ipRouteMetric5
DESCRIPTION     "Always returns -1."

VARIATION       ipRouteInfo
DESCRIPTION     "Always returns NULLOID."

VARIATION       tcpRtoAlgorithm
SYNTAX          INTEGER { vanj(4) }
DESCRIPTION     "Only supports vanj(4)."

VARIATION       tcpMaxConn
DESCRIPTION     "Always returns -1."

VARIATION       tcpConnState
ACCESS          read-only
DESCRIPTION     "Unable to modify tcpConnTable entries."

                ::= { ciscoRFC1213Capability 5 }

END
