ACC-SYSTEM DEFINITIONS ::= BEGIN

    IMPORTS
		OBJECT-TYPE, IpAddress, TimeTicks, Gauge, Counter FROM RFC1155-SMI
		TRAP-TYPE FROM RFC-1215
	accBRG, DisplayString FROM ACC-MIB;

	-- System Group
      accSystem         OBJECT IDENTIFIER ::= { accBRG 1 }
	accSysInfo	OBJECT IDENTIFIER ::= { accSystem 1 }
	  accUnitName	OBJECT-TYPE   
			SYNTAX  DisplayString	
			ACCESS	read-write
			STATUS	mandatory
			DESCRIPTION
                " A printable ASCII string up to 32 octets long that is
                 used to refer to a physical unit. This name is used
                 in the prompt displayed at the maintenance terminal."
			::= { accSysInfo 1 }
	  accRomId	OBJECT-TYPE   
			SYNTAX  DisplayString	
			ACCESS	read-only
			STATUS	mandatory
			DESCRIPTION
		 " A printable ASCII string that contains information about
		   the hardware and the firmware (NOT the software). "
			::= { accSysInfo 2 }
	  accSwVersion	OBJECT-TYPE   
			SYNTAX  DisplayString	
			ACCESS	read-only
			STATUS	mandatory
			DESCRIPTION
                   " A printable ASCII string representing the software
                     version number of the running code."
			::= { accSysInfo 3 }
	  accReset	OBJECT-TYPE   
			SYNTAX	INTEGER
			ACCESS	read-write
			STATUS	mandatory
			DESCRIPTION
                 " A Set  command on this object will cause an immediate reset
		   of the unit."
			::= { accSysInfo 4 }
          accMemStatTable    OBJECT-TYPE
                        SYNTAX SEQUENCE OF AccMemStatEntry
                        ACCESS not-accessible
                        STATUS mandatory
                        DESCRIPTION
                    " Information about data buffer pools.
                      Instance is pool number.
                      1 - 7 is D RAM
                      8 is M RAM
                      9 - is C RAM
		      10 - is H RAM"
                        ::= { accSysInfo 5 }
	  accMemStatEntry   OBJECT-TYPE
			SYNTAX AccMemStatEntry
                	ACCESS          not-accessible
                	STATUS          mandatory
			DESCRIPTION
                	"A single entry in the Memory stats table"
--                        INDEX { INTEGER }
                	::= { accMemStatTable 1 }
	  AccMemStatEntry ::= SEQUENCE {
			accMemBlkEntSize		INTEGER,
	    		accMemBlkEntTotal		INTEGER,
	    		accMemBlkEntMax 		Gauge,
	    		accMemBlkEntInUse		Gauge,
	    		accMemBlkEntFails		Counter,
			accMemBlkEntType		INTEGER,
	    		accMemBlkEntAllocs		Counter,
	    		accMemBlkEntInitial		INTEGER
			}
	    accMemBlkEntSize   OBJECT-TYPE  
			SYNTAX	INTEGER
			ACCESS	read-only
			STATUS	mandatory
			DESCRIPTION
                      " Size (bytes) of these buffers"
			::=  { accMemStatEntry 1 }
	    accMemBlkEntTotal	OBJECT-TYPE  
			SYNTAX	INTEGER
			ACCESS	read-only
			STATUS	mandatory
			DESCRIPTION
                       " Total number of these buffers in pool, whether
                         or not they are in use"
			::=  { accMemStatEntry 2 }
	    accMemBlkEntMax   OBJECT-TYPE  
			SYNTAX	Gauge
			ACCESS	read-only
			STATUS	mandatory
			DESCRIPTION
                        " High water mark of usage of buffers"
			::=  { accMemStatEntry 3 }
	    accMemBlkEntInUse	OBJECT-TYPE  
			SYNTAX	Gauge
			ACCESS	read-only
			STATUS	mandatory
			DESCRIPTION
                        " Number of buffers currently in use."
			::=  { accMemStatEntry 4 }
	    accMemBlkEntFails	OBJECT-TYPE  
			SYNTAX	Counter
			ACCESS	read-only
			STATUS	mandatory
			DESCRIPTION
                        "Number of times requests were made for a buffer
                         of this size that failed because none were avaliable."
			::=  { accMemStatEntry 5 }
	    accMemBlkEntType   OBJECT-TYPE  
               		 SYNTAX  INTEGER 
			ACCESS	read-only
			STATUS	mandatory
			DESCRIPTION
                        "Numeric classification of the buffer."
			::=  { accMemStatEntry 6 }
	    accMemBlkEntAllocs   OBJECT-TYPE  
			SYNTAX	Counter
			ACCESS	read-only
			STATUS	mandatory
			DESCRIPTION
                      " Number of times a request was made for a buffer
			of this size."
			::=  { accMemStatEntry 7 }
            accMemBlkEntInitial   OBJECT-TYPE
                        SYNTAX  INTEGER
                        ACCESS  read-only
                        STATUS  mandatory
                        DESCRIPTION
                      " Number of buffers of this size allocated at 
                        initialization."
			::=  { accMemStatEntry 8 }
--.(b
--          accMemStatTbl    OBJECT-TYPE
--                        SYNTAX AccMemBlkEntry
--                        ACCESS not-accessible
--                        STATUS Deprecated
--                        DESCRIPTION
--                    " Information about data buffer pools.
--                      Instance is pool number.
--
--                      1 - 7 is D RAM
--                      8 is M RAM
--                      9 - is C RAM
--		      10 - is H RAM"
--                      INDEX { INTEGER }
--                        ::= { accSysInfo 5 }
--.)b
--.sp
--.(b
--		AccMemBlkEntry ::= SEQUENCE {
--			accMemBlkEntSize		INTEGER,
--	    		accMemBlkEntTotal		INTEGER,
--	    		accMemBlkEntMax 		Gauge,
--	    		accMemBlkEntInUse		Gauge,
--	    		accMemBlkEntFails		Counter,
--			accMemBlkEntType		INTEGER,
--	    		accMemBlkEntAllocs		Counter,
--	    		accMemBlkEntInitial		INTEGER
--			}
--.)b
--.sp
--.(b
--	    accMemBlkEntSize   OBJECT-TYPE  
--			SYNTAX	INTEGER
--			ACCESS	read-only
--			STATUS	Deprecated
--			DESCRIPTION
--                      " Size (bytes) of these buffers"
--			::=  { accMemStatTbl 1 }
--.)b
--.sp
--.(b
--	    accMemBlkEntTotal	OBJECT-TYPE  
--			SYNTAX	INTEGER
--			ACCESS	read-only
--			STATUS	Deprecated
--			DESCRIPTION
--                       " Total number of these buffers in pool, whether
--                         or not they are in use"
--			::=  { accMemStatTbl 2 }
--.)b
--.sp
--.(b
--	    accMemBlkEntMax   OBJECT-TYPE  
--			SYNTAX	Gauge
--			ACCESS	read-only
--			STATUS	Deprecated
--			DESCRIPTION
--                        " High water mark of usage of buffers"
--			::=  { accMemStatTbl 3 }
--.)b
--.sp
--.(b
--	    accMemBlkEntInUse	OBJECT-TYPE  
--			SYNTAX	Gauge
--			ACCESS	read-only
--			STATUS	Deprecated
--			DESCRIPTION
--                        " Number of buffers currently in use."
--			::=  { accMemStatTbl 4 }
--.)b
--.sp
--.(b
--	    accMemBlkEntFails	OBJECT-TYPE  
--			SYNTAX	Counter
--			ACCESS	read-only
--			STATUS	Deprecated
--			DESCRIPTION
--                       " Number of times requests were made for a buffer
--                         of this size that failed because none were avaliable."
--			::=  { accMemStatTbl 5 }
--.)b
--.sp
--.(b
--	    accMemBlkEntType   OBJECT-TYPE  
--AWK_ENUM_0
--                SYNTAX  INTEGER {
--			dblk(1),
--			mblk(2),
--			cblk(3),
--			hblk(4),
--			fast(9),
--			local(10),
--			global(11),
--			reserved(12)
--                        }
--AWK_ENUM_0
--AWK_NO_ENUM_0
--                SYNTAX  INTEGER 
--AWK_NO_ENUM_0
--			ACCESS	read-only
--			STATUS	Deprecated
--			DESCRIPTION
--                      " Numeric classification of the buffer."
--			::=  { accMemStatTbl 6 }
--.)b
--.sp
--.(b
--	    accMemBlkEntAllocs   OBJECT-TYPE  
--			SYNTAX	Counter
--			ACCESS	read-only
--			STATUS	mandatory
--			DESCRIPTION
--                      " Number of times a request was made for a buffer
--			of this size."
--			::=  { accMemStatTbl 7 }
--.)b
--.sp
--.(b
--            accMemBlkEntInitial   OBJECT-TYPE
--                        SYNTAX  INTEGER
--                        ACCESS  read-only
--                        STATUS  mandatory
--                        DESCRIPTION
--                      " Number of buffers of this size allocated at 
--                        initialization."
--                        ::=  { accMemStatTbl 8 }
--.)b
	accSessionCtrl	OBJECT IDENTIFIER ::= { accSystem 2 }
	  accLogin	OBJECT-TYPE   
			SYNTAX  DisplayString	
			ACCESS	read-write
			STATUS	mandatory
			DESCRIPTION
                 " A read attempt of this object is interpreted as a request
                  for login to the unit. The instance is an ASCII string
                  with the following (case sensitive) format:
                          CommunityString:Password
                  The GetResponse-PDU will return the accUnitName of the unit.
                  A write attempt is interpreted as a request to change
                  the password.
                  A GetNextRequest will not acknowledge the presence
                   of this object."
			::= { accSessionCtrl 1 }
	  accLogout	OBJECT-TYPE   
			SYNTAX  DisplayString	
			ACCESS	read-only
			STATUS	mandatory
			DESCRIPTION
                 " A read attempt of this object is interpreted as a request
                  for logout to the unit. The instance is an ASCII string
                  with the following format:
                          CommunityString:Password
                  A GetNextRequest will not acknowledge the presence
                   of this object."
			::= { accSessionCtrl 2 }
	  accLoginTimeout  OBJECT-TYPE	
			SYNTAX TimeTicks 
			ACCESS read-write
			STATUS mandatory
			DESCRIPTION
			 " Session inactivity timer.
			   Zero disables timer (no timeout)
			   Default value is zero
			   Range is 0-86400 seconds"
			::= { accSessionCtrl 3 }
	accTrapTable	OBJECT-TYPE 
			SYNTAX	SEQUENCE OF AccTrapEntry
			ACCESS	not-accessible
			STATUS	mandatory
			DESCRIPTION
                   " A table of systems to which Trap Messages generated
                     by this unit shall be sent.
                     To delete an entry, a SetRequest-PDU for the specific
                     instance of accTrapAddr with a NULL value encoding is
                     used."
			::= { accSystem 3 }
	  accTrapEntry	OBJECT-TYPE
			SYNTAX	AccTrapEntry
			ACCESS	not-accessible
			STATUS	mandatory
			DESCRIPTION
                            " A Trap Table entry "
                        INDEX { accTrapAddr }
			::= { accTrapTable 1 }
	  AccTrapEntry	::= SEQUENCE {
			accTrapAddr	 IpAddress,
			accTrapSeverity	 INTEGER
			} 
	    accTrapAddr OBJECT-TYPE   
			SYNTAX	IpAddress
			ACCESS	read-write
			STATUS	mandatory
			DESCRIPTION
                " An IP address to which SNMP traps generated by the unit
                  are sent."
			::= { accTrapEntry 1 }
	    accTrapSeverity	OBJECT-TYPE   
			SYNTAX	INTEGER (1..7)
			ACCESS	read-write
			STATUS	mandatory
			DESCRIPTION
                 " severity level of the traps to be sent 
                   ACC products generate enterprise specific traps for which
                   different severity levels from 1 through 7 are assigned.
                   Level 1 refers to Only SNMP traps. Level 2 are
                   specific traps of highest urgency, and thus progressively
                   each level get more verbose. The normal operational level
                   is expected to be 3 or 4. Higher levels (i.e., 5-7) are
                   expected to generate many events which may be helpful
                   in identifying/isolating configuration related problems,
                   but may affect the performance of the unit."
			::= { accTrapEntry 2 }
	accClock	OBJECT IDENTIFIER ::= { accSystem 4 }
	  accDate	OBJECT-TYPE   
			SYNTAX	OCTET STRING
			ACCESS	read-write
			STATUS	deprecated
			DESCRIPTION
                 " The octet string of six bytes representing the date
                  and time has the following format:
                  YYMMDDHHMMSS
                  where the valid range of values for each of the bytes
                  is as follows:
                          YY      0..99
                          MM      1..12
                          DD      1..31
                          HH      0..23
                          MM      0..59
                          SS      0..59"
			::= { accClock 1 }
	  accUToffset	OBJECT-TYPE   
			SYNTAX	OCTET STRING
			ACCESS	read-write
			STATUS	mandatory
			DESCRIPTION
			 " 3-byte date string, HH MM SS"
			::= { accClock 2 }
	  accSysBootTime  OBJECT-TYPE	
			SYNTAX	OCTET STRING
			ACCESS	read-only
			STATUS	deprecated
			DESCRIPTION
			 " 3-byte date string, HH MM SS"
			::= { accClock 3 }
	  accSysCpuAvgShort  OBJECT-TYPE	
			SYNTAX	INTEGER
			ACCESS	read-only
			STATUS	mandatory
			DESCRIPTION
			 " percentage CPU used over the last minute "
			::= { accClock 4 }
	  accSysCpuAvgLong  OBJECT-TYPE	
			SYNTAX	INTEGER
			ACCESS	read-only
			STATUS	mandatory
			DESCRIPTION
			 " percentage CPU used over the last 5 minutes "
			::= { accClock 5 }
        accSysDataSwitchStatus OBJECT-TYPE
                SYNTAX INTEGER {
                        on (1),
                        off (2)
                }
                ACCESS read-only
                STATUS mandatory
                DESCRIPTION
                        "The status of the hardware switch, to determine
                whether Data calls could be initiated/accepted over the
                ISDN line. ONLY voice calls will be accepted or initiated
                when this h/w switch status is OFF."
                ::= { accClock 6 }
        accSysLastConfig  OBJECT-TYPE
		SYNTAX  TimeTicks
		ACCESS  read-write
		STATUS  mandatory
		DESCRIPTION
			"System Last Configuration Time"
		::= { accClock 8 }
	  accDateY2K	OBJECT-TYPE   
			SYNTAX	OCTET STRING
			ACCESS	read-write
			STATUS	mandatory
			DESCRIPTION
                 " The seven byte long octet string indicates system date and
		   time.  The octet string represents year 2000 compliant 
		   date and time, and is laid out in the following 
		   structured format:
			2 Byte unsigned short value of year
			1 Byte value of month
			1 Byte value of day of the month
			1 Byte value of hour
			1 Byte value of minutes
			1 Byte value of seconds
                  The valid range of values for each of the component
                  is as follows:
                        year      0..2079
                        month     1..12
                        day       1..31
                        hour      0..23
                        minutes   0..59
                        seconds   0..59"
			::= { accClock 10 }
	  accSysBootTimeY2K  OBJECT-TYPE	
			SYNTAX	OCTET STRING
			ACCESS	read-only
			STATUS	mandatory
			DESCRIPTION
                 " The seven bytes long octet string indicates system boot
		   time.  The octet string represents year 2000 compliant 
		   date and time, and is laid out in the following 
		   structured format:
			2 Byte unsigned short value of year
			1 Byte value of month
			1 Byte value of day of the month
			1 Byte value of hour
			1 Byte value of minutes
			1 Byte value of seconds "
			::= { accClock 11 }
	  accDay  OBJECT-TYPE	
			SYNTAX INTEGER
			{
			    tue(1),
			    wed(2),
			    thu(3),
			    fri(4),
			    sat(5),
			    sun(6)
			}	
			ACCESS	read-write
			STATUS	mandatory
			DESCRIPTION
		 "Day of the week (enumnerated MON-SUN [0-6])"
			::= { accClock 12 }
        accAccessTable	OBJECT-TYPE
			SYNTAX	SEQUENCE OF  AccAccessEntry
			ACCESS	not-accessible
			STATUS	mandatory
			DESCRIPTION
                   " A table of users authorized to log in to this unit.
                     To delete an entry, a SetRequest-PDU for the specific
                     instance of accAccessAddr with a NULL value encoding is
                     used."
			::= { accSystem 6 }
	 accAccessEntry	OBJECT-TYPE
		SYNTAX	AccAccessEntry
		ACCESS	not-accessible
		STATUS	mandatory
		DESCRIPTION
                    " An entry of information about an authorized user."
                INDEX { accAccessAddr, accAccessNetMask, accAccessUdpPort }     
		::= { accAccessTable 1 }
	 	AccAccessEntry	::= SEQUENCE {
			      accAccessCmty	 DisplayString,
			      accAccessAddr	 IpAddress,
			      accAccessNetMask	 IpAddress,
			      accAccessUdpPort	 INTEGER
			      }
	   accAccessCmty	OBJECT-TYPE   
			SYNTAX  DisplayString	
			ACCESS	read-write
			STATUS	mandatory
			DESCRIPTION
                 " Access community"
			::= { accAccessEntry 1 }
	   accAccessAddr	OBJECT-TYPE   
		SYNTAX	IpAddress
		ACCESS	read-write
		STATUS	mandatory
		DESCRIPTION
                 " IP address from which a login request is honored."
		::= { accAccessEntry 2 }
	   accAccessNetMask	OBJECT-TYPE   
		SYNTAX	IpAddress
		ACCESS	read-write
		STATUS	mandatory
		DESCRIPTION
                        " Subnet mask used to validate login requests."
		::= { accAccessEntry 3 }  
	   accAccessUdpPort	OBJECT-TYPE   
		SYNTAX	INTEGER
		ACCESS	read-write
		STATUS	mandatory
		DESCRIPTION
                 " UDP port number of the SNMP application. "
			::= { accAccessEntry 4 }
	  accReload	OBJECT-TYPE   
			SYNTAX	TimeTicks
			ACCESS	read-write
			STATUS	mandatory
			DESCRIPTION
			 " Time until system reload shall occur.
			   Upon expiry of the timer, the system will load
			   and execute a new image of the application code.
			   The load file will come from diskette, local
			   EPROM, or over the network, depending on the
			   configuration of the unit."
			::= { accSystem 7 }
        accIfNames  OBJECT IDENTIFIER  ::= { accSystem 8 }
           accIfNumNames  OBJECT-TYPE
                  SYNTAX  INTEGER
                  ACCESS  read-only
                  STATUS  mandatory
                  DESCRIPTION
                     "Number of interfaces (physical and logical).
                      There are this many entries in the Name table."
                   ::= { accIfNames 1 }
	  accIfNameTable	OBJECT-TYPE 
			SYNTAX	SEQUENCE OF AccIfNameEntry
			ACCESS	not-accessible
			STATUS	mandatory
			DESCRIPTION
                   " A table of of mnemonic 'names' for physical and
                     logical interfaces"
			::= { accIfNames 2 }
	     accIfNameEntry	OBJECT-TYPE
			SYNTAX	AccIfNameEntry
			ACCESS	not-accessible
			STATUS	mandatory
			DESCRIPTION
                            " An entry in the Interface Name table "
                        INDEX { accIfNameIndex }
			::= { accIfNameTable 1 }
		  AccIfNameEntry	::= SEQUENCE {
			accIfNameIndex	 INTEGER,
			accIfName  	 DisplayString,
			accIfNameDefault DisplayString 
			} 
	      accIfNameIndex OBJECT-TYPE   
			SYNTAX	INTEGER
			ACCESS	read-only
			STATUS	mandatory
			DESCRIPTION
                " Interface number "
			::= { accIfNameEntry 1 }
	       accIfName	OBJECT-TYPE   
			SYNTAX	DisplayString --(SIZE (5)) 
			ACCESS	read-write
			STATUS	mandatory
			DESCRIPTION
                 " Mnemonic name for this interface" 
			::= { accIfNameEntry 2 }
	       accIfNameDefault	OBJECT-TYPE   
			SYNTAX	DisplayString --(SIZE (5)) 
			ACCESS	read-only
			STATUS	mandatory
			DESCRIPTION
                 " Default Mnemonic name for this interface. The
		   interface may always be referred to by this name." 
			::= { accIfNameEntry 3 }
	    accIfGroupTable OBJECT-TYPE
		SYNTAX	SEQUENCE OF  AccIfGroupEntry
		ACCESS	not-accessible
		STATUS	mandatory
		DESCRIPTION
			" A table of interface group descriptors supported by
			this unit.  Interface groups may be populated by 
			physical or logical interfaces, or combinations of
			the two."
		::= { accSystem 9 }
	accIfGroupEntry	OBJECT-TYPE
		SYNTAX	AccIfGroupEntry
		ACCESS	not-accessible
		STATUS	mandatory
		DESCRIPTION
			" An entry of information about an interface group."
		INDEX { accIFGroupIndex }
		::= { accIfGroupTable 1 }
	AccIfGroupEntry	::= SEQUENCE {
		accIFGroupIndex		INTEGER,
		accIFGroupName		DisplayString,
		accIFGroupType		INTEGER,
		accIFGroupIndexBase	INTEGER,
		accIFGroupIndexMax	INTEGER,
		accIFGroupNameDefault	DisplayString
		}
	accIFGroupIndex	OBJECT-TYPE   
		SYNTAX	INTEGER 
		ACCESS	read-only
		STATUS	mandatory
		DESCRIPTION
			" Index for the accIfGroupTable."
		::= { accIfGroupEntry 1 }
	accIFGroupName	OBJECT-TYPE   
		SYNTAX  DisplayString	
		ACCESS	read-only
		STATUS	mandatory
		DESCRIPTION
			" If accIFGroupIndexBase and accIFGroupIndexMax
			are equal then this object provides the full
			name of the port, else this object has the prefix
			of the port name.  If this is a prefix then the
			suffix is a numeric value from 1 to
			(accIFGroupIndexMax - accIFGroupIndexBase + 1). "
		::= { accIfGroupEntry 2 }
	accIFGroupType	OBJECT-TYPE   
		SYNTAX	INTEGER {
			physical-port(1),
			bridge-port(2),
			dial-port(3),
			multi-link(4)
			}
		ACCESS	read-only
		STATUS	mandatory
		DESCRIPTION
			" Type of port group"
		::= { accIfGroupEntry 3 }
	accIFGroupIndexBase	OBJECT-TYPE   
		SYNTAX	INTEGER
		ACCESS	read-only
		STATUS	mandatory
		DESCRIPTION
			" Lowest IFIndex in this IFGroup"
		::= { accIfGroupEntry 4 }
	accIFGroupIndexMax	OBJECT-TYPE   
		SYNTAX	INTEGER
		ACCESS	read-only
		STATUS	mandatory
		DESCRIPTION
			" The number of interfaces supported in this 
			IFGroup"
		::= { accIfGroupEntry 5 }
        accIFGroupNameDefault  OBJECT-TYPE
                SYNTAX  DisplayString
                ACCESS  read-only
                STATUS  mandatory
                DESCRIPTION
                        " If accIFGroupIndexBase and accIFGroupIndexMax
                        are equal then this object provides the full
                        name of the port, else this object has the prefix
                        of the port name.  If this is a prefix then the
                        suffix is a numeric value from 1 to
                        (accIFGroupIndexMax - accIFGroupIndexBase + 1).
                        The interface group may always be referenced by
                        this name. It cannot be changed by the user. "
                ::= { accIfGroupEntry 6 }
accTrapLog      OBJECT IDENTIFIER  ::= { accSystem 10 }
    accTrapLogLevel    OBJECT-TYPE
                SYNTAX  INTEGER (1..7)
                ACCESS  read-write
                STATUS  mandatory
                DESCRIPTION
                   "The base severity level at which traps are recorded
                    in the log. Traps with values greater than this level 
                    will not be recorded in the log."
                ::= { accTrapLog 1 }
    accTrapLogSaveAction  OBJECT-TYPE
                SYNTAX  INTEGER {
                            save-now (1)
                        }
                ACCESS  read-write
                STATUS  mandatory
                DESCRIPTION
                "Setting the value to save-now writes the current trap log
                 to permanent storage."
                ::= { accTrapLog 2 }
    accTrapLogBufSize    OBJECT-TYPE
                SYNTAX  INTEGER (1..1024)
                ACCESS  read-write
                STATUS  mandatory
                DESCRIPTION
                "The trap log buffer size in kilobytes."
                ::= { accTrapLog 3 }
-- ACC Trap Log Tables
   accTrapLogTable        OBJECT-TYPE
                SYNTAX  SEQUENCE OF AccTrapLogEntry
                ACCESS  not-accessible
                STATUS  mandatory
                DESCRIPTION
                   "The trap logging table."
                ::= { accTrapLog 4 }
   AccTrapLogEntry ::= SEQUENCE {
                accTrapLogTblTime	TimeTicks,
                accTrapLogTblType	INTEGER,
                accTrapLogTblLevel	INTEGER,
                accTrapLogTblData	DisplayString,
		accTrapLogSeverityType      INTEGER,
		accTrapLogEnterpriseOID	OBJECT IDENTIFIER,
		accSpecificTrapNum	INTEGER,
		accTrapLogSeqNum    Counter
                }
    accTrapLogEntry      OBJECT-TYPE
                SYNTAX  AccTrapLogEntry
                ACCESS  not-accessible
                STATUS  mandatory
                DESCRIPTION
                  " A single trap log entry."
--                INDEX { INTEGER }
                ::= { accTrapLogTable 1 }
    accTrapLogTblTime   OBJECT-TYPE
                SYNTAX  TimeTicks
                ACCESS  read-only
                STATUS  mandatory
                DESCRIPTION
                  " SysUpTime when trap occurred."
                ::= { accTrapLogEntry 1 }
    accTrapLogTblType   OBJECT-TYPE
                SYNTAX  INTEGER {
                            trap-coldstart (1),
                            trap-warmstart (2),
                            trap-linkdown (3),
                            trap-linkup (4),
                            trap-authent-fail (5),
                            trap-egpnborloss (6),
                            trap-enterprise (7)
                        }
                ACCESS  read-only
                STATUS  mandatory
                DESCRIPTION
                  " SysUpTime when trap occurred."
                ::= { accTrapLogEntry 2 }
    accTrapLogTblLevel   OBJECT-TYPE
                SYNTAX  INTEGER (1..7)
                ACCESS  read-only
                STATUS  mandatory
                DESCRIPTION
                  "The severity level associated with this trap."
                ::= { accTrapLogEntry 3 }
    accTrapLogTblData   OBJECT-TYPE
                SYNTAX  DisplayString
                ACCESS  read-only
                STATUS  mandatory
                DESCRIPTION
                  "The text message of the trap."
                ::= { accTrapLogEntry 4 }
--
-- {accTrapLogEntry 5} used by trap log enhancements on future branch
-- for the accTrapLogTblSysTime object.
--
   accTrapLogSeqNum     OBJECT-TYPE
                SYNTAX  Counter
                ACCESS  read-only
                STATUS  mandatory
                DESCRIPTION
                " The Global Sequence Number for all Traps
                  generated in the System "
                  ::= { accTrapLogEntry 6 }
   accTrapLogSeverityType     OBJECT-TYPE
                SYNTAX  INTEGER {
                            critical (1),
                            major (2),
                            minor (3),
                            warning (4),
                            clear (5)
                        }
                ACCESS  read-only
                STATUS  mandatory
                DESCRIPTION
                " Severity type of the Trap generated "
                  ::= { accTrapLogEntry 7 }
   accTrapLogEnterpriseOID	OBJECT-TYPE
		SYNTAX	OBJECT IDENTIFIER
		ACCESS  read-only
      		STATUS  mandatory
        	DESCRIPTION
            	" Enterprise OID for the sent trap "
                  ::= { accTrapLogEntry 8 }
   accSpecificTrapNum	OBJECT-TYPE 
		SYNTAX	INTEGER
		ACCESS  read-only
      		STATUS  mandatory
      		DESCRIPTION
                " Specific Trap number "
                  ::= { accTrapLogEntry 9 }
   accTrapLogSumTable        OBJECT-TYPE
                SYNTAX  SEQUENCE OF AccTrapLogSumEntry
                ACCESS  not-accessible
                STATUS  mandatory
                DESCRIPTION
                   "The trap logging table."
                ::= { accTrapLog 5 }
   AccTrapLogSumEntry ::= SEQUENCE {
                accTrapLogSumTime       TimeTicks,
                accTrapLogSumType       INTEGER,
                accTrapLogSumData       DisplayString
                }
    accTrapLogSumEntry      OBJECT-TYPE
                SYNTAX  AccTrapLogSumEntry
                ACCESS  not-accessible
                STATUS  mandatory
                DESCRIPTION
                  " A single trap log entry."
--                INDEX { INTEGER }
                ::= { accTrapLogSumTable 1 }
    accTrapLogSumTime   OBJECT-TYPE
                SYNTAX  TimeTicks
                ACCESS  read-only
                STATUS  mandatory
                DESCRIPTION
                  " SysUpTime when trap occurred."
                ::= { accTrapLogSumEntry 1 }
    accTrapLogSumType   OBJECT-TYPE
                SYNTAX  INTEGER {
                            coldstart (1),
                            warmstart (2),
                            linkdown (3),
                            linkup (4),
                            authent-fail (5),
                            egpnborloss (6),
                            enterprise (7)
                        }
                ACCESS  read-only
                STATUS  mandatory
                DESCRIPTION
                  "The type of trap associated with this entry."
                ::= { accTrapLogSumEntry 2 }
    accTrapLogSumData   OBJECT-TYPE
                SYNTAX  DisplayString
                ACCESS  read-only
                STATUS  mandatory
                DESCRIPTION
                  "The text message of the trap."
                ::= { accTrapLogSumEntry 3 }
-- ACC Seep Information Table
   accSeepTable	        OBJECT-TYPE
                SYNTAX  SEQUENCE OF AccSeepEntry
                ACCESS  not-accessible
                STATUS  mandatory
                DESCRIPTION
                   "The SEEP information table."
                ::= { accSystem 13 }
   AccSeepEntry ::= SEQUENCE {
                accSeepEntrySlot	DisplayString,
                accSeepEntryType	DisplayString,
                accSeepEntrySerial	DisplayString,
                accSeepEntryAssembly	DisplayString,
		accSeepEntryRev		DisplayString,
		accSeepEntryDate	DisplayString
                }
    accSeepEntry      OBJECT-TYPE
                SYNTAX  AccSeepEntry
                ACCESS  not-accessible
                STATUS  mandatory
                DESCRIPTION
                  " A single SEEP information table entry."
--                INDEX { INTEGER }
                ::= { accSeepTable 1 }
    accSeepEntrySlot   OBJECT-TYPE
                SYNTAX  DisplayString
                ACCESS  read-only
                STATUS  mandatory
                DESCRIPTION
                  " The slot from which the SEEP information is taken."
                ::= { accSeepEntry 1 }
    accSeepEntryType   OBJECT-TYPE
                SYNTAX  DisplayString
                ACCESS  read-only
                STATUS  mandatory
                DESCRIPTION
                  " The type of SEEP."
                ::= { accSeepEntry 2 }
    accSeepEntrySerial   OBJECT-TYPE
                SYNTAX  DisplayString
                ACCESS  read-only
                STATUS  mandatory
                DESCRIPTION
                  " The serial number of the SEEP."
                ::= { accSeepEntry 3 }
    accSeepEntryAssembly   OBJECT-TYPE
                SYNTAX  DisplayString
                ACCESS  read-only
                STATUS  mandatory
                DESCRIPTION
                  " The assembly description of the SEEP."
                ::= { accSeepEntry 4 }
    accSeepEntryRev   OBJECT-TYPE
                SYNTAX  DisplayString
                ACCESS  read-only
                STATUS  mandatory
                DESCRIPTION
                  " The revision number of the SEEP."
                ::= { accSeepEntry 5 }
    accSeepEntryDate   OBJECT-TYPE
                SYNTAX  DisplayString
                ACCESS  read-only
                STATUS  mandatory
                DESCRIPTION
                  " The date contained in the SEEP."
                ::= { accSeepEntry 6 }
-- ACC Standby Processor Information Table
accStandbyInfo      OBJECT IDENTIFIER  ::= { accSystem 14 }
    accStandbySysDescr   OBJECT-TYPE
                SYNTAX  DisplayString
                ACCESS  read-only
                STATUS  mandatory
                DESCRIPTION
                  " System description for redundant processor."
                ::= { accStandbyInfo 1 }
    accStandbySoftwareVersion   OBJECT-TYPE
                SYNTAX  DisplayString
                ACCESS  read-only
                STATUS  mandatory
                DESCRIPTION
                  " Software version of redundant processor."
                ::= { accStandbyInfo 2 }
    accStandbySysProcType   OBJECT-TYPE
                SYNTAX  INTEGER {
			mips-idt (257)
		}
                ACCESS  read-only
                STATUS  mandatory
                DESCRIPTION
                  " System description for redundant processor."
                ::= { accStandbyInfo 3 }
    accStandbySysLocalRam   OBJECT-TYPE
                SYNTAX  INTEGER
                ACCESS  read-only
                STATUS  mandatory
                DESCRIPTION
                  " Local RAM size for redundant processor in kilobytes."
                ::= { accStandbyInfo 4 }
    accStandbySysGlobalRam   OBJECT-TYPE
                SYNTAX  INTEGER
                ACCESS  read-only
                STATUS  mandatory
                DESCRIPTION
                  " Global RAM size for redundant processor in kilobytes."
                ::= { accStandbyInfo 5 }
    accStandbyFsVolStatus   OBJECT-TYPE
                SYNTAX  INTEGER {
			synchronized     (1),
			not-available    (2),
			checking         (3),
			not-synchronized (4)
		}
                ACCESS  read-only
                STATUS  mandatory
                DESCRIPTION
                  " Flash volume status for redundant processor."
                ::= { accStandbyInfo 6 }
    accStandbyFsCfgStatus   OBJECT-TYPE
                SYNTAX  INTEGER {
			synchronized     (1),
			not-available    (2),
			checking         (3),
			not-synchronized (4)
		}
                ACCESS  read-only
                STATUS  mandatory
                DESCRIPTION
                  " Configuration status for redundant processor."
                ::= { accStandbyInfo 7 }
    accStandbyFsLoadFtkFile   OBJECT-TYPE
                SYNTAX  DisplayString
                ACCESS  read-only
                STATUS  mandatory
                DESCRIPTION
                  " Current flash toolkit file redundant processor."
                ::= { accStandbyInfo 8 }
    accStandbyFsLoadAplFile   OBJECT-TYPE
                SYNTAX  DisplayString
                ACCESS  read-only
                STATUS  mandatory
                DESCRIPTION
                  " Current application file for redundant processor."
                ::= { accStandbyInfo 9 }
    accStandbyFsLoadDiaFile   OBJECT-TYPE
                SYNTAX  DisplayString
                ACCESS  read-only
                STATUS  mandatory
                DESCRIPTION
                  " Current application file for redundant processor."
                ::= { accStandbyInfo 10 }
    accStandbySysHwVers   OBJECT-TYPE
                SYNTAX  DisplayString
                ACCESS  read-only
                STATUS  mandatory
                DESCRIPTION
                  " Hardware versions for redundant processor."
                ::= { accStandbyInfo 11 }
-- START CFG_TRAP_ENHANCEMENTS
-- ICP Traps
accIcpTraps      OBJECT IDENTIFIER  ::= { accSystem 16 }
    accIcpTrapMsg   OBJECT-TYPE
                SYNTAX  DisplayString
                ACCESS  read-only
                STATUS  mandatory
                DESCRIPTION
                  " ICP Trap Message "
                ::= { accIcpTraps 1 }
-- ACC Syslog Table
	accSyslogTable OBJECT-TYPE
	SYNTAX SEQUENCE OF AccSyslogEntry
	ACCESS not-accessible
	STATUS mandatory
	DESCRIPTION
	" A table of systems to which Syslog Messages generated
	by this unit shall be sent.
	To delete an entry, a SetRequest-PDU for the specific
	instance of accSyslogAddr with a NULL value encoding is
	used."
	::= { accSystem 15 }
	accSyslogEntry OBJECT-TYPE
	SYNTAX AccSyslogEntry
	ACCESS not-accessible
	STATUS mandatory
	DESCRIPTION
	" A Syslog Table entry "
	INDEX { accSyslogAddr }
	::= { accSyslogTable 1 }
	AccSyslogEntry ::= SEQUENCE {
	accSyslogAddr IpAddress,
	accSyslogSeverity INTEGER,
	accSyslogFacility INTEGER
	}
	accSyslogAddr OBJECT-TYPE
	SYNTAX IpAddress
	ACCESS read-write
	STATUS mandatory
	DESCRIPTION
		" An IP address to which syslog messages generated by the unit
		are sent."
	::= { accSyslogEntry 1 }
	accSyslogSeverity OBJECT-TYPE
	SYNTAX INTEGER (1..7)
	ACCESS read-write
	STATUS mandatory
	DESCRIPTION
		" severity level of the messages to be sent. "
	::= { accSyslogEntry 2 }
	accSyslogFacility OBJECT-TYPE
	SYNTAX INTEGER (0..7)
	ACCESS read-write
	STATUS mandatory
	DESCRIPTION
		"Facility identifier to use in syslog messages"
	::= { accSyslogEntry 3 }
   accTrapSequencingStatus    OBJECT-TYPE
                SYNTAX  INTEGER {
                            off (1),
                            on  (2)
                        }
                ACCESS read-write
                STATUS mandatory
                DESCRIPTION
                " Indicates trap sequencing feature is On or Off. When
                  set to On, a accTrapLogSeqNum varbind will be
                  appended to every trap issued by the system, and will
		  always be the last varbind "
                  ::= { accSystem 18 }
accNvm	OBJECT IDENTIFIER ::= { accSysInfo 6 }
        accNvmTotalBlks OBJECT-TYPE
                SYNTAX  INTEGER
                ACCESS  read-only
                STATUS  mandatory
                DESCRIPTION
                        " Total number of NVM blocks."
                ::= { accNvm 1 }
        accNvmBlkSize   OBJECT-TYPE 
                SYNTAX  INTEGER 
                ACCESS  read-only 
                STATUS  mandatory 
                DESCRIPTION 
                        " NVM block size in bytes." 
                ::= { accNvm 2 }
        accNvmDirSize   OBJECT-TYPE 
                SYNTAX  INTEGER 
                ACCESS  read-only 
                STATUS  mandatory 
                DESCRIPTION 
                        " The NVM directory size." 
                ::= { accNvm 3 }
        accNvmFreeBlks  OBJECT-TYPE 
                SYNTAX  INTEGER 
                ACCESS  read-only 
                STATUS  mandatory 
                DESCRIPTION 
                        " The number of free NVM blocks." 
                ::= { accNvm 4 }
        accNvmFileNumber OBJECT-TYPE 
                SYNTAX  INTEGER 
                ACCESS  read-only 
                STATUS  mandatory 
                DESCRIPTION 
                        " The NVM file number." 
                ::= { accNvm 5 }
        accNvmFileName   OBJECT-TYPE 
                SYNTAX  OCTET STRING 
                ACCESS  read-only 
                STATUS  mandatory 
                DESCRIPTION 
                        " The NVM file name." 
                ::= { accNvm 6 }
        accNvmFileSize  OBJECT-TYPE 
                SYNTAX  INTEGER 
                ACCESS  read-only 
                STATUS  mandatory 
                DESCRIPTION 
                        " The NVM file size in bytes." 
                ::= { accNvm 7 }
accSysConfigInfo OBJECT IDENTIFIER ::= { accSysInfo 7 }
     accConfiguration   OBJECT-TYPE
                        SYNTAX  INTEGER {
                                save(1),  -- Save Configuration to NVM
                                load(2),  -- Load Configuration from NVM
                                default(3)  -- Set Configuration to default
                                }
                        ACCESS  read-write
                        STATUS  mandatory
                        DESCRIPTION
                 " Set the action to perform on the active configuration.
                   A set to load or default will immediately reset the unit.
                   On the restart the new configuration (either a previously
                   saved one or the default configuration) will be used."
                        ::= { accSysConfigInfo 1 }
accConfigurationStatus      OBJECT-TYPE
                        SYNTAX  INTEGER {
                                saved(1),
                                changed(2)
                                }
                        ACCESS  read-only
                        STATUS  mandatory
                        DESCRIPTION
                 " The current state of the active configuration.  The value
                   changed indicates that the active configuration has
                   changed since the last time it was saved to NVM."
                        ::= { accSysConfigInfo 2 }
          accScriptHalt OBJECT-TYPE
                        SYNTAX  INTEGER
                        ACCESS  read-write
                        STATUS  mandatory
                        DESCRIPTION
                 " A Set  command on this object will cause an immediate
                   halt to any existing configuration script execution."
                        ::= { accSysInfo 8 }
	accScriptCont	OBJECT IDENTIFIER  ::= { accSysInfo 9 }
          accScriptContServer	 OBJECT-TYPE
                        SYNTAX  IpAddress
                        ACCESS  read-write
                        STATUS  mandatory
                        DESCRIPTION
			" The IP address of the server holding the 
			  configuration script to be downloaded and executed
			  following the next reset."
                        ::= { accScriptCont 1 }
          accScriptContFile	 OBJECT-TYPE
                        SYNTAX  DisplayString
                        ACCESS  read-write
                        STATUS  mandatory
                        DESCRIPTION
			" The filename (with complete pathname) of the  
			  configuration script to be downloaded and executed
			  following the next reset."
                        ::= { accScriptCont 2 }
	  accSysUpgradeCmd	OBJECT-TYPE   
			SYNTAX	OCTET STRING
			ACCESS	read-only
			STATUS	mandatory
			DESCRIPTION
			" On platforms that execute the application from Flash and 
			  that support the optional Flash SIMM memory for TFTP 
			  upgrades, it indicates the upgrade command (SL or TFTP).
			  If the optional Flash SIMM is not installed, maintenance 
			  mode SL command is the only way to upgrade."
			::= { accSysInfo 10 }
        accSysHWType  OBJECT-TYPE
                SYNTAX  INTEGER {
			acc4100(0),
			acc4100R(1),
			acc4200(2),
			ub8000(3),
			infotron(4),
			nile(5),
			tigris(6),
			amazon(7),
			tahoe(8),
			danube(9)
                        }
                ACCESS  read-only
                STATUS  mandatory
                DESCRIPTION
                        " The hardware platform product name"
                ::= { accSysInfo 11 }
        accSysProcType  OBJECT-TYPE
                SYNTAX  INTEGER {
                        motorola-68000(0),
                        motorola-68010(16),
                        motorola-68020(32),
                        motorola-68030(48),
                        motorola-68040(64),
                        motorola-68060(96)
                        }
                ACCESS  read-only
                STATUS  mandatory
                DESCRIPTION
                        " Type of processor on this platform"
                ::= { accSysInfo 12 }
          accSysLocalRam OBJECT-TYPE
                SYNTAX  INTEGER
                ACCESS  read-only
                STATUS  mandatory
                DESCRIPTION
			" The amount of local RAM installed in the system 
			  in kilobytes"
               ::= { accSysInfo 13 }
          accSysGlobalRam OBJECT-TYPE
                SYNTAX  INTEGER
                ACCESS  read-only
                STATUS  mandatory
                DESCRIPTION
                        " The amount of global RAM installed in the system 
                          in kilobytes"
                ::= { accSysInfo 14 }
        accSysPowerSupply  OBJECT-TYPE
                SYNTAX  INTEGER {
                        single(1),
                        dual-both-operational(2),
                        dual-one-malfunctioning(3)
                        }
                ACCESS  read-only
                STATUS  mandatory
                DESCRIPTION
                        " Type of processor on this platform"
                ::= { accSysInfo 15 }
	accMemPoolTable    OBJECT-TYPE
		SYNTAX	SEQUENCE OF  AccMemPoolEntry
		ACCESS	not-accessible
		STATUS	mandatory
		DESCRIPTION
			" A table of memory pools supported by this unit.
			Each pool describes a physical memory resource."
		::= { accSysInfo 16 }
	accMemPoolEntry	OBJECT-TYPE
		SYNTAX	AccMemPoolEntry
		ACCESS	not-accessible
		STATUS	mandatory
		DESCRIPTION
			" An entry of information about a memory pool."
--		INDEX { INTEGER }
		::= { accMemPoolTable 1 }
	  AccMemPoolEntry	::= SEQUENCE {
			accMemPoolName			DisplayString,
			accMemPoolMaximum		Gauge,
                        accMemPoolBytes			Gauge,
                        accMemPoolFrags			Gauge,
                        accMemPoolAlign			INTEGER,
                        accMemPoolAllocs		Counter,
                        accMemPoolFails			Counter
			} 
        accMemPoolName  OBJECT-TYPE
                SYNTAX  DisplayString
                ACCESS  read-only
                STATUS  mandatory
                DESCRIPTION
                        "A printable ASCII string describing this
			 memory pool."
                ::= { accMemPoolEntry 1 }
        accMemPoolMaximum OBJECT-TYPE
                SYNTAX  Gauge
                ACCESS  read-only
                STATUS  mandatory
                DESCRIPTION
			"The maximum amount of memory in this memory pool."
               ::= { accMemPoolEntry 2 }
        accMemPoolBytes OBJECT-TYPE
                SYNTAX  Gauge
                ACCESS  read-only
                STATUS  mandatory
                DESCRIPTION
			"The amount of memory currently available
                         in this memory pool."
               ::= { accMemPoolEntry 3 }
        accMemPoolFrags OBJECT-TYPE
                SYNTAX  Gauge
                ACCESS  read-only
                STATUS  mandatory
                DESCRIPTION
			"The number of times this memory pool has been
                         fragmented."
               ::= { accMemPoolEntry 4 }
        accMemPoolAlign OBJECT-TYPE
                SYNTAX  INTEGER
                ACCESS  read-only
                STATUS  mandatory
                DESCRIPTION
			"The alignment this memory pool maintains.  For
			 example, a 4 in this field means memory from this
			 pool is aligned on 32-bit boundaries."
               ::= { accMemPoolEntry 5 }
        accMemPoolAllocs OBJECT-TYPE
                SYNTAX  Counter
                ACCESS  read-only
                STATUS  mandatory
                DESCRIPTION
			"The number of allocation requests addressed to
			 this memory pool."
               ::= { accMemPoolEntry 6 }
        accMemPoolFails OBJECT-TYPE
                SYNTAX  Counter
                ACCESS  read-only
                STATUS  mandatory
                DESCRIPTION
			"The number of times an allocation request addressed
			 to this memory could not be satisfied."
               ::= { accMemPoolEntry 7 }
	  accMemAddDblk	OBJECT-TYPE   
			SYNTAX  INTEGER	
			ACCESS	read-only
			STATUS	mandatory
			DESCRIPTION
		 " Number of D blocks added. "
			::= { accSysInfo 17 }
-- The slave CPU configuration table
	accSlvConfTable		OBJECT-TYPE
		SYNTAX          SEQUENCE OF AccSlvConfEntry
        	ACCESS          not-accessible
        	STATUS          mandatory
        	DESCRIPTION
        	" Table of slave CPU configuration parameters. "
       		::= { accSysInfo 18 }
	accSlvConfEntry	OBJECT-TYPE
		SYNTAX          AccSlvConfEntry
        	ACCESS          not-accessible
        	STATUS          mandatory
        	DESCRIPTION
        	"A single entry in the slave CPU configuration Table"
        	INDEX		{ accSlvConfCPUIndex }
        	::= { accSlvConfTable 1 }
	AccSlvConfEntry ::= SEQUENCE {
		accSlvConfCPUIndex		INTEGER,
		accSlvConfCPUID			DisplayString,
    		accSlvConfSysDesc		DisplayString,
    		accSlvConfSWVers 		DisplayString,
    		accSlvConfProcType		INTEGER,
    		accSlvConfLocalRam		INTEGER,
		accSlvConfGlobalRam		INTEGER
		}
	    accSlvConfCPUIndex   OBJECT-TYPE  
			SYNTAX	INTEGER
			ACCESS	read-only
			STATUS	mandatory
			DESCRIPTION
                      " Slave CPU Index "
			::=  { accSlvConfEntry 1 }
	    accSlvConfCPUID   OBJECT-TYPE  
			SYNTAX	DisplayString
			ACCESS	read-only
			STATUS	mandatory
			DESCRIPTION
                      " Slave CPU ID "
			::=  { accSlvConfEntry 2 }
	    accSlvConfSysDesc	OBJECT-TYPE  
			SYNTAX	DisplayString
			ACCESS	read-only
			STATUS	mandatory
			DESCRIPTION
                       " Slave CPU System Description "
			::=  { accSlvConfEntry 3 }
	    accSlvConfSWVers   OBJECT-TYPE  
			SYNTAX	DisplayString
			ACCESS	read-only
			STATUS	mandatory
			DESCRIPTION
                        " Slave CPU Software Version "
			::=  { accSlvConfEntry 4 }
	    accSlvConfProcType	OBJECT-TYPE  
                SYNTAX  INTEGER {
                        motorola-68000(0),
                        motorola-68010(16),
                        motorola-68020(32),
                        motorola-68030(48),
                        motorola-68040(64)
                        }
			ACCESS	read-only
			STATUS	mandatory
			DESCRIPTION
                        " Slave CPU Processor Type "
			::=  { accSlvConfEntry 5 }
	    accSlvConfLocalRam	OBJECT-TYPE  
			SYNTAX	INTEGER
			ACCESS	read-only
			STATUS	mandatory
			DESCRIPTION
                       " Slave CPU Local RAM Size (kb) "
			::=  { accSlvConfEntry 6 }
	    accSlvConfGlobalRam   OBJECT-TYPE  
			SYNTAX  INTEGER
			ACCESS	read-only
			STATUS	mandatory
			DESCRIPTION
                      " Slave CPU Global RAM Size (kb) "
			::=  { accSlvConfEntry 7 }
-- ACC slave CPU memory block stats table
        accSlvMemBlkTable     OBJECT-TYPE
                   SYNTAX      SEQUENCE OF AccSlvMemBlkEntry
                   ACCESS      not-accessible
                   STATUS      mandatory
                   DESCRIPTION
                   "Table of entries in the slave CPU configuration Table."
                    ::= { accSysInfo 19 }
	accSlvMemBlkEntry	OBJECT-TYPE
		SYNTAX          AccSlvMemBlkEntry
        	ACCESS          not-accessible
        	STATUS          mandatory
        	DESCRIPTION
        	"A single entry in the slave CPU configuration Table"
--                INDEX { INTEGER }
        	::= { accSlvMemBlkTable 1 }
		AccSlvMemBlkEntry ::= SEQUENCE {
			accSlvMemCPUID			DisplayString,
			accSlvMemBlkEntSize		INTEGER,
	    		accSlvMemBlkEntTotal		INTEGER,
	    		accSlvMemBlkEntMax 		Gauge,
	    		accSlvMemBlkEntInUse		Gauge,
	    		accSlvMemBlkEntFails		Counter,
			accSlvMemBlkEntType		INTEGER,
	    		accSlvMemBlkEntAllocs		Counter
			}
	    accSlvMemCPUID   OBJECT-TYPE  
			SYNTAX	DisplayString
			ACCESS	read-only
			STATUS	mandatory
			DESCRIPTION
                      " Slave CPU ID "
			::=  { accSlvMemBlkEntry 3 }
	    accSlvMemBlkEntSize   OBJECT-TYPE  
			SYNTAX	INTEGER
			ACCESS	read-only
			STATUS	mandatory
			DESCRIPTION
                      " Size (bytes) of these buffers"
			::=  { accSlvMemBlkEntry 4 }
	    accSlvMemBlkEntTotal	OBJECT-TYPE  
			SYNTAX	INTEGER
			ACCESS	read-only
			STATUS	mandatory
			DESCRIPTION
                       " Total number of these buffers in pool, whether
                         or not they are in use"
			::=  { accSlvMemBlkEntry 5 }
	    accSlvMemBlkEntMax   OBJECT-TYPE  
			SYNTAX	Gauge
			ACCESS	read-only
			STATUS	mandatory
			DESCRIPTION
                        " High water mark of usage of buffers"
			::=  { accSlvMemBlkEntry 6 }
	    accSlvMemBlkEntInUse	OBJECT-TYPE  
			SYNTAX	Gauge
			ACCESS	read-only
			STATUS	mandatory
			DESCRIPTION
                        " Number of buffers currently in use."
			::=  { accSlvMemBlkEntry 7 }
	    accSlvMemBlkEntFails	OBJECT-TYPE  
			SYNTAX	Counter
			ACCESS	read-only
			STATUS	mandatory
			DESCRIPTION
                       " Number of times requests were made for a buffer
                         of this size that failed because none were avaliable."
			::=  { accSlvMemBlkEntry 8 }
	    accSlvMemBlkEntType   OBJECT-TYPE  
                SYNTAX  INTEGER {
			dblk(1),
			mblk(2),
			cblk(3),
			fast(9),
			local(10),
			global(11),
			reserved(12)
                        }
			ACCESS	read-only
			STATUS	mandatory
			DESCRIPTION
                      " Numeric classification of the buffer."
			::=  { accSlvMemBlkEntry 9 }
	    accSlvMemBlkEntAllocs   OBJECT-TYPE  
			SYNTAX	Counter
			ACCESS	read-only
			STATUS	mandatory
			DESCRIPTION
                      " Number of times a request was made for a buffer
			of this size."
			::=  { accSlvMemBlkEntry 10 }
-- The slave CPU memory pool stats table 
        accSlvMemPool      OBJECT IDENTIFIER  ::= { accSysInfo 20 }
	accSlvMemPoolTable    OBJECT-TYPE
		SYNTAX	SEQUENCE OF  AccSlvMemPoolEntry
		ACCESS	not-accessible
		STATUS	mandatory
		DESCRIPTION
			" A table of memory pools supported by this unit.
			Each pool describes a physical memory resource."
		::= { accSlvMemPool 1 }
	accSlvMemPoolEntry	OBJECT-TYPE
		SYNTAX	AccSlvMemPoolEntry
		ACCESS	not-accessible
		STATUS	mandatory
		DESCRIPTION
			" An entry of information about a memory pool."
--		INDEX { INTEGER, INTEGER }
		::= { accSlvMemPoolTable 1 }
	  AccSlvMemPoolEntry	::= SEQUENCE {
			accSlvMemPoolCPUID		DisplayString,
			accSlvMemPoolName		DisplayString,
			accSlvMemPoolMaximum		Gauge,
                        accSlvMemPoolBytes		Gauge,
                        accSlvMemPoolFrags		Gauge,
                        accSlvMemPoolAlign		INTEGER,
                        accSlvMemPoolAllocs		Counter,
                        accSlvMemPoolFails		Counter
			} 
	accSlvMemPoolCPUID   OBJECT-TYPE  
			SYNTAX	DisplayString
			ACCESS	read-only
			STATUS	mandatory
			DESCRIPTION
                      " Slave CPU ID "
			::=  { accSlvMemPoolEntry 1 }
        accSlvMemPoolName  OBJECT-TYPE
                SYNTAX  DisplayString
                ACCESS  read-only
                STATUS  mandatory
                DESCRIPTION
                        "A printable ASCII string describing this
			 memory pool."
                ::= { accSlvMemPoolEntry 2 }
        accSlvMemPoolMaximum OBJECT-TYPE
                SYNTAX  Gauge
                ACCESS  read-only
                STATUS  mandatory
                DESCRIPTION
			"The maximum amount of memory in this memory pool."
               ::= { accSlvMemPoolEntry 3 }
        accSlvMemPoolBytes OBJECT-TYPE
                SYNTAX  Gauge
                ACCESS  read-only
                STATUS  mandatory
                DESCRIPTION
			"The amount of memory currently available
                         in this memory pool."
               ::= { accSlvMemPoolEntry 4 }
        accSlvMemPoolFrags OBJECT-TYPE
                SYNTAX  Gauge
                ACCESS  read-only
                STATUS  mandatory
                DESCRIPTION
			"The number of times this memory pool has been
                         fragmented."
               ::= { accSlvMemPoolEntry 5 }
        accSlvMemPoolAlign OBJECT-TYPE
                SYNTAX  INTEGER
                ACCESS  read-only
                STATUS  mandatory
                DESCRIPTION
			"The alignment this memory pool maintains.  For
			 example, a 4 in this field means memory from this
			 pool is aligned on 32-bit boundaries."
               ::= { accSlvMemPoolEntry 6 }
        accSlvMemPoolAllocs OBJECT-TYPE
                SYNTAX  Counter
                ACCESS  read-only
                STATUS  mandatory
                DESCRIPTION
			"The number of allocation requests addressed to
			 this memory pool."
               ::= { accSlvMemPoolEntry 7 }
        accSlvMemPoolFails OBJECT-TYPE
                SYNTAX  Counter
                ACCESS  read-only
                STATUS  mandatory
                DESCRIPTION
			"The number of times an allocation request addressed
			 to this memory could not be satisfied."
               ::= { accSlvMemPoolEntry 8 }
-- Slave CPU stat table
	accSlvSysTable    OBJECT-TYPE
		SYNTAX SEQUENCE OF AccSlvSysEntry
		ACCESS not-accessible
		STATUS mandatory
		DESCRIPTION
		" Information about slave CPU system stats. "
		::= { accSysInfo 21 }
	accSlvSysEntry	OBJECT-TYPE
		SYNTAX          AccSlvSysEntry
        	ACCESS          not-accessible
        	STATUS          mandatory
        	DESCRIPTION
        	"A single entry in the slave CPU system stats table"
--        	INDEX		{ INTEGER }
        	::= { accSlvSysTable 1 }
	AccSlvSysEntry ::= SEQUENCE {
			accSlvSysUpTime			TimeTicks,
			accSlvSysCpuAvgShort		INTEGER,
	    		accSlvSysCpuAvgLong		INTEGER
			}
	accSlvSysUpTime   OBJECT-TYPE  
			SYNTAX	TimeTicks
			ACCESS	read-only
			STATUS	mandatory
			DESCRIPTION
                      " Slave system uptime "
			::=  { accSlvSysEntry 1 }
	accSlvSysCpuAvgShort   OBJECT-TYPE  
			SYNTAX	INTEGER
			ACCESS	read-only
			STATUS	mandatory
			DESCRIPTION
                      " Slave system current CPU usage. "
			::=  { accSlvSysEntry 2 }
	accSlvSysCpuAvgLong	OBJECT-TYPE  
			SYNTAX	INTEGER
			ACCESS	read-only
			STATUS	mandatory
			DESCRIPTION
                       " Slave system average CPU usage. "
			::=  { accSlvSysEntry 3 }
        -- Memory Group (New Enhancements)
        accMem          OBJECT IDENTIFIER       ::= { accSysInfo 22 }
	-- Memory Dblock Increment Objects
	accMemDblkIncTable	OBJECT-TYPE
	  SYNTAX          SEQUENCE OF AccMemDblkIncEntry
          ACCESS          not-accessible
          STATUS          mandatory
          DESCRIPTION
          "Table of Memory Dblock Increments"
        ::= { accMem 1 }
	accMemDblkIncEntry	OBJECT-TYPE
	  SYNTAX          AccMemDblkIncEntry
          ACCESS          not-accessible
          STATUS          mandatory
          DESCRIPTION
          "A single entry of the Memory Dblock Increment Table"
        INDEX             { accMemDblkIndex }
        ::= { accMemDblkIncTable 1 }
	AccMemDblkIncEntry ::=
	  SEQUENCE {
	  accMemDblkIndex	INTEGER,
	  accMemDblkSize	INTEGER,
	  accMemDblkIncrement   INTEGER
	}
	accMemDblkIndex		OBJECT-TYPE
	  SYNTAX	INTEGER
	  ACCESS        read-only
          STATUS        mandatory	
	  DESCRIPTION
	  "The index of this entry in the Memory Dblock Increment Table"
	::= { accMemDblkIncEntry 1 }
	accMemDblkSize		OBJECT-TYPE
	  SYNTAX	INTEGER
	  ACCESS        read-only
          STATUS        mandatory	
	  DESCRIPTION
	  "The Size of the Dblock for this entry in the Mem Dblock Inc Table"
	::= { accMemDblkIncEntry 2 }
	accMemDblkIncrement	OBJECT-TYPE
	  SYNTAX	INTEGER
	  ACCESS        read-write
          STATUS        mandatory	
	  DESCRIPTION
	  "The User specified Increment of this entry Memory Dblock Increment 
	   Table"
	::= { accMemDblkIncEntry 3 }
	-- Memory Enhancements Objects
        accOpt 		OBJECT IDENTIFIER       ::= { accMem 2 }
	-- Memory Optimizer (EME) Global Objects
	accMemEMEStatus		OBJECT-TYPE
	  SYNTAX	INTEGER {
			on (1),
			off (2)
		}
	  ACCESS        read-write
          STATUS        mandatory	
	  DESCRIPTION
	  "The Global Memory Optimizer (EME) Status "
	::= { accOpt 1 }
	accMemEMEMaxReclMem	OBJECT-TYPE
	  SYNTAX	INTEGER
	  ACCESS        read-only
          STATUS        mandatory	
	  DESCRIPTION
	  "The Maximum Memory in bytes available for Reclaimation by the
	   Memory Optimizer (EME) "
	::= { accOpt 2 }
	accMemEMECurReclMem	OBJECT-TYPE
	  SYNTAX	INTEGER
	  ACCESS        read-only
          STATUS        mandatory	
	  DESCRIPTION
	  "The Memory in bytes Reclaimed by the Memory Optimizer (EME)"
	::= { accOpt 3 }
-- Memory Optimizer (EME) Table Objects
	accMemOptTable		OBJECT-TYPE
	  SYNTAX          SEQUENCE OF AccMemOptEntry
          ACCESS          not-accessible
          STATUS          mandatory
          DESCRIPTION
          "Table of Memory Optimizer"
        ::= { accOpt 4 }
	accMemOptEntry		OBJECT-TYPE
	  SYNTAX          AccMemOptEntry
          ACCESS          not-accessible
          STATUS          mandatory
          DESCRIPTION
          "A single entry of the Memory Optimizer Table"
        INDEX             { accMemOptimiserFeature }
        ::= { accMemOptTable 1 }
	AccMemOptEntry ::=
	  SEQUENCE {
	  accMemOptimiserFeature	OCTET STRING,
	  accMemOptimiserMemory		INTEGER,
	  accMemOptimiserPref   	INTEGER,
	  accMemOptimiserStatus		INTEGER
	}
	accMemOptimiserFeature	OBJECT-TYPE
	  SYNTAX	OCTET STRING
	  ACCESS        read-only
          STATUS        mandatory	
	  DESCRIPTION
	  "The Reclaimable Feature in the Memory Optimizer Table for this entry"
	::= { accMemOptEntry 1 }
	accMemOptimiserMemory	OBJECT-TYPE
	  SYNTAX	INTEGER
	  ACCESS        read-only
          STATUS        mandatory	
	  DESCRIPTION
	  "The amount of memory (in bytes) associated with the reclaimable
           feature under consideration"
	::= { accMemOptEntry 2 }
	accMemOptimiserPref	OBJECT-TYPE
	  SYNTAX	INTEGER {
			reclaim (1),
			use (2),
			automatic (3)
		}
	  ACCESS        read-write
          STATUS        mandatory	
	  DESCRIPTION
	  "The User's preference for this Feature "
	::= { accMemOptEntry 3 }
	accMemOptimiserStatus	OBJECT-TYPE
	  SYNTAX	INTEGER {
			reclaimed (1),
			inuse (2)
		}
	  ACCESS        read-only
          STATUS        mandatory	
	  DESCRIPTION
	  "The Current Status for this Feature "
	::= { accMemOptEntry 4 }
        accMacro          OBJECT IDENTIFIER       ::= { accSysInfo 23 }
	-- Macro Command Objects
	accMacroExecute   OBJECT-TYPE
	  SYNTAX          INTEGER {
			  none (1),
			  ipx-dial-filter(2)
			  }
          ACCESS          read-write
          STATUS          mandatory
          DESCRIPTION
          "Macro Name to Execute"
        ::= { accMacro 1 }
        accSwRegistrationKey   OBJECT-TYPE
          		SYNTAX	DisplayString 
          		ACCESS	read-write
          		STATUS  mandatory
        	  	DESCRIPTION
       				"Software Registration key to upgrade 
				software levels." 
	::= { accSysInfo 24 }
        accMACAddr          OBJECT IDENTIFIER       ::= { accSysInfo 25 }
	-- MAC Addr Command Objects
	accSysMessage	OBJECT IDENTIFIER ::= { accSysInfo 26 }
	    accSysMsgInfo OBJECT IDENTIFIER ::= { accSysMessage 1 }
		accSysMsgLevel OBJECT-TYPE
			SYNTAX INTEGER (1..7)
			ACCESS read-write
			STATUS mandatory
			DESCRIPTION
				" The severity level of system message 
				  allowed to be generated"
		::= { accSysMsgInfo 1 }
		accWinDefLenNetman OBJECT-TYPE
			SYNTAX INTEGER (22..65535)
			ACCESS read-write
			STATUS mandatory
			DESCRIPTION
				" The session window default length NETMAN"
		::= { accSysMsgInfo 2 }
		accWinDefLenPublic OBJECT-TYPE
			SYNTAX INTEGER (22..65535)
			ACCESS read-write
			STATUS mandatory
			DESCRIPTION
				" The session window default length PUBLIC"
		::= { accSysMsgInfo 3 }
		accWinDefWidNetman OBJECT-TYPE
			SYNTAX INTEGER (80..512)
			ACCESS read-write
			STATUS mandatory
			DESCRIPTION
				" The session window default width NETMAN"
		::= { accSysMsgInfo 4 }
		accWinDefWidPublic OBJECT-TYPE
			SYNTAX INTEGER (80..512)
			ACCESS read-write
			STATUS mandatory
			DESCRIPTION
				" The session window default width PUBLIC"
		::= { accSysMsgInfo 5 }
	   accUserInfo	OBJECT IDENTIFIER ::= { accSysMessage 2 }
		accUserTrapMsgEntry OBJECT-TYPE
			SYNTAX DisplayString -- (SIZE (0..255))
			ACCESS read-write
			STATUS mandatory
			DESCRIPTION
				" A message to be sent through an SNMP trap."
		::= { accUserInfo 1 }
	    accSysMACAddrUser  OBJECT-TYPE   
			SYNTAX	OCTET STRING -- (SIZE(6))
			ACCESS	read-write
			STATUS	mandatory
			DESCRIPTION
                         "MAC address to be used to override rom MAC address.
			  A value of 0 means use the value stored in rom. Any
			  other value, overrides the ROM MAC address."
			::= { accMACAddr 1 }
	    accSystemServiceTable  OBJECT-TYPE
			SYNTAX  SEQUENCE OF  AccSystemServiceEntry
			ACCESS  not-accessible
			STATUS  mandatory
			DESCRIPTION
			" A table of changeable TCP/UDP services."
			::= { accSystem 26 }
	   accSystemServiceEntry OBJECT-TYPE
			SYNTAX  AccSystemServiceEntry
			ACCESS  not-accessible
			STATUS  mandatory
			DESCRIPTION
			" An entry of information about System Service."
			INDEX { accSystemService }
			::= { accSystemServiceTable 1 }
	   AccSystemServiceEntry  ::= SEQUENCE {
					accSystemService  INTEGER,
					accSystemPort     INTEGER
					}
											  accSystemService   OBJECT-TYPE
			SYNTAX  INTEGER {
				telnet (1),
				tftp (2),
				http (3)
				}
			ACCESS  read-write
			STATUS  mandatory
			DESCRIPTION
			"This object is used to identify the TCP/UDP service
			whose port number is being changed."
			::= { accSystemServiceEntry 1 }
	   accSystemPort   OBJECT-TYPE
			SYNTAX  INTEGER
			ACCESS  read-write
			STATUS  mandatory
			DESCRIPTION
			"This object is used to set the TCP/UDP service port
			associated with various system services."
			::= { accSystemServiceEntry 2 }
    --
    --  ACC general VIRTUAL PORT objects
    --
    --
        accVirtualPort          OBJECT IDENTIFIER       ::= { accSysInfo 30 }
	accVirtualPortGeneral	OBJECT IDENTIFIER	::= { accVirtualPort 1 }
    accVirtualPortCount  OBJECT-TYPE
        SYNTAX  INTEGER (0..1000)
        ACCESS  read-write
        STATUS  mandatory
        DESCRIPTION
             "Number of Virtual ports available on the platform"
        ::= { accVirtualPortGeneral 1 }
    accVirtualPortXotCount  OBJECT-TYPE
        SYNTAX  INTEGER (0..20)
        ACCESS  read-write
        STATUS  mandatory
        DESCRIPTION
             "Number of XOT Virtual ports available on the platform"
        ::= { accVirtualPortGeneral 2 }
        --
        --  ACC general System Parameter objects
        --
        --
    accSystemGracefulShutdown   OBJECT IDENTIFIER       ::= { accSysInfo 32 }
        accSystemGracefulShutdownState  OBJECT-TYPE
        SYNTAX  INTEGER {
                                enabled(1),
                                disabled(2)
                                }
                ACCESS  read-write
                STATUS mandatory
                DESCRIPTION
                        "System Graceful Shutdown state"
        ::= { accSystemGracefulShutdown 1 }
        accSystemGracefulShutdownTO     OBJECT-TYPE
                SYNTAX  INTEGER (1..600)
                ACCESS  read-write
                STATUS  mandatory
                DESCRIPTION
                        "System graceful shutdown timeout. When Timeout is exceeded, the system will reset automatically"
                DEFVAL  { 60 }
        ::= { accSystemGracefulShutdown 2 }
    accSystemAuthGeneral    OBJECT IDENTIFIER           ::= { accSysInfo 33 }
        accSystemAuthMode       OBJECT-TYPE
                SYNTAX  INTEGER {
                                local(1),
                                radius(2)
                                }
                ACCESS  read-write
                STATUS  mandatory
                DESCRIPTION
                        "System authentication mode"
                DEFVAL  { local }
        ::= { accSystemAuthGeneral 1 }
    accSystemAuthAccessPart   OBJECT-TYPE
                SYNTAX  DisplayString
                ACCESS  read-write
                STATUS  mandatory
                DESCRIPTION
                                "Access Partn for RADIUS servers"
        ::= { accSystemAuthGeneral 2 }
    accSystemAccess    OBJECT IDENTIFIER           ::= { accSysInfo 34 }
        accPscopeEnable       OBJECT-TYPE
                SYNTAX  INTEGER {
                                enabled(1),
                                disabled(2)
                                }
                ACCESS  read-write
                STATUS  mandatory
                DESCRIPTION
                        "Permits or denies use of built-in packet
                         monitoring functionality (PSCOPE)"
                DEFVAL  { enabled }
        ::= { accSystemAccess 1 }
        accDBscopeCntl       OBJECT-TYPE
                SYNTAX  INTEGER 
                ACCESS  read-write
                STATUS  mandatory
                DESCRIPTION
                        "Controls use of built-in debugger
                         functionality (DBSCOPE).
                         Currently non-zero permits full functionality."
        ::= { accSystemAccess 2 }

    accIcpInfoTrap TRAP-TYPE
                ENTERPRISE   accIcpTraps 
                VARIABLES  { accIcpTrapMsg,
                              accSlvConfCPUID ,
                               accTrapLogSeqNum}
                DESCRIPTION
                   "Indicates that status data ring full while writing
                    data passed in status calls into structure used for
                    passing status data. 
SEVERITY-DEFAULT: Minor 
EVENTTYPE-DEFAULT: 10 
ADDITIONAL-TEXT-VARIABLES: { accTrapLogSeqNum,accIcpTrapMsg }
PCAUSE-DEFAULT: 32 " 
 
                ::= 1
END
