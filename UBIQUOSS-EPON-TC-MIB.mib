--
-- UBIQUOSS-EPON-TC-MIB.my
-- MIB generated by MG-SOFT Visual MIB Builder Version 3.0 Build 271
-- Tuesday, November 21, 2006 at 10:25:15
--

	UBIQUOSS-EPON-TC-MIB DEFINITIONS ::= BEGIN
 
		IMPORTS      

			Integer32			
				FROM SNMPv2-SMI			
			TEXTUAL-CONVENTION			
				FROM SNMPv2-TC;
	
	
--
-- Textual conventions
--
	
		PortList ::= TEXTUAL-CONVENTION
			STATUS current
			DESCRIPTION 
				"Each octet within this value specifies a set of eight
				ports, with the first octet specifying ports 1 through
				8, the second octet specifying ports 9 through 16, etc.
				Within each octet, the most significant bit represents
				the lowest numbered port, and the least significant bit
				represents the highest numbered port.  Thus, each port
				of the bridge is represented by a single bit within the
				value of this object.  If that bit has a value of '1'
				then that port is included in the set of ports; the port
				is not included if its bit has a value of '0'"
			SYNTAX Integer32
			
		OnuType ::= TEXTUAL-CONVENTION
			STATUS current
			DESCRIPTION 
				"Description."
			SYNTAX INTEGER
				{
				og1100(1),
				u9024a(2),
				hybridOnu(19),
				hybridOnu2(20),
				hybridOnu2b(21), 
				hybridOnu2e(22),
				hybridOnuSfp(23), 
				hybridPmc(24),
				hybridPmc2b(25),
				hybrid10gOnu(30),
				hybrid10gOnub(31),
				ctc-tk(41),
				ctc-tk4(42),
				c1004(61),
				c1001a(62),
				c1010at(63),
				c1010ax(64),
				og3410ab(113),
				og3500ab(116),
				og3400aa(117),
				og3500db(118),
				og3500ec(121),
				og3500jc(122),
				og3500kc(123),
				cc3802tg(124),
				corecess3801t(125),
				corecess3804tn(126),
				corecess3801tn(127),
				dongwon204d(128),
				dongwon201d(129), 
				c501m(131),
				c501a(132),
				c501b(133),
				c501g(134), 
				c501l(135),
				c502j(136),
				c504a(137),
				c504b(138),
				c501n(139),
				c504n(140),
				c504k(141),
				c504j(142), 
				dongwon301d(143),
				dongwon304d(144),
				iop-TK(145),
				iop-TK4(146),
				iop-PMC(147),
				iop-PMC(148),
				iop-CTN(149),
				iop-CTN4(150),
				c504e(151),
				c501f(152),
				c504g(153),
				c504w(154),
				c504l(155),
				iop-TK4N(156),
				iop-CTN4N(157),
				c502ep(158),
				c501v(159),
				c504gr(160),
				c502p(161),
				c502d(162),
				c524a(170),
				c514k(171),				
				filter(250),
				unknown(251)
				}
			
		PonFilterRuleField ::= TEXTUAL-CONVENTION
			STATUS current
			DESCRIPTION 
				"Description."
			SYNTAX INTEGER
				{
				layer2DstAddr(0),
				layer2SrcAddr(1),
				logicalLinkId(2),
				etherType(3),
				vlanId(4),
				--layer3DstAddr(5),
				ipV4Protocol(6),
				--layer3SrcAddr(7),
				--layer4DstPort(8),
				--layer4SrcPort(9),
				dscp(10),
				cos(11),
				noExist(16)
				}
			
		PonFilterRuleOperator ::= TEXTUAL-CONVENTION
			STATUS current
			DESCRIPTION 
				"Description."
			SYNTAX INTEGER
				{
				neverMatch(0),
				equalTo(1),
				notEqualTo(2),
				lessThanOrEqualTo(3),
				greaterThanOrEqualTo(4),
				matchWhenFieldExists(5),
				matchWhenFieldNotExists(6),
				alwaysMatch(7),
				noExist(8),
				mask(9)
				}
		
		
	
	
	END

--
-- UBIQUOSS-EPON-TC-MIB.my
--
