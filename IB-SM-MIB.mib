-- extracted from draft-ietf-ipoib-subnet-manager-mib-00.txt
-- at Wed Mar 10 06:17:27 2004

   IB-SM-MIB DEFINITIONS ::= BEGIN 
    
   IMPORTS  
      MODULE-IDENTITY, OBJECT-TYPE,  
      Counter32, Integer32, Unsigned32, Gauge32, 
      NOTIFICATION-TYPE, TimeTicks            FROM SNMPv2-SMI  
      MODULE-COMPLIANCE, OBJECT-GROUP,  
      NOTIFICATION-GROUP                      FROM SNMPv2-CONF 
      TEXTUAL-CONVENTION,                               
      TruthValue, RowStatus                   FROM SNMPv2-TC  
      SnmpAdminString                         FROM SNMP-FRAMEWORK-MIB 
      IbDataPort, IbUnicastLid, 
      IbMulticastLid,IbGuid, 
      IbSmSubnetPrefix, IbSmState, 
      IbNodeType, IbMtu, IbPartitionKey, 


 
 
 
 
      IbTransportTime, 
      infinibandMIB                           FROM IB-TC-MIB; 
    
   ibSmMIB MODULE-IDENTITY  
      LAST-UPDATED "200403030000Z"  -- 3 March 2004 
      ORGANIZATION "IETF IP over IB Working Group" 
      CONTACT-INFO  
         "Working Group Email:   ipoverib@ietf.org 
    
         Carl Yang/Edwin Tsang  
         Postal: TopSpin Communications, Inc.  
         515 Ellis Street 
         Mountain View, CA 94043  
         United States  
         Tel:    +1 650 316 3300 
         Email:  carl@topspin.com edwin@topspin.com 
    
         Cheng Yang 
         Postal: Sun Microsystems, Inc. 
         4150 Network Circle 
         Santa Clara, CA 95054 
         United States  
         Tel:    1-800-555-9SUN or 1-650-960-1300 
         Email:  cheng.yang@sun.com 
         http://www.sun.com"  
    
      DESCRIPTION   
         "The managed objects for Infiniband Subnet Managers(SM)."   
    
      REVISION    "200403030000Z"  -- 3 March 2004 
      DESCRIPTION "Second revision of this MIB." 
    
      REVISION    "200310200000Z"  -- 20 October 2003 
      DESCRIPTION "Complete revision of this MIB. " 
       
      REVISION    "200110220000Z"  
      DESCRIPTION "Initial version of this MIB." 
    
      ::={ infinibandMIB 7 }   
    
   -- Objects  
    
   ibSmMIBObjects        OBJECT IDENTIFIER ::= { ibSmMIB 1 }  
   ibSmConfigInfo        OBJECT IDENTIFIER ::= { ibSmMIBObjects 1 }  
   ibSmNodeInfo          OBJECT IDENTIFIER ::= { ibSmMIBObjects 2 }  
   ibSmPortInfo          OBJECT IDENTIFIER ::= { ibSmMIBObjects 3 }  
   ibSmSwitchInfo        OBJECT IDENTIFIER ::= { ibSmMIBObjects 4 }  
   ibSmPartitionInfo     OBJECT IDENTIFIER ::= { ibSmMIBObjects 5 }  
   ibSmMcastInfo         OBJECT IDENTIFIER ::= { ibSmMIBObjects 6 }  
 
 
 
 
   ibSmSMInfo            OBJECT IDENTIFIER ::= { ibSmMIBObjects 7 }  
   ibSmLinkInfo          OBJECT IDENTIFIER ::= { ibSmMIBObjects 8 }  
   ibSmPathInfo          OBJECT IDENTIFIER ::= { ibSmMIBObjects 9 }  
   ibSmMultiPathInfo     OBJECT IDENTIFIER ::= { ibSmMIBObjects 10 } 
   ibSmTraceInfo         OBJECT IDENTIFIER ::= { ibSmMIBObjects 11 } 
   ibSmServiceInfo       OBJECT IDENTIFIER ::= { ibSmMIBObjects 12 } 
   ibSmGUIDInfo       OBJECT IDENTIFIER ::= { ibSmMIBObjects 13 } 
    
   ibSmMIBTrap           OBJECT IDENTIFIER ::= { ibSmMIB 2 }  
   ibSmTrapData          OBJECT IDENTIFIER ::= { ibSmMIBTrap 1 }  
   ibSmGenericTraps      OBJECT IDENTIFIER ::= { ibSmMIBTrap 2 }  
   ibSmVendorTraps    OBJECT IDENTIFIER ::= { ibSmMIBTrap 3 }  
    
   ibSmMIBConformance    OBJECT IDENTIFIER ::= { ibSmMIB 3 } 
   ibSmMIBCompliances    OBJECT IDENTIFIER ::= { ibSmMIBConformance 1 } 
   ibSmMIBGroups         OBJECT IDENTIFIER ::= { ibSmMIBConformance 2 } 
    
   -- Textual Conventions  
    
   IbSmVendorID ::= TEXTUAL-CONVENTION 
      DISPLAY-HINT "1x:" 
      STATUS              current  
      DESCRIPTION  
         "Device vendor ID, per IEEE.  
         see www.standards.ieee.org/regauth/oui/oui.txt for details." 
      SYNTAX OCTET STRING (SIZE(3))  
    
   -- Subnet Manager Configuration Table  
    
   ibSmConfigTable     OBJECT-TYPE  
      SYNTAX          SEQUENCE OF IbSmConfigEntry  
      MAX-ACCESS      not-accessible  
      STATUS          current  
      DESCRIPTION  
         "A table used to list all configured Subnet Managers on this  
         node."  
      ::= { ibSmConfigInfo 1 }  
    
   ibSmConfigEntry     OBJECT-TYPE  
      SYNTAX              IbSmConfigEntry  
      MAX-ACCESS          not-accessible  
      STATUS              current  
      DESCRIPTION  
         "Table entry for ibSmConfigTable."  
      INDEX { ibSmConfigSubnetPrefix }  
      ::= { ibSmConfigTable 1 }  
    
   IbSmConfigEntry ::= SEQUENCE { 
      ibSmConfigSubnetPrefix       IbSmSubnetPrefix,  
 
 
 
 
      ibSmConfigSubnetGUID         IbGuid, 
      ibSmConfigPriority        Unsigned32, 
      ibSmConfigSMKey              OCTET STRING,     
      ibSmConfigAdminSMState       INTEGER,  
      ibSmConfigSMState            IbSmState, 
      ibSmConfigActCount           Counter32,  
      ibSmConfigStatus             RowStatus, 
      ibSmConfigSweepInterval      Unsigned32, 
      ibSmConfigResponseTimeout    Unsigned32, 
      ibSmConfigPortAgingTime      Unsigned32, 
      ibSmConfigMinUnicastLID      IbUnicastLid, 
      ibSmConfigMaxUnicastLID      IbUnicastLid, 
      ibSmConfigDefaultLMC         Unsigned32, 
      ibSmConfigMasterPollInterval Unsigned32, 
      ibSmConfigMasterPollRetries  Unsigned32, 
      ibSmConfigMKeyLeasePeriod    Unsigned32 
      }  
    
   ibSmConfigSubnetPrefix  OBJECT-TYPE  
      SYNTAX               IbSmSubnetPrefix  
      MAX-ACCESS           not-accessible 
      STATUS               current  
      DESCRIPTION  
         "Subnet prefix of this IB subnet."  
      ::= { ibSmConfigEntry 1 }  
    
   ibSmConfigSubnetGUID OBJECT-TYPE  
      SYNTAX            IbGuid 
      MAX-ACCESS        read-create 
      STATUS            current  
      DESCRIPTION  
         "PortGUID of the port where the SM resides." 
      ::= { ibSmConfigEntry 2 }  
    
   ibSmConfigPriority      OBJECT-TYPE  
      SYNTAX              Unsigned32(0..15) 
      MAX-ACCESS          read-create 
      STATUS              current  
      DESCRIPTION  
         "Assigned priority for this Subnet Manager.  It is used as one of  
         parameters in selecting the master Subnet Manager in an IB subnet."  
      ::= { ibSmConfigEntry 3 }  
    
   ibSmConfigSMKey        OBJECT-TYPE  
      SYNTAX              OCTET STRING (SIZE(8))  
      MAX-ACCESS          read-create 
      STATUS              current  
      DESCRIPTION  
         "SM_Key of the SM.  SM Key exclusively identifies an SM on the 
 
 
 
 
         subnet.  User should take extra caution when setting this value."  
      ::= { ibSmConfigEntry 4 }  
    
   ibSmConfigAdminSMState   OBJECT-TYPE  
      SYNTAX                INTEGER { enable(1), disable(2) }  
      MAX-ACCESS            read-create  
      STATUS                current  
      DESCRIPTION  
         "Administrative state of the Subnet Manager."  
      ::= { ibSmConfigEntry 5 }  
    
   ibSmConfigSMState     OBJECT-TYPE  
      SYNTAX              IbSmState 
      MAX-ACCESS          read-only  
      STATUS              current 
      DESCRIPTION  
         "Subnet Manager's State: 
         0: notActive; 1: discovering; 2: standby; 3: master(3);" 
      ::= { ibSmConfigEntry 6 }  
    
   ibSmConfigActCount   OBJECT-TYPE  
      SYNTAX              Counter32  
      MAX-ACCESS          read-only  
      STATUS              current  
      DESCRIPTION  
         "Activity counter that increments each time the SM issues   
         an SMP or performs other management activities.  Used as a 
         heartbeat indicator by standby SMs."  
      ::= { ibSmConfigEntry 7 }  
    
   ibSmConfigStatus       OBJECT-TYPE  
      SYNTAX             RowStatus  
      MAX-ACCESS         read-create  
      STATUS             current  
      DESCRIPTION  
         "Used to create or delete a row in this table.  Creating a row  
         has the effect of assigning a Subnet Manager to an IB subnet.  
         Depending on the negotiation process the Subnet Manager can take 
         the role of a master or standby Subnet Manager for the IB subnet. 
         Deleting a row has the effect of removing the Subnet Manager from 
         the IB subnet."  
      ::= { ibSmConfigEntry 8 }  
    
   ibSmConfigSweepInterval OBJECT-TYPE  
      SYNTAX              Unsigned32(0..255) 
      UNITS               "seconds" 
      MAX-ACCESS          read-create 
      STATUS              current  
      DESCRIPTION  
 
 
 
 
         "Used to configure the interval the SM should sweep the 
         IB network.  The value is specified in seconds."  
      ::= { ibSmConfigEntry 9 }  
    
   ibSmConfigResponseTimeout   OBJECT-TYPE  
      SYNTAX                  Unsigned32 
      UNITS             "milliseconds" 
      MAX-ACCESS              read-create 
      STATUS                  current  
      DESCRIPTION  
         "Used to configure the time-out interval for that SM should 
         wait for a response before the SM declares a port to 
         be unresponsive." 
      ::= { ibSmConfigEntry 10 }  
    
   ibSmConfigPortAgingTime    OBJECT-TYPE  
      SYNTAX                  Unsigned32 
      UNITS             "minutes" 
      MAX-ACCESS              read-create 
      STATUS                  current  
      DESCRIPTION  
         "Used to configure the time interval for that SM should 
         retain a port's configuration after the port is unresponsive." 
      ::= { ibSmConfigEntry 11 }      
                        
   ibSmConfigMinUnicastLID    OBJECT-TYPE  
      SYNTAX                  IbUnicastLid 
      MAX-ACCESS              read-create 
      STATUS                  current  
      DESCRIPTION  
         "Used to configure unicast LID range for the Subnet Manager. 
         This is the low limit of the LID and its value must be less than 
         the value of ibSmConfigMaxUnicastLID." 
      ::= { ibSmConfigEntry 12 }  
    
   ibSmConfigMaxUnicastLID    OBJECT-TYPE  
      SYNTAX                  IbUnicastLid 
      MAX-ACCESS              read-create 
      STATUS                  current  
      DESCRIPTION  
         "Used to configure unicast LID range for the Subnet Manager. 
         This is the high limit of the LID and its value must be greater 
         Than the value of ibSmConfigMinUnicastLID." 
      ::= { ibSmConfigEntry 13 }  
    
   ibSmConfigDefaultLMC       OBJECT-TYPE  
      SYNTAX                  Unsigned32(0..7) 
      MAX-ACCESS              read-create 
      STATUS                  current  
 
 
 
 
      DESCRIPTION  
         "Used to configure how many LID to be assigned per port. The user  
         should take extra caution when setting this value because the change  
         affects the routing of the packets and existing LID assignments." 
       ::= { ibSmConfigEntry 14 }  
    
   ibSmConfigMasterPollInterval    OBJECT-TYPE  
      SYNTAX                      Unsigned32 
      UNITS                       "seconds" 
      MAX-ACCESS                  read-create 
      STATUS                      current  
      DESCRIPTION  
         "Used to configure the time interval the Standby Subnet Manager 
         will use to poll the Master Subnet Manager." 
      ::= { ibSmConfigEntry 15 }  
    
   ibSmConfigMasterPollRetries     OBJECT-TYPE  
      SYNTAX                      Unsigned32 
      UNITS                       "seconds" 
      MAX-ACCESS                  read-create 
      STATUS                      current  
      DESCRIPTION  
         "Used to configure the number of retries the Standby Subnet Manager  
         will retry its poll of the Master Subnet Manager." 
      ::= { ibSmConfigEntry 16 }  
    
   ibSmConfigMKeyLeasePeriod  OBJECT-TYPE  
      SYNTAX                  Unsigned32(0..65535) 
      UNITS                   "seconds" 
      MAX-ACCESS              read-create 
      STATUS                  current  
      DESCRIPTION  
         "Used to configure the MKey lease period." 
      ::= { ibSmConfigEntry 17 }  
          
   -- node information table  
    
   ibSmNodeInfoTable   OBJECT-TYPE  
      SYNTAX          SEQUENCE OF IbSmNodeInfoEntry  
      MAX-ACCESS      not-accessible  
      STATUS          current  
      DESCRIPTION  
         "A table used to list all IB nodes that are actively managed   
         by the Subnet Managers on this device."  
      ::= { ibSmNodeInfo 1 }  
    
   ibSmNodeInfoEntry   OBJECT-TYPE  
      SYNTAX              IbSmNodeInfoEntry  
      MAX-ACCESS          not-accessible  
 
 
 
 
      STATUS              current  
      DESCRIPTION  
         "Table entry for ibSmNodeInfoTable."  
      INDEX { ibSmNodeInfoSubnetPrefix, ibSmNodeInfoNodeGUID } 
      ::= { ibSmNodeInfoTable 1 }  
    
   IbSmNodeInfoEntry ::= SEQUENCE {   
      ibSmNodeInfoSubnetPrefix      IbSmSubnetPrefix,  
      ibSmNodeInfoNodeGUID          IbGuid, 
      ibSmNodeInfoBaseVersion       Unsigned32,  
      ibSmNodeInfoClassVersion      Unsigned32,  
      ibSmNodeInfoType              IbNodeType, 
      ibSmNodeInfoNumPorts          Unsigned32,  
      ibSmNodeInfoSystemImageGUID   IbGuid, 
      ibSmNodeInfoPartitionCap      Unsigned32,  
      ibSmNodeInfoDeviceID          OCTET STRING,  
      ibSmNodeInfoRevision          OCTET STRING,  
      ibSmNodeInfoVendorID          IbSmVendorID, 
      ibSmNodeInfoDescription       SnmpAdminString 
      }  
    
   ibSmNodeInfoSubnetPrefix    OBJECT-TYPE  
      SYNTAX                  IbSmSubnetPrefix  
      MAX-ACCESS              not-accessible  
      STATUS                  current  
      DESCRIPTION  
         "Subnet prefix of this IB subnet."  
      ::= { ibSmNodeInfoEntry 1 }  
    
   ibSmNodeInfoNodeGUID    OBJECT-TYPE  
      SYNTAX          IbGuid 
      MAX-ACCESS      not-accessible  
      STATUS          current  
      DESCRIPTION  
         "The GUID of this node."  
      ::= { ibSmNodeInfoEntry 2 }  
    
   ibSmNodeInfoBaseVersion OBJECT-TYPE  
      SYNTAX              Unsigned32(0..255) 
      MAX-ACCESS          read-only  
      STATUS              current  
      DESCRIPTION  
         "Supported base management datagram version."  
      ::= { ibSmNodeInfoEntry 3 }  
    
   ibSmNodeInfoClassVersion OBJECT-TYPE  
      SYNTAX                 Unsigned32(0..255) 
      MAX-ACCESS             read-only  
      STATUS                 current  
 
 
 
 
      DESCRIPTION  
         "Supported subnet management class."  
      ::= { ibSmNodeInfoEntry 4 }  
    
   ibSmNodeInfoType    OBJECT-TYPE  
      SYNTAX         IbNodeType 
      MAX-ACCESS      read-only  
      STATUS          current  
      DESCRIPTION  
         "Type of node being managed: 
         reserved(0), channelAdapter(1), switch(2), router(3),error(4)."  
      ::= { ibSmNodeInfoEntry 5 }  
    
   ibSmNodeInfoNumPorts OBJECT-TYPE  
      SYNTAX              Unsigned32(1..254) 
      MAX-ACCESS          read-only  
      STATUS              current  
      DESCRIPTION  
         "Number of physical ports on this node."  
      ::= { ibSmNodeInfoEntry 6 }  
    
   ibSmNodeInfoSystemImageGUID  OBJECT-TYPE  
      SYNTAX                   IbGuid 
      MAX-ACCESS               read-only  
      STATUS                   current  
      DESCRIPTION  
         "GUID associating this node with other nodes controlled by common 
         supervisory code. Provides a means for system software to indicate 
         the availability of multiple paths to the same destination via  
         multiple nodes. All zero indicates that node association is  
         not desired. The SystemImageGUID may be the NodeGUID of one of  
         the associated nodes if that node is not field-replaceable." 
      ::= { ibSmNodeInfoEntry 7 }  
    
   ibSmNodeInfoPartitionCap   OBJECT-TYPE  
      SYNTAX               Unsigned32(1..65535) 
      MAX-ACCESS           read-only  
      STATUS               current  
      DESCRIPTION  
         "Number of entries in the partition table for CA, router, and the  
         switch management port.  This is at a minimum set to 1 for all  
         nodes including switch."  
      ::= { ibSmNodeInfoEntry 8 }  
    
   ibSmNodeInfoDeviceID       OBJECT-TYPE  
      SYNTAX               OCTET STRING (SIZE(2))  
      MAX-ACCESS           read-only  
      STATUS               current  
      DESCRIPTION  
 
 
 
 
         "Device ID information as assigned by device manufacturer."  
      ::= { ibSmNodeInfoEntry 9 }  
    
   ibSmNodeInfoRevision OBJECT-TYPE  
      SYNTAX               OCTET STRING (SIZE(4))  
      MAX-ACCESS           read-only  
      STATUS               current  
      DESCRIPTION  
         "Device revision, assigned by manufacturer."  
      ::= { ibSmNodeInfoEntry 10 }  
    
   ibSmNodeInfoVendorID OBJECT-TYPE  
      SYNTAX              IbSmVendorID 
      MAX-ACCESS          read-only  
      STATUS              current  
      DESCRIPTION  
         "Device vendor ID, per IEEE.  
         see www.standards.ieee.org/regauth/oui/oui.txt for details."  
      ::= { ibSmNodeInfoEntry 11 }  
    
   ibSmNodeInfoDescription OBJECT-TYPE  
      SYNTAX              SnmpAdminString 
      MAX-ACCESS          read-only 
      STATUS              current  
      DESCRIPTION  
         "A vendor specific optional text string describing this node."  
      ::= { ibSmNodeInfoEntry 12 } 
    
   -- Subnet Manager port information table  
    
   ibSmPortInfoTable     OBJECT-TYPE  
      SYNTAX              SEQUENCE OF IbSmPortInfoEntry  
      MAX-ACCESS          not-accessible  
      STATUS              current  
      DESCRIPTION  
         "A table used to list all IB ports that are actively managed by  
         the Subnet Managers on this device."  
      ::= { ibSmPortInfo 1 }  
    
   ibSmPortInfoEntry     OBJECT-TYPE  
      SYNTAX              IbSmPortInfoEntry  
      MAX-ACCESS          not-accessible  
      STATUS              current  
      DESCRIPTION  
         "Table entry for ibSmPortInfoTable."  
      INDEX  { ibSmPortInfoSubnetPrefix, ibSmPortInfoNodeGUID,  
               ibSmPortInfoPortNum } 
      ::= { ibSmPortInfoTable 1 }  
    
 
 
 
 
   IbSmPortInfoEntry ::= SEQUENCE {   
      ibSmPortInfoSubnetPrefix              IbSmSubnetPrefix,  
      ibSmPortInfoNodeGUID                  IbGuid, 
      ibSmPortInfoPortNum                   IbDataPort, 
      ibSmPortInfoMKey                      OCTET STRING,  
      ibSmPortInfoGIDPrefix                 OCTET STRING,  
      ibSmPortInfoLID                       IbUnicastLid, 
      ibSmPortInfoMasterSmLID               IbUnicastLid, 
      ibSmPortInfoCapMask                   BITS, 
      ibSmPortInfoDiagCode                  OCTET STRING,  
      ibSmPortInfoMKeyLeasePeriod           Unsigned32,  
      ibSmPortInfoLinkWidthEnabled          Unsigned32,  
      ibSmPortInfoLinkWidthSupported        Unsigned32,  
      ibSmPortInfoLinkWidthActive           Unsigned32,  
      ibSmPortInfoLinkSpeedSupported        Unsigned32,  
      ibSmPortInfoState                     Unsigned32,  
      ibSmPortInfoPhyState                  Unsigned32,  
      ibSmPortInfoLinkDownDefState          Unsigned32,  
      ibSmPortInfoMKeyProtBits              Unsigned32,  
      ibSmPortInfoLMC                       Unsigned32,  
      ibSmPortInfoLinkSpeedActive           Unsigned32,  
      ibSmPortInfoLinkSpeedEnabled          Unsigned32,  
      ibSmPortInfoNeighborMTU               IbMtu, 
      ibSmPortInfoMasterSmSL                Unsigned32,  
      ibSmPortInfoVLCap                     Unsigned32,  
      ibSmPortInfoVLHighLimit               Unsigned32,  
      ibSmPortInfoVLArbHighCap              Unsigned32,  
      ibSmPortInfoVLArbLowCap               Unsigned32,  
      ibSmPortInfoMTUCap                    IbMtu, 
      ibSmPortInfoVLStallCount              Unsigned32,  
      ibSmPortInfoHOQLife                   Unsigned32,  
      ibSmPortInfoOperVL                    Unsigned32,  
      ibSmPortInfoInPartEnforce             TruthValue,  
      ibSmPortInfoOutPartEnforce            TruthValue,  
      ibSmPortInfoInFilterRawPktEnf         TruthValue,  
      ibSmPortInfoOutFilterRawPktEnf        TruthValue,  
      ibSmPortInfoMKeyViolation             Gauge32, 
      ibSmPortInfoPKeyViolation             Gauge32, 
      ibSmPortInfoQKeyViolation             Gauge32, 
      ibSmPortInfoGUIDCap                   Unsigned32,  
      ibSmPortInfoSubnetTimeout             IbTransportTime, 
      ibSmPortInfoRespTime                  IbTransportTime, 
      ibSmPortInfoLocalPhyError             Gauge32, 
      ibSmPortInfoOverrunError              Gauge32, 
      ibSmPortInfoInitType                  OCTET STRING, 
      ibSmPortInfoInitTypeReply             OCTET STRING 
      }  
    
   ibSmPortInfoSubnetPrefix OBJECT-TYPE  
 
 
 
 
      SYNTAX              IbSmSubnetPrefix  
      MAX-ACCESS          not-accessible  
      STATUS              current  
      DESCRIPTION  
         "Subnet prefix of this IB subnet."  
      ::= { ibSmPortInfoEntry 1 }  
    
   ibSmPortInfoNodeGUID    OBJECT-TYPE  
      SYNTAX              IbGuid 
      MAX-ACCESS          not-accessible 
      STATUS              current  
      DESCRIPTION  
         "The 64-bit GUID of the node that contains this port."  
      ::= { ibSmPortInfoEntry 2 }  
    
   ibSmPortInfoPortNum    OBJECT-TYPE 
      SYNTAX              IbDataPort 
      MAX-ACCESS          not-accessible 
      STATUS              current 
      DESCRIPTION 
         "The port number of this port." 
      ::= { ibSmPortInfoEntry 3 } 
    
   ibSmPortInfoMKey          OBJECT-TYPE  
      SYNTAX              OCTET STRING (SIZE(8))  
      MAX-ACCESS          read-only  
      STATUS              current  
      DESCRIPTION  
         "The 64-bit management Key for this port."  
      ::= { ibSmPortInfoEntry 4 }  
    
   ibSmPortInfoGIDPrefix     OBJECT-TYPE  
      SYNTAX              OCTET STRING (SIZE(8))  
      MAX-ACCESS          read-only  
      STATUS              current  
      DESCRIPTION  
         "The 64-bit GID prefix for this port."  
      ::= { ibSmPortInfoEntry 5 }  
    
   ibSmPortInfoLID           OBJECT-TYPE  
      SYNTAX              IbUnicastLid 
      MAX-ACCESS          read-only  
      STATUS              current  
      DESCRIPTION  
         "The 16-bit base LID of this port."  
      ::= { ibSmPortInfoEntry 6 }  
    
   ibSmPortInfoMasterSmLID   OBJECT-TYPE  
      SYNTAX              IbUnicastLid 
 
 
 
 
      MAX-ACCESS          read-only  
      STATUS              current  
      DESCRIPTION  
         "The 16-bit base LID of the master SM that is managing this  
         port."  
      ::= { ibSmPortInfoEntry 7 }  
    
   ibSmPortInfoCapMask       OBJECT-TYPE  
      SYNTAX                 BITS { 
                             reserved(0), 
                             isSM(1), 
                             isNoticeSupported(2), 
                             isTrapSupported(3), 
                             isResetSupported(4), 
                             isAutomaticMigrationSupported(5), 
                             isSLMappingSupported(6), 
                             isMKeyNVRAM(7), 
                             isPKeyNVRAM(8), 
                             isLEDInfoSupported(9), 
                             isSMDisabled(10), 
                             isSystemImageGUIDSuppported(11), 
                             isPKeySwitchExternalPortTrapSupported(12), 
                             reserved1(13), reserved2(14), reserved3(15), 
                             isConnectionManagerSupported(16),  
                             isSNMPTunnelingSupported(17), 
                             isReinitSupported(18), 
                             issDeviceManagementSupported(19), 
                             isVendorClassSupported(20), 
                             isDRNoticeSupported(21), 
                             isCapabilityMaskNoticeSupported(22), 
                             isBootManagementSupported(23), 
                             reserved4(24), reserved5(25), reserved6(26), 
                             reserved7(27), reserved8(28), reserved9(29), 
                             reserved10(30), reserved11(31) 
                             } 
      MAX-ACCESS          read-only  
      STATUS              current  
      DESCRIPTION  
         "Supported capabilities of this node.  A bit set to 1 for  
         affirmation of supported capability:  
    
         0: Reserved, shall be zero  
         1: IsSM  
         2: IsNoticeSupported  
         3: IsTrapSupported  
         4: IsResetSupported  
         5: IsAutomaticMigrationSupported  
         6: IsSLMappingSupported  
         7: IsMKeyNVRAM  
 
 
 
 
         8: IsPKeyNVRAM  
         9: IsLEDInfoSupported  
         10: IsSMDisabled  
         11: IsSystemImageGUIDSuppported 
         12: IsPKeySwitchExternalPortTrapSupported 
         13-15: Reserved, shall be zero  
         16: IsConnectionManagerSupported  
         17: IsSNMPTunnelingSupported  
         18: Reserved, shall be zero  
         19: IsDeviceManagementSupported  
         20: IsVendorClassSupported  
         21: IsDRNoticeSupported, 
         22: IsCapabilityMaskNoticeSupported 
         23: IsBootManagementSupported(23), 
         24-31: Reserved, shall be zero"   
      ::= { ibSmPortInfoEntry 8 }  
    
   ibSmPortInfoDiagCode      OBJECT-TYPE  
      SYNTAX              OCTET STRING (SIZE(2))  
      MAX-ACCESS          read-only  
      STATUS              current  
      DESCRIPTION  
         "Diagnostic code: 
         Bits 3-0:  
              0x0: Port Ready; 0x1: Performing Self Test; 0x2: Initializing; 
              0x3: soft error - port has a non-fatal error and may be used; 
              0x4: hard error -port may not be used; 
              0x5-0xF: Reserved. 
         Bits 14-4: for vender specific information."  
      ::= { ibSmPortInfoEntry 9 }  
    
   ibSmPortInfoMKeyLeasePeriod  OBJECT-TYPE  
      SYNTAX                    Unsigned32(0..65535)  
      UNITS                     "seconds" 
      MAX-ACCESS                read-only 
      STATUS                    current  
      DESCRIPTION  
         "Specifies the initial value of the lease period timer in seconds. 
         It's the length of time that the M_Key Protection bits are to remain 
         non zero after a SubnSet(PortInfo) fails a M_Key check." 
      ::= { ibSmPortInfoEntry 10 }  
    
   ibSmPortInfoLinkWidthEnabled      OBJECT-TYPE  
      SYNTAX                      Unsigned32(0..255) 
      MAX-ACCESS                  read-write  
      STATUS                      current  
      DESCRIPTION  
         "Enabled link width.  Indicated as follows:  
    
 
 
 
 
         0: No state change; 1: 1x; 2: 4x; 3: 1x or 4x; 8: 12x; 
         9: 1x or 12x; 10: 4x or 12x; 11: 1x, 4x or 12x;  
         1-7, 12-254: reserved; 
         255: Set to ibSmPortInfoLinkWidthSupported value."  
      ::= { ibSmPortInfoEntry 11 }  
    
   ibSmPortInfoLinkWidthSupported    OBJECT-TYPE  
      SYNTAX                      Unsigned32(0..255)  
      MAX-ACCESS                  read-only  
      STATUS                      current  
      DESCRIPTION  
         "Supported link width.  Indicated as follows:  
         1: 1x; 3: 1x or 4x; 11: 1x, 4x or 12x; other values reserved."  
      ::= { ibSmPortInfoEntry 12 }  
    
   ibSmPortInfoLinkWidthActive       OBJECT-TYPE  
      SYNTAX                      Unsigned32(0..255) 
      MAX-ACCESS                  read-only  
      STATUS                      current  
      DESCRIPTION  
         "Currently active link width.  Indicated as follows:  
         1: 1x; 2: 4x; 8: 12x; other values reserved."  
      ::= { ibSmPortInfoEntry 13 }  
    
   ibSmPortInfoLinkSpeedSupported    OBJECT-TYPE  
      SYNTAX                      Unsigned32(0..15)  
      MAX-ACCESS                  read-only  
      STATUS                      current  
      DESCRIPTION  
         "Supported link speed.  Indicated as follows:  
         1: 2.5Gps; other values reserved."  
      ::= { ibSmPortInfoEntry 14 }  
    
   ibSmPortInfoState         OBJECT-TYPE  
      SYNTAX              Unsigned32(0..5) 
      MAX-ACCESS          read-write  
      STATUS              current  
      DESCRIPTION  
         "Port state.  When writing to this field, only legal transitions  
         are valid: 
         0: noStateChange; 1: down; 2: initialize; 3: armed; 4: active; 
         5: reserved. "  
      ::= { ibSmPortInfoEntry 15 }  
    
   ibSmPortInfoPhyState      OBJECT-TYPE  
      SYNTAX              Unsigned32(0..7) 
      MAX-ACCESS          read-write  
      STATUS              current  
      DESCRIPTION  
 
 
 
 
         "When writing this field, only legal transition are valid. 
         noStateChange(0), sleep(1), polling(2), disabled(3),  
         portConfigurationTraining(4), linkup(5),linkErrorRecovery(6), 
         reserved(7). "  
      ::= { ibSmPortInfoEntry 16 }  
    
   ibSmPortInfoLinkDownDefState    OBJECT-TYPE  
      SYNTAX                      Unsigned32(0..3) 
      MAX-ACCESS                  read-write  
      STATUS                      current  
      DESCRIPTION  
         "When writing this field, only legal transitions are valid. 
         noStateChange(0), sleep(1), polling(2), reserved(3) "  
      ::= { ibSmPortInfoEntry 17 }  
    
   ibSmPortInfoMKeyProtBits  OBJECT-TYPE  
      SYNTAX              Unsigned32(0..3) 
      MAX-ACCESS          read-write  
      STATUS              current  
      DESCRIPTION  
         "The bits are described below:  
    
         0: SubnGet() shall succeed for any Key in the  
         MADHeader:M_Key and SubnGetResp(PortInfo) shall return  
         the contents of the PortInfo:M_Key component.  
    
         1: SubnGet() shall succeed for any Key in the  
         MADHeader:M_Key and SubnGetResp(PortInfo) shall return  
         the contents of the PortInfo:M_Key component set to zero  
         if MADHeader:M_Key does not match the PortInfo:M Key  
         component of the port.  
    
         2: SubnGet() and SubnSet() shall fail if MADHeader:M_Key  
         does not match the PortInfo:M_Key component in the port.  
    
         3: SubnGet() and SubnSet() shall fail if MADHeader:M_Key  
         does not match the PortInfo:M_Key component in the port."  
      ::= { ibSmPortInfoEntry 18 }  
    
   ibSmPortInfoLMC           OBJECT-TYPE  
      SYNTAX              Unsigned32(0..7) 
      MAX-ACCESS          read-write  
      STATUS              current  
      DESCRIPTION  
         "LID mask for multipath support.  User should take extra caution 
         when setting this value, since any change will effect packet 
         routing."  
      ::= { ibSmPortInfoEntry 19 }  
    
 
 
 
 
   ibSmPortInfoLinkSpeedActive       OBJECT-TYPE  
      SYNTAX                      Unsigned32(0..15) 
      MAX-ACCESS                  read-only  
      STATUS                      current  
      DESCRIPTION  
         "Current active link speed, indicated as follows:  
         1: 2.5Gps; other values reserved."  
      ::= { ibSmPortInfoEntry 20 }  
    
   ibSmPortInfoLinkSpeedEnabled      OBJECT-TYPE  
      SYNTAX                      Unsigned32(0..15)  
      MAX-ACCESS                  read-write  
      STATUS                      current  
      DESCRIPTION  
         "Enabled link speed, indicated as follows:  
         0: No state change; 1: 2.5Gps; 2-14: reserved;  
         15: Set to ibSmPortLinkSpeedSupported value.    
    
         When writing this field only legal transitions are  
         valid."  
      ::= { ibSmPortInfoEntry 21 }  
    
   ibSmPortInfoNeighborMTU   OBJECT-TYPE  
      SYNTAX            IbMtu 
      UNITS             "bytes" 
      MAX-ACCESS          read-write  
      STATUS              current  
      DESCRIPTION  
         "Active maximum MTU enabled on this port for transmit.  
         1: 256; 2: 512; 3: 1024; 4: 2048; 5: 4096" 
      ::= { ibSmPortInfoEntry 22 }  
    
   ibSmPortInfoMasterSmSL    OBJECT-TYPE  
      SYNTAX              Unsigned32(0..15) 
      MAX-ACCESS          read-only  
      STATUS              current  
      DESCRIPTION  
         "The administrative SL of the master SM that is managing this  
         port."  
      ::= { ibSmPortInfoEntry 23 }  
    
   ibSmPortInfoVLCap         OBJECT-TYPE  
      SYNTAX               Unsigned32(0..15)  
      MAX-ACCESS          read-only  
         STATUS              current  
      DESCRIPTION  
         "Virtual Lanes supported on this port: 
         1:VL0, 2:VL0-VL1, 3:VL0-VL3, 4:VL0-VL7, 5:VL0-VL14,  
         0, 6-15: reserved."  
 
 
 
 
      ::= { ibSmPortInfoEntry 24 }  
    
   ibSmPortInfoVLHighLimit   OBJECT-TYPE  
      SYNTAX              Unsigned32(0..255) 
      MAX-ACCESS          read-write  
      STATUS              current  
      DESCRIPTION  
         "Limit of high priority component of VL arbitration table."  
      ::= { ibSmPortInfoEntry 25 }  
    
   ibSmPortInfoVLArbHighCap  OBJECT-TYPE  
      SYNTAX              Unsigned32(0..255) 
      MAX-ACCESS          read-only  
      STATUS              current  
      DESCRIPTION  
         "VL/Weight pairs supported on this port in the smVLArbTable for  
         high priority."  
      ::= { ibSmPortInfoEntry 26 }  
    
   ibSmPortInfoVLArbLowCap   OBJECT-TYPE  
      SYNTAX              Unsigned32(0..255) 
      MAX-ACCESS          read-only  
      STATUS              current  
      DESCRIPTION  
         "VL/Weight pairs supported on this port in the smVLArbTable for  
         low priority."  
      ::= { ibSmPortInfoEntry 27 }  
    
   ibSmPortInfoMTUCap OBJECT-TYPE  
      SYNTAX            IbMtu 
      UNITS             "bytes" 
      MAX-ACCESS        read-only  
      STATUS            current  
      DESCRIPTION  
         "Maximum MTU supported by this port: 
         1: 256; 2: 512; 3: 1024; 4: 2048; 5: 4096" 
      ::= { ibSmPortInfoEntry 28 }  
    
   ibSmPortInfoVLStallCount  OBJECT-TYPE  
      SYNTAX              Unsigned32(0..7)  
      UNITS               "packets" 
      MAX-ACCESS          read-write  
      STATUS              current  
      DESCRIPTION  
         "Specifies the number of sequential packets dropped that causes  
         the port to enter the VLStalled state."  
      ::= { ibSmPortInfoEntry 29 }  
    
   ibSmPortInfoHOQLife       OBJECT-TYPE  
 
 
 
 
      SYNTAX              Unsigned32(0..31)  
      MAX-ACCESS          read-write  
      STATUS              current  
      DESCRIPTION  
         "Sets the time a packet can live at the head of a VL queue."  
      ::= { ibSmPortInfoEntry 30 }  
    
   ibSmPortInfoOperVL         OBJECT-TYPE  
      SYNTAX               Unsigned32(0..15)  
      MAX-ACCESS          read-write  
      STATUS              current  
      DESCRIPTION  
         "Virtual Lanes operational on this port: 
         1:VL0, 2:VL0-VL1, 3:VL0-VL3, 4:VL0-VL7, 5:VL0-VL14,  
         0, 6-15: reserved."  
      ::= { ibSmPortInfoEntry 31 }  
    
   ibSmPortInfoInPartEnforce OBJECT-TYPE  
      SYNTAX              TruthValue  
      MAX-ACCESS          read-write  
      STATUS              current  
      DESCRIPTION  
         "Indicates support of optional partition enforcement on packets  
         received from this port."  
      ::= { ibSmPortInfoEntry 32 }  
    
   ibSmPortInfoOutPartEnforce OBJECT-TYPE  
      SYNTAX              TruthValue  
      MAX-ACCESS          read-write  
      STATUS              current  
      DESCRIPTION  
         "Indicates support of optional partition enforcement on packets  
         transmitted from this port."  
      ::= { ibSmPortInfoEntry 33 }  
    
   ibSmPortInfoInFilterRawPktEnf     OBJECT-TYPE  
      SYNTAX                      TruthValue  
      MAX-ACCESS                  read-write  
      STATUS                      current  
      DESCRIPTION  
         "Indicates support of optional raw packet enforcement on raw  
         packets received from this port."  
      ::= { ibSmPortInfoEntry 34 }  
    
   ibSmPortInfoOutFilterRawPktEnf    OBJECT-TYPE  
      SYNTAX                      TruthValue  
      MAX-ACCESS                  read-write  
      STATUS                      current  
      DESCRIPTION  
 
 
 
 
         "Indicates support of optional raw packet enforcement on raw  
         packets transmitted from this port."  
      ::= { ibSmPortInfoEntry 35 }  
    
   ibSmPortInfoMKeyViolation OBJECT-TYPE  
      SYNTAX              Gauge32(0..65535) 
      UNITS               "packets" 
      MAX-ACCESS          read-write  
      STATUS              current  
      DESCRIPTION  
         "Counts the number of SMP packets that have been received on the  
         port that have had invalid M_Key, since power on or reset.   
         Increments till count reaches all 1s and then must be set back to  
         zero to re-able incrementing."  
      ::= { ibSmPortInfoEntry 36 }  
    
   ibSmPortInfoPKeyViolation OBJECT-TYPE  
      SYNTAX              Gauge32(0..65535) 
      UNITS               "packets" 
      MAX-ACCESS          read-write  
      STATUS              current  
      DESCRIPTION  
         "Counts the number of packets that have been received on the port  
         that have had invalid P_Key, since power on or reset.  Increments  
         till count reaches all 1s and then must be set back to zero to  
         re-able incrementing."  
      ::= { ibSmPortInfoEntry 37 }  
    
   ibSmPortInfoQKeyViolation OBJECT-TYPE  
      SYNTAX              Gauge32(0..65535) 
      UNITS               "packets" 
      MAX-ACCESS          read-only  
      STATUS              current  
      DESCRIPTION  
         "Counts the number of packets that have been received on the port  
         that have had invalid Q_Key, since power on or reset.  Increments  
         till count reaches all 1s and then must be set back to zero to  
         re-able incrementing."  
      ::= { ibSmPortInfoEntry 38 }  
    
   ibSmPortInfoGUIDCap       OBJECT-TYPE  
      SYNTAX              Unsigned32(0..255) 
      UNITS               "GUIDs" 
      MAX-ACCESS          read-only  
      STATUS              current  
      DESCRIPTION  
         "Number of GUID entries supported in the GUIDInfo attribute for  
         this port."  
      ::= { ibSmPortInfoEntry 39 }  
 
 
 
 
    
   ibSmPortInfoSubnetTimeout OBJECT-TYPE  
      SYNTAX              IbTransportTime 
      MAX-ACCESS          read-write  
      STATUS              current  
      DESCRIPTION  
         "Specifies the maximum expected subnet propagation delay, which  
         depends upon the configuration of the switches, to reach any  
         other port in the subnet and shall also be used to determine the  
         maximum rate which SubnTraps() can be sent from this port. 
         The duration of time is calculated based on 
         (4.096 microsecond * 2 ^ object value)" 
      ::= { ibSmPortInfoEntry 40 }  
    
   ibSmPortInfoRespTime      OBJECT-TYPE  
      SYNTAX              IbTransportTime 
      MAX-ACCESS          read-only  
      STATUS              current  
      DESCRIPTION  
         "Specifies the expected maximum time between the port reception  
         of a SMP and the transmission of the associated response. 
         The duration of time is calculated based on 
         (4.096 microsecond * 2 ^ object value)" 
      ::= { ibSmPortInfoEntry 41 }  
    
   ibSmPortInfoLocalPhyError OBJECT-TYPE  
      SYNTAX              Gauge32(0..15)  
      MAX-ACCESS          read-write  
      STATUS              current  
      DESCRIPTION  
         "Threshold value.  When the count of marginal link errors exceeds  
         this threshold, the local link integrity error shall be generated." 
      ::= { ibSmPortInfoEntry 42 }  
    
   ibSmPortInfoOverrunError     OBJECT-TYPE  
      SYNTAX                   Gauge32(0..15)  
      MAX-ACCESS                  read-write  
      STATUS                      current  
      DESCRIPTION  
         "Threshold value.  When the count of buffer overruns over  
         consecutive flow control update periods exceeds this threshold,  
         the excessive buffer overrun error shall be generated."  
      ::= { ibSmPortInfoEntry 43 }  
    
   ibSmPortInfoInitType     OBJECT-TYPE  
      SYNTAX                      BITS { 
                                       noLoad(0), 
                                       preserveContent(1), 
                                       preservePresense(2), 
 
 
 
 
                                       doNotResuscitate(3) 
                                       } 
      MAX-ACCESS                  read-only 
      STATUS                      current  
      DESCRIPTION 
         "Optional; shall be 0 if not implemented. Type of initialization  
         requested by this port before SM moves it to Active or Armed state. 
          
         Bit 0: NoLoad. 0 = Port is requesting that its  
         attributes be initialized.   1 = Port is requesting that  
         no data be loaded into its attributes at all, asserting  
         that the last-loaded data still exists and is valid.  
    
         Bit 1: PreserveContent. 0 = Port makes no  
         request regarding content of the data that is  
         loaded into its attributes. 1 = Port is requesting  
         that all such data, if loaded, be set to the most  
         recent content loaded by the SM.  
    
         Bit 2: PreservePresence. 0 = Port is requesting  
         that all settable SA attributes referencing this port  
         be removed prior to activating this port and Report()s  
         of in/out of service (trap numbers 64/65) be sent. 1 = Port is  
         requesting that all such data be preserved, and  
         Report()s of in/out of service (trap numbers 64/65) not be sent  
         for this port.  
    
         Bit 3: DoNotResuscitate. 0 = bits 0, 1, and 2 of this  
         field are valid; initialization of this port should  
         begin based on their values. 1 = bits 0, 1, and 2  
         are not valid; port is requesting that reinitialization  
         of this port, and any Report()s of in/out of service  
         (trap numbers 64/65) be delayed until this bit is  
         set to 0.  
    
         Other Bits: Reserved. " 
    
      ::= { ibSmPortInfoEntry 44 }  
    
   ibSmPortInfoInitTypeReply     OBJECT-TYPE  
      SYNTAX                      BITS { 
                                       noLoadReply(0), 
                                       preserveContentReply(1), 
                                       preservePresenceReply(2) 
                                       } 
      MAX-ACCESS                  read-write 
      STATUS                      current  
      DESCRIPTION  
         "Written by the SM prior to changing the port to Active or  
 
 
 
 
         Armed state. Optional; shall be set to all 0s if not implemented. 
         Indicates the type of initialization performed.  
    
         Bit 0: NoLoadReply. 0 = Port attributes were initialized.  
         1 = No data was loaded into the port attributes.  
          
         Bit 1: PreserveContentReply. 0 = No information  
         is available regarding content of the data loaded  
         into the port attributes. 1 = The data loaded into  
         the port attributes was set to the content most  
         recently loaded by the SM.  
    
         Bit 2: PreservePresenceReply. 0 = All settable SA  
         attributes referencing this port were removed prior to activating  
         this port and Report()s of in/out of service (trap numbers  
         64/65) were sent. 1 = All such data existing  
         when this port was last active was not removed  
         and Report()s of in/out of service (trap numbers  
         64/65) were not sent.  
    
         Other Bits: Reserved. " 
    
      ::= { ibSmPortInfoEntry 45 }  
    
   -- switch information table  
    
   ibSmSwitchInfoTable   OBJECT-TYPE  
      SYNTAX              SEQUENCE OF IbSmSwitchInfoEntry  
      MAX-ACCESS          not-accessible  
      STATUS              current  
      DESCRIPTION  
         "A table used to list all IB switches that are actively   
         managed by the Subnet Managers on this device."  
      ::= { ibSmSwitchInfo 1 }  
    
   ibSmSwitchInfoEntry   OBJECT-TYPE  
      SYNTAX              IbSmSwitchInfoEntry  
      MAX-ACCESS          not-accessible  
      STATUS              current  
      DESCRIPTION  
         "Table entry for ibSmSwitchInfoTable."  
      INDEX { ibSmSwitchInfoSubnetPrefix, ibSmSwitchInfoNodeGUID }  
      ::= { ibSmSwitchInfoTable 1 }  
    
   IbSmSwitchInfoEntry ::= SEQUENCE {   
      ibSmSwitchInfoSubnetPrefix            IbSmSubnetPrefix,  
      ibSmSwitchInfoNodeGUID                IbGuid, 
      ibSmSwitchInfoLinearFdbCap            Unsigned32,  
      ibSmSwitchInfoRandomFdbCap            Unsigned32,  
 
 
 
 
      ibSmSwitchInfoMcastFdbCap             Unsigned32,  
      ibSmSwitchInfoLinearFdbTop            Unsigned32,  
      ibSmSwitchInfoDefaultPort             Unsigned32,  
      ibSmSwitchInfoDefPriMcastPort         Unsigned32,  
      ibSmSwitchInfoDefNonPriMcastPort      Unsigned32,  
      ibSmSwitchInfoLifeTimeValue           Unsigned32,  
      ibSmSwitchInfoPortStateChange         Unsigned32,  
      ibSmSwitchInfoLIDsPerPort             Unsigned32,  
      ibSmSwitchInfoPartitionEnfCap         Unsigned32,  
      ibSmSwitchInfoInEnfCap                TruthValue,  
      ibSmSwitchInfoOutEnfCap               TruthValue,  
      ibSmSwitchInfoInFilterRawPktCap       TruthValue,  
      ibSmSwitchInfoOutFilterRawPktCap      TruthValue, 
      ibSmSwitchInfoEnhanced0               TruthValue 
      }  
    
   ibSmSwitchInfoSubnetPrefix OBJECT-TYPE  
      SYNTAX              IbSmSubnetPrefix  
      MAX-ACCESS          not-accessible  
      STATUS              current  
      DESCRIPTION  
         "Subnet prefix of this IB subnet."  
      ::= { ibSmSwitchInfoEntry 1 }  
    
   ibSmSwitchInfoNodeGUID    OBJECT-TYPE  
      SYNTAX              IbGuid 
      MAX-ACCESS          not-accessible  
      STATUS              current  
      DESCRIPTION  
         "The GUID of this node."  
      ::= { ibSmSwitchInfoEntry 2 }  
    
   ibSmSwitchInfoLinearFdbCap OBJECT-TYPE  
      SYNTAX              Unsigned32(0..65535) 
      UNITS               "entries"  
      MAX-ACCESS          read-only  
      STATUS              current  
      DESCRIPTION  
         "Number of entries supported in the Linear Unicast Forwarding  
         table.  Zero indicates that there is no Linear Forwarding  
         Database."  
      ::= { ibSmSwitchInfoEntry 3 }  
    
   ibSmSwitchInfoRandomFdbCap OBJECT-TYPE  
      SYNTAX              Unsigned32(0..65535)  
      UNITS               "entries"  
      MAX-ACCESS          read-only  
      STATUS              current  
      DESCRIPTION  
 
 
 
 
         "Number of entries supported in the Random Unicast Forwarding  
         table.  Zero indicates that there is no Random Forwarding  
         Database."  
      ::= { ibSmSwitchInfoEntry 4 }  
    
   ibSmSwitchInfoMcastFdbCap OBJECT-TYPE  
      SYNTAX              Unsigned32(0..65535)  
      UNITS               "entries"  
      MAX-ACCESS          read-only  
      STATUS              current  
      DESCRIPTION  
         "Number of entries supported in the Multicast Forwarding table."  
      ::= { ibSmSwitchInfoEntry 5 }  
    
   ibSmSwitchInfoLinearFdbTop OBJECT-TYPE  
      SYNTAX              Unsigned32(0..65535) 
      MAX-ACCESS          read-write  
      STATUS              current  
      DESCRIPTION  
         "Indicates the top of the linear forwarding table.  Packets  
         received with unicast DLIDs greater than this value are discarded  
         by the switch.  This component applies only to switches that  
         implement linear forwarding tables and is ignored by switches  
         that implement random forwarding tables."  
      ::= { ibSmSwitchInfoEntry 6 }  
    
   ibSmSwitchInfoDefaultPort OBJECT-TYPE  
      SYNTAX              Unsigned32(0..255)  
      MAX-ACCESS          read-write  
      STATUS              current  
      DESCRIPTION  
         "Forward to this port all the unicast packets from the other  
         ports whose DLID does not exist in the random forwarding table."  
      ::= { ibSmSwitchInfoEntry 7 }  
    
   ibSmSwitchInfoDefPriMcastPort     OBJECT-TYPE  
      SYNTAX                      Unsigned32(0..255)  
      MAX-ACCESS                  read-write  
      STATUS                      current  
      DESCRIPTION  
         "Forward to this port all the multicast packets from the other  
         ports whose DLID does not exist in the forwarding table."  
      ::= { ibSmSwitchInfoEntry 8 }  
    
   ibSmSwitchInfoDefNonPriMcastPort  OBJECT-TYPE  
      SYNTAX                      Unsigned32(0..255)  
      MAX-ACCESS                  read-write  
      STATUS                      current  
      DESCRIPTION  
 
 
 
 
         "Forward to this port all the multicast packets from the  
         smDefPriMcastPort port whose DLID does not exist in the  
         forwarding table."  
      ::= { ibSmSwitchInfoEntry 9 }  
    
   ibSmSwitchInfoLifeTimeValue       OBJECT-TYPE  
      SYNTAX                      Unsigned32(0..31)  
      MAX-ACCESS                  read-write  
      STATUS                      current  
      DESCRIPTION  
         "The time a packet can live in the switch."  
      ::= { ibSmSwitchInfoEntry 10 }  
    
   ibSmSwitchInfoPortStateChange   OBJECT-TYPE  
      SYNTAX                      Unsigned32(0..1) 
      MAX-ACCESS                  read-only  
      STATUS                      current  
      DESCRIPTION  
         "It is set to PortInTransition(1) anytime the PortState component  
         in the PortInfo of any ports transition from Down to Initialize,  
         Initialize to Down, Armed to Down, or Active to Down as a result  
         of link state machine logic: 
         0: portNotInTransition; 1: portInTransition."  
      ::= { ibSmSwitchInfoEntry 11 }  
    
   ibSmSwitchInfoLIDsPerPort  OBJECT-TYPE  
      SYNTAX              Unsigned32(0..65535) 
      MAX-ACCESS          read-only  
      STATUS              current  
      DESCRIPTION  
         "Number of LID/LMC combinations that may be assigned to a given  
         external port for switches that support the random forwarding  
         table."  
      ::= { ibSmSwitchInfoEntry 12 }  
    
   ibSmSwitchInfoPartitionEnfCap     OBJECT-TYPE  
      SYNTAX                      Unsigned32(0..65535)  
      MAX-ACCESS                  read-only  
      STATUS                      current  
      DESCRIPTION  
         "The number of entries in this partition enforcement table per  
         physical port.  Zero indicates that partition enforcement is not  
         supported by the switch"  
      ::= { ibSmSwitchInfoEntry 13 }  
    
   ibSmSwitchInfoInEnfCap    OBJECT-TYPE  
      SYNTAX              TruthValue  
      MAX-ACCESS          read-only  
      STATUS              current  
 
 
 
 
      DESCRIPTION  
         "Indicates switch is capable of partition enforcement on received  
         packets."  
      ::= { ibSmSwitchInfoEntry 14 }  
    
   ibSmSwitchInfoOutEnfCap   OBJECT-TYPE  
      SYNTAX              TruthValue  
      MAX-ACCESS          read-only  
      STATUS              current  
      DESCRIPTION  
         "Indicates switch is capable of partition enforcement on  
         transmitted packets."  
      ::= { ibSmSwitchInfoEntry 15 }  
    
   ibSmSwitchInfoInFilterRawPktCap   OBJECT-TYPE  
      SYNTAX                      TruthValue  
      MAX-ACCESS                  read-only  
      STATUS                      current  
      DESCRIPTION  
         "Indicates switch is capable of raw packet enforcement on  
         received packets."  
      ::= { ibSmSwitchInfoEntry 16 }  
    
   ibSmSwitchInfoOutFilterRawPktCap  OBJECT-TYPE  
      SYNTAX                      TruthValue  
      MAX-ACCESS                  read-only  
      STATUS                      current  
      DESCRIPTION  
         "Indicates switch is capable of raw packet enforcement on  
         transmitted packets."  
      ::= { ibSmSwitchInfoEntry 17 }  
    
   ibSmSwitchInfoEnhanced0        OBJECT-TYPE  
      SYNTAX                      TruthValue  
      MAX-ACCESS                  read-only  
      STATUS                      current  
      DESCRIPTION  
         "Indicates whether switch port 0 supports enhanced functions."  
      ::= { ibSmSwitchInfoEntry 18 }  
    
   -- Subnet Manager Network Partition table  
    
   ibSmPartitionTable OBJECT-TYPE  
      SYNTAX              SEQUENCE OF IbSmPartitionEntry  
      MAX-ACCESS          not-accessible  
      STATUS              current  
      DESCRIPTION  
         "A table used to list all partitions that are managed by the  
         Subnet Managers on this device."  
 
 
 
 
      ::= { ibSmPartitionInfo 1 }  
    
   ibSmPartitionEntry OBJECT-TYPE  
      SYNTAX              IbSmPartitionEntry  
      MAX-ACCESS          not-accessible  
      STATUS              current  
      DESCRIPTION  
         "Table entry for ibSmPartitionTable."  
      INDEX { ibSmPartitionSubnetPrefix, ibSmPartitionKey,  
            ibSmPartitionVectorIndex }  
      ::= { ibSmPartitionTable 1 }  
    
   IbSmPartitionEntry ::= SEQUENCE {   
      ibSmPartitionSubnetPrefix     IbSmSubnetPrefix,  
      ibSmPartitionKey              IbPartitionKey, 
      ibSmPartitionVectorIndex      Integer32,  
      ibSmPartitionVector           OCTET STRING,  
      ibSmPartitionVectorSize       Integer32,  
      ibSmPartitionVectorElementSize Integer32,  
      ibSmPartitionLastChange       TimeTicks  
      }  
    
   ibSmPartitionSubnetPrefix  OBJECT-TYPE  
      SYNTAX                  IbSmSubnetPrefix  
      MAX-ACCESS              not-accessible  
      STATUS                  current  
      DESCRIPTION  
         "Subnet prefix of this IB subnet."  
      ::= { ibSmPartitionEntry 1 }  
    
   ibSmPartitionKey        OBJECT-TYPE  
      SYNTAX              IbPartitionKey 
      MAX-ACCESS          not-accessible  
      STATUS              current  
      DESCRIPTION  
         "The 16-bit P-Key of this Partition entry."  
      ::= { ibSmPartitionEntry 2 }  
    
   ibSmPartitionVectorIndex   OBJECT-TYPE  
      SYNTAX                  Integer32 (0..2147483647) 
      MAX-ACCESS              not-accessible  
      STATUS                  current  
      DESCRIPTION  
         "An index indentifying a particular vector of the partition  
         table." 
      ::= { ibSmPartitionEntry 3 }  
    
   ibSmPartitionVector        OBJECT-TYPE  
      SYNTAX               OCTET STRING (SIZE(0..255))  
 
 
 
 
      MAX-ACCESS           read-only  
      STATUS               current  
      DESCRIPTION  
         "A vector containing a portion of the partition table.  To 
         retrieve the entire table, the user must perform consecutive 
         GET operations to read one vector at a time." 
      ::= { ibSmPartitionEntry 4 }  
    
   ibSmPartitionVectorSize     OBJECT-TYPE  
      SYNTAX                  Integer32 
      MAX-ACCESS              read-only  
      STATUS                  current  
      DESCRIPTION  
         "Indicates the size (in bytes) of the current vector."  
      ::= { ibSmPartitionEntry 5 }  
    
   ibSmPartitionVectorElementSize OBJECT-TYPE  
      SYNTAX                     Integer32 
      MAX-ACCESS                    read-only  
      STATUS                        current  
      DESCRIPTION  
         "Indicates the size (in bytes) of each element in the vector. 
         Each GET operation on the 'ibSmPartitionVector' variable will 
         return zero or more elements.  Each element is ten(10) bytes  
         long.  This is how the ten bytes are coded (in network byte  
         order): 
    
         byte  description 
         ----  ----------- 
         1-8   Node-GUID of the member 
         9     Port number (0..255) 
         10    Partition type (1=full-membership, 2=limited-membership) 
    
         The number of elements in 'ibSmPartitionVector' can be 
         calculated by dividing 'ibSmPartitionVectorSize' by 
         'ibSmPartitionVectorElementSize'." 
      ::= { ibSmPartitionEntry 6 }  
    
   ibSmPartitionLastChange    OBJECT-TYPE  
      SYNTAX                        TimeTicks 
      MAX-ACCESS                    read-only  
      STATUS                        current  
      DESCRIPTION  
         "Indicates the time stamp when the partition table was last  
         changed.  To verify the entire partition table was read without  
         any changes to the table in between GET operations, the user  
         can do a comparion on this time stamp." 
      ::= { ibSmPartitionEntry 7 }  
    
 
 
 
 
   -- Subnet Manager Network Partition Configuration Group  
    
   ibSmPartitionConfig  OBJECT IDENTIFIER ::= { ibSmPartitionInfo 2 } 
    
   -- The ibSmPartitionConfigSubnetPrefix, ibSmPartitionConfigKey and  
   -- ibSmPartitionConfigAction are mandatory for all configuration    operations.   
   -- 
   -- The ibSmPartitionConfigMemberNodeGUID,  ibSmPartitionConfigMemberPortNum  
   -- and ibSmPartitionConfigMemberType are required depending on the specific  
   -- configuration operations (see below for details). 
   -- 
   -- This group can be used to perform the following operations : 
   -- 
   -- (1) Create a new partition or delete an existing partition. 
   -- 
   -- (2) Add a port or ports to a partition. 
   --     The ibSmPartitionConfigMemberNodeGUID, and  
   --     ibSmPartitionConfigMemberType are required.  
   --     The ibSmPartitionConfigMemberPortNum is optional.   
   --     If the ibSmPartitionConfigMemberPortNum is not specified,  
   --     all ports on IB device will be added to the partition. 
   --     If ibSmPartitionConfigMemberPortNum is specified, only  
   --     the specified port is added to the partition. 
   -- 
   -- (3) Remove a port or ports from a partition. 
   --     The ibSmPartitionConfigMemberNodeGUID is required.  
   --     The ibSmPartitionConfigMemberPortNum is optional.   
   --     If the ibSmPartitionConfigMemberPortNum is not  
   --     specified, all ports on IB device will be removed from the partition. 
   --     If ibSmPartitionConfigMemberPortNum is specified,  
   --     only the specified port is removed from the partition. 
   --  
   -- (4) Update the membership type for a particular member.  
   --     The ibSmPartitionConfigMemberNodeGUID,  
   --     ibSmPartitionConfigMemberPortNum and    ibSmPartitionConfigMemberType  
   --     are mandatory.  
   -- 
   -- Each operation must be performed within one single SNMP set operation, 
   -- to ensure data integrity.  If any of required fields is missing,  
   -- the agent must reject the request. 
    
   ibSmPartitionConfigSubnetPrefix  OBJECT-TYPE  
      SYNTAX                     IbSmSubnetPrefix  
      MAX-ACCESS                 read-write  
      STATUS                     current  
 
 
 
 
      DESCRIPTION  
         "Subnet prefix of an IB subnet."  
      ::= { ibSmPartitionConfig 1 }  
    
   ibSmPartitionConfigKey     OBJECT-TYPE  
      SYNTAX               IbPartitionKey 
      MAX-ACCESS           read-write  
      STATUS               current  
      DESCRIPTION  
         "The 16-bit P-Key of an IB partition."  
      ::= { ibSmPartitionConfig 2 }  
    
   ibSmPartitionConfigAction  OBJECT-TYPE  
      SYNTAX                  INTEGER { 
                               none(1), 
                               createPartition(2), 
                               deletePartition(3), 
                               addMember(4), 
                               removeMember(5), 
                               updateMemberType(6) 
                               }  
       MAX-ACCESS             read-write  
      STATUS                  current  
      DESCRIPTION  
         "Used to specify an action to perform on a specified 
         IB Subnet Partition." 
      DEFVAL         { none } 
      ::= { ibSmPartitionConfig 3 }  
    
   ibSmPartitionConfigMemberNodeGUID OBJECT-TYPE  
      SYNTAX                  IbGuid 
      MAX-ACCESS              read-write  
      STATUS                  current  
      DESCRIPTION  
         "Used to specify the Node GUID of a member."  
      ::= { ibSmPartitionConfig 4 }  
    
   ibSmPartitionConfigMemberPortNum OBJECT-TYPE  
      SYNTAX                  IbDataPort 
      MAX-ACCESS              read-write  
      STATUS                  current  
      DESCRIPTION  
         "Used to specify the local port number of a member."  
      ::= { ibSmPartitionConfig 5 }  
    
   ibSmPartitionConfigMemberType OBJECT-TYPE  
      SYNTAX                  INTEGER { 
                  fullMembership(1), 
                  limitedMembership(2)  
 
 
 
 
                  } 
      MAX-ACCESS              read-write  
      STATUS                  current  
      DESCRIPTION  
         "Used to specify the type of membership of a member."  
      ::= { ibSmPartitionConfig 6 }  
        
   -- Subnet Manager Multicast group table  
    
   ibSmMcastGroupTable   OBJECT-TYPE  
      SYNTAX              SEQUENCE OF IbSmMcastGroupEntry  
      MAX-ACCESS          not-accessible  
      STATUS              current  
      DESCRIPTION  
         "A table used to list all multicast groups actively managed by  
         the Subnet Managers on this device."  
      ::= { ibSmMcastInfo 1 }  
    
   ibSmMcastGroupEntry   OBJECT-TYPE  
      SYNTAX              IbSmMcastGroupEntry  
      MAX-ACCESS          not-accessible  
      STATUS              current  
      DESCRIPTION  
         "Table entry for ibSmMcastGroupTable."  
      INDEX        { ibSmMcastGroupSubnetPrefix, ibSmMcastGroupMGID }  
      ::= { ibSmMcastGroupTable 1 }  
    
   IbSmMcastGroupEntry ::= SEQUENCE {   
      ibSmMcastGroupSubnetPrefix    IbSmSubnetPrefix, 
      ibSmMcastGroupMGID         OCTET STRING,  
      ibSmMcastGroupQKey         OCTET STRING,  
      ibSmMcastGroupMLID         IbMulticastLid,  
      ibSmMcastGroupMTU             IbMtu, 
      ibSmMcastGroupTClass          Unsigned32,  
      ibSmMcastGroupPKey         IbPartitionKey, 
      ibSmMcastGroupRate         Unsigned32,  
      ibSmMcastGroupPacketLifeTime  Unsigned32,  
      ibSmMcastGroupSL              Unsigned32,  
      ibSmMcastGroupFlowLabel       OCTET STRING,  
      ibSmMcastGroupHopLimit        Unsigned32,  
      ibSmMcastGroupScope           Unsigned32 
      }  
    
   ibSmMcastGroupSubnetPrefix OBJECT-TYPE 
      SYNTAX              IbSmSubnetPrefix 
      MAX-ACCESS          not-accessible 
      STATUS              current 
      DESCRIPTION 
         "Subnet prefix of this IB subnet." 
 
 
 
 
      ::= { ibSmMcastGroupEntry 1 }  
    
   ibSmMcastGroupMGID    OBJECT-TYPE  
      SYNTAX              OCTET STRING (SIZE(16))  
      MAX-ACCESS          not-accessible  
      STATUS              current  
      DESCRIPTION  
         "The 128-bit multicast GID address for this multicast group."  
      ::= { ibSmMcastGroupEntry 2 }  
    
   ibSmMcastGroupQKey    OBJECT-TYPE  
      SYNTAX              OCTET STRING (SIZE(4))  
      MAX-ACCESS          read-only  
      STATUS              current  
      DESCRIPTION  
         "The 16-bit Q-Key of this multicast group."  
      ::= { ibSmMcastGroupEntry 3 }  
    
   ibSmMcastGroupMLID    OBJECT-TYPE  
      SYNTAX              IbMulticastLid 
      MAX-ACCESS          read-only  
      STATUS              current  
      DESCRIPTION  
         "The 16-bit LID of this multicast group."  
      ::= { ibSmMcastGroupEntry 4 }  
    
   ibSmMcastGroupMTU    OBJECT-TYPE  
      SYNTAX            IbMtu 
      UNITS             "bytes" 
      MAX-ACCESS        read-only  
      STATUS            current  
      DESCRIPTION  
         "The MTU of this multicast group: 
         1: 256; 2: 512; 3: 1024; 4: 2048; 5: 4096" 
      ::= { ibSmMcastGroupEntry 5 }  
    
   ibSmMcastGroupTClass  OBJECT-TYPE  
      SYNTAX              Unsigned32(0..255) 
      MAX-ACCESS          read-only  
      STATUS              current  
      DESCRIPTION  
         "The Tclass to be used in the GRH if GRH is used."  
      ::= { ibSmMcastGroupEntry 6 }  
    
   ibSmMcastGroupPKey    OBJECT-TYPE  
      SYNTAX              IbPartitionKey 
      MAX-ACCESS          read-only  
      STATUS              current  
      DESCRIPTION  
 
 
 
 
         "The 16-bit Partition Key for this multicast group."  
      ::= { ibSmMcastGroupEntry 7 }  
    
   ibSmMcastGroupRate OBJECT-TYPE  
      SYNTAX              Unsigned32(0..63) 
      MAX-ACCESS          read-only  
      STATUS              current  
      DESCRIPTION  
         "Traffic rate of this multicast group: 
         2: 2.5 Gb/sec; 3: 10 Gb/sec; 4: 30 Gb/sec; 0, 1, 5-63: reserved." 
      ::= { ibSmMcastGroupEntry 8 }  
    
   ibSmMcastGroupPacketLifeTime OBJECT-TYPE  
      SYNTAX              Unsigned32(0..63) 
      MAX-ACCESS          read-only  
      STATUS              current  
      DESCRIPTION  
         "Packet life time of this multicast group."  
      ::= { ibSmMcastGroupEntry 9 }  
    
   ibSmMcastGroupSL      OBJECT-TYPE  
      SYNTAX              Unsigned32(0..15) 
      MAX-ACCESS          read-only  
      STATUS              current  
      DESCRIPTION  
         "Service level of this multicast group."  
      ::= { ibSmMcastGroupEntry 11 }  
    
   ibSmMcastGroupFlowLabel OBJECT-TYPE  
      SYNTAX              OCTET STRING (SIZE(3))  
      MAX-ACCESS          read-only  
      STATUS              current  
      DESCRIPTION  
         "Flow label to be used on this multicast group if GRH Is used."  
      ::= { ibSmMcastGroupEntry 12 }  
    
   ibSmMcastGroupHopLimit OBJECT-TYPE  
      SYNTAX              Unsigned32(0..255)  
      MAX-ACCESS          read-only  
      STATUS              current  
      DESCRIPTION  
         "Hop limit to be used on this multicast group if GRH Is used."  
      ::= { ibSmMcastGroupEntry 13 }  
    
   ibSmMcastGroupScope   OBJECT-TYPE  
      SYNTAX              Unsigned32(0..15) 
      MAX-ACCESS          read-only  
      STATUS              current  
      DESCRIPTION  
 
 
 
 
         "Scope of this multicast group: 
         2: link local; 5: site local; 8: organization local; 14: global;  
         other values reserved."  
      ::= { ibSmMcastGroupEntry 14 }  
    
   -- Subnet Manager Multicast Member table  
    
   ibSmMcastMemberTable OBJECT-TYPE  
      SYNTAX              SEQUENCE OF IbSmMcastMemberEntry  
      MAX-ACCESS          not-accessible  
      STATUS              current  
      DESCRIPTION  
         "A table used to list all members of multicast groups managed  
         by the Subnet Managers on this device."  
      ::= { ibSmMcastInfo 2 }  
    
   ibSmMcastMemberEntry OBJECT-TYPE  
      SYNTAX              IbSmMcastMemberEntry  
      MAX-ACCESS          not-accessible  
      STATUS              current  
      DESCRIPTION  
         "Table entry for ibSmMcastMemberTable."  
      INDEX { ibSmMcastMemberSubnetPrefix, ibSmMcastMemberMGID,  
               ibSmMcastMemberVectorIndex }  
      ::= { ibSmMcastMemberTable 1 }  
    
   IbSmMcastMemberEntry ::= SEQUENCE {   
      ibSmMcastMemberSubnetPrefix      IbSmSubnetPrefix,  
      ibSmMcastMemberMGID              OCTET STRING,  
      ibSmMcastMemberVectorIndex       Integer32,  
      ibSmMcastMemberVector            OCTET STRING,  
      ibSmMcastMemberVectorSize        Integer32,  
      ibSmMcastMemberVectorElementSize Integer32,  
      ibSmMcastMemberLastChange        TimeTicks  
   }  
    
   ibSmMcastMemberSubnetPrefix   OBJECT-TYPE  
      SYNTAX                  IbSmSubnetPrefix  
      MAX-ACCESS              not-accessible  
      STATUS                  current  
      DESCRIPTION  
         "Subnet prefix of this IB subnet."  
      ::= { ibSmMcastMemberEntry 1 }  
    
   ibSmMcastMemberMGID        OBJECT-TYPE  
      SYNTAX                  OCTET STRING (SIZE(16))  
      MAX-ACCESS              not-accessible  
      STATUS                  current  
      DESCRIPTION  
 
 
 
 
         "The 128-bit multicast GID address for this multicast group." 
      ::= { ibSmMcastMemberEntry 2 }  
    
   ibSmMcastMemberVectorIndex    OBJECT-TYPE  
      SYNTAX                        Integer32 (0..2147483647) 
      MAX-ACCESS                    not-accessible  
      STATUS                        current  
      DESCRIPTION  
         "An index indentifying a particular vector of the multicast member  
         table." 
      ::= { ibSmMcastMemberEntry 3 }  
    
   ibSmMcastMemberVector      OBJECT-TYPE  
      SYNTAX                  OCTET STRING (SIZE(0..255))  
      MAX-ACCESS              read-only  
      STATUS                  current  
      DESCRIPTION  
         "A vector containing a portion of the multicast member table.  To 
         retrieve the entire table, the user must perform consecutive 
         GET operations to read one vector at a time." 
      ::= { ibSmMcastMemberEntry 4 }  
    
   ibSmMcastMemberVectorSize     OBJECT-TYPE  
      SYNTAX                        Integer32 
      MAX-ACCESS                    read-only  
      STATUS                        current  
      DESCRIPTION  
         "Indicates the size (in bytes) of the current vector."  
      ::= { ibSmMcastMemberEntry 5 }  
    
   ibSmMcastMemberVectorElementSize OBJECT-TYPE  
      SYNTAX                        Integer32 
      MAX-ACCESS                    read-only  
      STATUS                        current  
      DESCRIPTION  
         "Indicates the size (in bytes) of each element in the vector. 
         Each GET operation on the 'ibSmMcastMemberVector' variable will 
         return zero or more elements.  Each element is eighteen(18) bytes  
         long.  This is how the eighteen bytes are coded (in network byte  
         order): 
    
         byte  description 
         ----  ----------- 
         1-16   Member port GID 
         17     Member join state (bitmask  bit 0=fullMember, 
                                            bit 1=nonMember, 
                                              bit 2=sendOnlyMember) 
           18     Member proxy join status (1=true, 2=false) 
    
 
 
 
 
         The number of elements in 'ibSmMcastMemberVector' can be 
         calculated by dividing 'ibSmMcastMemberVectorSize' by 
         'ibSmMcastMemberVectorElementSize'." 
      ::= { ibSmMcastMemberEntry 6 }  
    
   ibSmMcastMemberLastChange     OBJECT-TYPE  
      SYNTAX                        TimeTicks 
      MAX-ACCESS                    read-only  
      STATUS                        current  
      DESCRIPTION  
         "Indicates the time stamp when the multicast member table was last  
         changed.  To verify the entire table was read without any changes  
         to the table in between GET operations, the user can do a comparison  
         on this time stamp." 
      ::= { ibSmMcastMemberEntry 7 }  
    
   -- Subnet Manager Information table  
    
    
   ibSmSMInfoTable         OBJECT-TYPE  
      SYNTAX              SEQUENCE OF IbSmSMInfoEntry  
      MAX-ACCESS          not-accessible  
      STATUS              current  
      DESCRIPTION  
         "A table used to list other Subnet Managers that are on the same  
         IB subnet as the Subnet Managers on this device."  
      ::= { ibSmSMInfo 1 }  
    
   ibSmSMInfoEntry         OBJECT-TYPE  
      SYNTAX              IbSmSMInfoEntry  
      MAX-ACCESS          not-accessible  
      STATUS              current  
      DESCRIPTION  
         "Table entry for ibSmSMInfoTable."  
      INDEX        { ibSmSMInfoSubnetPrefix, ibSmSMInfoGUID }  
      ::= { ibSmSMInfoTable 1 }  
    
   IbSmSMInfoEntry ::= SEQUENCE { 
      ibSmSMInfoSubnetPrefix    IbSmSubnetPrefix,  
      ibSmSMInfoGUID            IbGuid, 
      ibSmSMInfoSMKey           OCTET STRING,  
      ibSmSMInfoActCount        Counter32,  
      ibSmSMInfoPriority        Unsigned32,  
      ibSmSMInfoSMState         IbSmState 
   }  
    
   ibSmSMInfoSubnetPrefix OBJECT-TYPE  
      SYNTAX              IbSmSubnetPrefix  
      MAX-ACCESS          not-accessible  
 
 
 
 
      STATUS              current  
      DESCRIPTION  
         "Subnet prefix of this IB subnet."  
      ::= { ibSmSMInfoEntry 1 }  
    
   ibSmSMInfoGUID          OBJECT-TYPE  
      SYNTAX              IbGuid 
      MAX-ACCESS          not-accessible  
      STATUS              current  
      DESCRIPTION  
         "PortGUID of the port where the SM resides." 
      ::= { ibSmSMInfoEntry 2 }  
    
   ibSmSMInfoSMKey         OBJECT-TYPE  
      SYNTAX              OCTET STRING (SIZE(8))  
      MAX-ACCESS          read-only  
      STATUS              current  
      DESCRIPTION  
           "Subnet management Key of this subnet manager."  
      ::= { ibSmSMInfoEntry 3 }  
    
   ibSmSMInfoActCount      OBJECT-TYPE  
      SYNTAX              Counter32  
      MAX-ACCESS          read-only  
      STATUS              current  
      DESCRIPTION  
           "Activity counter of this subnet manager.  The counter  
           increments each time the SM issues an SMP or perform other  
           management activities."  
      ::= { ibSmSMInfoEntry 4 }  
    
   ibSmSMInfoPriority      OBJECT-TYPE  
      SYNTAX              Unsigned32(0..15) 
      MAX-ACCESS          read-only  
      STATUS              current  
      DESCRIPTION  
           "The Priority of this Subnet Manager."  
      ::= { ibSmSMInfoEntry 5 }  
    
   ibSmSMInfoSMState       OBJECT-TYPE  
      SYNTAX              IbSmState 
      MAX-ACCESS          read-only  
      STATUS              current  
      DESCRIPTION  
         "The state of this Subnet Manager: 
         0: not active; 1: discovering; 2: standby; 3: master" 
      ::= { ibSmSMInfoEntry 6 }  
    
   -- Physical Link Table 
 
 
 
 
    
   ibSmLinkTable   OBJECT-TYPE  
      SYNTAX              SEQUENCE OF IbSmLinkEntry  
      MAX-ACCESS          not-accessible  
      STATUS              current  
      DESCRIPTION  
         "A table used to list physical link topology of the subnet." 
      ::= { ibSmLinkInfo 1 }  
    
   ibSmLinkEntry   OBJECT-TYPE  
      SYNTAX              IbSmLinkEntry  
      MAX-ACCESS          not-accessible  
      STATUS              current  
      DESCRIPTION  
         "Table entry for ibSmLinkTable."  
      INDEX { ibSmLinkSubnetPrefix, ibSmLinkFromNodeGUID, 
              ibSmLinkFromPortNum} 
      ::= { ibSmLinkTable 1 }  
    
   IbSmLinkEntry ::= SEQUENCE {   
      ibSmLinkSubnetPrefix    IbSmSubnetPrefix, 
      ibSmLinkFromNodeGUID    IbGuid, 
      ibSmLinkFromPortNum     IbDataPort, 
      ibSmLinkToNodeGUID   IbGuid, 
      ibSmLinkToPortNum       IbDataPort 
   }  
    
   ibSmLinkSubnetPrefix OBJECT-TYPE 
      SYNTAX              IbSmSubnetPrefix 
      MAX-ACCESS          not-accessible 
      STATUS              current 
      DESCRIPTION 
         "Subnet prefix of this IB subnet." 
      ::= { ibSmLinkEntry 1 }  
    
   ibSmLinkFromNodeGUID OBJECT-TYPE  
      SYNTAX              IbGuid 
      MAX-ACCESS          not-accessible  
      STATUS              current  
      DESCRIPTION  
         "From Node GUID"  
      ::= { ibSmLinkEntry 2 }  
    
   ibSmLinkFromPortNum        OBJECT-TYPE  
      SYNTAX            IbDataPort 
      MAX-ACCESS          not-accessible  
      STATUS              current  
      DESCRIPTION  
         "From Port Number"  
 
 
 
 
      ::= { ibSmLinkEntry 3 }  
    
   ibSmLinkToNodeGUID    OBJECT-TYPE  
      SYNTAX              IbGuid 
      MAX-ACCESS          read-only  
      STATUS              current  
      DESCRIPTION  
         "To Node GUID"  
      ::= { ibSmLinkEntry 4 }  
    
   ibSmLinkToPortNum  OBJECT-TYPE  
      SYNTAX              IbDataPort 
      MAX-ACCESS          read-only  
      STATUS              current  
      DESCRIPTION  
         "To Port Number" 
      ::= { ibSmLinkEntry 5 }  
    
   -- Subnet Manager Path Tables  
   -- 
   -- In order to query IB PathRecords, management client should 
   -- create a row in ibSmPathReqTable, with the proper values of:  
   -- ibSmPathReqSubnetPrefix, ibSmPathReqSessionId, ibSmPathReqRowStatus 
   -- ibSmPathReqRowCompMask, and other relevant PathRecord attribute  
   -- values. 
   -- 
   -- ibSmPathReqSessionId is a positive pseudo-random 32-bit integer  
   -- generated by the client.  This number should be based on per request,  
   -- and should not be reused by the client.  Before the client creates  
   -- the row, it should try to do a GET operation to ensure the number is 
   -- not being used currently.  If it detects a conflict, the client should  
   -- re-generate another random value and try again.  When a row is  
   -- successfully created in ibSmPathReqTable, that means a request of the  
   -- path has been issued. 
   -- 
   -- ibSmPathResultTable is used to retrieve the query results.  The client  
   -- should use the same value of ibSmPathReqSessionId as  
   -- ibSmPathResultSessionId to retrieve the results. 
   -- 
   -- The management application should delete the row it created from  
   -- ibSmPathReqTable after it finishes retrieving the results.   
   -- This will effectively remove the results from ibSmPathResultTable.   
   -- It is suggested that the MIB agent remove the row after a timeout  
   -- period, to avoid resource leak. 
    
    
   ibSmPathReqTable         OBJECT-TYPE  
      SYNTAX              SEQUENCE OF IbSmPathReqEntry  
      MAX-ACCESS          not-accessible  
 
 
 
 
      STATUS              current  
      DESCRIPTION 
         "A table used to list all the path entries that satisfy the  
         multi path request."  
      ::= { ibSmPathInfo 1 }  
    
   ibSmPathReqEntry         OBJECT-TYPE  
      SYNTAX              IbSmPathReqEntry  
      MAX-ACCESS          not-accessible  
      STATUS              current  
      DESCRIPTION  
         "Table entry for ibSmPathReqTable."  
      INDEX        { ibSmPathReqSubnetPrefix, ibSmPathReqSessionId } 
    
      ::= { ibSmPathReqTable 1 }  
    
   IbSmPathReqEntry ::= SEQUENCE { 
      ibSmPathReqSubnetPrefix      IbSmSubnetPrefix, 
      ibSmPathReqSessionId         Integer32, 
      ibSmPathReqRowStatus         RowStatus,   
      ibSmPathReqCreationTime      TimeTicks, 
      ibSmPathReqRowCompMask       OCTET STRING, 
      ibSmPathReqDstGID            OCTET STRING,  
      ibSmPathReqSrcGID            OCTET STRING,  
      ibSmPathReqNumbPath          Unsigned32, 
      ibSmPathReqDstLID            Unsigned32, 
      ibSmPathReqSrcLID            Unsigned32, 
      ibSmPathReqRawTraffic     Unsigned32,  
      ibSmPathReqFlowLabel         OCTET STRING,  
      ibSmPathReqHopLimit          Unsigned32,  
      ibSmPathReqTClass            Unsigned32,  
      ibSmPathReqPKey              IbPartitionKey, 
      ibSmPathReqSL                Unsigned32,  
      ibSmPathReqMTUSel            INTEGER, 
      ibSmPathReqMTU               IbMtu, 
      ibSmPathReqRateSel           INTEGER, 
      ibSmPathReqRate              Unsigned32,  
      ibSmPathReqPktLifeTimeSel    INTEGER, 
      ibSmPathReqPktLifeTime       Unsigned32, 
      ibSmPathReqPreference        Unsigned32 
   }  
   ibSmPathReqSubnetPrefix  OBJECT-TYPE  
       SYNTAX              IbSmSubnetPrefix  
       MAX-ACCESS          not-accessible  
       STATUS              current  
       DESCRIPTION  
           "Subnet prefix of this IB subnet."  
       ::= { ibSmPathReqEntry 1 }  
    
 
 
 
 
   ibSmPathReqSessionId OBJECT-TYPE          
      SYNTAX         Integer32(0..2147483647) 
      MAX-ACCESS     not-accessible 
      STATUS         current 
      DESCRIPTION 
         "pseudo-random 32 bit number provided by the client." 
      ::= { ibSmPathReqEntry 2 } 
    
   ibSmPathReqRowStatus OBJECT-TYPE 
      SYNTAX            RowStatus 
      MAX-ACCESS        read-create 
      STATUS            current 
      DESCRIPTION 
         "RowStatus for row creation/deletion." 
      ::= { ibSmPathReqEntry 3 } 
    
   ibSmPathReqCreationTime OBJECT-TYPE 
      SYNTAX   TimeTicks 
      MAX-ACCESS  read-only 
      STATUS   current 
      DESCRIPTION 
         "Time stamp when this row is created." 
      ::= { ibSmPathReqEntry 4 } 
    
   ibSmPathReqRowCompMask  OBJECT-TYPE 
      SYNTAX OCTET STRING(SIZE(8)) 
      MAX-ACCESS read-create 
      STATUS current 
      DESCRIPTION 
         "64-bit Component Mask for the request." 
      ::= { ibSmPathReqEntry 5 } 
    
   ibSmPathReqDstGID         OBJECT-TYPE  
      SYNTAX              OCTET STRING (SIZE(16))  
      MAX-ACCESS          read-create  
      STATUS              current  
      DESCRIPTION  
         "The 128-bit destination GID of this path entry."  
      ::= { ibSmPathReqEntry 6 }  
    
   ibSmPathReqSrcGID         OBJECT-TYPE  
      SYNTAX              OCTET STRING (SIZE(16))  
      MAX-ACCESS          read-create  
      STATUS              current  
      DESCRIPTION  
         "The 128-bit source GID of this path entry."  
      ::= { ibSmPathReqEntry 7 }  
    
   ibSmPathReqNumbPath OBJECT-TYPE  
 
 
 
 
      SYNTAX              Unsigned32(0..127) 
      MAX-ACCESS          read-create  
      STATUS              current  
      DESCRIPTION  
         "Number of path between this source and destination GID pair."  
      ::= { ibSmPathReqEntry 8 }  
    
   ibSmPathReqDstLID         OBJECT-TYPE  
      SYNTAX              Unsigned32(1..65535) 
      MAX-ACCESS          read-create  
      STATUS              current  
      DESCRIPTION  
         "A 16-bit destination LID."  
      ::= { ibSmPathReqEntry 9 }  
    
   ibSmPathReqSrcLID         OBJECT-TYPE  
      SYNTAX              Unsigned32(1..65535) 
      MAX-ACCESS          read-create  
      STATUS              current  
      DESCRIPTION  
         "A 16-bit source LID."  
      ::= { ibSmPathReqEntry 10 }  
    
   ibSmPathReqRawTraffic   OBJECT-TYPE  
      SYNTAX              Unsigned32(0..1) 
      MAX-ACCESS          read-create  
      STATUS              current  
      DESCRIPTION  
         "The type of traffic that is on this path:                    
         0: IB Packet; 1: Raw Packet." 
      ::= { ibSmPathReqEntry 11 }  
    
   ibSmPathReqFlowLabel     OBJECT-TYPE  
      SYNTAX              OCTET STRING (SIZE(3))  
      MAX-ACCESS          read-create  
      STATUS              current  
      DESCRIPTION  
         "Flow label used on this path if GRH is used."  
      ::= { ibSmPathReqEntry 12 }  
    
   ibSmPathReqHopLimit      OBJECT-TYPE  
      SYNTAX              Unsigned32(0..255)  
      MAX-ACCESS          read-create  
      STATUS              current  
      DESCRIPTION  
         "Hop limit used on this path if GRH is used."  
      ::= { ibSmPathReqEntry 13 }  
    
   ibSmPathReqTClass         OBJECT-TYPE  
 
 
 
 
      SYNTAX              Unsigned32(0..255) 
      MAX-ACCESS          read-create  
      STATUS              current  
      DESCRIPTION  
         "TClass used on this path if GRH is used."  
      ::= { ibSmPathReqEntry 14 }  
    
   ibSmPathReqPKey          OBJECT-TYPE  
      SYNTAX              IbPartitionKey 
      MAX-ACCESS          read-create  
      STATUS              current  
      DESCRIPTION  
         "The 16-bit P-Key used on this path."  
      ::= { ibSmPathReqEntry 15 }  
    
   ibSmPathReqSL            OBJECT-TYPE  
      SYNTAX              Unsigned32(0..15)  
      MAX-ACCESS          read-create  
      STATUS              current  
      DESCRIPTION  
         "Service level used on this path."  
      ::= { ibSmPathReqEntry 16 }  
    
   ibSmPathReqMTUSel         OBJECT-TYPE  
      SYNTAX              INTEGER{ 
                          greater(0), 
                          less(1), 
                          exact(2), 
                          largestAvailable(3)} 
      MAX-ACCESS          read-create  
      STATUS              current  
      DESCRIPTION  
         "MTU selector used on this path: 
         0: greater; 1: less; 2: exact; 3: largest available." 
      ::= { ibSmPathReqEntry 17 }  
    
   ibSmPathReqMTU         OBJECT-TYPE  
      SYNTAX              IbMtu 
      UNITS               "bytes" 
      MAX-ACCESS          read-create  
      STATUS              current  
      DESCRIPTION  
         "MTU used on this path: 
         1: 256; 2: 512; 3: 1024; 4: 2048; 5: 4096" 
      ::= { ibSmPathReqEntry 18 }  
    
   ibSmPathReqRateSel       OBJECT-TYPE  
      SYNTAX              INTEGER{ 
                          greater(0), 
 
 
 
 
                          less(1), 
                          exact(2), 
                          largestAvailable(3)} 
      MAX-ACCESS          read-create  
      STATUS              current  
      DESCRIPTION  
           "Rate selector used on this path. 
         0: greater; 1: less; 2: exact; 3: largest available." 
      ::= { ibSmPathReqEntry 19 }  
    
   ibSmPathReqRate          OBJECT-TYPE  
      SYNTAX              Unsigned32(0..63)  
      MAX-ACCESS          read-create  
      STATUS              current  
      DESCRIPTION  
         "Rate used on this path.  Specified as follows:  
         1: 1Gps; 2: 2.5Gps; 3: 10Gps; 4: 30Gps; other values reserved."  
      ::= { ibSmPathReqEntry 20 }  
    
   ibSmPathReqPktLifeTimeSel OBJECT-TYPE  
      SYNTAX              INTEGER{ 
                          greater(0), 
                          less(1), 
                          exact(2), 
                          smallestAvailable(3)} 
      MAX-ACCESS          read-create  
      STATUS              current  
      DESCRIPTION  
         "Packet life time selector used on this path: 
          0: greater; 1: less; 2: exact; 3: smallest available."  
      ::= { ibSmPathReqEntry 21 }  
    
   ibSmPathReqPktLifeTime   OBJECT-TYPE  
      SYNTAX              Unsigned32(0..63)  
      MAX-ACCESS          read-create  
      STATUS              current  
      DESCRIPTION  
         "Packet life time used on this path"  
      ::= { ibSmPathReqEntry 22 }  
    
   ibSmPathReqPreference   OBJECT-TYPE  
      SYNTAX              Unsigned32(0..255) 
      MAX-ACCESS          read-create  
      STATUS              current  
      DESCRIPTION  
         "The preference of the path, larger number indicates worse paths." 
      ::= { ibSmPathReqEntry 23 }  
    
   ibSmPathResultTable         OBJECT-TYPE  
 
 
 
 
      SYNTAX              SEQUENCE OF IbSmPathResultEntry  
      MAX-ACCESS          not-accessible  
      STATUS              current  
      DESCRIPTION  
         "A table used to specify path requests to the Subnet Managers on 
         this device."  
      ::= { ibSmPathInfo 2 }  
    
   ibSmPathResultEntry         OBJECT-TYPE  
      SYNTAX              IbSmPathResultEntry  
      MAX-ACCESS          not-accessible  
      STATUS              current  
      DESCRIPTION  
         "Table entry for ibSmPathResultTable."  
      INDEX { ibSmPathResultSubnetPrefix, ibSmPathResultSessionId, 
              ibSmPathResultIndex } 
      ::= { ibSmPathResultTable 1 }  
    
   IbSmPathResultEntry ::= SEQUENCE { 
      ibSmPathResultSubnetPrefix      IbSmSubnetPrefix, 
      ibSmPathResultSessionId         Integer32, 
      ibSmPathResultIndex             Integer32, 
      ibSmPathResultDstGID            OCTET STRING,  
      ibSmPathResultSrcGID            OCTET STRING,  
      ibSmPathResultNumbPath          Unsigned32,  
      ibSmPathResultDstLID            Unsigned32, 
      ibSmPathResultSrcLID            Unsigned32, 
      ibSmPathResultRawTraffic        Unsigned32,  
      ibSmPathResultFlowLabel         OCTET STRING,  
      ibSmPathResultHopLimit          Unsigned32,  
      ibSmPathResultTClass            Unsigned32,  
      ibSmPathResultPKey              IbPartitionKey, 
      ibSmPathResultSL                Unsigned32,  
      ibSmPathResultMTUSel            INTEGER, 
      ibSmPathResultMTU               IbMtu, 
      ibSmPathResultRateSel           INTEGER, 
      ibSmPathResultRate              Unsigned32,  
      ibSmPathResultPktLifeTimeSel    INTEGER, 
      ibSmPathResultPktLifeTime       Unsigned32, 
      ibSmPathResultPreference        Unsigned32 
   }  
    
   ibSmPathResultSubnetPrefix  OBJECT-TYPE  
       SYNTAX              IbSmSubnetPrefix  
       MAX-ACCESS          not-accessible  
       STATUS              current  
       DESCRIPTION  
           "Subnet prefix of this IB subnet."  
       ::= { ibSmPathResultEntry 1 }  
 
 
 
 
    
   ibSmPathResultSessionId OBJECT-TYPE          
      SYNTAX         Integer32(0..2147483647) 
      MAX-ACCESS     not-accessible 
      STATUS         current 
      DESCRIPTION 
         "pseudo-random 32 bit number provided by the client." 
      ::= { ibSmPathResultEntry 2 } 
    
   ibSmPathResultIndex  OBJECT-TYPE  
       SYNTAX              Integer32(0..2147483647) 
       MAX-ACCESS          not-accessible 
       STATUS              current  
       DESCRIPTION  
           "The index of Path Records." 
       ::= { ibSmPathResultEntry 3 }  
    
   ibSmPathResultDstGID         OBJECT-TYPE  
      SYNTAX              OCTET STRING (SIZE(16))  
      MAX-ACCESS          read-only  
      STATUS              current  
      DESCRIPTION  
         "The 128-bit destination GID of this path entry."  
      ::= { ibSmPathResultEntry 4 }  
    
   ibSmPathResultSrcGID         OBJECT-TYPE  
      SYNTAX              OCTET STRING (SIZE(16))  
      MAX-ACCESS          read-only  
      STATUS              current  
      DESCRIPTION  
         "The 128-bit source GID of this path entry."  
      ::= { ibSmPathResultEntry 5 }  
    
   ibSmPathResultNumbPath OBJECT-TYPE  
      SYNTAX              Unsigned32(0..127) 
      MAX-ACCESS          read-only  
      STATUS              current  
      DESCRIPTION  
         "Number of path between this source and destination GID pair."  
      ::= { ibSmPathResultEntry 6 }  
    
   ibSmPathResultDstLID         OBJECT-TYPE  
      SYNTAX              Unsigned32(1..65535) 
      MAX-ACCESS          read-only  
      STATUS              current  
      DESCRIPTION  
         "A 16-bit destination LID."  
      ::= { ibSmPathResultEntry 7 }  
    
 
 
 
 
   ibSmPathResultSrcLID         OBJECT-TYPE  
      SYNTAX              Unsigned32(1..65535) 
      MAX-ACCESS          read-only  
      STATUS              current  
      DESCRIPTION  
         "A 16-bit source LID."  
      ::= { ibSmPathResultEntry 8 }  
    
   ibSmPathResultRawTraffic    OBJECT-TYPE  
      SYNTAX              Unsigned32(0..1)  
      MAX-ACCESS          read-only  
      STATUS              current  
      DESCRIPTION  
         "The type of traffic that is on this path. 
         0: IB Packet; 1: Raw Packet." 
      ::= { ibSmPathResultEntry 9 }  
    
   ibSmPathResultFlowLabel     OBJECT-TYPE  
      SYNTAX              OCTET STRING (SIZE(3))  
      MAX-ACCESS          read-only  
      STATUS              current  
      DESCRIPTION  
         "Flow label used on this path if GRH is used."  
      ::= { ibSmPathResultEntry 10 }  
    
   ibSmPathResultHopLimit      OBJECT-TYPE  
      SYNTAX              Unsigned32(0..255) 
      MAX-ACCESS          read-only  
      STATUS              current  
      DESCRIPTION  
         "Hop limit used on this path if GRH is used."  
      ::= { ibSmPathResultEntry 11 }  
    
   ibSmPathResultTClass         OBJECT-TYPE  
      SYNTAX              Unsigned32(0..255) 
      MAX-ACCESS          read-only  
      STATUS              current  
      DESCRIPTION  
         "TClass used on this path if GRH is used."  
      ::= { ibSmPathResultEntry 12 }  
    
   ibSmPathResultPKey          OBJECT-TYPE  
      SYNTAX              IbPartitionKey 
      MAX-ACCESS          read-only  
      STATUS              current  
      DESCRIPTION  
         "The 16-bit P-Key used on this path."  
      ::= { ibSmPathResultEntry 13 }  
    
 
 
 
 
   ibSmPathResultSL            OBJECT-TYPE  
      SYNTAX              Unsigned32(0..15) 
      MAX-ACCESS          read-only  
      STATUS              current  
      DESCRIPTION  
         "Service level used on this path."  
      ::= { ibSmPathResultEntry 14 }  
    
   ibSmPathResultMTUSel         OBJECT-TYPE  
      SYNTAX              INTEGER{ 
                          greater(0), 
                          less(1), 
                          exact(2), 
                          largestAvailable(3)} 
      MAX-ACCESS          read-only  
      STATUS              current  
      DESCRIPTION  
         "MTU selector used on this path. 
         0: greater; 1: less; 2: exact; 3: largest available." 
      ::= { ibSmPathResultEntry 15 }  
    
   ibSmPathResultMTU           OBJECT-TYPE  
      SYNTAX              IbMtu 
      UNITS             "bytes" 
      MAX-ACCESS          read-only  
      STATUS              current  
      DESCRIPTION  
         "MTU used on this path.  
         1: 256; 2: 512; 3: 1024; 4: 2048; 5: 4096." 
      ::= { ibSmPathResultEntry 16 }  
    
   ibSmPathResultRateSel       OBJECT-TYPE  
      SYNTAX              INTEGER{ 
                          greater(0), 
                          less(1), 
                          exact(2), 
                          largestAvailable(3)} 
      MAX-ACCESS          read-only  
      STATUS              current  
      DESCRIPTION  
           "Rate selector used on this path. 
         0: greater; 1: less; 2: exact; 3: largest available." 
      ::= { ibSmPathResultEntry 17 }  
    
   ibSmPathResultRate          OBJECT-TYPE  
      SYNTAX              Unsigned32(0..63) 
      MAX-ACCESS          read-only  
      STATUS              current  
      DESCRIPTION  
 
 
 
 
         "Rate used on this path.  Specified as follows:  
         1: 1Gps; 2: 2.5Gps;  3: 10Gps; 4: 30Gps; other values reserved."  
      ::= { ibSmPathResultEntry 18 }  
    
   ibSmPathResultPktLifeTimeSel OBJECT-TYPE  
      SYNTAX              INTEGER{ 
                          greater(0), 
                          less(1), 
                          exact(2), 
                          smallestAvailable(3)} 
      MAX-ACCESS          read-only  
      STATUS              current  
      DESCRIPTION  
         "Packet life time selector used on this path. 
         0: greater; 1: less; 2: exact; 3: smallest available." 
      ::= { ibSmPathResultEntry 19 }  
    
   ibSmPathResultPktLifeTime   OBJECT-TYPE  
      SYNTAX              Unsigned32(0..63)  
      MAX-ACCESS          read-only  
      STATUS              current  
      DESCRIPTION  
         "Packet life time used on this path"  
      ::= { ibSmPathResultEntry 20 }  
    
   ibSmPathResultPreference   OBJECT-TYPE  
      SYNTAX              Unsigned32(0..255)  
      MAX-ACCESS          read-only  
      STATUS              current  
      DESCRIPTION  
         "The preference of the path, larger number indicates worse paths." 
      ::= { ibSmPathResultEntry 21 }  
    
   -- Subnet Manager MultiPath Tables  
   -- 
   -- In order to query IB MultiPathRecords, management client should 
   -- create a row in ibSmMultiPathReqTable, with the proper values of:  
   -- ibSmMultiPathReqSubnetPrefix, ibSmMultiPathReqSessionId,  
   -- ibSmMultiPathReqRowStatus, ibSmMultiPathReqRowCompMask, and other 
   -- relevant MultiPathRecord attribute values. 
   -- 
   -- ibSmMultiPathReqSessionId is a positive pseudo-random 32-bit integer  
   -- generated by the client.  This number should be based on per request, 
   -- and should not be reused by the client.  Before the client creates  
   -- the row, it should try to do a GET operation to ensure the number is  
   -- not being used currently.  If it detects a conflict, the client should  
   -- re-generate another random value and try again.  When a row is  
   -- successfully created in ibSmMultiPathReqTable, that means a request 
   -- of the path has been issued. 
 
 
 
 
   -- 
   -- ibSmMultiPathResultTable is used to retrieve the query results.  The 
   -- client should use the same value of ibSmMultiPathReqSessionId as  
   -- ibSmMultiPathResultSessionId to retrieve the results. 
   -- 
   -- The management application should delete the row it created from  
   -- ibSmMultiPathReqTable after it finishes retrieving the results.   
   -- This will effectively remove the results from  
   -- ibSmMultiPathResultTable.  It is suggested that the MIB agent remove  
   -- the row after a timeout period, to avoid resource leak. 
    
   ibSmMultiPathReqTable         OBJECT-TYPE  
      SYNTAX              SEQUENCE OF IbSmMultiPathReqEntry  
      MAX-ACCESS          not-accessible  
      STATUS              current  
      DESCRIPTION  
         "A table used to specify multipath request to the Subnet Managers 
          on this device."  
      ::= { ibSmMultiPathInfo 1 }  
    
   ibSmMultiPathReqEntry         OBJECT-TYPE  
      SYNTAX              IbSmMultiPathReqEntry  
      MAX-ACCESS          not-accessible  
      STATUS              current  
      DESCRIPTION  
         "Table entry for ibSmMultiPathReqTable."  
      INDEX { ibSmMultiPathReqSubnetPrefix, ibSmMultiPathReqSessionId }
      ::= { ibSmMultiPathReqTable 1 }  
    
   IbSmMultiPathReqEntry ::= SEQUENCE { 
      ibSmMultiPathReqSubnetPrefix      IbSmSubnetPrefix, 
      ibSmMultiPathReqSessionId         Integer32, 
      ibSmMultiPathReqRowStatus         RowStatus,   
      ibSmMultiPathReqCreationTime   TimeTicks, 
      ibSmMultiPathReqCompMask       OCTET STRING, 
      ibSmMultiPathReqRawTraffic       Unsigned32,  
      ibSmMultiPathReqFlowLabel         OCTET STRING,  
      ibSmMultiPathReqHopLimit          Unsigned32,  
      ibSmMultiPathReqTClass            Unsigned32,  
      ibSmMultiPathReqNumbPath          Unsigned32,  
      ibSmMultiPathReqPKey              IbPartitionKey, 
      ibSmMultiPathReqSL                Unsigned32,  
      ibSmMultiPathReqMTUSel            Unsigned32,  
      ibSmMultiPathReqMTU               IbMtu, 
      ibSmMultiPathReqRateSel           Unsigned32,  
      ibSmMultiPathReqRate              Unsigned32,  
      ibSmMultiPathReqPktLifeTimeSel    Unsigned32,  
      ibSmMultiPathReqPktLifeTime       Unsigned32, 
      ibSmMultiPathReqIndepSel          Unsigned32, 
 
 
 
 
      ibSmMultiPathReqSGIDCount        Unsigned32, 
      ibSmMultiPathReqDGIDCount        Unsigned32, 
      ibSmMultiPathReqSDGIDBlock1       OCTET STRING, 
      ibSmMultiPathReqSDGIDBlock2       OCTET STRING, 
      ibSmMultiPathReqSDGIDBlock3       OCTET STRING, 
      ibSmMultiPathReqSDGIDBlock4       OCTET STRING, 
      ibSmMultiPathReqSDGIDBlock5       OCTET STRING, 
      ibSmMultiPathReqSDGIDBlock6       OCTET STRING, 
      ibSmMultiPathReqSDGIDBlock7       OCTET STRING, 
      ibSmMultiPathReqSDGIDBlock8       OCTET STRING,     
      ibSmMultiPathReqSDGIDBlock9       OCTET STRING,     
      ibSmMultiPathReqSDGIDBlock10      OCTET STRING,     
      ibSmMultiPathReqSDGIDBlock11      OCTET STRING,     
      ibSmMultiPathReqSDGIDBlock12      OCTET STRING,     
      ibSmMultiPathReqSDGIDBlock13      OCTET STRING,     
      ibSmMultiPathReqSDGIDBlock14      OCTET STRING,     
      ibSmMultiPathReqSDGIDBlock15      OCTET STRING,     
      ibSmMultiPathReqSDGIDBlock16      OCTET STRING,     
      ibSmMultiPathReqSDGIDBlock17      OCTET STRING,     
      ibSmMultiPathReqSDGIDBlock18      OCTET STRING,     
      ibSmMultiPathReqSDGIDBlock19      OCTET STRING,     
      ibSmMultiPathReqSDGIDBlock20      OCTET STRING,     
      ibSmMultiPathReqSDGIDBlock21      OCTET STRING,     
      ibSmMultiPathReqSDGIDBlock22      OCTET STRING,     
      ibSmMultiPathReqSDGIDBlock23      OCTET STRING,     
      ibSmMultiPathReqSDGIDBlock24      OCTET STRING,     
      ibSmMultiPathReqSDGIDBlock25      OCTET STRING,     
      ibSmMultiPathReqSDGIDBlock26      OCTET STRING,     
      ibSmMultiPathReqSDGIDBlock27      OCTET STRING,     
      ibSmMultiPathReqSDGIDBlock28      OCTET STRING,     
      ibSmMultiPathReqSDGIDBlock29      OCTET STRING,     
      ibSmMultiPathReqSDGIDBlock30      OCTET STRING,     
      ibSmMultiPathReqSDGIDBlock31      OCTET STRING,     
      ibSmMultiPathReqSDGIDBlock32      OCTET STRING 
   }  
   ibSmMultiPathReqSubnetPrefix  OBJECT-TYPE  
       SYNTAX              IbSmSubnetPrefix  
       MAX-ACCESS          not-accessible  
       STATUS              current  
       DESCRIPTION  
           "Subnet prefix of this IB subnet."  
       ::= { ibSmMultiPathReqEntry 1 }  
    
   ibSmMultiPathReqSessionId  OBJECT-TYPE          
      SYNTAX         Integer32(0..2147483647) 
      MAX-ACCESS     not-accessible 
      STATUS         current 
      DESCRIPTION 
         "pseudo-random 32 bit number provided by the client." 
 
 
 
 
      ::= { ibSmMultiPathReqEntry 2 } 
    
   ibSmMultiPathReqRowStatus  OBJECT-TYPE 
      SYNTAX            RowStatus 
      MAX-ACCESS        read-create 
      STATUS            current 
      DESCRIPTION 
         "RowStatus for row creation/deletion." 
      ::= { ibSmMultiPathReqEntry 3 } 
    
   ibSmMultiPathReqCreationTime  OBJECT-TYPE 
      SYNTAX   TimeTicks 
      MAX-ACCESS  read-only 
      STATUS   current 
      DESCRIPTION 
         "Time stamp when this row is created." 
      ::= { ibSmMultiPathReqEntry 4 } 
    
   ibSmMultiPathReqCompMask  OBJECT-TYPE 
      SYNTAX OCTET STRING(SIZE(8)) 
      MAX-ACCESS read-create 
      STATUS current 
      DESCRIPTION 
         "64-bit Component Mask for the request." 
      ::= { ibSmMultiPathReqEntry 5 } 
    
   ibSmMultiPathReqRawTraffic   OBJECT-TYPE  
      SYNTAX              Unsigned32(0..1) 
      MAX-ACCESS          read-create  
      STATUS              current  
      DESCRIPTION  
         "The type of traffic that is on this path.                    
         0: IB Packet; 1: Raw Packet." 
      ::= { ibSmMultiPathReqEntry 6 }  
    
   ibSmMultiPathReqFlowLabel     OBJECT-TYPE  
      SYNTAX              OCTET STRING (SIZE(3))  
      MAX-ACCESS          read-create  
      STATUS              current  
      DESCRIPTION  
         "Flow label used on this path if GRH is used."  
      ::= { ibSmMultiPathReqEntry 7 }  
    
   ibSmMultiPathReqHopLimit      OBJECT-TYPE  
      SYNTAX              Unsigned32(0..255)  
      MAX-ACCESS          read-create  
      STATUS              current  
      DESCRIPTION  
         "Hop limit used on this path if GRH is used."  
 
 
 
 
      ::= { ibSmMultiPathReqEntry 8 }  
    
   ibSmMultiPathReqTClass         OBJECT-TYPE  
      SYNTAX              Unsigned32(0..255) 
      MAX-ACCESS          read-create  
      STATUS              current  
      DESCRIPTION  
         "TClass used on this path if GRH is used."  
      ::= { ibSmMultiPathReqEntry 9 }  
    
   ibSmMultiPathReqNumbPath OBJECT-TYPE  
      SYNTAX              Unsigned32(0..127)  
      MAX-ACCESS          read-create  
      STATUS              current  
      DESCRIPTION  
         "Number of path between this source and destination GID pair."  
      ::= { ibSmMultiPathReqEntry 10 }  
    
   ibSmMultiPathReqPKey          OBJECT-TYPE  
      SYNTAX            IbPartitionKey    
      MAX-ACCESS          read-create  
      STATUS              current  
      DESCRIPTION  
         "The 16-bit P-Key used on this path."  
      ::= { ibSmMultiPathReqEntry 11 }  
    
   ibSmMultiPathReqSL            OBJECT-TYPE  
      SYNTAX              Unsigned32(0..15) 
      MAX-ACCESS          read-create  
      STATUS              current  
      DESCRIPTION  
         "Service level used on this path."  
      ::= { ibSmMultiPathReqEntry 12 }  
    
   ibSmMultiPathReqMTUSel         OBJECT-TYPE  
      SYNTAX              Unsigned32(0..3) 
      MAX-ACCESS          read-create  
      STATUS              current  
      DESCRIPTION  
         "MTU selector used on this path. 
         0: greater; 1: less; 2: exact; 3: largest available." 
      ::= { ibSmMultiPathReqEntry 13 }  
    
   ibSmMultiPathReqMTU           OBJECT-TYPE  
      SYNTAX              IbMtu 
      UNITS             "bytes" 
      MAX-ACCESS          read-create  
      STATUS              current  
      DESCRIPTION  
 
 
 
 
         "MTU used on this path.    
         1: 256; 2: 512; 3: 1024; 4: 2048; 5: 4096." 
      ::= { ibSmMultiPathReqEntry 14 }  
    
   ibSmMultiPathReqRateSel       OBJECT-TYPE  
      SYNTAX              Unsigned32(0..3) 
      MAX-ACCESS          read-create  
      STATUS              current  
      DESCRIPTION  
           "Rate selector used on this path. 
         0: greater; 1: less; 2: exact; 3: largest available." 
      ::= { ibSmMultiPathReqEntry 15 }  
    
   ibSmMultiPathReqRate          OBJECT-TYPE  
      SYNTAX              Unsigned32(0..63)  
      MAX-ACCESS          read-create  
      STATUS              current  
      DESCRIPTION  
         "Rate used on this path.  Specified as follows:  
         1: 1Gps; 2: 2.5Gps;  3: 10Gps; 4: 30Gps; other values reserved."  
      ::= { ibSmMultiPathReqEntry 16 }  
    
   ibSmMultiPathReqPktLifeTimeSel OBJECT-TYPE  
      SYNTAX              Unsigned32(0..3) 
      MAX-ACCESS          read-create  
      STATUS              current  
      DESCRIPTION  
         "Packet life time selector used on this path. 
         0: greater; 1: less; 2: exact; 3: smallest available." 
      ::= { ibSmMultiPathReqEntry 17 }  
    
   ibSmMultiPathReqPktLifeTime   OBJECT-TYPE  
      SYNTAX              Unsigned32(0..63) 
      MAX-ACCESS          read-create  
      STATUS              current  
      DESCRIPTION  
         "Packet life time used on this path"  
      ::= { ibSmMultiPathReqEntry 18 }  
    
   ibSmMultiPathReqIndepSel   OBJECT-TYPE  
      SYNTAX              Unsigned32(0..3)  
      MAX-ACCESS          read-create  
      STATUS              current  
      DESCRIPTION  
         "1: paths that are as fault-independent as possible.  
         other values reserved. "  
      ::= { ibSmMultiPathReqEntry 19 }  
    
   ibSmMultiPathReqSGIDCount   OBJECT-TYPE  
 
 
 
 
      SYNTAX              Unsigned32(0..255)  
      MAX-ACCESS          read-create  
      STATUS              current  
      DESCRIPTION  
         "Number of SGIDs. "  
      ::= { ibSmMultiPathReqEntry 20 }  
    
   ibSmMultiPathReqDGIDCount   OBJECT-TYPE  
      SYNTAX              Unsigned32(0..255)  
      MAX-ACCESS          read-create  
      STATUS              current  
      DESCRIPTION  
         "Number of DGIDs. "  
      ::= { ibSmMultiPathReqEntry 21 }  
    
   ibSmMultiPathReqSDGIDBlock1   OBJECT-TYPE  
      SYNTAX              OCTET STRING(SIZE(0..256))  
      MAX-ACCESS          read-create  
      STATUS              current  
      DESCRIPTION  
         "May contain a block of 0 to 16 SGIDs or DGIDs. Empty if not set" 
      ::= { ibSmMultiPathReqEntry 22 }  
    
   ibSmMultiPathReqSDGIDBlock2   OBJECT-TYPE  
      SYNTAX              OCTET STRING(SIZE(0..256))  
      MAX-ACCESS          read-create  
      STATUS              current  
      DESCRIPTION  
         "May contain a block of 0 to 16 SGIDs or DGIDs. Empty if not set" 
      ::= { ibSmMultiPathReqEntry 23 }  
    
   ibSmMultiPathReqSDGIDBlock3   OBJECT-TYPE  
      SYNTAX              OCTET STRING(SIZE(0..256))  
      MAX-ACCESS          read-create  
      STATUS              current  
      DESCRIPTION  
         "May contain a block of 0 to 16 SGIDs or DGIDs. Empty if not set" 
      ::= { ibSmMultiPathReqEntry 24 }  
    
   ibSmMultiPathReqSDGIDBlock4   OBJECT-TYPE  
      SYNTAX              OCTET STRING(SIZE(0..256))  
      MAX-ACCESS          read-create  
      STATUS              current  
      DESCRIPTION  
         "May contain a block of 0 to 16 SGIDs or DGIDs. Empty if not set" 
      ::= { ibSmMultiPathReqEntry 25 }  
    
   ibSmMultiPathReqSDGIDBlock5   OBJECT-TYPE  
      SYNTAX              OCTET STRING(SIZE(0..256))  
 
 
 
 
      MAX-ACCESS          read-create  
      STATUS              current  
      DESCRIPTION  
         "May contain a block of 0 to 16 SGIDs or DGIDs. Empty if not set" 
      ::= { ibSmMultiPathReqEntry 26 }  
    
   ibSmMultiPathReqSDGIDBlock6   OBJECT-TYPE  
      SYNTAX              OCTET STRING(SIZE(0..256))  
      MAX-ACCESS          read-create  
      STATUS              current  
      DESCRIPTION  
         "May contain a block of 0 to 16 SGIDs or DGIDs. Empty if not set" 
      ::= { ibSmMultiPathReqEntry 27 }  
    
   ibSmMultiPathReqSDGIDBlock7   OBJECT-TYPE  
      SYNTAX              OCTET STRING(SIZE(0..256))  
      MAX-ACCESS          read-create  
      STATUS              current  
      DESCRIPTION  
         "May contain a block of 0 to 16 SGIDs or DGIDs. Empty if not set" 
      ::= { ibSmMultiPathReqEntry 28 }  
    
   ibSmMultiPathReqSDGIDBlock8   OBJECT-TYPE  
      SYNTAX              OCTET STRING(SIZE(0..256))  
      MAX-ACCESS          read-create  
      STATUS              current  
      DESCRIPTION  
         "May contain a block of 0 to 16 SGIDs or DGIDs. Empty if not set" 
      ::= { ibSmMultiPathReqEntry 29 }  
    
   ibSmMultiPathReqSDGIDBlock9   OBJECT-TYPE  
      SYNTAX              OCTET STRING(SIZE(0..256))  
      MAX-ACCESS          read-create  
      STATUS              current  
      DESCRIPTION  
         "May contain a block of 0 to 16 SGIDs or DGIDs. Empty if not set" 
      ::= { ibSmMultiPathReqEntry 30 }  
    
   ibSmMultiPathReqSDGIDBlock10   OBJECT-TYPE  
      SYNTAX              OCTET STRING(SIZE(0..256))  
      MAX-ACCESS          read-create  
      STATUS              current  
      DESCRIPTION  
         "May contain a block of 0 to 16 SGIDs or DGIDs. Empty if not set" 
      ::= { ibSmMultiPathReqEntry 31 }  
    
   ibSmMultiPathReqSDGIDBlock11   OBJECT-TYPE  
      SYNTAX              OCTET STRING(SIZE(0..256))  
      MAX-ACCESS          read-create  
 
 
 
 
      STATUS              current  
      DESCRIPTION  
         "May contain a block of 0 to 16 SGIDs or DGIDs. Empty if not set" 
      ::= { ibSmMultiPathReqEntry 32 }  
    
   ibSmMultiPathReqSDGIDBlock12   OBJECT-TYPE  
      SYNTAX              OCTET STRING(SIZE(0..256))  
      MAX-ACCESS          read-create  
      STATUS              current  
      DESCRIPTION  
         "May contain a block of 0 to 16 SGIDs or DGIDs. Empty if not set" 
      ::= { ibSmMultiPathReqEntry 33 }  
    
   ibSmMultiPathReqSDGIDBlock13   OBJECT-TYPE  
      SYNTAX              OCTET STRING(SIZE(0..256))  
      MAX-ACCESS          read-create  
      STATUS              current  
      DESCRIPTION  
         "May contain a block of 0 to 16 SGIDs or DGIDs. Empty if not set" 
      ::= { ibSmMultiPathReqEntry 34 }  
    
   ibSmMultiPathReqSDGIDBlock14   OBJECT-TYPE  
      SYNTAX              OCTET STRING(SIZE(0..256))  
      MAX-ACCESS          read-create  
      STATUS              current  
      DESCRIPTION  
         "May contain a block of 0 to 16 SGIDs or DGIDs. Empty if not set" 
      ::= { ibSmMultiPathReqEntry 35 }  
    
   ibSmMultiPathReqSDGIDBlock15   OBJECT-TYPE  
      SYNTAX              OCTET STRING(SIZE(0..256))  
      MAX-ACCESS          read-create  
      STATUS              current  
      DESCRIPTION  
         "May contain a block of 0 to 16 SGIDs or DGIDs. Empty if not set" 
      ::= { ibSmMultiPathReqEntry 36 }  
    
   ibSmMultiPathReqSDGIDBlock16   OBJECT-TYPE  
      SYNTAX              OCTET STRING(SIZE(0..256))  
      MAX-ACCESS          read-create  
      STATUS              current  
      DESCRIPTION  
         "May contain a block of 0 to 16 SGIDs or DGIDs. Empty if not set" 
      ::= { ibSmMultiPathReqEntry 37 }  
    
   ibSmMultiPathReqSDGIDBlock17   OBJECT-TYPE  
      SYNTAX              OCTET STRING(SIZE(0..256))  
      MAX-ACCESS          read-create  
      STATUS              current  
 
 
 
 
      DESCRIPTION  
         "May contain a block of 0 to 16 SGIDs or DGIDs. Empty if not set" 
      ::= { ibSmMultiPathReqEntry 38 }  
    
   ibSmMultiPathReqSDGIDBlock18   OBJECT-TYPE  
      SYNTAX              OCTET STRING(SIZE(0..256))  
      MAX-ACCESS          read-create  
      STATUS              current  
      DESCRIPTION  
         "May contain a block of 0 to 16 SGIDs or DGIDs. Empty if not set" 
      ::= { ibSmMultiPathReqEntry 39 }  
    
   ibSmMultiPathReqSDGIDBlock19   OBJECT-TYPE  
      SYNTAX              OCTET STRING(SIZE(0..256))  
      MAX-ACCESS          read-create  
      STATUS              current  
      DESCRIPTION  
         "May contain a block of 0 to 16 SGIDs or DGIDs. Empty if not set" 
      ::= { ibSmMultiPathReqEntry 40 }  
    
   ibSmMultiPathReqSDGIDBlock20   OBJECT-TYPE  
      SYNTAX              OCTET STRING(SIZE(0..256))  
      MAX-ACCESS          read-create  
      STATUS              current  
      DESCRIPTION  
         "May contain a block of 0 to 16 SGIDs or DGIDs. Empty if not set" 
      ::= { ibSmMultiPathReqEntry 41 }  
    
   ibSmMultiPathReqSDGIDBlock21   OBJECT-TYPE  
      SYNTAX              OCTET STRING(SIZE(0..256))  
      MAX-ACCESS          read-create  
      STATUS              current  
      DESCRIPTION  
         "May contain a block of 0 to 16 SGIDs or DGIDs. Empty if not set" 
      ::= { ibSmMultiPathReqEntry 42 }  
    
   ibSmMultiPathReqSDGIDBlock22   OBJECT-TYPE  
      SYNTAX              OCTET STRING(SIZE(0..256))  
      MAX-ACCESS          read-create  
      STATUS              current  
      DESCRIPTION  
         "May contain a block of 0 to 16 SGIDs or DGIDs. Empty if not set" 
      ::= { ibSmMultiPathReqEntry 43 }  
    
   ibSmMultiPathReqSDGIDBlock23   OBJECT-TYPE  
      SYNTAX              OCTET STRING(SIZE(0..256))  
      MAX-ACCESS          read-create  
      STATUS              current  
      DESCRIPTION  
 
 
 
 
         "May contain a block of 0 to 16 SGIDs or DGIDs. Empty if not set" 
      ::= { ibSmMultiPathReqEntry 44 }  
    
   ibSmMultiPathReqSDGIDBlock24   OBJECT-TYPE  
      SYNTAX              OCTET STRING(SIZE(0..256))  
      MAX-ACCESS          read-create  
      STATUS              current  
      DESCRIPTION  
         "May contain a block of 0 to 16 SGIDs or DGIDs. Empty if not set" 
      ::= { ibSmMultiPathReqEntry 45 }  
    
   ibSmMultiPathReqSDGIDBlock25   OBJECT-TYPE  
      SYNTAX              OCTET STRING(SIZE(0..256))  
      MAX-ACCESS          read-create  
      STATUS              current  
      DESCRIPTION  
         "May contain a block of 0 to 16 SGIDs or DGIDs. Empty if not set" 
      ::= { ibSmMultiPathReqEntry 46 }  
    
   ibSmMultiPathReqSDGIDBlock26   OBJECT-TYPE  
      SYNTAX              OCTET STRING(SIZE(0..256))  
      MAX-ACCESS          read-create  
      STATUS              current  
      DESCRIPTION  
         "May contain a block of 0 to 16 SGIDs or DGIDs. Empty if not set" 
      ::= { ibSmMultiPathReqEntry 47 }  
    
   ibSmMultiPathReqSDGIDBlock27   OBJECT-TYPE  
      SYNTAX              OCTET STRING(SIZE(0..256))  
      MAX-ACCESS          read-create  
      STATUS              current  
      DESCRIPTION  
         "May contain a block of 0 to 16 SGIDs or DGIDs. Empty if not set" 
      ::= { ibSmMultiPathReqEntry 48 }  
    
   ibSmMultiPathReqSDGIDBlock28   OBJECT-TYPE  
      SYNTAX              OCTET STRING(SIZE(0..256))  
      MAX-ACCESS          read-create  
      STATUS              current  
      DESCRIPTION  
         "May contain a block of 0 to 16 SGIDs or DGIDs. Empty if not set" 
      ::= { ibSmMultiPathReqEntry 49 }  
    
   ibSmMultiPathReqSDGIDBlock29   OBJECT-TYPE  
      SYNTAX              OCTET STRING(SIZE(0..256))  
      MAX-ACCESS          read-create  
      STATUS              current  
      DESCRIPTION  
         "May contain a block of 0 to 16 SGIDs or DGIDs. Empty if not set" 
 
 
 
 
      ::= { ibSmMultiPathReqEntry 50 }  
    
   ibSmMultiPathReqSDGIDBlock30   OBJECT-TYPE  
      SYNTAX              OCTET STRING(SIZE(0..256))  
      MAX-ACCESS          read-create  
      STATUS              current  
      DESCRIPTION  
         "May contain a block of 0 to 16 SGIDs or DGIDs. Empty if not set" 
      ::= { ibSmMultiPathReqEntry 51 }  
    
   ibSmMultiPathReqSDGIDBlock31   OBJECT-TYPE  
      SYNTAX              OCTET STRING(SIZE(0..256))  
      MAX-ACCESS          read-create  
      STATUS              current  
      DESCRIPTION  
         "May contain a block of 0 to 16 SGIDs or DGIDs. Empty if not set" 
      ::= { ibSmMultiPathReqEntry 52 }  
    
   ibSmMultiPathReqSDGIDBlock32   OBJECT-TYPE  
      SYNTAX              OCTET STRING(SIZE(0..256))  
      MAX-ACCESS          read-create  
      STATUS              current  
      DESCRIPTION  
         "May contain a block of 0 to 16 SGIDs or DGIDs. Empty if not set" 
      ::= { ibSmMultiPathReqEntry 53 }  
    
   ibSmMultiPathResultTable         OBJECT-TYPE  
      SYNTAX              SEQUENCE OF IbSmMultiPathResultEntry  
      MAX-ACCESS          not-accessible  
      STATUS              current  
      DESCRIPTION  
         "A table used to list all the path entries that satisfy the  
         multi path request." 
      ::= { ibSmMultiPathInfo 2 }  
    
   ibSmMultiPathResultEntry         OBJECT-TYPE  
      SYNTAX              IbSmMultiPathResultEntry  
      MAX-ACCESS          not-accessible  
      STATUS              current  
      DESCRIPTION  
         "Table entry for ibSmMultiPathResultTable."  
      INDEX { ibSmMultiPathResultSubnetPrefix, 
         ibSmMultiPathResultSessionId, ibSmMultiPathResultIndex } 
    
      ::= { ibSmMultiPathResultTable 1 }  
    
   IbSmMultiPathResultEntry ::= SEQUENCE { 
      ibSmMultiPathResultSubnetPrefix      IbSmSubnetPrefix, 
      ibSmMultiPathResultSessionId         Integer32, 
 
 
 
 
      ibSmMultiPathResultIndex             Integer32, 
      ibSmMultiPathResultDstGID            OCTET STRING,  
      ibSmMultiPathResultSrcGID            OCTET STRING,  
      ibSmMultiPathResultNumbPath          Unsigned32,  
      ibSmMultiPathResultDstLID            Unsigned32, 
      ibSmMultiPathResultSrcLID            Unsigned32, 
      ibSmMultiPathResultRawTraffic        Unsigned32,  
      ibSmMultiPathResultFlowLabel         OCTET STRING,  
      ibSmMultiPathResultHopLimit          Unsigned32,  
      ibSmMultiPathResultTClass            Unsigned32,  
      ibSmMultiPathResultPKey              IbPartitionKey, 
      ibSmMultiPathResultSL                Unsigned32,  
      ibSmMultiPathResultMTUSel            INTEGER,  
      ibSmMultiPathResultMTU               IbMtu, 
      ibSmMultiPathResultRateSel           INTEGER,  
      ibSmMultiPathResultRate              Unsigned32,  
      ibSmMultiPathResultPktLifeTimeSel    INTEGER,  
      ibSmMultiPathResultPktLifeTime       Unsigned32,  
      ibSmMultiPathResultPreference        Unsigned32 
   }  
    
   ibSmMultiPathResultSubnetPrefix  OBJECT-TYPE  
       SYNTAX              IbSmSubnetPrefix  
       MAX-ACCESS          not-accessible  
       STATUS              current  
       DESCRIPTION  
           "Subnet prefix of this IB subnet."  
       ::= { ibSmMultiPathResultEntry 1 }  
    
   ibSmMultiPathResultSessionId  OBJECT-TYPE          
      SYNTAX         Integer32(0..2147483647) 
      MAX-ACCESS     not-accessible 
      STATUS         current 
      DESCRIPTION 
         "pseudo-random 32 bit number provided by the client." 
      ::= { ibSmMultiPathResultEntry 2 } 
    
   ibSmMultiPathResultIndex  OBJECT-TYPE  
       SYNTAX              Integer32(0..2147483647) 
       MAX-ACCESS          not-accessible 
       STATUS              current  
       DESCRIPTION  
           "The index of Path Records." 
       ::= { ibSmMultiPathResultEntry 3 }  
    
   ibSmMultiPathResultDstGID         OBJECT-TYPE  
      SYNTAX              OCTET STRING (SIZE(16))  
      MAX-ACCESS          read-only  
      STATUS              current  
 
 
 
 
      DESCRIPTION  
         "The 128-bit destination GID of this path entry."  
      ::= { ibSmMultiPathResultEntry 4 }  
    
   ibSmMultiPathResultSrcGID         OBJECT-TYPE  
      SYNTAX              OCTET STRING (SIZE(16))  
      MAX-ACCESS          read-only  
      STATUS              current  
      DESCRIPTION  
         "The 128-bit source GID of this path entry."  
      ::= { ibSmMultiPathResultEntry 5 }  
    
   ibSmMultiPathResultNumbPath OBJECT-TYPE  
      SYNTAX              Unsigned32(0..127)  
      MAX-ACCESS          read-only  
      STATUS              current  
      DESCRIPTION  
         "Number of path between this source and destination GID pair."  
      ::= { ibSmMultiPathResultEntry 6 }  
    
   ibSmMultiPathResultDstLID         OBJECT-TYPE  
      SYNTAX              Unsigned32(1..65535) 
      MAX-ACCESS          read-only  
      STATUS              current  
      DESCRIPTION  
         "A 16-bit destination LID."  
      ::= { ibSmMultiPathResultEntry 7 }  
    
   ibSmMultiPathResultSrcLID         OBJECT-TYPE  
      SYNTAX              Unsigned32(1..65535) 
      MAX-ACCESS          read-only  
      STATUS              current  
      DESCRIPTION  
         "A 16-bit source LID."  
      ::= { ibSmMultiPathResultEntry 8 }  
    
   ibSmMultiPathResultRawTraffic   OBJECT-TYPE  
      SYNTAX              Unsigned32(0..1)  
      MAX-ACCESS          read-only  
      STATUS              current  
      DESCRIPTION  
         "The type of traffic that is on this path. 
         0: IB Packet; 1: Raw Packet." 
      ::= { ibSmMultiPathResultEntry 9 }  
    
   ibSmMultiPathResultFlowLabel     OBJECT-TYPE  
      SYNTAX              OCTET STRING (SIZE(3))  
      MAX-ACCESS          read-only  
      STATUS              current  
 
 
 
 
      DESCRIPTION  
         "Flow label used on this path if GRH is used."  
      ::= { ibSmMultiPathResultEntry 10 }  
    
   ibSmMultiPathResultHopLimit      OBJECT-TYPE  
      SYNTAX              Unsigned32(0..255) 
      MAX-ACCESS          read-only  
      STATUS              current  
      DESCRIPTION  
         "Hop limit used on this path if GRH is used."  
      ::= { ibSmMultiPathResultEntry 11 }  
    
   ibSmMultiPathResultTClass         OBJECT-TYPE  
      SYNTAX              Unsigned32(0..255) 
      MAX-ACCESS          read-only  
      STATUS              current  
      DESCRIPTION  
         "TClass used on this path if GRH is used."  
      ::= { ibSmMultiPathResultEntry 12 }  
    
   ibSmMultiPathResultPKey          OBJECT-TYPE  
      SYNTAX            IbPartitionKey            
      MAX-ACCESS          read-only  
      STATUS              current  
      DESCRIPTION  
         "The 16-bit P-Key used on this path."  
      ::= { ibSmMultiPathResultEntry 13 }  
    
   ibSmMultiPathResultSL            OBJECT-TYPE  
      SYNTAX              Unsigned32(0..15) 
      MAX-ACCESS          read-only  
      STATUS              current  
      DESCRIPTION  
         "Service level used on this path."  
      ::= { ibSmMultiPathResultEntry 14 }  
    
   ibSmMultiPathResultMTUSel         OBJECT-TYPE  
      SYNTAX              INTEGER { 
                          greater(0), 
                          less(1), 
                          exact(2), 
                          largestAvailable(3)} 
      MAX-ACCESS          read-only  
      STATUS              current  
      DESCRIPTION  
         "MTU selector used on this path. 
         0: greater; 1: less; 2: exact; 3: largest available." 
      ::= { ibSmMultiPathResultEntry 15 }  
    
 
 
 
 
   ibSmMultiPathResultMTU           OBJECT-TYPE  
      SYNTAX              IbMtu 
      UNITS             "bytes" 
      MAX-ACCESS          read-only  
      STATUS              current  
      DESCRIPTION  
         "MTU used on this path. 
         1: 256; 2: 512; 3: 1024; 4: 2048; 5: 4096; other values reserved."  
      ::= { ibSmMultiPathResultEntry 16 }  
    
   ibSmMultiPathResultRateSel       OBJECT-TYPE  
      SYNTAX              INTEGER{ 
                          greater(0), 
                          less(1), 
                          exact(2), 
                          largestAvailable(3)} 
      MAX-ACCESS          read-only  
      STATUS              current  
      DESCRIPTION  
           "Rate selector used on this path. 
         0: greater; 1: less; 2: exact; 3: largest available." 
      ::= { ibSmMultiPathResultEntry 17 }  
    
   ibSmMultiPathResultRate          OBJECT-TYPE  
      SYNTAX              Unsigned32(0..63)  
      MAX-ACCESS          read-only  
      STATUS              current  
      DESCRIPTION  
         "Rate used on this path.  Specified as follows:  
         1: 1Gps; 2: 2.5Gps;  3: 10Gps; 4: 30Gps; other values reserved."  
      ::= { ibSmMultiPathResultEntry 18 }  
    
   ibSmMultiPathResultPktLifeTimeSel OBJECT-TYPE  
      SYNTAX              INTEGER { 
                          greater(0), 
                          less(1), 
                          exact(2), 
                          smallestAvailable(3)} 
      MAX-ACCESS          read-only  
      STATUS              current  
      DESCRIPTION  
         "Packet life time selector used on this path. 
         0: greater; 1: less; 2: exact; 3: smallest available." 
      ::= { ibSmMultiPathResultEntry 19 }  
    
   ibSmMultiPathResultPktLifeTime   OBJECT-TYPE  
      SYNTAX              Unsigned32(0..63) 
      MAX-ACCESS          read-only  
      STATUS              current  
 
 
 
 
      DESCRIPTION  
         "Packet life time used on this path"  
      ::= { ibSmMultiPathResultEntry 20 }  
    
   ibSmMultiPathResultPreference   OBJECT-TYPE  
      SYNTAX              Unsigned32(0..255)  
      MAX-ACCESS          read-only  
      STATUS              current  
      DESCRIPTION  
         "The preference of the path, larger number indicates worse paths." 
      ::= { ibSmMultiPathResultEntry 21 }  
    
   -- Subnet Manager Trace Tables  
   -- 
   -- In order to query IB TraceRecords, management client should 
   -- create a row in ibSmTraceReqTable, with the proper values of:  
   -- ibSmTraceReqSubnetPrefix, ibSmTraceReqSessionId,  
   -- ibSmTraceReqRowStatus, ibSmTraceReqRowCompMask, and other 
   -- relevant TraceRecord attribute values. 
   -- 
   -- ibSmTraceReqSessionId is a positive pseudo-random 32-bit integer  
   -- generated by the client.  This number should be based on per request, 
   -- and should not be reused by the client.  Before the client creates  
   -- the row, it should try to do a GET operation to ensure the number is  
   -- not being used currently.  If it detects a conflict, the client should  
   -- re-generate another random value and try again.  When a row is  
   -- successfully created in ibSmTraceReqTable, that means a request 
   -- of the path has been issued. 
   -- 
   -- ibSmTraceResultTable is used to retrieve the query results.  The 
   -- client should use the same value of ibSmTraceReqSessionId as  
   -- ibSmTraceResultSessionId to retrieve the results. 
   -- 
   -- The management application should delete the row it created from  
   -- ibSmTraceReqTable after it finishes retrieving the results.  This will 
   -- effectively remove the results from ibSmTraceResultTable.  It is  
   -- suggested that the MIB agent remove the row after a timeout period,  
   -- to avoid resource leak. 
    
    
   ibSmTraceReqTable         OBJECT-TYPE  
      SYNTAX              SEQUENCE OF IbSmTraceReqEntry  
      MAX-ACCESS          not-accessible  
      STATUS              current  
      DESCRIPTION  
         "A table used to specify trace request to the Subnet Managers on 
         this device."  
      ::= { ibSmTraceInfo 1 }  
    
 
 
 
 
   ibSmTraceReqEntry         OBJECT-TYPE  
      SYNTAX              IbSmTraceReqEntry  
      MAX-ACCESS          not-accessible  
      STATUS              current  
      DESCRIPTION  
         "Table entry for ibSmTraceReqTable."  
      INDEX { ibSmTraceReqSubnetPrefix, ibSmTraceReqSessionId } 
      ::= { ibSmTraceReqTable 1 }  
    
   IbSmTraceReqEntry ::= SEQUENCE { 
      ibSmTraceReqSubnetPrefix      IbSmSubnetPrefix, 
      ibSmTraceReqSessionId         Integer32, 
      ibSmTraceReqRowStatus         RowStatus,   
      ibSmTraceReqCreationTime   TimeTicks, 
      ibSmTraceReqCompMask       OCTET STRING, 
      ibSmTraceReqIDGeneration      Unsigned32, 
      ibSmTraceReqNodeType          IbNodeType, 
      ibSmTraceReqNodeID            OCTET STRING, 
      ibSmTraceReqChassisID         OCTET STRING, 
      ibSmTraceReqEntryPortID       OCTET STRING, 
      ibSmTraceReqExitPortID        OCTET STRING, 
      ibSmTraceReqEntryPort         Unsigned32, 
      ibSmTraceReqExitPort          Unsigned32  
   }  
    
   ibSmTraceReqSubnetPrefix  OBJECT-TYPE  
       SYNTAX              IbSmSubnetPrefix  
       MAX-ACCESS          not-accessible  
       STATUS              current  
       DESCRIPTION  
           "Subnet prefix of this IB subnet."  
       ::= { ibSmTraceReqEntry 1 }  
    
   ibSmTraceReqSessionId OBJECT-TYPE          
      SYNTAX         Integer32(0..2147483647) 
      MAX-ACCESS     not-accessible 
      STATUS         current 
      DESCRIPTION 
         "pseudo-random 32 bit number provided by the client." 
      ::= { ibSmTraceReqEntry 2 } 
    
   ibSmTraceReqRowStatus OBJECT-TYPE 
      SYNTAX            RowStatus 
      MAX-ACCESS        read-create 
      STATUS            current 
      DESCRIPTION 
         "RowStatus for row creation/deletion." 
      ::= { ibSmTraceReqEntry 3 } 
    
 
 
 
 
   ibSmTraceReqCreationTime OBJECT-TYPE 
      SYNTAX   TimeTicks 
      MAX-ACCESS  read-only 
      STATUS   current 
      DESCRIPTION 
         "Time stamp when this row is created." 
      ::= { ibSmTraceReqEntry 4 } 
    
   ibSmTraceReqCompMask  OBJECT-TYPE 
      SYNTAX OCTET STRING(SIZE(8)) 
      MAX-ACCESS read-create 
      STATUS current 
      DESCRIPTION 
         "64-bit Component Mask for the request." 
      ::= { ibSmTraceReqEntry 5 } 
    
   ibSmTraceReqIDGeneration         OBJECT-TYPE  
      SYNTAX              Unsigned32(0..65535) 
      MAX-ACCESS          read-create  
      STATUS              current  
      DESCRIPTION  
         "Generation of the IDs used in this attribute." 
      ::= { ibSmTraceReqEntry 6 }  
    
   ibSmTraceReqNodeType         OBJECT-TYPE  
      SYNTAX              IbNodeType 
      MAX-ACCESS          read-create  
      STATUS              current  
      DESCRIPTION  
         "Type of node being managed: 
         reserved(0), channelAdapter(1), switch(2), router(3),error(4)."  
      ::= { ibSmTraceReqEntry 7 }  
    
   ibSmTraceReqNodeID OBJECT-TYPE  
      SYNTAX              OCTET STRING(SIZE(8)) 
      MAX-ACCESS          read-create  
      STATUS              current  
      DESCRIPTION  
         "ID of the Node." 
      ::= { ibSmTraceReqEntry 8 }  
    
   ibSmTraceReqChassisID         OBJECT-TYPE  
      SYNTAX              OCTET STRING(SIZE(8)) 
      MAX-ACCESS          read-create  
      STATUS              current  
      DESCRIPTION  
         "ID of the chassis or power domain, or 0 if ChassisGUID or equivalent 
         information is unavailable."  
      ::= { ibSmTraceReqEntry 9 }  
 
 
 
 
    
   ibSmTraceReqEntryPortID         OBJECT-TYPE  
      SYNTAX              OCTET STRING(SIZE(8)) 
      MAX-ACCESS          read-create  
      STATUS              current  
      DESCRIPTION  
         "If NodeType is CA: ID of the port used. 
         If NodeType is router: ID of Entry Port. 
         Otherwise reserved."  
      ::= { ibSmTraceReqEntry 10 }  
    
   ibSmTraceReqExitPortID   OBJECT-TYPE  
      SYNTAX              OCTET STRING(SIZE(8)) 
      MAX-ACCESS          read-create  
      STATUS              current  
      DESCRIPTION  
         "If NodeType is router and path continues past this router: 
         ID of the exit port of the router.  Otherwise reserved." 
      ::= { ibSmTraceReqEntry 11 }  
    
   ibSmTraceReqEntryPort     OBJECT-TYPE  
      SYNTAX              Unsigned32(0..255) 
      MAX-ACCESS          read-create  
      STATUS              current  
      DESCRIPTION  
         "If NodeType is switch: number of the entry port. 
         Otherwise: reserved." 
      ::= { ibSmTraceReqEntry 12 }  
    
   ibSmTraceReqExitPort      OBJECT-TYPE  
      SYNTAX              Unsigned32(0..255) 
      MAX-ACCESS          read-create  
      STATUS              current  
      DESCRIPTION  
         "If NodeType is switch: number of the exit port. 
         Otherwise: reserved." 
      ::= { ibSmTraceReqEntry 13 }  
    
   ibSmTraceResultTable         OBJECT-TYPE  
      SYNTAX              SEQUENCE OF IbSmTraceResultEntry  
      MAX-ACCESS          not-accessible  
      STATUS              current  
      DESCRIPTION  
         "A table used to list all the path entries that are actively  
         managed by the Subnet Managers on this device."  
      ::= { ibSmTraceInfo 2 }  
    
   ibSmTraceResultEntry         OBJECT-TYPE  
      SYNTAX              IbSmTraceResultEntry  
 
 
 
 
      MAX-ACCESS          not-accessible  
      STATUS              current  
      DESCRIPTION  
         "Table entry for ibSmTraceResultTable."  
      INDEX { ibSmTraceResultSubnetPrefix, ibSmTraceResultSessionId, 
              ibSmTraceResultIndex } 
    
      ::= { ibSmTraceResultTable 1 }  
    
   IbSmTraceResultEntry ::= SEQUENCE { 
      ibSmTraceResultSubnetPrefix      IbSmSubnetPrefix, 
      ibSmTraceResultSessionId         Integer32, 
      ibSmTraceResultIndex          Integer32, 
      ibSmTraceResultIDGeneration      Unsigned32, 
      ibSmTraceResultNodeType          IbNodeType, 
      ibSmTraceResultNodeID            OCTET STRING, 
      ibSmTraceResultChassisID         OCTET STRING, 
      ibSmTraceResultEntryPortID       OCTET STRING, 
      ibSmTraceResultExitPortID        OCTET STRING, 
      ibSmTraceResultEntryPort         Unsigned32, 
      ibSmTraceResultExitPort          Unsigned32 
   }  
    
   ibSmTraceResultSubnetPrefix  OBJECT-TYPE  
       SYNTAX              IbSmSubnetPrefix  
       MAX-ACCESS          not-accessible  
       STATUS              current  
       DESCRIPTION  
           "Subnet prefix of this IB subnet."  
       ::= { ibSmTraceResultEntry 1 }  
    
   ibSmTraceResultSessionId OBJECT-TYPE          
      SYNTAX         Integer32(0..2147483647) 
      MAX-ACCESS     not-accessible 
      STATUS         current 
      DESCRIPTION 
         "pseudo-random 32 bit number provided by the client." 
      ::= { ibSmTraceResultEntry 2 } 
    
   ibSmTraceResultIndex  OBJECT-TYPE 
      SYNTAX         Integer32(0..2147483647) 
      MAX-ACCESS     not-accessible 
      STATUS         current 
      DESCRIPTION 
         "Index for the results." 
      ::= { ibSmTraceResultEntry 3 } 
    
   ibSmTraceResultIDGeneration         OBJECT-TYPE  
      SYNTAX              Unsigned32(0..65535) 
 
 
 
 
      MAX-ACCESS          read-only  
      STATUS              current  
      DESCRIPTION  
         "Generation of the IDs used in this attribute." 
      ::= { ibSmTraceResultEntry 4 }  
    
   ibSmTraceResultNodeType         OBJECT-TYPE  
      SYNTAX              IbNodeType 
      MAX-ACCESS          read-only  
      STATUS              current  
      DESCRIPTION  
         "Type of node being managed: 
         reserved(0), channelAdapter(1), switch(2), router(3),error(4)."  
      ::= { ibSmTraceResultEntry 5 }  
    
   ibSmTraceResultNodeID OBJECT-TYPE  
      SYNTAX              OCTET STRING(SIZE(8)) 
      MAX-ACCESS          read-only  
      STATUS              current  
      DESCRIPTION  
         "ID of the Node." 
      ::= { ibSmTraceResultEntry 6 }  
    
   ibSmTraceResultChassisID         OBJECT-TYPE  
      SYNTAX              OCTET STRING(SIZE(8)) 
      MAX-ACCESS          read-only  
      STATUS              current  
      DESCRIPTION  
         "ID of the chassis or power domain, or 0 if ChassisGUID or equivalent 
         information is unavailable."  
      ::= { ibSmTraceResultEntry 7 }  
    
   ibSmTraceResultEntryPortID         OBJECT-TYPE  
      SYNTAX              OCTET STRING(SIZE(8)) 
      MAX-ACCESS          read-only  
      STATUS              current  
      DESCRIPTION  
         "If NodeType is CA: ID of the port used. 
         If NodeType is router: ID of Entry Port. 
         Otherwise reserved."  
      ::= { ibSmTraceResultEntry 8 }  
    
   ibSmTraceResultExitPortID   OBJECT-TYPE  
      SYNTAX              OCTET STRING(SIZE(8)) 
      MAX-ACCESS          read-only  
      STATUS              current  
      DESCRIPTION  
         "If NodeType is router and path continues past this router: 
         ID of the exit port of the router.  Otherwise reserved." 
 
 
 
 
      ::= { ibSmTraceResultEntry 9 }  
    
   ibSmTraceResultEntryPort     OBJECT-TYPE  
      SYNTAX              Unsigned32(0..255) 
      MAX-ACCESS          read-only  
      STATUS              current  
      DESCRIPTION  
         "If NodeType is switch: number of the entry port. 
         Otherwise: reserved." 
      ::= { ibSmTraceResultEntry 10 }  
    
   ibSmTraceResultExitPort      OBJECT-TYPE  
      SYNTAX              Unsigned32(0..255) 
      MAX-ACCESS          read-only  
      STATUS              current  
      DESCRIPTION  
         "If NodeType is switch: number of the exit port. 
         Otherwise: reserved." 
      ::= { ibSmTraceResultEntry 11 }  
    
   -- Subnet Manager Service table  
    
   ibSmServiceTable   OBJECT-TYPE  
      SYNTAX              SEQUENCE OF IbSmServiceEntry  
      MAX-ACCESS          not-accessible  
      STATUS              current  
      DESCRIPTION  
         "A table used to list services managed by the Subnet  
         Managers on this device."  
      ::= { ibSmServiceInfo 1 }  
    
   ibSmServiceEntry   OBJECT-TYPE  
      SYNTAX              IbSmServiceEntry  
      MAX-ACCESS          not-accessible  
      STATUS              current  
      DESCRIPTION  
         "Table entry for ibSmServiceTable."  
      INDEX        { ibSmServiceSubnetPrefix, ibSmServiceID, 
                     ibSmServiceGID, ibSmServicePKey } 
       ::= { ibSmServiceTable 1 }  
    
   IbSmServiceEntry ::= SEQUENCE {   
      ibSmServiceSubnetPrefix    IbSmSubnetPrefix, 
      ibSmServiceID              OCTET STRING,  
      ibSmServiceGID             OCTET STRING,  
      ibSmServicePKey            IbPartitionKey, 
      ibSmServiceLease           Unsigned32,  
      ibSmServiceKey             OCTET STRING,  
      ibSmServiceName         SnmpAdminString,   
 
 
 
 
      ibSmServiceData         OCTET STRING 
      }  
    
   ibSmServiceSubnetPrefix OBJECT-TYPE 
      SYNTAX              IbSmSubnetPrefix 
      MAX-ACCESS          not-accessible 
      STATUS              current 
      DESCRIPTION 
         "Subnet prefix of this IB subnet." 
      ::= { ibSmServiceEntry 1 }  
    
   ibSmServiceID         OBJECT-TYPE  
      SYNTAX              OCTET STRING (SIZE(8))  
      MAX-ACCESS          not-accessible 
      STATUS              current  
      DESCRIPTION  
         "The 64-bit ID of the service."  
      ::= { ibSmServiceEntry 2 }  
    
   ibSmServiceGID        OBJECT-TYPE  
      SYNTAX              OCTET STRING (SIZE(16))  
      MAX-ACCESS          not-accessible 
      STATUS              current  
      DESCRIPTION  
         "The 128-bit multicast GID address."  
      ::= { ibSmServiceEntry 3 }  
    
   ibSmServicePKey    OBJECT-TYPE  
      SYNTAX              IbPartitionKey 
      MAX-ACCESS          not-accessible 
      STATUS              current  
      DESCRIPTION  
         "The 16-bit P-Key."  
      ::= { ibSmServiceEntry 4 }  
    
   ibSmServiceLease  OBJECT-TYPE  
      SYNTAX              Unsigned32  
      MAX-ACCESS          read-only  
      STATUS              current  
      DESCRIPTION  
         "Lease period remaining (in seconds) for this service. 
         A value of 4294967295 means the lease is indefinite." 
      ::= { ibSmServiceEntry 5 }  
    
   ibSmServiceKey    OBJECT-TYPE  
      SYNTAX              OCTET STRING (SIZE(16))  
      MAX-ACCESS          read-only  
      STATUS              current  
      DESCRIPTION  
 
 
 
 
         "The 64-bit service key."  
      ::= { ibSmServiceEntry 6 }  
    
   ibSmServiceName OBJECT-TYPE  
      SYNTAX              SnmpAdminString(SIZE(0..64))  
      MAX-ACCESS          read-only  
      STATUS              current  
      DESCRIPTION  
         "The name of this service." 
      ::= { ibSmServiceEntry 7 }  
    
   ibSmServiceData OBJECT-TYPE  
      SYNTAX              OCTET STRING (SIZE(64))  
      MAX-ACCESS          read-only  
      STATUS              current  
      DESCRIPTION  
         "Data associated with this service." 
      ::= { ibSmServiceEntry 8 }  
    
   -- Subnet Manager Service Association table  
   -- 
   -- When a row of this table is created or deleted, a pair of  
   -- { Service Key, Service Name } mapping is being added or removed on  
   -- the device. 
   -- 
    
   ibSmServiceAssocTable   OBJECT-TYPE  
      SYNTAX              SEQUENCE OF IbSmServiceAssocEntry  
      MAX-ACCESS          not-accessible  
      STATUS              current  
      DESCRIPTION  
         "A table used to list service associations managed by the  
         Subnet Managers on this device."  
      ::= { ibSmServiceInfo 2 }  
    
   ibSmServiceAssocEntry   OBJECT-TYPE  
      SYNTAX              IbSmServiceAssocEntry  
      MAX-ACCESS          not-accessible  
      STATUS              current  
      DESCRIPTION  
         "Table entry for ibSmServiceAssocTable."  
      INDEX { ibSmServiceAssocSubnetPrefix, ibSmServiceAssocKey,  
              IMPLIED ibSmServiceName} 
       ::= { ibSmServiceAssocTable 1 }  
    
   IbSmServiceAssocEntry ::= SEQUENCE {   
      ibSmServiceAssocSubnetPrefix    IbSmSubnetPrefix, 
      ibSmServiceAssocKey             OCTET STRING,  
      ibSmServiceAssocName          SnmpAdminString,   
 
 
 
 
      ibSmServiceAssocRowStatus     RowStatus 
      }  
    
   ibSmServiceAssocSubnetPrefix OBJECT-TYPE 
      SYNTAX              IbSmSubnetPrefix 
      MAX-ACCESS          not-accessible 
      STATUS              current 
      DESCRIPTION 
         "Subnet prefix of this IB subnet." 
      ::= { ibSmServiceAssocEntry 1 }  
    
   ibSmServiceAssocKey    OBJECT-TYPE  
      SYNTAX              OCTET STRING (SIZE(16))  
      MAX-ACCESS          not-accessible  
      STATUS              current 
      DESCRIPTION  
         "The 64-bit service key."  
      ::= { ibSmServiceAssocEntry 2 }  
    
   ibSmServiceAssocName OBJECT-TYPE  
      SYNTAX            SnmpAdminString(SIZE(0..64))  
      MAX-ACCESS          not-accessible  
      STATUS              current  
      DESCRIPTION  
         "The name of this service." 
      ::= { ibSmServiceAssocEntry 3 }  
    
   ibSmServiceAssocRowStatus OBJECT-TYPE  
      SYNTAX              RowStatus 
      MAX-ACCESS          read-create  
      STATUS              current  
      DESCRIPTION  
         "The RowStatus for row creation and deletion." 
      ::= { ibSmServiceAssocEntry 4 }  
    
   -- GUID Info table 
    
   ibSmGUIDInfoTable        OBJECT-TYPE  
      SYNTAX                      SEQUENCE OF IbSmGUIDInfoEntry  
      MAX-ACCESS                  not-accessible  
      STATUS                      current  
      DESCRIPTION  
         "A table used to list Guid information of ports on CA, routers and  
         switches that are managed by the Subnet Managers on this device."  
      ::= { ibSmGUIDInfo 1 }  
    
   ibSmGUIDInfoEntry        OBJECT-TYPE  
      SYNTAX                      IbSmGUIDInfoEntry  
      MAX-ACCESS                  not-accessible  
 
 
 
 
      STATUS                      current  
      DESCRIPTION  
         "Table entry for ibSmGUIDInfoTable."  
      INDEX { ibSmGUIDInfoSubnetPrefix, ibSmGUIDInfoNodeGUID,  
         ibSmGUIDInfoPortNum, ibSmGUIDInfoBlockNum }  
       ::= { ibSmGUIDInfoTable 1 }  
    
   IbSmGUIDInfoEntry ::= SEQUENCE {   
      ibSmGUIDInfoSubnetPrefix    IbSmSubnetPrefix,  
      ibSmGUIDInfoNodeGUID        IbGuid, 
      ibSmGUIDInfoPortNum         IbDataPort, 
      ibSmGUIDInfoBlockNum        Unsigned32,  
      ibSmGUIDInfoBlock           OCTET STRING 
   }  
    
   ibSmGUIDInfoSubnetPrefix OBJECT-TYPE  
      SYNTAX              IbSmSubnetPrefix  
      MAX-ACCESS          not-accessible  
      STATUS              current  
      DESCRIPTION  
         "Subnet prefix of this IB subnet."  
      ::= { ibSmGUIDInfoEntry 1 }  
    
   ibSmGUIDInfoNodeGUID OBJECT-TYPE  
      SYNTAX                IbGuid 
      MAX-ACCESS          not-accessible  
      STATUS              current  
      DESCRIPTION  
         "The 64-bit Node GUID of this Guid Info entry."  
      ::= { ibSmGUIDInfoEntry 2 }  
    
   ibSmGUIDInfoPortNum OBJECT-TYPE  
      SYNTAX           IbDataPort 
      MAX-ACCESS          not-accessible  
      STATUS              current  
      DESCRIPTION  
         "The port number of this Guid Info entry."  
      ::= { ibSmGUIDInfoEntry 3 }  
    
   ibSmGUIDInfoBlockNum OBJECT-TYPE  
      SYNTAX            Unsigned32(0..31) 
      MAX-ACCESS          not-accessible  
      STATUS              current  
      DESCRIPTION  
         "The port number of this Guid Info entry."  
      ::= { ibSmGUIDInfoEntry 4 }  
    
   ibSmGUIDInfoBlock   OBJECT-TYPE  
      SYNTAX            OCTET STRING(SIZE(64)) 
 
 
 
 
      MAX-ACCESS          read-only 
      STATUS              current  
      DESCRIPTION  
         "The GUIDInfo block."  
      ::= { ibSmGUIDInfoEntry 5 }  
    
   -- Notification data objects 
    
   ibSmTrapSubnetPrefix OBJECT-TYPE 
      SYNTAX IbSmSubnetPrefix 
      MAX-ACCESS accessible-for-notify 
      STATUS current 
      DESCRIPTION 
         "Subnet prefix of the source of the trap." 
      ::= { ibSmTrapData 1 } 
    
   ibSmTrapType OBJECT-TYPE 
      SYNTAX INTEGER { 
            fatal(0), 
            urgent(1), 
            security(2), 
            subnetMgmt(3), 
            informational(4) 
            }   
      MAX-ACCESS accessible-for-notify 
      STATUS current 
      DESCRIPTION 
         "Enumeration indicates the type of the trap." 
      ::= { ibSmTrapData 2 } 
    
   ibSmTrapProducerType OBJECT-TYPE 
      SYNTAX INTEGER {   
            channelAdapter(1),  
            switch(2),  
            router(3), 
            subnetMgmt(4)  
            } 
      MAX-ACCESS accessible-for-notify 
      STATUS current 
      DESCRIPTION 
         "Type of node producing the trap: 
         1: channelAdapter; 2: switch; 3: router; 4: subnet management."  
      ::= { ibSmTrapData 3 } 
    
   ibSmTrapNodeGUID1 OBJECT-TYPE 
      SYNTAX IbGuid 
      MAX-ACCESS accessible-for-notify 
      STATUS current 
      DESCRIPTION 
 
 
 
 
         "Node GUID of the related node." 
      ::= { ibSmTrapData 4 } 
    
   ibSmTrapPortNum1 OBJECT-TYPE 
      SYNTAX IbDataPort 
      MAX-ACCESS accessible-for-notify 
      STATUS current 
      DESCRIPTION 
         "Local port number of the related port." 
      ::= { ibSmTrapData 5 } 
    
   ibSmTrapNodeGUID2 OBJECT-TYPE 
      SYNTAX IbGuid 
      MAX-ACCESS accessible-for-notify 
      STATUS current 
      DESCRIPTION 
         "Node GUID of the related node." 
      ::= { ibSmTrapData 6 } 
    
   ibSmTrapPortNum2 OBJECT-TYPE 
      SYNTAX IbDataPort 
      MAX-ACCESS accessible-for-notify 
      STATUS current 
      DESCRIPTION 
         "Local port number of the related port." 
      ::= { ibSmTrapData 7 } 
    
   ibSmTrapMCGid OBJECT-TYPE 
      SYNTAX OCTET STRING(SIZE(16)) 
      MAX-ACCESS accessible-for-notify 
      STATUS current 
      DESCRIPTION 
         "Related Multicast GID." 
      ::= { ibSmTrapData 8 } 
    
   ibSmTrapSwitchGUID OBJECT-TYPE 
      SYNTAX IbGuid 
      MAX-ACCESS accessible-for-notify 
      STATUS current 
      DESCRIPTION 
         "Related Switch node guid." 
      ::= { ibSmTrapData 9 } 
    
   ibSmTrapSwitchPortNum OBJECT-TYPE 
      SYNTAX IbDataPort 
      MAX-ACCESS accessible-for-notify 
      STATUS current 
      DESCRIPTION 
         "Related Switch port number." 
 
 
 
 
      ::= { ibSmTrapData 10 } 
    
   ibSmTrapCapabilityMask OBJECT-TYPE 
      SYNTAX OCTET STRING(SIZE(4)) 
      MAX-ACCESS accessible-for-notify 
      STATUS current 
      DESCRIPTION 
         "Related port capability mask." 
      ::= { ibSmTrapData 11 } 
    
   ibSmTrapSystemImageGUID OBJECT-TYPE 
      SYNTAX IbGuid 
      MAX-ACCESS accessible-for-notify 
      STATUS current 
      DESCRIPTION 
         "Related system image guid." 
      ::= { ibSmTrapData 12 } 
    
   ibSmTrapMethod OBJECT-TYPE 
      SYNTAX Unsigned32(0..65535) 
      MAX-ACCESS accessible-for-notify 
      STATUS current 
      DESCRIPTION 
         "Related MAD method." 
      ::= { ibSmTrapData 13 } 
    
   ibSmTrapAttribId OBJECT-TYPE 
      SYNTAX Unsigned32(0..65535) 
      MAX-ACCESS accessible-for-notify 
      STATUS current 
      DESCRIPTION 
         "Related MAD attribute ID." 
      ::= { ibSmTrapData 14 } 
    
   ibSmTrapAttribModifier OBJECT-TYPE 
      SYNTAX Unsigned32 
      MAX-ACCESS accessible-for-notify 
      STATUS current 
      DESCRIPTION 
         "Related MAD attribute modifier." 
      ::= { ibSmTrapData 15 } 
    
   ibSmTrapMKey OBJECT-TYPE 
      SYNTAX OCTET STRING(SIZE(8)) 
      MAX-ACCESS accessible-for-notify 
      STATUS current 
      DESCRIPTION 
         "Related voliating M Key." 
      ::= { ibSmTrapData 16 } 
 
 
 
 
    
   ibSmTrapDRSLid OBJECT-TYPE 
      SYNTAX Unsigned32(0..65535) 
      MAX-ACCESS accessible-for-notify 
      STATUS current 
      DESCRIPTION 
         "Directed Route LID of the SMP causing this trap." 
      ::= { ibSmTrapData 17 } 
    
   ibSmTrapDRNotice OBJECT-TYPE 
      SYNTAX TruthValue 
      MAX-ACCESS accessible-for-notify 
      STATUS current 
      DESCRIPTION 
         "Indicates whether this event results from a directed  
         route SMP." 
      ::= { ibSmTrapData 18 } 
    
   ibSmTrapDRPathTruncated OBJECT-TYPE 
      SYNTAX TruthValue 
      MAX-ACCESS accessible-for-notify 
      STATUS current 
      DESCRIPTION 
         "Indicates whether the return path has been truncated." 
      ::= { ibSmTrapData 19 } 
    
   ibSmTrapDRHopCount OBJECT-TYPE 
      SYNTAX Unsigned32(0..63) 
      MAX-ACCESS accessible-for-notify 
      STATUS current 
      DESCRIPTION 
         "Number of hops in the route." 
      ::= { ibSmTrapData 20 } 
    
   ibSmTrapDRReturnPath OBJECT-TYPE 
      SYNTAX OCTET STRING(SIZE(0..30)) 
      MAX-ACCESS accessible-for-notify 
      STATUS current 
      DESCRIPTION 
         "Return path from the directed route SMP." 
      ::= { ibSmTrapData 21 } 
    
   ibSmTrapPKey OBJECT-TYPE 
      SYNTAX IbPartitionKey 
      MAX-ACCESS accessible-for-notify 
      STATUS current 
      DESCRIPTION 
         "The violating partition key." 
      ::= { ibSmTrapData 22 } 
 
 
 
 
    
   ibSmTrapQueuePair1 OBJECT-TYPE 
      SYNTAX Unsigned32(0..16777215) 
      MAX-ACCESS accessible-for-notify 
      STATUS current 
      DESCRIPTION 
         "The related queue pair." 
      ::= { ibSmTrapData 23 } 
    
   ibSmTrapQueuePair2 OBJECT-TYPE 
      SYNTAX Unsigned32(0..16777215) 
      MAX-ACCESS accessible-for-notify 
      STATUS current 
      DESCRIPTION 
         "The related queue pair." 
      ::= { ibSmTrapData 24 } 
    
   ibSmTrapServiceLevel OBJECT-TYPE 
      SYNTAX Unsigned32(0..15) 
      MAX-ACCESS accessible-for-notify 
      STATUS current 
      DESCRIPTION 
         "The related service level." 
      ::= { ibSmTrapData 25 } 
    
   ibSmTrapQKey OBJECT-TYPE 
      SYNTAX OCTET STRING(SIZE(4)) 
      MAX-ACCESS accessible-for-notify 
      STATUS current 
      DESCRIPTION 
         "The violating Q key." 
      ::= { ibSmTrapData 26 } 
            
   ibSmTrapDataValid OBJECT-TYPE 
      SYNTAX BITS { 
             lidAddr1(0), 
             lidAddr2(1), 
             pKey(2), 
             sl(3), 
             qp1(4), 
             qp2(5), 
             gidAddr1(6), 
             gidAddr2(7), 
             reserved(8) 
             } 
      MAX-ACCESS accessible-for-notify 
      STATUS current 
      DESCRIPTION 
         "Indicates validity of the optional data fields of  
 
 
 
 
         ibSmTrapSwitchExternalPortsBadPKey." 
      ::= { ibSmTrapData 27 } 
    
   ibSmTrapVendorID OBJECT-TYPE 
      SYNTAX IbSmVendorID 
      MAX-ACCESS accessible-for-notify 
      STATUS current 
      DESCRIPTION 
         "Device vendor ID, per IEEE.  
         see www.standards.ieee.org/regauth/oui/oui.txt for details." 
      ::= { ibSmTrapData 28 } 
    
   ibSmTrapDeviceID OBJECT-TYPE  
      SYNTAX OCTET STRING (SIZE(2))  
      MAX-ACCESS accessible-for-notify 
      STATUS current  
      DESCRIPTION  
         "Device ID information as assigned by device manufacturer."  
      ::= { ibSmTrapData 29 } 
    
   ibSmTrapVendorDetailedData OBJECT-TYPE  
      SYNTAX OCTET STRING (SIZE(54)) 
      MAX-ACCESS accessible-for-notify 
      STATUS current  
      DESCRIPTION  
         "Vendor specific detailed notification data." 
      ::= { ibSmTrapData 30 } 
    
   -- generic notifications(traps) -- 
    
   -- to make the notifications reversible  
   ibSmGenericTrapsPrefix OBJECT IDENTIFIER 
      ::= { ibSmGenericTraps 0 } 
    
   ibSmTrapInService NOTIFICATION-TYPE 
      OBJECTS {  
         ibSmTrapSubnetPrefix, 
         ibSmTrapType, 
         ibSmTrapProducerType, 
         ibSmTrapNodeGUID1, 
         ibSmTrapPortNum1 
         } 
      STATUS    current 
      DESCRIPTION 
         "Port is now in service." 
      ::= { ibSmGenericTrapsPrefix 1 } 
    
   ibSmTrapOutOfService NOTIFICATION-TYPE 
      OBJECTS {  
 
 
 
 
         ibSmTrapSubnetPrefix, 
         ibSmTrapType, 
         ibSmTrapProducerType, 
         ibSmTrapNodeGUID1, 
         ibSmTrapPortNum1 
         } 
      STATUS    current 
      DESCRIPTION 
         "Port is now out of service." 
      ::= { ibSmGenericTrapsPrefix 2 } 
    
   ibSmTrapMCGroupCreated NOTIFICATION-TYPE 
      OBJECTS {  
         ibSmTrapSubnetPrefix, 
         ibSmTrapType, 
         ibSmTrapProducerType, 
         ibSmTrapMCGid 
         } 
      STATUS    current 
      DESCRIPTION 
         "A multicast group has been created." 
      ::= { ibSmGenericTrapsPrefix 3 } 
    
   ibSmTrapMCGroupDeleted NOTIFICATION-TYPE 
      OBJECTS {  
         ibSmTrapSubnetPrefix, 
         ibSmTrapType, 
         ibSmTrapProducerType, 
         ibSmTrapMCGid 
         } 
      STATUS    current 
      DESCRIPTION 
         "A multicast group has been deleted." 
      ::= { ibSmGenericTrapsPrefix 4 } 
    
   ibSmTrapSwitchLinkStateChanged NOTIFICATION-TYPE 
      OBJECTS {  
         ibSmTrapSubnetPrefix, 
         ibSmTrapType, 
         ibSmTrapProducerType, 
         ibSmTrapSwitchGUID, 
         ibSmTrapSwitchPortNum 
         } 
      STATUS    current 
      DESCRIPTION 
         "A switch port's link state has changed." 
      ::= { ibSmGenericTrapsPrefix 5 } 
    
   ibSmTrapLinkIntegrityThreasholdReached NOTIFICATION-TYPE 
 
 
 
 
      OBJECTS {  
         ibSmTrapSubnetPrefix, 
         ibSmTrapType, 
         ibSmTrapProducerType, 
         ibSmTrapNodeGUID1, 
         ibSmTrapPortNum1 
         } 
      STATUS    current 
      DESCRIPTION 
         "A port's link integrity threashold has been reached." 
      ::= { ibSmGenericTrapsPrefix 6 } 
    
   ibSmTrapBufferOverrunThresholdReached NOTIFICATION-TYPE 
      OBJECTS {  
         ibSmTrapSubnetPrefix, 
         ibSmTrapType, 
         ibSmTrapProducerType, 
         ibSmTrapNodeGUID1, 
         ibSmTrapPortNum1 
         } 
      STATUS    current 
      DESCRIPTION 
         "A port's buffer overrun threashold has been reached." 
      ::= { ibSmGenericTrapsPrefix 7 } 
    
   ibSmTrapFlowControlUpdateWatchdogTimerExpired NOTIFICATION-TYPE 
      OBJECTS {  
         ibSmTrapSubnetPrefix, 
         ibSmTrapType, 
         ibSmTrapProducerType, 
         ibSmTrapNodeGUID1, 
         ibSmTrapPortNum1 
         } 
      STATUS    current 
      DESCRIPTION 
         "A port's flow control update watchdog timer has expired." 
      ::= { ibSmGenericTrapsPrefix 8 } 
    
   ibSmTrapCapabilityMaskChanged NOTIFICATION-TYPE 
      OBJECTS {  
         ibSmTrapSubnetPrefix, 
         ibSmTrapType, 
         ibSmTrapProducerType, 
         ibSmTrapNodeGUID1, 
         ibSmTrapPortNum1, 
         ibSmTrapCapabilityMask 
         } 
      STATUS    current 
      DESCRIPTION 
 
 
 
 
         "A port's capability mask has changed." 
      ::= { ibSmGenericTrapsPrefix 9 } 
    
   ibSmTrapSystemImageGUIDChanged NOTIFICATION-TYPE 
      OBJECTS {  
         ibSmTrapSubnetPrefix, 
         ibSmTrapType, 
         ibSmTrapProducerType, 
         ibSmTrapNodeGUID1, 
         ibSmTrapSystemImageGUID 
         } 
      STATUS    current 
      DESCRIPTION 
         "A node's system image guid has changed." 
      ::= { ibSmGenericTrapsPrefix 10 } 
    
   ibSmTrapBadMKey NOTIFICATION-TYPE 
      OBJECTS {  
         ibSmTrapSubnetPrefix, 
         ibSmTrapType, 
         ibSmTrapProducerType, 
         ibSmTrapNodeGUID1, 
         ibSmTrapPortNum1, 
         ibSmTrapNodeGUID2, 
         ibSmTrapPortNum2, 
         ibSmTrapMethod, 
         ibSmTrapAttribId, 
         ibSmTrapAttribModifier, 
         ibSmTrapMKey, 
         ibSmTrapDRSLid, 
         ibSmTrapDRNotice, 
         ibSmTrapDRPathTruncated, 
         ibSmTrapDRHopCount, 
         ibSmTrapDRReturnPath 
         } 
      STATUS    current 
      DESCRIPTION 
         "An invalid M Key has been encountered." 
      ::= { ibSmGenericTrapsPrefix 11 } 
    
   ibSmTrapBadPKey NOTIFICATION-TYPE 
      OBJECTS {  
         ibSmTrapSubnetPrefix, 
         ibSmTrapType, 
         ibSmTrapProducerType, 
         ibSmTrapNodeGUID1, 
         ibSmTrapPortNum1, 
         ibSmTrapNodeGUID2, 
         ibSmTrapPortNum2, 
 
 
 
 
         ibSmTrapPKey, 
         ibSmTrapQueuePair1, 
         ibSmTrapQueuePair2, 
         ibSmTrapServiceLevel 
         } 
      STATUS    current 
      DESCRIPTION 
         "An invalid Partition Key has been encountered." 
      ::= { ibSmGenericTrapsPrefix 12 } 
    
   ibSmTrapBadQKey NOTIFICATION-TYPE 
      OBJECTS {  
         ibSmTrapSubnetPrefix, 
         ibSmTrapType, 
         ibSmTrapProducerType, 
         ibSmTrapNodeGUID1, 
         ibSmTrapPortNum1, 
         ibSmTrapNodeGUID2, 
         ibSmTrapPortNum2, 
         ibSmTrapQKey, 
         ibSmTrapQueuePair1, 
         ibSmTrapQueuePair2, 
         ibSmTrapServiceLevel 
         } 
      STATUS    current 
      DESCRIPTION 
         "An invalid Partition Key has been encountered." 
      ::= { ibSmGenericTrapsPrefix 13 } 
    
   ibSmTrapSwitchExternalPortsBadPKey NOTIFICATION-TYPE 
      OBJECTS {  
         ibSmTrapSubnetPrefix, 
         ibSmTrapType, 
         ibSmTrapProducerType, 
         ibSmTrapSwitchGUID, 
         ibSmTrapSwitchPortNum, 
         ibSmTrapDataValid, 
         ibSmTrapNodeGUID1, 
         ibSmTrapPortNum1, 
         ibSmTrapNodeGUID2, 
         ibSmTrapPortNum2, 
         ibSmTrapPKey, 
         ibSmTrapQueuePair1, 
         ibSmTrapQueuePair2, 
         ibSmTrapServiceLevel 
         } 
      STATUS    current 
      DESCRIPTION 
         "An invalid Partition Key has been encountered by switch." 
 
 
 
 
      ::= { ibSmGenericTrapsPrefix 14 } 
    
   -- Vendor specific notifications(traps) -- 
    
   -- to make notifications reversible  
   ibSmVendorTrapsPrefix OBJECT IDENTIFIER 
      ::= { ibSmVendorTraps 0 } 
    
   ibSmTrapVendorSpecific NOTIFICATION-TYPE 
      OBJECTS {  
         ibSmTrapSubnetPrefix, 
         ibSmTrapType, 
         ibSmTrapVendorID, 
         ibSmTrapDeviceID, 
         ibSmTrapNodeGUID1, 
         ibSmTrapPortNum1, 
         ibSmTrapVendorDetailedData 
         } 
      STATUS    current 
      DESCRIPTION 
         "Vendor specific notification." 
      ::= { ibSmVendorTrapsPrefix 1 } 
    
   -- compliance statements 
   ibSmMIBCompliance MODULE-COMPLIANCE 
      STATUS current 
      DESCRIPTION  
         "The compliance statement for SNMP entities which implement 
         version 1 of the IB SM MIB." 
      MODULE  -- this module 
      MANDATORY-GROUPS { 
                       ibSmConfigInfoGroup, 
                       ibSmNodeInfoGroup, 
                       ibSmPortInfoGroup, 
                       ibSmSwitchInfoGroup, 
                       ibSmPartitionInfoGroup, 
                       ibSmSMInfoGroup, 
                       ibSmPathInfoGroup, 
                       ibSmServiceInfoGroup, 
                       ibSmGenericTrapsObjGroup, 
                       ibSmGenericTrapsGroup 
           } 
      GROUP ibSmMcastInfoGroup 
      DESCRIPTION 
         "The ibSmMcastInfoGroup will be implemented only on those 
         Subnet Manager where MCMemeberRecord is supported." 
    
      GROUP ibSmGUIDInfoGroup 
      DESCRIPTION 
 
 
 
 
         "The ibSmGUIDInfoGroup will be implemented only on those 
         Subnet Manager where GUIDInfoRecord is supported." 
    
      GROUP ibSmLinkInfoGroup 
      DESCRIPTION 
         "The ibSmLinkInfoGroup will be implemented only on those 
         Subnet Manager where LinkRecord is supported." 
    
      GROUP ibSmTraceInfoGroup 
      DESCRIPTION 
         "The ibSmTraceInfoGroup will be implemented only on those 
         Subnet Manager where TraceRecord is supported." 
    
      GROUP ibSmMultiPathInfoGroup 
      DESCRIPTION 
         "The ibSmMultiPathInfoGroup will be implemented only on those 
         Subnet Manager where MultiPathRecord is supported." 
    
      OBJECT ibSmConfigResponseTimeout 
      MIN-ACCESS not-accessible 
      DESCRIPTION 
         "Read and write access is not required for agents which 
         cannot provide a mechanism to manage this object." 
    
      OBJECT ibSmConfigDefaultLMC 
      MIN-ACCESS read-only 
      DESCRIPTION 
         "Write access is not required for agents which 
         cannot provide a mechanism to manage this object." 
    
      OBJECT ibSmPortInfoLMC  
      MIN-ACCESS read-only 
      DESCRIPTION 
         "Write access is not required for agents which 
         cannot provide a mechanism to modify this value safely." 
    
      OBJECT ibSmPartitionLastChange  
      MIN-ACCESS not-accessible 
      DESCRIPTION 
         "Read access is not required for agents which 
         cannot provide a reliable mechanism to manage this object." 
    
      GROUP ibSmVendorSpecificTrapsObjGroup 
      DESCRIPTION 
         "The ibSmVendorSpecificTrapsObjGroup will be implemented only on 
   those 
         Subnet Manager where vendor specific traps are supported." 
    
      GROUP ibSmVendorSpecificTrapsGroup  
 
 
 
 
      DESCRIPTION 
         "The ibSmVendorSpecificTrapsGroup will be implemented only on 
   those 
         Subnet Manager where vendor specific traps are supported." 
    
    
      ::= { ibSmMIBCompliances 1 } 
    
   ibSmConfigInfoGroup OBJECT-GROUP 
      OBJECTS { 
         ibSmConfigSubnetGUID, 
         ibSmConfigPriority, 
         ibSmConfigSMKey,          
         ibSmConfigAdminSMState, 
         ibSmConfigSMState,         
         ibSmConfigActCount,       
         ibSmConfigStatus,         
         ibSmConfigSweepInterval,  
         ibSmConfigResponseTimeout, 
         ibSmConfigPortAgingTime,   
         ibSmConfigMinUnicastLID,   
         ibSmConfigMaxUnicastLID,   
         ibSmConfigDefaultLMC,      
         ibSmConfigMasterPollInterval, 
         ibSmConfigMasterPollRetries,  
         ibSmConfigMKeyLeasePeriod    
      }  
      STATUS current 
      DESCRIPTION 
         "The collection of objects which configures the subnet manager." 
      ::= { ibSmMIBGroups 1 } 
    
   ibSmNodeInfoGroup OBJECT-GROUP 
      OBJECTS { 
         ibSmNodeInfoBaseVersion,  
         ibSmNodeInfoClassVersion,    
         ibSmNodeInfoType,            
         ibSmNodeInfoNumPorts,        
         ibSmNodeInfoSystemImageGUID, 
         ibSmNodeInfoPartitionCap,    
         ibSmNodeInfoDeviceID, 
         ibSmNodeInfoRevision,        
         ibSmNodeInfoVendorID,        
         ibSmNodeInfoDescription     
      }  
      STATUS current 
      DESCRIPTION 
         "The collection of objects which represent ib nodes." 
      ::= { ibSmMIBGroups 2 } 
 
 
 
 
    
   ibSmPortInfoGroup OBJECT-GROUP 
      OBJECTS { 
         ibSmPortInfoMKey,            
         ibSmPortInfoGIDPrefix,       
         ibSmPortInfoLID,             
         ibSmPortInfoMasterSmLID,     
         ibSmPortInfoCapMask,         
         ibSmPortInfoDiagCode,        
         ibSmPortInfoMKeyLeasePeriod, 
         ibSmPortInfoLinkWidthEnabled, 
         ibSmPortInfoLinkWidthSupported, 
         ibSmPortInfoLinkWidthActive,    
         ibSmPortInfoLinkSpeedSupported, 
         ibSmPortInfoState, 
         ibSmPortInfoPhyState,           
         ibSmPortInfoLinkDownDefState, 
         ibSmPortInfoMKeyProtBits,       
         ibSmPortInfoLMC,                
         ibSmPortInfoLinkSpeedActive,    
         ibSmPortInfoLinkSpeedEnabled, 
         ibSmPortInfoNeighborMTU,      
         ibSmPortInfoMasterSmSL,       
         ibSmPortInfoVLCap,            
         ibSmPortInfoVLHighLimit,      
         ibSmPortInfoVLArbHighCap,     
         ibSmPortInfoVLArbLowCap,      
         ibSmPortInfoMTUCap,           
         ibSmPortInfoVLStallCount,     
         ibSmPortInfoHOQLife,          
         ibSmPortInfoOperVL,           
         ibSmPortInfoInPartEnforce,    
         ibSmPortInfoOutPartEnforce,   
         ibSmPortInfoInFilterRawPktEnf, 
         ibSmPortInfoOutFilterRawPktEnf, 
         ibSmPortInfoMKeyViolation,      
         ibSmPortInfoPKeyViolation,      
         ibSmPortInfoQKeyViolation,      
         ibSmPortInfoGUIDCap,            
         ibSmPortInfoSubnetTimeout,      
         ibSmPortInfoRespTime,           
         ibSmPortInfoLocalPhyError,      
         ibSmPortInfoOverrunError,      
         ibSmPortInfoInitType,           
         ibSmPortInfoInitTypeReply 
      }  
      STATUS current 
      DESCRIPTION 
         "The collection of objects which represent ib ports." 
 
 
 
 
      ::= { ibSmMIBGroups 3 } 
    
   ibSmSwitchInfoGroup OBJECT-GROUP 
      OBJECTS { 
         ibSmSwitchInfoLinearFdbCap, 
         ibSmSwitchInfoRandomFdbCap, 
         ibSmSwitchInfoMcastFdbCap, 
         ibSmSwitchInfoLinearFdbTop, 
         ibSmSwitchInfoDefaultPort, 
         ibSmSwitchInfoDefPriMcastPort, 
         ibSmSwitchInfoDefNonPriMcastPort, 
         ibSmSwitchInfoLifeTimeValue, 
         ibSmSwitchInfoPortStateChange, 
         ibSmSwitchInfoLIDsPerPort, 
         ibSmSwitchInfoPartitionEnfCap, 
         ibSmSwitchInfoInEnfCap, 
         ibSmSwitchInfoOutEnfCap, 
         ibSmSwitchInfoInFilterRawPktCap, 
         ibSmSwitchInfoOutFilterRawPktCap, 
         ibSmSwitchInfoEnhanced0 
      }  
      STATUS current 
      DESCRIPTION 
         "The collection of objects which represent ib switches." 
      ::= { ibSmMIBGroups 4 } 
    
   ibSmPartitionInfoGroup OBJECT-GROUP 
      OBJECTS { 
         ibSmPartitionVector, 
         ibSmPartitionVectorSize, 
         ibSmPartitionVectorElementSize, 
         ibSmPartitionLastChange, 
         ibSmPartitionConfigSubnetPrefix, 
         ibSmPartitionConfigKey,     
         ibSmPartitionConfigAction,  
         ibSmPartitionConfigMemberNodeGUID, 
         ibSmPartitionConfigMemberPortNum, 
         ibSmPartitionConfigMemberType 
      }  
      STATUS current 
      DESCRIPTION 
         "The collection of objects for partition management." 
      ::= { ibSmMIBGroups 5 } 
    
   ibSmMcastInfoGroup OBJECT-GROUP 
      OBJECTS { 
         ibSmMcastGroupQKey, 
         ibSmMcastGroupMLID, 
         ibSmMcastGroupMTU, 
 
 
 
 
         ibSmMcastGroupTClass, 
         ibSmMcastGroupPKey, 
         ibSmMcastGroupRate, 
         ibSmMcastGroupPacketLifeTime, 
         ibSmMcastGroupSL, 
         ibSmMcastGroupFlowLabel, 
         ibSmMcastGroupHopLimit, 
         ibSmMcastGroupScope, 
         ibSmMcastMemberVector, 
         ibSmMcastMemberVectorSize, 
         ibSmMcastMemberVectorElementSize, 
         ibSmMcastMemberLastChange 
      }  
      STATUS current 
      DESCRIPTION 
         "The collection of objects for multicast management." 
      ::= { ibSmMIBGroups 6 } 
    
   ibSmSMInfoGroup OBJECT-GROUP 
      OBJECTS { 
         ibSmSMInfoSMKey, 
         ibSmSMInfoActCount, 
         ibSmSMInfoPriority, 
         ibSmSMInfoSMState 
      }  
      STATUS current 
      DESCRIPTION 
         "The collection of objects which represent IB subnet managers." 
      ::= { ibSmMIBGroups 7 } 
    
   ibSmLinkInfoGroup OBJECT-GROUP 
      OBJECTS { 
         ibSmLinkToNodeGUID, 
         ibSmLinkToPortNum 
      }  
      STATUS current 
      DESCRIPTION 
         "The collection of objects which represent IB links." 
      ::= { ibSmMIBGroups 8 } 
    
   ibSmPathInfoGroup OBJECT-GROUP 
      OBJECTS { 
         ibSmPathReqRowStatus, 
         ibSmPathReqCreationTime, 
         ibSmPathReqRowCompMask, 
         ibSmPathReqDstGID, 
         ibSmPathReqSrcGID, 
         ibSmPathReqNumbPath, 
         ibSmPathReqDstLID, 
 
 
 
 
         ibSmPathReqSrcLID, 
         ibSmPathReqRawTraffic, 
         ibSmPathReqFlowLabel, 
         ibSmPathReqHopLimit, 
         ibSmPathReqTClass, 
         ibSmPathReqPKey, 
         ibSmPathReqSL, 
         ibSmPathReqMTUSel, 
         ibSmPathReqMTU, 
         ibSmPathReqRateSel, 
         ibSmPathReqRate, 
         ibSmPathReqPktLifeTimeSel, 
         ibSmPathReqPktLifeTime, 
         ibSmPathReqPreference, 
         ibSmPathResultDstGID, 
         ibSmPathResultSrcGID, 
         ibSmPathResultNumbPath, 
         ibSmPathResultDstLID, 
         ibSmPathResultSrcLID, 
         ibSmPathResultRawTraffic, 
         ibSmPathResultFlowLabel, 
         ibSmPathResultHopLimit, 
         ibSmPathResultTClass, 
         ibSmPathResultPKey, 
         ibSmPathResultSL, 
         ibSmPathResultMTUSel, 
         ibSmPathResultMTU, 
         ibSmPathResultRateSel, 
         ibSmPathResultRate, 
         ibSmPathResultPktLifeTimeSel, 
         ibSmPathResultPktLifeTime, 
         ibSmPathResultPreference 
      }  
      STATUS current 
      DESCRIPTION 
         "The collection of objects for path management." 
      ::= { ibSmMIBGroups 9 } 
    
   ibSmMultiPathInfoGroup OBJECT-GROUP 
      OBJECTS { 
         ibSmMultiPathReqRowStatus, 
         ibSmMultiPathReqCreationTime, 
         ibSmMultiPathReqCompMask, 
         ibSmMultiPathReqRawTraffic, 
         ibSmMultiPathReqFlowLabel, 
         ibSmMultiPathReqHopLimit, 
         ibSmMultiPathReqTClass, 
         ibSmMultiPathReqNumbPath, 
         ibSmMultiPathReqPKey, 
 
 
 
 
         ibSmMultiPathReqSL, 
         ibSmMultiPathReqMTUSel, 
         ibSmMultiPathReqMTU, 
         ibSmMultiPathReqRateSel, 
         ibSmMultiPathReqRate, 
         ibSmMultiPathReqPktLifeTimeSel, 
         ibSmMultiPathReqPktLifeTime, 
         ibSmMultiPathReqIndepSel, 
         ibSmMultiPathReqSGIDCount, 
         ibSmMultiPathReqDGIDCount, 
         ibSmMultiPathReqSDGIDBlock1, 
         ibSmMultiPathReqSDGIDBlock2, 
         ibSmMultiPathReqSDGIDBlock3, 
         ibSmMultiPathReqSDGIDBlock4, 
         ibSmMultiPathReqSDGIDBlock5, 
         ibSmMultiPathReqSDGIDBlock6, 
         ibSmMultiPathReqSDGIDBlock7, 
         ibSmMultiPathReqSDGIDBlock8, 
         ibSmMultiPathReqSDGIDBlock9, 
         ibSmMultiPathReqSDGIDBlock10, 
         ibSmMultiPathReqSDGIDBlock11, 
         ibSmMultiPathReqSDGIDBlock12, 
         ibSmMultiPathReqSDGIDBlock13, 
         ibSmMultiPathReqSDGIDBlock14, 
         ibSmMultiPathReqSDGIDBlock15, 
         ibSmMultiPathReqSDGIDBlock16, 
         ibSmMultiPathReqSDGIDBlock17, 
         ibSmMultiPathReqSDGIDBlock18, 
         ibSmMultiPathReqSDGIDBlock19, 
         ibSmMultiPathReqSDGIDBlock20, 
         ibSmMultiPathReqSDGIDBlock21, 
         ibSmMultiPathReqSDGIDBlock22, 
         ibSmMultiPathReqSDGIDBlock23, 
         ibSmMultiPathReqSDGIDBlock24, 
         ibSmMultiPathReqSDGIDBlock25, 
         ibSmMultiPathReqSDGIDBlock26, 
         ibSmMultiPathReqSDGIDBlock27, 
         ibSmMultiPathReqSDGIDBlock28, 
         ibSmMultiPathReqSDGIDBlock29, 
         ibSmMultiPathReqSDGIDBlock30, 
         ibSmMultiPathReqSDGIDBlock31, 
         ibSmMultiPathReqSDGIDBlock32, 
         ibSmMultiPathResultDstGID, 
         ibSmMultiPathResultSrcGID, 
         ibSmMultiPathResultNumbPath, 
         ibSmMultiPathResultDstLID,      
         ibSmMultiPathResultSrcLID,      
         ibSmMultiPathResultRawTraffic,  
         ibSmMultiPathResultFlowLabel,   
 
 
 
 
         ibSmMultiPathResultHopLimit,    
         ibSmMultiPathResultTClass,      
         ibSmMultiPathResultPKey,        
         ibSmMultiPathResultSL,          
         ibSmMultiPathResultMTUSel,           
         ibSmMultiPathResultMTU,         
         ibSmMultiPathResultRateSel,     
         ibSmMultiPathResultRate, 
         ibSmMultiPathResultPktLifeTimeSel, 
         ibSmMultiPathResultPktLifeTime, 
         ibSmMultiPathResultPreference 
      }  
      STATUS current 
      DESCRIPTION 
         "The collection of objects for multipath management." 
      ::= { ibSmMIBGroups 10 } 
    
   ibSmTraceInfoGroup OBJECT-GROUP 
      OBJECTS { 
         ibSmTraceReqRowStatus, 
         ibSmTraceReqCreationTime, 
         ibSmTraceReqCompMask, 
         ibSmTraceReqIDGeneration, 
         ibSmTraceReqNodeType, 
         ibSmTraceReqNodeID, 
         ibSmTraceReqChassisID, 
         ibSmTraceReqEntryPortID, 
         ibSmTraceReqExitPortID, 
         ibSmTraceReqEntryPort, 
         ibSmTraceReqExitPort, 
         ibSmTraceResultIDGeneration, 
         ibSmTraceResultNodeType, 
         ibSmTraceResultNodeID, 
         ibSmTraceResultChassisID, 
         ibSmTraceResultEntryPortID, 
         ibSmTraceResultExitPortID, 
         ibSmTraceResultEntryPort, 
         ibSmTraceResultExitPort 
      }  
      STATUS current 
      DESCRIPTION 
         "The collection of objects for trace management." 
      ::= { ibSmMIBGroups 11 } 
    
   ibSmServiceInfoGroup OBJECT-GROUP 
      OBJECTS { 
         ibSmServiceLease, 
         ibSmServiceKey, 
         ibSmServiceName, 
 
 
 
 
         ibSmServiceData, 
         ibSmServiceAssocRowStatus 
      }  
      STATUS current 
      DESCRIPTION 
         "The collection of objects for service management." 
      ::= { ibSmMIBGroups 12 } 
    
   ibSmGUIDInfoGroup OBJECT-GROUP 
      OBJECTS { 
         ibSmGUIDInfoBlock 
      }  
      STATUS current 
      DESCRIPTION 
         "The collection of objects for GUID information management." 
      ::= { ibSmMIBGroups 13 } 
    
   ibSmGenericTrapsObjGroup OBJECT-GROUP 
      OBJECTS { 
         ibSmTrapSubnetPrefix, 
         ibSmTrapType, 
         ibSmTrapProducerType, 
         ibSmTrapNodeGUID1, 
         ibSmTrapPortNum1, 
         ibSmTrapNodeGUID2, 
         ibSmTrapPortNum2, 
         ibSmTrapMCGid, 
         ibSmTrapSwitchGUID, 
         ibSmTrapSwitchPortNum, 
         ibSmTrapCapabilityMask, 
         ibSmTrapSystemImageGUID, 
         ibSmTrapMethod, 
         ibSmTrapAttribId, 
         ibSmTrapAttribModifier, 
         ibSmTrapMKey, 
         ibSmTrapDRSLid, 
         ibSmTrapDRNotice, 
         ibSmTrapDRPathTruncated, 
         ibSmTrapDRHopCount, 
         ibSmTrapDRReturnPath, 
         ibSmTrapPKey, 
         ibSmTrapQueuePair1, 
         ibSmTrapQueuePair2, 
         ibSmTrapServiceLevel, 
         ibSmTrapQKey,        
         ibSmTrapDataValid, 
         ibSmTrapVendorID, 
         ibSmTrapDeviceID 
      } 
 
 
 
 
      STATUS current 
      DESCRIPTION 
         "The collection of objects contained in generic notifications." 
      ::= { ibSmMIBGroups 15 } 
    
   ibSmGenericTrapsGroup NOTIFICATION-GROUP 
      NOTIFICATIONS { 
         ibSmTrapInService, 
         ibSmTrapOutOfService, 
         ibSmTrapMCGroupCreated, 
         ibSmTrapMCGroupDeleted, 
         ibSmTrapSwitchLinkStateChanged, 
         ibSmTrapLinkIntegrityThreasholdReached, 
         ibSmTrapBufferOverrunThresholdReached, 
         ibSmTrapFlowControlUpdateWatchdogTimerExpired, 
         ibSmTrapCapabilityMaskChanged,  
         ibSmTrapSystemImageGUIDChanged, 
         ibSmTrapBadMKey,  
         ibSmTrapBadPKey,  
         ibSmTrapBadQKey,  
         ibSmTrapSwitchExternalPortsBadPKey  
      }  
      STATUS current 
      DESCRIPTION 
         "The collection of generic notifications." 
      ::= { ibSmMIBGroups 16 } 
    
   ibSmVendorSpecificTrapsObjGroup OBJECT-GROUP 
      OBJECTS { 
            ibSmTrapVendorDetailedData 
      } 
      STATUS current 
      DESCRIPTION 
         "The collection of objects contained in vendor specific 
   notifications." 
      ::= { ibSmMIBGroups 17 } 
    
   ibSmVendorSpecificTrapsGroup NOTIFICATION-GROUP 
      NOTIFICATIONS { 
         ibSmTrapVendorSpecific 
      }  
      STATUS current 
      DESCRIPTION 
         "The collection of vendor specific notifications." 
      ::= { ibSmMIBGroups 18 } 
    
   END 

--     
--    Copyright (C) The Internet Society (2003).  All Rights Reserved. 
--      
--    This document and translations of it may be copied and furnished to 
--    others, and derivative works that comment on or otherwise explain it or 
--    assist in its implementation may be prepared, copied, published and 
--    distributed, in whole or in part, without restriction of any kind, 
--    provided that the above copyright notice and this paragraph are included 
--    on all such copies and derivative works.  However, this document itself 
--    may not be modified in any way, such as by removing the copyright notice 
--  
--  
-- Expires: September 2004                                    [Page 103 ] 
-- INTERNET-DRAFT    Infiniband Subnet Manager(SM) MIB        March 2004 
--  
--  
--    or references to the Internet Society or other Internet organizations, 
--    except as needed for the purpose of developing Internet standards in which 
--    case the procedures for copyrights defined in the Internet Standards 
--    process must be followed, or as required to translate it into languages 
--    other than English. 
--      
--    The limited permissions granted above are perpetual and will not be 
--    revoked by the Internet Society or its successors or assigns. 
--     
--    This document and the information contained herein is provided on an "AS 
--    IS" basis and THE INTERNET SOCIETY AND THE INTERNET ENGINEERING TASK FORCE 
--    DISCLAIMS ALL WARRANTIES, EXPRESS OR IMPLIED, INCLUDING BUT NOT LIMITED 
--    TO ANY WARRANTY THAT THE USE OF THE INFORMATION HEREIN WILL NOT INFRINGE 
--    ANY RIGHTS OR ANY IMPLIED WARRANTIES OF MERCHANTABILITY OR FITNESS FOR 
--    A PARTICULAR PURPOSE.             
--  
-- 10 Intellectual Property Notice 
--         
--    The IETF takes no position regarding the validity or scope of any 
--    intellectual property or other rights that might be claimed to pertain 
--    to the implementation or use of the technology described in this document 
--    or the extent to which any license under such rights might or might not 
--    be available; neither does it represent that it has made any effort to 
--    identify any such rights.  Information on the IETF's procedures with 
--    respect to rights in standards-track and standards-related documentation 
--    can be found in BCP-11.  Copies of claims of rights made available for 
--    publication and any assurances of licenses to be made available, or the 
--    result of an attempt made to obtain a general license or permission for 
--    the use of such proprietary rights by implementers or users of this 
--    specification can be obtained from the IETF Secretariat.  
--         
--    The IETF invites any interested party to bring to its attention any 
--    copyrights, patents or patent applications, or other proprietary rights 
--    which may cover technology that may be required to practice this standard.  
--    Please address the information to the IETF Executive Director.  
--  
-- 11 Normative References 
--     
--    [RFC2578] McCloghrie, K., Perkins, D., Schoenwaelder, J., Case, J., 
--              Rose, M. and S. Waldbusser, "Structure of Management 
--              Information Version 2 (SMIv2)", STD 58, RFC 2578, April
