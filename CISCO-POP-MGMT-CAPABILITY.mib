-- *****************************************************************
-- CISCO-POP-MGMT-CAPABILITY.my: CISCO-POP-MGMT-MIB
--                               AGENT-CAPABILITIES
--
-- August 2005  Lizzie Cheung   
--
-- Copyright (c) 2005 by cisco Systems, Inc.
-- All rights reserved.
-- *****************************************************************

CISCO-POP-MGMT-CAPABILITY DEFINITIONS ::= BEGIN

IMPORTS
    MODULE-IDENTITY, Counter32, TimeTicks, Gauge32
        FROM SNMPv2-SMI
    AGENT-CAPABILITIES
        FROM SNMPv2-CONF
    ciscoAgentCapability
        FROM CISCO-SMI
	InterfaceIndexOrZero FROM CISCO-TC;


ciscoPopMgmtCapability MODULE-IDENTITY
        LAST-UPDATED    "200510120000Z"
        ORGANIZATION    "Cisco Systems, Inc."
        CONTACT-INFO
                "       Cisco Systems
                        Customer Service

                Postal: 170 W. Tasman Drive
                        San Jose, CA  95134
                        USA

                Tel: +1 800 553-NETS

                E-mail: cs-voice@cisco.com"
        DESCRIPTION
                "Agent capabilities for CISCO-POP-MGMT-MIB."
        REVISION    "200510120000Z"
        DESCRIPTION
                "Added variations for cpmDS0UsageGroupRev2."
        REVISION    "200508250000Z"
        DESCRIPTION
                "Initial version of this MIB module."
        ::= { ciscoAgentCapability 447 }

ciscoPopMgmtCapabilityV12R04 AGENT-CAPABILITIES
PRODUCT-RELEASE "Cisco IOS 12.4 for C3600 family platforms"
    STATUS      current
    DESCRIPTION "Cisco POP management agent capabilities for 
                 C3600 family platforms"

SUPPORTS    CISCO-POP-MGMT-MIB
    INCLUDES    { cpmDS0UsageGroupRev2,
                  cpmDS0StatusGroup,
                  cpmNotificationGroupRev1 }

VARIATION           cpmConfiguredType
    SYNTAX          INTEGER {
                      unknown(1),
                      isdn(2),
                      ct1(3),
                      ce1(4)
                    }
    DESCRIPTION     "Only ISDN/modem applications are supported
                     on c3600 family of platforms."

VARIATION           cpmDS0CallType
    SYNTAX          INTEGER {
                      idle(1),
                      unknown(2),
                      analog(3),
                      digital(4),
                      v110(5),
                      v120(6),
                      voice(7)
                    }
    DESCRIPTION     "Only ISDN/modem applications are supported
                     on c3600 family of platforms."

VARIATION           cpmL2Encapsulation
    SYNTAX          INTEGER {
                      idle(1),
                      unknown(2),
                      ppp(3),
                      slip(4),
                      arap(5),
                      hdlc(6),
                      exec(7),
                      voice(8)
                    }
    DESCRIPTION     "OnlyISDN/modem applications are supported
                     on c3600 family of platforms."

VARIATION           cpmCallCount
    SYNTAX          Counter32
    DESCRIPTION     "Only ISDN/modem applications are supported
                     on c3600 family of platforms."

VARIATION           cpmTimeInUse
    SYNTAX          TimeTicks
    DESCRIPTION     "Only ISDN/modem applications are supported
                     on c3600 family of platforms."

VARIATION           cpmInOctets
    SYNTAX          Counter32
    DESCRIPTION     "Only ISDN/modem applications are supported
                     on c3600 family of platforms."

VARIATION           cpmOutOctets
    SYNTAX          Counter32
    DESCRIPTION     "Only ISDN/modem applications are supported
                     on c3600 family of platforms."

VARIATION           cpmInPackets
    SYNTAX          Counter32
    DESCRIPTION     "Only ISDN/modem applications are supported
                     on c3600 family of platforms."

VARIATION           cpmOutPackets
    SYNTAX          Counter32
    DESCRIPTION     "Only ISDN/modem applications are supported
                     on c3600 family of platforms."

VARIATION           cpmAssociatedInterface
    SYNTAX          InterfaceIndexOrZero
    DESCRIPTION     "Only ISDN/modem applications are supported
                     on c3600 family of platforms."

VARIATION           cpmISDNCfgBChanInUseForAnalog
    SYNTAX          Gauge32
    DESCRIPTION     "Only ISDN/modem applications are supported
                     on c3600 family of platforms."

VARIATION           cpmISDNCfgBChannelsInUse
    SYNTAX          Gauge32
    DESCRIPTION     "Only ISDN/modem applications are supported
                     on c3600 family of platforms."

VARIATION           cpmActiveDS0s
    SYNTAX          Gauge32
    DESCRIPTION     "Only ISDN/modem applications are supported
                     on c3600 family of platforms."

VARIATION           cpmPPPCalls
    SYNTAX          Gauge32
    DESCRIPTION     "Only ISDN/modem applications are supported
                     on c3600 family of platforms."

VARIATION           cpmV120Calls
    SYNTAX          Gauge32
    DESCRIPTION     "Only ISDN/modem applications are supported
                     on c3600 family of platforms."

VARIATION           cpmV110Calls
    SYNTAX          Gauge32
    DESCRIPTION     "Only ISDN/modem applications are supported
                     on c3600 family of platforms."

VARIATION           cpmActiveDS0sHighWaterMark
    SYNTAX          Counter32
    DESCRIPTION     "Only ISDN/modem applications are supported
                     on c3600 family of platforms."

VARIATION           cpmDS1ActiveDS0s
    SYNTAX          Gauge32
    DESCRIPTION     "Only ISDN/modem applications are supported
                     on c3600 family of platforms."

VARIATION           cpmDS1ActiveDS0sHighWaterMark
    SYNTAX          Counter32
    DESCRIPTION     "Only ISDN/modem applications are supported
                     on c3600 family of platforms."

VARIATION           cpmSW56CfgBChannelsInUse
    SYNTAX          Gauge32
    DESCRIPTION     "Only ISDN/modem applications are supported
                     on c3600 family of platforms."

VARIATION           cpmISDNCfgBChanInUseForVoice
    SYNTAX          Gauge32
    DESCRIPTION     "Only ISDN/modem applications are supported
                     on c3600 family of platforms."

VARIATION           cpmCASCfgBChanInUseForVoice
    SYNTAX          Gauge32
    DESCRIPTION     "Only ISDN/modem applications are supported
                     on c3600 family of platforms."

VARIATION           cpmDS1LoopbackNotification
    ACCESS          not-implemented
    DESCRIPTION     "Not supported on c3600 family of platforms."

    ::= { ciscoPopMgmtCapability 1 }

END
