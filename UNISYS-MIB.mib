UNISYS-MIB DEFINITIONS     ::=BEGIN

-- Title:	UNISYS MIB
-- Date:	June 28, 1990
-- By:		Andy Weingarten/Unisys

        IMPORTS 
                 OBJECT-TYPE FROM RFC-1212
					  NetworkAddress, IpAddress,
                Counter, Gauge
                FROM RFC1065-SMI;
		internet      OBJECT IDENTIFIER ::= { iso org(3) dod(6) 1 }
		private       OBJECT IDENTIFIER ::= { internet 4 }
		enterprises   OBJECT IDENTIFIER ::= { private 1 }
--
               unisys           OBJECT IDENTIFIER ::= { enterprises 16 }
               u-mgmt           OBJECT IDENTIFIER ::= { unisys 2 }
               u-mib            OBJECT IDENTIFIER ::= { u-mgmt 1 }
               u-system         OBJECT IDENTIFIER ::= { u-mib 1 }
               u-interfaces     OBJECT IDENTIFIER ::= { u-mib 2 }
               u-at             OBJECT IDENTIFIER ::= { u-mib 3 }
               u-icmp           OBJECT IDENTIFIER ::= { u-mib 5 }
               u-tcp            OBJECT IDENTIFIER ::= { u-mib 6 }
               u-udp            OBJECT IDENTIFIER ::= { u-mib 7 }
               u-egp            OBJECT IDENTIFIER ::= { u-mib 8 }
               u-ggp            OBJECT IDENTIFIER ::= { u-mib 12 }
               u-rip            OBJECT IDENTIFIER ::= { u-mib 13 }
               u-snmp           OBJECT IDENTIFIER ::= { u-mib 14 }
               u-hfp            OBJECT IDENTIFIER ::= { u-mib 15 }
               u-ddn            OBJECT IDENTIFIER ::= { u-mib 16 }
               u-x25            OBJECT IDENTIFIER ::= { u-mib 17 }
               u-fddi           OBJECT IDENTIFIER ::= { u-mib 18 }
               u-ip             OBJECT IDENTIFIER ::= { u-mib 19 }
               u-fddiSMT        OBJECT IDENTIFIER ::= { u-fddi 1 }
               u-fddiMACTable   OBJECT IDENTIFIER ::= { u-fddi 2 }
               u-fddiMACEntry   OBJECT IDENTIFIER ::= { u-fddiMACTable 1 }
               u-fddiPHYTable   OBJECT IDENTIFIER ::= { u-fddi 3 }
               u-fddiPHYEntry   OBJECT IDENTIFIER ::= { u-fddiPHYTable 1 }


        u-systemAction OBJECT-TYPE
           SYNTAX  INTEGER {
       		normal (0),
                reset (1),
                shutdown (2)
           }
           ACCESS  read-write
           STATUS  mandatory
DESCRIPTION ""
           ::= { u-system 1 }
        

        u-systemReboots OBJECT-TYPE
           SYNTAX  INTEGER
           ACCESS  read-only
           STATUS  mandatory
DESCRIPTION ""
           ::= { u-system 2 }


        u-systemErrorCode OBJECT-TYPE
           SYNTAX  INTEGER
           ACCESS  read-only
           STATUS  mandatory
DESCRIPTION ""
           ::= { u-system 3 }
        

        u-ifTable OBJECT-TYPE
           SYNTAX  SEQUENCE OF U-ifEntry
           ACCESS  read-write
           STATUS  mandatory
DESCRIPTION ""
           ::= { u-interfaces 1 }
        

        u-ifEntry OBJECT-TYPE
           SYNTAX  U-ifEntry
           ACCESS  read-write
           STATUS  mandatory
DESCRIPTION ""
           ::= { u-ifTable 1 }

U-ifEntry ::= SEQUENCE
{		u-ifEthernetArpWait
                        INTEGER,
                u-ifIpAddr
                        IpAddress,
                u-ifSubnetMask
                        NetworkAddress,
                u-ifHdlcBaudRate
                        INTEGER,
                u-ifHdlcRto
                        INTEGER,
                u-ifHdlcAckTo
                        INTEGER,
                u-ifHdlcSabmInterval
                        INTEGER,
                u-ifHdlcRnrInterval
                        INTEGER,
                u-ifHdlcClockType 
                        INTEGER,
                u-ifHdlcDCE 
                        INTEGER --* BOOLEAN *--,
                u-ifHdlcThrowaway
                        INTEGER --* BOOLEAN *--,
                u-ifHdlcAckCount 
                        INTEGER,
		u-ifFddiArpWait
                        INTEGER
           }

        u-ifEthernetArpWait OBJECT-TYPE
           SYNTAX  INTEGER (1..65535)
           ACCESS  read-write
           STATUS  mandatory
DESCRIPTION ""
           ::= { u-ifEntry 1 }


        u-ifIpAddr OBJECT-TYPE
           SYNTAX  IpAddress
           ACCESS  read-write
           STATUS  mandatory
DESCRIPTION ""
           ::= { u-ifEntry 2 }


        u-ifSubnetMask OBJECT-TYPE
           SYNTAX  NetworkAddress
           ACCESS  read-write
           STATUS  mandatory
DESCRIPTION ""
           ::= { u-ifEntry 3 }


        u-ifHdlcBaudRate OBJECT-TYPE
           SYNTAX  INTEGER (0..16384)
           ACCESS  read-write
           STATUS  mandatory
DESCRIPTION ""
           ::= { u-ifEntry 4 }


        u-ifHdlcRto OBJECT-TYPE
           SYNTAX  INTEGER (1..16384)
           ACCESS  read-write
           STATUS  mandatory
DESCRIPTION ""
           ::= { u-ifEntry 5 }


        u-ifHdlcAckTo OBJECT-TYPE
           SYNTAX  INTEGER (1..16384) 
           ACCESS  read-write
           STATUS  mandatory
DESCRIPTION ""
           ::= { u-ifEntry 6 }


        u-ifHdlcSabmInterval OBJECT-TYPE
           SYNTAX  INTEGER (1..16384)
           ACCESS  read-write
           STATUS  mandatory
DESCRIPTION ""
           ::= { u-ifEntry 7 }


        u-ifHdlcRnrInterval OBJECT-TYPE
           SYNTAX  INTEGER (1..16384)
           ACCESS  read-write
           STATUS  mandatory
DESCRIPTION ""
           ::= { u-ifEntry 8 }


        u-ifHdlcClockType OBJECT-TYPE
           SYNTAX  INTEGER {
                 dTE-accepts-tx-and-rx-clocks (3),
                 dCE-generates-tx-and-rx-clocks (4)
           }
           ACCESS  read-write
           STATUS  mandatory
DESCRIPTION ""
           ::= { u-ifEntry 9 }


        u-ifHdlcDCE OBJECT-TYPE
           SYNTAX  INTEGER --* BOOLEAN *-- 
           ACCESS  read-write
           STATUS  mandatory
DESCRIPTION ""
           ::= { u-ifEntry 10 }


        u-ifHdlcThrowaway OBJECT-TYPE
           SYNTAX  INTEGER --* BOOLEAN *-- 
           ACCESS  read-write
           STATUS  mandatory
DESCRIPTION ""
           ::= { u-ifEntry 11 }


        u-ifHdlcAckCount OBJECT-TYPE
           SYNTAX  INTEGER (1..255)
           ACCESS  read-write
           STATUS  mandatory
DESCRIPTION ""
           ::= { u-ifEntry 12 }


        u-ifFddiArpWait OBJECT-TYPE
           SYNTAX  INTEGER (1..255)
           ACCESS  read-write
           STATUS  mandatory
DESCRIPTION ""
           ::= { u-ifEntry 13 }


        u-ipLogicalDisconnect OBJECT-TYPE
           SYNTAX  INTEGER --* BOOLEAN *-- 
           ACCESS  read-write
           STATUS  mandatory
DESCRIPTION ""
           ::= { u-ip 1 }


        u-ipLoopback OBJECT-TYPE
           SYNTAX  INTEGER --* BOOLEAN *-- 
           ACCESS  read-write
           STATUS  mandatory
DESCRIPTION ""
           ::= { u-ip 2 }


        u-ipRedirectTo OBJECT-TYPE
           SYNTAX  INTEGER (1..65535)
           ACCESS  read-write     
           STATUS  mandatory
DESCRIPTION ""
           ::= { u-ip 3 }


        u-ipMasker OBJECT-TYPE
           SYNTAX  INTEGER --* BOOLEAN *-- 
           ACCESS  read-write
           STATUS  mandatory
DESCRIPTION ""
           ::= { u-ip 4 }


        u-ipWellKnownGateway OBJECT-TYPE
           SYNTAX  IpAddress
           ACCESS  read-write
           STATUS  mandatory
DESCRIPTION ""
           ::= { u-ip 5 }


        u-ipMaxRoutePids OBJECT-TYPE
           SYNTAX  INTEGER
           ACCESS  read-only
           STATUS  mandatory
DESCRIPTION ""
           ::= { u-ip 6 }


        u-ipRoutePidsTable OBJECT-TYPE
           SYNTAX  SEQUENCE OF U-ipRoutePidsEntry
           ACCESS  read-write
           STATUS  mandatory
DESCRIPTION ""
           ::= { u-ip 7 }


        u-ipRoutePidsEntry OBJECT-TYPE
           SYNTAX  U-ipRoutePidsEntry
           ACCESS  read-write
           STATUS  mandatory
DESCRIPTION ""
           ::= { u-ipRoutePidsTable 1 }

U-ipRoutePidsEntry ::= SEQUENCE {
        	u-ipRoutePid
                	INTEGER 
	   }

        u-ipRoutePid OBJECT-TYPE
           SYNTAX  INTEGER {
                gateway-to-Gateway-protocol (3),
                routing-Information-Protocol (7),
		exterior-Gateway-Protocol (8),
		internet-Protocol (1)
           }
           ACCESS  read-write
           STATUS  mandatory
DESCRIPTION ""
           ::= { u-ipRoutePidsEntry 1 }


        u-ipNbrStaticRoutes OBJECT-TYPE
           SYNTAX  INTEGER
           ACCESS  read-only
           STATUS  mandatory
DESCRIPTION ""
           ::= { u-ip 8 }


        u-ipStaticRouteTable OBJECT-TYPE
           SYNTAX  SEQUENCE OF U-ipStaticRouteEntry
           ACCESS  read-write
           STATUS  mandatory
DESCRIPTION ""
           ::= { u-ip 9 }


        u-ipStaticRouteEntry OBJECT-TYPE
           SYNTAX  U-ipStaticRouteEntry
           ACCESS  read-write
           STATUS  mandatory
DESCRIPTION ""
           ::= { u-ipStaticRouteTable 1 }

U-ipStaticRouteEntry ::=           SEQUENCE {
	        u-ipStaticRouteNetwork
	       	        NetworkAddress,
        	u-ipStaticRouteGateway
                	IpAddress,
	        u-ipStaticRouteCost
        	        INTEGER,
	        u-ipStaticRouteOverride
        	        INTEGER --* BOOLEAN *--
	   }

        u-ipStaticRouteNetwork OBJECT-TYPE
           SYNTAX  NetworkAddress
           ACCESS  read-only
           STATUS  mandatory
DESCRIPTION ""
           ::= { u-ipStaticRouteEntry 1 }


        u-ipStaticRouteGateway OBJECT-TYPE
           SYNTAX  IpAddress
           ACCESS  read-write
           STATUS  mandatory
DESCRIPTION ""
           ::= { u-ipStaticRouteEntry 2 }


        u-ipStaticRouteCost OBJECT-TYPE
           SYNTAX  INTEGER (0..255)
           ACCESS  read-write
           STATUS  mandatory
DESCRIPTION ""
           ::= { u-ipStaticRouteEntry 3 }


        u-ipStaticRouteOverride OBJECT-TYPE
           SYNTAX  INTEGER --* BOOLEAN *-- 
           ACCESS  read-write
           STATUS  mandatory
DESCRIPTION ""
           ::= { u-ipStaticRouteEntry 4 }


        u-ipRemotegTable OBJECT-TYPE
           SYNTAX  SEQUENCE OF U-ipRemotegEntry
           ACCESS  read-write
           STATUS  mandatory
DESCRIPTION ""
           ::= { u-ip 10 }


        u-ipRemotegEntry OBJECT-TYPE
           SYNTAX  U-ipRemotegEntry
           ACCESS  read-write
           STATUS  mandatory
DESCRIPTION ""
           ::= { u-ipRemotegTable 1 }

U-ipRemotegEntry ::= SEQUENCE {
        	u-ipRemoteg
                	INTEGER --* BOOLEAN *-- 
	   }
        u-ipRemoteg OBJECT-TYPE
           SYNTAX  INTEGER --* BOOLEAN *-- 
           ACCESS  read-write
           STATUS  mandatory
DESCRIPTION ""
           ::= { u-ipRemotegEntry 1 }


        u-ipNetMaxPktTable OBJECT-TYPE
           SYNTAX  SEQUENCE OF U-ipNetMaxPktEntry
           ACCESS  read-write
           STATUS  mandatory
DESCRIPTION ""
           ::= { u-ip 11 }


        u-ipNetMaxPktEntry OBJECT-TYPE
           SYNTAX  U-ipNetMaxPktEntry
           ACCESS  read-write
           STATUS  mandatory
DESCRIPTION ""
           ::= { u-ipNetMaxPktTable 1 }

U-ipNetMaxPktEntry ::= SEQUENCE {
        	u-ipNetMaxPkt
                	INTEGER
	   }
        u-ipNetMaxPkt OBJECT-TYPE
           SYNTAX  INTEGER (65..65535)
           ACCESS  read-write
           STATUS  mandatory
DESCRIPTION ""
           ::= { u-ipNetMaxPktEntry 1 }


        u-tcpRetransTo OBJECT-TYPE
           SYNTAX  INTEGER (1..65535)
           ACCESS  read-write
           STATUS  mandatory
DESCRIPTION ""
           ::= { u-tcp 1 }


        u-tcpRtoMin OBJECT-TYPE
           SYNTAX  INTEGER (1..65535)
           ACCESS  read-write
           STATUS  mandatory
DESCRIPTION ""
           ::= { u-tcp 2 }


        u-tcpRtoMax OBJECT-TYPE
           SYNTAX  INTEGER (1..65635)
           ACCESS  read-write
           STATUS  mandatory
DESCRIPTION ""
           ::= { u-tcp 3 }


        u-tcpWakeup OBJECT-TYPE
           SYNTAX  INTEGER (1..16384)
           ACCESS  read-write
           STATUS  mandatory
DESCRIPTION ""
           ::= { u-tcp 4 }


        u-tcpAckTime OBJECT-TYPE
           SYNTAX  INTEGER (1..16384)
           ACCESS  read-write
           STATUS  mandatory
DESCRIPTION ""
           ::= { u-tcp 5 }


        u-tcpTimeToLive OBJECT-TYPE
           SYNTAX  INTEGER (1..255)
           ACCESS  read-write
           STATUS  mandatory
DESCRIPTION ""
           ::= { u-tcp 6 }


        u-tcpThruput OBJECT-TYPE
           SYNTAX  INTEGER (1..255)
           ACCESS  read-write
           STATUS  mandatory
DESCRIPTION ""
           ::= { u-tcp 7 }


        u-tcpFlowAck OBJECT-TYPE
           SYNTAX  INTEGER (1..u-tcpThruput)
           ACCESS  read-write
           STATUS  mandatory
DESCRIPTION ""
           ::= { u-tcp 8 }


        u-egpMaxNeighbors OBJECT-TYPE
           SYNTAX  INTEGER
           ACCESS  read-only
           STATUS  mandatory
DESCRIPTION ""
           ::= { u-egp 1 }


        u-egpNumberTrustedNeighbors OBJECT-TYPE
           SYNTAX  INTEGER (0..u-egpMaxNeighbors)
           ACCESS  read-write
           STATUS  mandatory
DESCRIPTION ""
           ::= { u-egp 2 }


        u-egpNumberNeighbors OBJECT-TYPE
           SYNTAX  INTEGER (0..u-egpNumberTrustedNeighbors)
           ACCESS  read-write
           STATUS  mandatory
DESCRIPTION ""
           ::= { u-egp 3 }


        u-egpNeighborTable OBJECT-TYPE
           SYNTAX  SEQUENCE OF U-egpNeighborEntry
           ACCESS  read-write
           STATUS  mandatory
DESCRIPTION ""
           ::= { u-egp 4 }


        u-egpNeighborEntry OBJECT-TYPE
           SYNTAX  U-egpNeighborEntry
           ACCESS  read-write
           STATUS  mandatory
DESCRIPTION ""
           ::= { u-egpNeighborTable 1 }

U-egpNeighborEntry ::= SEQUENCE {
	        u-egpNeighbor
        	        IpAddress
	   }
        u-egpNeighbor OBJECT-TYPE
           SYNTAX  IpAddress
           ACCESS  read-write
           STATUS  mandatory
DESCRIPTION ""
           ::= { u-egpNeighborEntry 1 }


        u-egpAutoSysNumber OBJECT-TYPE
           SYNTAX  INTEGER (0..65535)
           ACCESS  read-write
           STATUS  mandatory
DESCRIPTION ""
           ::= { u-egp 5 }


        u-egpMinHelloInterval OBJECT-TYPE
           SYNTAX  INTEGER (15..65535)
           ACCESS  read-write
           STATUS  mandatory
DESCRIPTION ""
           ::= { u-egp 6 }


        u-egpMinPollInterval OBJECT-TYPE
           SYNTAX  INTEGER (30..65535)
           ACCESS  read-write
           STATUS  mandatory
DESCRIPTION ""
           ::= { u-egp 7 }


        u-egpRequestCeaseInterval OBJECT-TYPE
           SYNTAX  INTEGER (15..65535)
           ACCESS  read-write
           STATUS  mandatory
DESCRIPTION ""
           ::= { u-egp 8 }


        u-egpDeclareDownInterval OBJECT-TYPE
           SYNTAX  INTEGER (1800..65535)
           ACCESS  read-write
           STATUS  mandatory
DESCRIPTION ""
           ::= { u-egp 9 }


        u-egpAcquireCeaseInterval OBJECT-TYPE
           SYNTAX  INTEGER (30..240)
           ACCESS  read-write
           STATUS  mandatory
DESCRIPTION ""
           ::= { u-egp 10 }


        u-egpEnoughInterval OBJECT-TYPE
           SYNTAX  INTEGER (60..65535)
           ACCESS  read-write
           STATUS  mandatory
DESCRIPTION ""
           ::= { u-egp 11 }


        u-egpPurgeInterval OBJECT-TYPE
           SYNTAX  INTEGER (0..600)
           ACCESS  read-write
           STATUS  mandatory
DESCRIPTION ""
           ::= { u-egp 12 }


        u-egpMode OBJECT-TYPE
           SYNTAX  INTEGER {
                both-active-and-passive(0),
                active(1),
                passive(2)
           }
           ACCESS  read-write
           STATUS  mandatory
DESCRIPTION ""
           ::= { u-egp 13 }


        u-egpErrorTreatment OBJECT-TYPE
           SYNTAX  INTEGER (0..255) 
           ACCESS  read-write
           STATUS  mandatory
DESCRIPTION ""
           ::= { u-egp 14 }


        u-egpSharedNetwork OBJECT-TYPE
           SYNTAX  IpAddress
           ACCESS  read-write
           STATUS  mandatory
DESCRIPTION ""
           ::= { u-egp 15 }


        u-ggpEchoInterval OBJECT-TYPE
           SYNTAX  INTEGER (1..65535)
           ACCESS  read-write
           STATUS  mandatory
DESCRIPTION ""
           ::= { u-ggp 1 }


        u-ggpMaxNeighbors OBJECT-TYPE
           SYNTAX  INTEGER
           ACCESS  read-only
           STATUS  mandatory
DESCRIPTION ""
           ::= { u-ggp 2 }


        u-ggpNumberNeighbors OBJECT-TYPE
           SYNTAX  INTEGER (0..u-ggpMaxNeighbors)
           ACCESS  read-only
           STATUS  mandatory
DESCRIPTION ""
           ::= { u-ggp 3 }


        u-ggpNeighborTable OBJECT-TYPE
           SYNTAX  SEQUENCE OF U-ggpNeighborEntry
           ACCESS  read-write
           STATUS  mandatory
DESCRIPTION ""
           ::= { u-ggp 4 }


        u-ggpNeighborEntry OBJECT-TYPE
           SYNTAX  U-ggpNeighborEntry
           ACCESS  read-write
           STATUS  mandatory
DESCRIPTION ""
           ::= { u-ggpNeighborTable 1 }

			  U-ggpNeighborEntry ::= SEQUENCE {
	        u-ggpNeighbor
        	        IpAddress 
	   }

        u-ggpNeighbor OBJECT-TYPE
           SYNTAX  IpAddress
           ACCESS  read-write
           STATUS  mandatory
DESCRIPTION ""
           ::= { u-ggpNeighborEntry 1 }


         u-snmpVersion OBJECT-TYPE
           SYNTAX  INTEGER
           ACCESS  read-only
           STATUS  mandatory
DESCRIPTION ""
           ::= { u-snmp 1 }


        u-snmpCommunity OBJECT-TYPE
           SYNTAX  OCTET STRING
           ACCESS  read-write
           STATUS  mandatory
DESCRIPTION ""
           ::= { u-snmp 2 }


        u-snmpRequests OBJECT-TYPE
           SYNTAX  Counter
           ACCESS  read-only
           STATUS  mandatory
DESCRIPTION ""
           ::= { u-snmp 3 }

        u-snmpTraps OBJECT-TYPE
           SYNTAX  Counter
           ACCESS  read-only
           STATUS  mandatory
DESCRIPTION ""
           ::= { u-snmp 4 }


        u-snmpForwardTraps OBJECT-TYPE
           SYNTAX  INTEGER --* BOOLEAN *-- 
           ACCESS  read-write
           STATUS  mandatory
DESCRIPTION ""
           ::= { u-snmp 5 }


        u-hfpMaxMsg OBJECT-TYPE
           SYNTAX  INTEGER (9..1420)
           ACCESS  read-write
           STATUS  mandatory
DESCRIPTION ""
           ::= { u-hfp 1 }


        u-hfpPad OBJECT-TYPE
           SYNTAX  INTEGER (0..6)
           ACCESS  read-write
           STATUS  mandatory
DESCRIPTION ""
           ::= { u-hfp 2 }


        u-hfpSwap OBJECT-TYPE
           SYNTAX  INTEGER --* BOOLEAN *-- 
           ACCESS  read-write
           STATUS  mandatory
DESCRIPTION ""
           ::= { u-hfp 3 }


        u-ddnTimeout OBJECT-TYPE
           SYNTAX  INTEGER (1..65535)
           ACCESS  read-write
           STATUS  mandatory
DESCRIPTION ""
           ::= { u-ddn 1 }


        u-ddnMsgout OBJECT-TYPE
           SYNTAX  INTEGER (1..8)
           ACCESS  read-write
           STATUS  mandatory
DESCRIPTION ""
           ::= { u-ddn 2 }


        u-ddnHipUp OBJECT-TYPE
           SYNTAX  INTEGER --* BOOLEAN *-- 
           ACCESS  read-only
           STATUS  mandatory
DESCRIPTION ""
           ::= { u-ddn 3 }

        u-ddnHdhUp OBJECT-TYPE
           SYNTAX  INTEGER --* BOOLEAN *-- 
           ACCESS  read-only
           STATUS  mandatory
DESCRIPTION ""
           ::= { u-ddn 4 }


        u-ddnLinkUp OBJECT-TYPE
           SYNTAX  INTEGER --* BOOLEAN *-- 
           ACCESS  read-only
           STATUS  mandatory
DESCRIPTION ""
           ::= { u-ddn 5 }


        u-ddnTotalQ OBJECT-TYPE
           SYNTAX  Gauge
           ACCESS  read-only
           STATUS  mandatory
DESCRIPTION ""
           ::= { u-ddn 6 }

        u-ddnConnections OBJECT-TYPE
           SYNTAX  Gauge
           ACCESS  read-only
           STATUS  mandatory
DESCRIPTION ""
           ::= { u-ddn 7 }


        u-ddnLinkDownTo OBJECT-TYPE
           SYNTAX  INTEGER  
           ACCESS  read-only
           STATUS  mandatory
DESCRIPTION ""
           ::= { u-ddn 8 }


        u-ddnRcvIncomplete OBJECT-TYPE
           SYNTAX  Counter
           ACCESS  read-only
           STATUS  mandatory
DESCRIPTION ""
           ::= { u-ddn 9 }


        u-ddnConnectionsReused OBJECT-TYPE
           SYNTAX  Counter
           ACCESS  read-only
           STATUS  mandatory
DESCRIPTION ""
           ::= { u-ddn 10 }


        u-ddnHdhWentDown OBJECT-TYPE
           SYNTAX  Counter
           ACCESS  read-only
           STATUS  mandatory
DESCRIPTION ""
           ::= { u-ddn 11 }


        u-ddnLinkWentDown OBJECT-TYPE
           SYNTAX  Counter
           ACCESS  read-only
           STATUS  mandatory
DESCRIPTION ""
           ::= { u-ddn 12 }


        u-ddnLeaderErrs OBJECT-TYPE
           SYNTAX  Counter
           ACCESS  read-only
           STATUS  mandatory
DESCRIPTION ""
           ::= { u-ddn 13 }


        u-ddnPSNGoingDown OBJECT-TYPE
           SYNTAX  Counter
           ACCESS  read-only
           STATUS  mandatory
DESCRIPTION ""
           ::= { u-ddn 14 }


        u-ddnDeadHostSTATUS OBJECT-TYPE
           SYNTAX  Counter
           ACCESS  read-only
           STATUS  mandatory
DESCRIPTION ""
           ::= { u-ddn 15 }


        u-ddnIfReset OBJECT-TYPE
           SYNTAX  Counter
           ACCESS  read-only
           STATUS  mandatory
DESCRIPTION ""
           ::= { u-ddn 16 }


        u-x25IfTable OBJECT-TYPE
           SYNTAX  SEQUENCE OF X25IfEntry
           ACCESS  read-write
           STATUS  mandatory
DESCRIPTION ""
           ::= { u-x25 1 }


        u-x25IfEntry OBJECT-TYPE
           SYNTAX  X25IfEntry
           ACCESS  read-write
           STATUS  mandatory
DESCRIPTION ""
           ::= { u-x25IfTable 1 }

X25IfEntry ::= SEQUENCE {
                u-x25Service
                        INTEGER,
                u-x25Window
                        INTEGER,
                u-x25PktSize
                        INTEGER
           }

        u-x25Service OBJECT-TYPE
           SYNTAX  INTEGER {
		basic-service(0),
		standard-service(7)
           }
           ACCESS  read-write
           STATUS  mandatory
DESCRIPTION ""
           ::= { u-x25IfEntry 1 }


        u-x25Window OBJECT-TYPE
           SYNTAX  INTEGER (2..7)
           ACCESS  read-write
           STATUS  mandatory
DESCRIPTION ""
           ::= { u-x25IfEntry 2 }


        u-x25PktSize OBJECT-TYPE
           SYNTAX  INTEGER (7..11) 
           ACCESS  read-write
           STATUS  mandatory
DESCRIPTION ""
           ::= { u-x25IfEntry 3 }


        u-fddiSMTStationIdGrp OBJECT-TYPE
           SYNTAX  SEQUENCE {
		u-fddiSMTStationId
			OCTET STRING,
		u-fddiSMTStationType
			INTEGER,
		u-fddiSMTVersionId
			INTEGER
 	   }
           ACCESS  read-only
           STATUS  mandatory
DESCRIPTION ""
           ::= { u-fddiSMT 1 }


        u-fddiSMTStationId OBJECT-TYPE
           SYNTAX  OCTET STRING
           ACCESS  read-only
           STATUS  mandatory
DESCRIPTION ""
           ::= { u-fddiSMTStationIdGrp 1 }


        u-fddiSMTStationType OBJECT-TYPE
           SYNTAX  INTEGER {
		station (1),
		concentrator (2)
	   }
           ACCESS  read-only
           STATUS  mandatory
DESCRIPTION ""
           ::= { u-fddiSMTStationIdGrp 2 }


        u-fddiSMTVersionId OBJECT-TYPE
           SYNTAX  INTEGER
           ACCESS  read-only
           STATUS  mandatory
DESCRIPTION ""
           ::= { u-fddiSMTStationIdGrp 3 }


        u-fddiSMTStationCfgGrp OBJECT-TYPE
           SYNTAX  SEQUENCE {
		u-fddiSMTMACCount
			INTEGER,
		u-fddiSMTAttachCount
			INTEGER,
		u-fddiSMTSpurCount
			INTEGER
	   }
           ACCESS  read-only
           STATUS  mandatory
DESCRIPTION ""
           ::= { u-fddiSMT 2 }


        u-fddiSMTMACCount OBJECT-TYPE
           SYNTAX  INTEGER
           ACCESS  read-only
           STATUS  mandatory
DESCRIPTION ""
           ::= { u-fddiSMTStationCfgGrp 1 }

        u-fddiSMTAttachCount OBJECT-TYPE
           SYNTAX  INTEGER
           ACCESS  read-only
           STATUS  mandatory
DESCRIPTION ""
           ::= { u-fddiSMTStationCfgGrp 2 }


        u-fddiSMTSpurCount OBJECT-TYPE
           SYNTAX  INTEGER
           ACCESS  read-only
           STATUS  mandatory
DESCRIPTION ""
           ::= { u-fddiSMTStationCfgGrp 3 }


        u-fddiSMTOperationalGrp OBJECT-TYPE
           SYNTAX  SEQUENCE {
		u-fddiSMTDasScmState
			INTEGER
	   }
           ACCESS  read-only
           STATUS  mandatory
DESCRIPTION ""
           ::= { u-fddiSMT 3 }


        u-fddiSMTDasScmState OBJECT-TYPE
           SYNTAX  INTEGER {
                isolated (1),
                wrap-a (2),
                wrap-b (3),
                thru (4)
           }
           ACCESS  read-only
           STATUS  mandatory
DESCRIPTION ""
           ::= { u-fddiSMTOperationalGrp 1 }

        u-fddiMACAddressGrp OBJECT-TYPE
           SYNTAX  SEQUENCE {
		u-fddiMACSMTLongAddr
			OCTET STRING,
		u-fddiMACShortGrpAddr
			OCTET STRING
	   }
           ACCESS  read-write
           STATUS  mandatory
DESCRIPTION ""
           ::= { u-fddiMACEntry 1 }


        u-fddiMACSMTLongAddr OBJECT-TYPE
           SYNTAX  OCTET STRING (SIZE (6))
           ACCESS  read-write
           STATUS  mandatory
DESCRIPTION ""
           ::= { u-fddiMACAddressGrp 1 }


        u-fddiMACShortGrpAddr OBJECT-TYPE
           SYNTAX  OCTET STRING (SIZE (2))
           ACCESS  read-write
           STATUS  mandatory
DESCRIPTION ""
           ::= { u-fddiMACAddressGrp 2 }


        u-fddiMACCfgGrp OBJECT-TYPE
           SYNTAX  SEQUENCE {
		u-fddiMACUpstreamNeighbor
			OCTET STRING,
		u-fddiMACDownstreamNeighbor
			OCTET STRING,
		u-fddiMACResourceIndex
			INTEGER,
		u-fddiMACConnectedResId
			INTEGER
	   }
           ACCESS  read-only
           STATUS  mandatory
DESCRIPTION ""
           ::= { u-fddiMACEntry 2 }


        u-fddiMACUpstreamNeighbor OBJECT-TYPE
           SYNTAX  OCTET STRING
           ACCESS  read-only
           STATUS  mandatory
DESCRIPTION ""
           ::= { u-fddiMACCfgGrp 1 }


        u-fddiMACDownstreamNeighbor OBJECT-TYPE
           SYNTAX  OCTET STRING
           ACCESS  read-only
           STATUS  mandatory
DESCRIPTION ""
           ::= { u-fddiMACCfgGrp 2 }


        u-fddiMACResourceIndex OBJECT-TYPE
           SYNTAX  INTEGER
           ACCESS  read-only
           STATUS  mandatory
DESCRIPTION ""
           ::= { u-fddiMACCfgGrp 3 }


        u-fddiMACConnectedResId OBJECT-TYPE
           SYNTAX  INTEGER
           ACCESS  read-only
           STATUS  mandatory
DESCRIPTION ""
           ::= { u-fddiMACCfgGrp 4 }


        u-fddiMACOperGrp OBJECT-TYPE
           SYNTAX  SEQUENCE {
		u-fddiMACTReq
			INTEGER,
		u-fddiMACTMax
			INTEGER,
		u-fddiMACTvxValue
			INTEGER,
		u-fddiMACTMin
			INTEGER
	   }
           ACCESS  read-write
           STATUS  mandatory
DESCRIPTION ""
           ::= { u-fddiMACEntry 3 }


        u-fddiMACTReq OBJECT-TYPE
           SYNTAX  INTEGER (u-fddiMACTMin..u-fddiMACTMax)
           ACCESS  read-write
           STATUS  mandatory
DESCRIPTION ""
           ::= { u-fddiMACOperGrp 1 }


        u-fddiMACTMax OBJECT-TYPE
           SYNTAX  INTEGER (u-fddiMACTMin..540)
           ACCESS  read-write
           STATUS  mandatory
DESCRIPTION ""
           ::= { u-fddiMACOperGrp 2 }


        u-fddiMACTvxValue OBJECT-TYPE
           SYNTAX  INTEGER (1..5000)
           ACCESS  read-write
           STATUS  mandatory
DESCRIPTION ""
           ::= { u-fddiMACOperGrp 3 }


        u-fddiMACTMin OBJECT-TYPE
           SYNTAX  INTEGER (4000..u-fddiMACTMax)
           ACCESS  read-write
           STATUS  mandatory
DESCRIPTION ""
           ::= { u-fddiMACOperGrp 4 }


        u-fddiMACCountersGrp OBJECT-TYPE
           SYNTAX  SEQUENCE {
		u-fddiMACReceiveCt
			Counter,
		u-fddiMACTransmitCt
			Counter,
		u-fddiMACTokenCt
			Counter
	   }
           ACCESS  read-only
           STATUS  mandatory
DESCRIPTION ""
           ::= { u-fddiMACEntry 4 }


        u-fddiMACReceiveCt OBJECT-TYPE
           SYNTAX  Counter
           ACCESS  read-only
           STATUS  mandatory
DESCRIPTION ""
           ::= { u-fddiMACCountersGrp 1 }


        u-fddiMACTransmitCt OBJECT-TYPE
           SYNTAX  Counter
           ACCESS  read-only
           STATUS  mandatory
DESCRIPTION ""
           ::= { u-fddiMACCountersGrp 2 }


        u-fddiMACTokenCt OBJECT-TYPE
           SYNTAX  Counter
           ACCESS  read-only
           STATUS  mandatory
DESCRIPTION ""
           ::= { u-fddiMACCountersGrp 3 }


        u-fddiMACErrorCntrsGrp OBJECT-TYPE
           SYNTAX  SEQUENCE {
		u-fddiMACTvxExpiredCt
			Counter,
		u-fddiMACNotCopiedCt
			Counter,
		u-fddiMACLateCt
			Counter,
		u-fddiMACReceeiveOverflowCt
			Counter
	   }
           ACCESS  read-only
           STATUS  mandatory
DESCRIPTION ""
           ::= { u-fddiMACEntry 5 }


        u-fddiMACTvxExpiredCt OBJECT-TYPE
           SYNTAX  Counter
           ACCESS  read-only
           STATUS  mandatory
DESCRIPTION ""
           ::= { u-fddiMACErrorCntrsGrp 1 }


        u-fddiMACNotCopiedCt OBJECT-TYPE
           SYNTAX  Counter
           ACCESS  read-only
           STATUS  mandatory
DESCRIPTION ""
           ::= { u-fddiMACErrorCntrsGrp 2 }


        u-fddiMACLateCt OBJECT-TYPE
           SYNTAX  Counter
           ACCESS  read-only
           STATUS  mandatory
DESCRIPTION ""
           ::= { u-fddiMACErrorCntrsGrp 3 }


        u-fddiMACReceiveOverflowCt OBJECT-TYPE
           SYNTAX  Counter
           ACCESS  read-only
           STATUS  mandatory
DESCRIPTION ""
           ::= { u-fddiMACErrorCntrsGrp 4 }


        u-fddiMACSTATUSGrp OBJECT-TYPE
           SYNTAX  SEQUENCE {
		u-fddiMACRingOpCt
			Counter,
		u-fddiMACEnteredBeaconCt
			Counter
	   }
           ACCESS  read-only
           STATUS  mandatory
DESCRIPTION ""
           ::= { u-fddiMACEntry 6 }


        u-fddiMACRingOpCt OBJECT-TYPE
           SYNTAX  Counter
           ACCESS  read-only
           STATUS  mandatory
DESCRIPTION ""
           ::= { u-fddiMACSTATUSGrp 1 }


        u-fddiMACEnteredBeaconCt OBJECT-TYPE
           SYNTAX  Counter
           ACCESS  read-only
           STATUS  mandatory
DESCRIPTION ""
           ::= { u-fddiMACSTATUSGrp 2 }

        u-fddiPHYCfgGrp OBJECT-TYPE
           SYNTAX  SEQUENCE {
		u-fddiPHYType
			INTEGER,
		u-fddiPHYConnectState
			INTEGER,
		u-fddiPHYRemotePHYType
			INTEGER,
		u-fddiPHYRemoteMACIndicated
			INTEGER --* BOOLEAN *--,
		u-fddiPHYResourceIndex
			INTEGER,
		u-fddiPHYConnectedResId
			INTEGER
	   }
           ACCESS  read-only
           STATUS  mandatory
DESCRIPTION ""
           ::= { u-fddiPHYEntry 1 }


        u-fddiPHYType OBJECT-TYPE
           SYNTAX  INTEGER {
		a (1),
		b (2),
		m (3),
		s (4)
	   }
           ACCESS  read-only
           STATUS  mandatory
DESCRIPTION ""
           ::= { u-fddiPHYCfgGrp 1 }


        u-fddiPHYConnectState OBJECT-TYPE
           SYNTAX  INTEGER {
		disabled (1),
		connecting (2),
		standby (3),
		active (4)
	   }
           ACCESS  read-only
           STATUS  mandatory
DESCRIPTION ""
           ::= { u-fddiPHYCfgGrp 2 }


        u-fddiPHYRemotePHYType OBJECT-TYPE
           SYNTAX  INTEGER {
		a (1),
		b (2),
		m (3),
		s (4),
		unknown (5)
	   }
           ACCESS  read-only
           STATUS  mandatory
DESCRIPTION ""
           ::= { u-fddiPHYCfgGrp 3 }


        u-fddiPHYRemoteMACIndicated OBJECT-TYPE
           SYNTAX  INTEGER --* BOOLEAN *-- 
           ACCESS  read-only
           STATUS  mandatory
DESCRIPTION ""
           ::= { u-fddiPHYCfgGrp 4 }


        u-fddiPHYResourceIndex OBJECT-TYPE
           SYNTAX  INTEGER
           ACCESS  read-only
           STATUS  mandatory
DESCRIPTION ""
           ::= { u-fddiPHYCfgGrp 5 }


        u-fddiPHYConnectedResId OBJECT-TYPE
           SYNTAX  INTEGER
           ACCESS  read-only
           STATUS  mandatory
DESCRIPTION ""
           ::= { u-fddiPHYCfgGrp 6 }


        u-fddiPHYAction OBJECT-TYPE
           SYNTAX  INTEGER {
		enabled  (0),
		disabled (1)
	   }
           ACCESS  read-write
           STATUS  mandatory
DESCRIPTION ""
           ::= { u-fddiPHYEntry 2 }

END
