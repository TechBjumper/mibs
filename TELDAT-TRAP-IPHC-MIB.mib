-- file automatically created


TELDAT-TRAP-IPHC-MIB DEFINITIONS ::= BEGIN


IMPORTS
	MODULE-IDENTITY,OBJECT-TYPE,OBJECT-IDENTITY,NOTIFICATION-TYPE,Integer32,IpAddress
		FROM SNMPv2-SMI
	DisplayString
		FROM SNMPv2-TC
	telEventTraps
		FROM TELDAT-MIB;


iphcTrapsMIB MODULE-IDENTITY
    LAST-UPDATED "201401200930Z"
    ORGANIZATION "Teldat, S.A."
    CONTACT-INFO 
        "Teldat, S.A.
        Customer Service

        Postal: Parque Tecnologico de Madrid
                Tres Cantos 28760
                Madrid, SPAIN

        Tel.: +34 918 076 565

        http://www.teldat.com"
    DESCRIPTION
        "This Module Information Base file is defined for managing received
        SNMP notifications generated by the IPHC event subsystem."
    REVISION "201401200930Z"
    DESCRIPTION "Initial implementation"
        ::= { telEventTraps 181 }


iphcEventsGroup	OBJECT IDENTIFIER	::= { iphcTrapsMIB 1 }

iphcNotifications	OBJECT IDENTIFIER	::= { iphcTrapsMIB 2 }
iphcNotificationsPrefix	OBJECT IDENTIFIER	::= { iphcNotifications 0 }

iphcEventObjects1 OBJECT-IDENTITY
    STATUS current
    DESCRIPTION
        "Event IPHC.1
        ."
    ::= { iphcEventsGroup 1 }

iphc1-interface OBJECT-TYPE
    SYNTAX DisplayString
    MAX-ACCESS accessible-for-notify
    STATUS current
    DESCRIPTION
        "Parameter 'interface' in event IPHC.1"
    ::= { iphcEventObjects1 1 }

iphc1-cid OBJECT-TYPE
    SYNTAX Integer32
    MAX-ACCESS accessible-for-notify
    STATUS current
    DESCRIPTION
        "Parameter 'cid' in event IPHC.1"
    ::= { iphcEventObjects1 2 }

iphc1-cause OBJECT-TYPE
    SYNTAX DisplayString
    MAX-ACCESS accessible-for-notify
    STATUS current
    DESCRIPTION
        "Parameter 'cause' in event IPHC.1"
    ::= { iphcEventObjects1 3 }

iphc1-pkt-counter OBJECT-TYPE
    SYNTAX Integer32
    MAX-ACCESS accessible-for-notify
    STATUS current
    DESCRIPTION
        "Parameter 'pkt-counter' in event IPHC.1"
    ::= { iphcEventObjects1 4 }

iphcEventObjects2 OBJECT-IDENTITY
    STATUS current
    DESCRIPTION
        "Event IPHC.2
        ."
    ::= { iphcEventsGroup 2 }

iphc2-interface OBJECT-TYPE
    SYNTAX DisplayString
    MAX-ACCESS accessible-for-notify
    STATUS current
    DESCRIPTION
        "Parameter 'interface' in event IPHC.2"
    ::= { iphcEventObjects2 1 }

iphc2-cid OBJECT-TYPE
    SYNTAX Integer32
    MAX-ACCESS accessible-for-notify
    STATUS current
    DESCRIPTION
        "Parameter 'cid' in event IPHC.2"
    ::= { iphcEventObjects2 2 }

iphc2-pkt-counter OBJECT-TYPE
    SYNTAX Integer32
    MAX-ACCESS accessible-for-notify
    STATUS current
    DESCRIPTION
        "Parameter 'pkt-counter' in event IPHC.2"
    ::= { iphcEventObjects2 3 }

iphcEventObjects3 OBJECT-IDENTITY
    STATUS current
    DESCRIPTION
        "Event IPHC.3
        ."
    ::= { iphcEventsGroup 3 }

iphc3-interface OBJECT-TYPE
    SYNTAX DisplayString
    MAX-ACCESS accessible-for-notify
    STATUS current
    DESCRIPTION
        "Parameter 'interface' in event IPHC.3"
    ::= { iphcEventObjects3 1 }

iphc3-cid OBJECT-TYPE
    SYNTAX Integer32
    MAX-ACCESS accessible-for-notify
    STATUS current
    DESCRIPTION
        "Parameter 'cid' in event IPHC.3"
    ::= { iphcEventObjects3 2 }

iphc3-generation OBJECT-TYPE
    SYNTAX Integer32
    MAX-ACCESS accessible-for-notify
    STATUS current
    DESCRIPTION
        "Parameter 'generation' in event IPHC.3"
    ::= { iphcEventObjects3 3 }

iphc3-flag-D OBJECT-TYPE
    SYNTAX DisplayString
    MAX-ACCESS accessible-for-notify
    STATUS current
    DESCRIPTION
        "Parameter 'flag-D' in event IPHC.3"
    ::= { iphcEventObjects3 4 }

iphc3-link-sequence OBJECT-TYPE
    SYNTAX Integer32
    MAX-ACCESS accessible-for-notify
    STATUS current
    DESCRIPTION
        "Parameter 'link-sequence' in event IPHC.3"
    ::= { iphcEventObjects3 5 }

iphc3-ip-id OBJECT-TYPE
    SYNTAX Integer32
    MAX-ACCESS accessible-for-notify
    STATUS current
    DESCRIPTION
        "Parameter 'ip-id' in event IPHC.3"
    ::= { iphcEventObjects3 6 }

iphc3-pkt-counter OBJECT-TYPE
    SYNTAX Integer32
    MAX-ACCESS accessible-for-notify
    STATUS current
    DESCRIPTION
        "Parameter 'pkt-counter' in event IPHC.3"
    ::= { iphcEventObjects3 7 }

iphcEventObjects4 OBJECT-IDENTITY
    STATUS current
    DESCRIPTION
        "Event IPHC.4
        ."
    ::= { iphcEventsGroup 4 }

iphc4-interface OBJECT-TYPE
    SYNTAX DisplayString
    MAX-ACCESS accessible-for-notify
    STATUS current
    DESCRIPTION
        "Parameter 'interface' in event IPHC.4"
    ::= { iphcEventObjects4 1 }

iphc4-cid OBJECT-TYPE
    SYNTAX Integer32
    MAX-ACCESS accessible-for-notify
    STATUS current
    DESCRIPTION
        "Parameter 'cid' in event IPHC.4"
    ::= { iphcEventObjects4 2 }

iphc4-generation OBJECT-TYPE
    SYNTAX Integer32
    MAX-ACCESS accessible-for-notify
    STATUS current
    DESCRIPTION
        "Parameter 'generation' in event IPHC.4"
    ::= { iphcEventObjects4 3 }

iphc4-flag-D OBJECT-TYPE
    SYNTAX DisplayString
    MAX-ACCESS accessible-for-notify
    STATUS current
    DESCRIPTION
        "Parameter 'flag-D' in event IPHC.4"
    ::= { iphcEventObjects4 4 }

iphc4-link-sequence OBJECT-TYPE
    SYNTAX Integer32
    MAX-ACCESS accessible-for-notify
    STATUS current
    DESCRIPTION
        "Parameter 'link-sequence' in event IPHC.4"
    ::= { iphcEventObjects4 5 }

iphc4-ip-id OBJECT-TYPE
    SYNTAX Integer32
    MAX-ACCESS accessible-for-notify
    STATUS current
    DESCRIPTION
        "Parameter 'ip-id' in event IPHC.4"
    ::= { iphcEventObjects4 6 }

iphc4-pkt-counter OBJECT-TYPE
    SYNTAX Integer32
    MAX-ACCESS accessible-for-notify
    STATUS current
    DESCRIPTION
        "Parameter 'pkt-counter' in event IPHC.4"
    ::= { iphcEventObjects4 7 }

iphcEventObjects5 OBJECT-IDENTITY
    STATUS current
    DESCRIPTION
        "Event IPHC.5
        ."
    ::= { iphcEventsGroup 5 }

iphc5-interface OBJECT-TYPE
    SYNTAX DisplayString
    MAX-ACCESS accessible-for-notify
    STATUS current
    DESCRIPTION
        "Parameter 'interface' in event IPHC.5"
    ::= { iphcEventObjects5 1 }

iphc5-cid OBJECT-TYPE
    SYNTAX Integer32
    MAX-ACCESS accessible-for-notify
    STATUS current
    DESCRIPTION
        "Parameter 'cid' in event IPHC.5"
    ::= { iphcEventObjects5 2 }

iphc5-flags OBJECT-TYPE
    SYNTAX DisplayString
    MAX-ACCESS accessible-for-notify
    STATUS current
    DESCRIPTION
        "Parameter 'flags' in event IPHC.5"
    ::= { iphcEventObjects5 3 }

iphc5-sequence-number OBJECT-TYPE
    SYNTAX Integer32
    MAX-ACCESS accessible-for-notify
    STATUS current
    DESCRIPTION
        "Parameter 'sequence-number' in event IPHC.5"
    ::= { iphcEventObjects5 4 }

iphc5-ack-number OBJECT-TYPE
    SYNTAX Integer32
    MAX-ACCESS accessible-for-notify
    STATUS current
    DESCRIPTION
        "Parameter 'ack-number' in event IPHC.5"
    ::= { iphcEventObjects5 5 }

iphc5-window-size OBJECT-TYPE
    SYNTAX Integer32
    MAX-ACCESS accessible-for-notify
    STATUS current
    DESCRIPTION
        "Parameter 'window-size' in event IPHC.5"
    ::= { iphcEventObjects5 6 }

iphc5-checksum OBJECT-TYPE
    SYNTAX Integer32
    MAX-ACCESS accessible-for-notify
    STATUS current
    DESCRIPTION
        "Parameter 'checksum' in event IPHC.5"
    ::= { iphcEventObjects5 7 }

iphc5-ip-id OBJECT-TYPE
    SYNTAX Integer32
    MAX-ACCESS accessible-for-notify
    STATUS current
    DESCRIPTION
        "Parameter 'ip-id' in event IPHC.5"
    ::= { iphcEventObjects5 8 }

iphc5-pkt-counter OBJECT-TYPE
    SYNTAX Integer32
    MAX-ACCESS accessible-for-notify
    STATUS current
    DESCRIPTION
        "Parameter 'pkt-counter' in event IPHC.5"
    ::= { iphcEventObjects5 9 }

iphcEventObjects6 OBJECT-IDENTITY
    STATUS current
    DESCRIPTION
        "Event IPHC.6
        ."
    ::= { iphcEventsGroup 6 }

iphc6-interface OBJECT-TYPE
    SYNTAX DisplayString
    MAX-ACCESS accessible-for-notify
    STATUS current
    DESCRIPTION
        "Parameter 'interface' in event IPHC.6"
    ::= { iphcEventObjects6 1 }

iphc6-cid OBJECT-TYPE
    SYNTAX Integer32
    MAX-ACCESS accessible-for-notify
    STATUS current
    DESCRIPTION
        "Parameter 'cid' in event IPHC.6"
    ::= { iphcEventObjects6 2 }

iphc6-flags OBJECT-TYPE
    SYNTAX DisplayString
    MAX-ACCESS accessible-for-notify
    STATUS current
    DESCRIPTION
        "Parameter 'flags' in event IPHC.6"
    ::= { iphcEventObjects6 3 }

iphc6-sequence-number OBJECT-TYPE
    SYNTAX Integer32
    MAX-ACCESS accessible-for-notify
    STATUS current
    DESCRIPTION
        "Parameter 'sequence-number' in event IPHC.6"
    ::= { iphcEventObjects6 4 }

iphc6-ack-number OBJECT-TYPE
    SYNTAX Integer32
    MAX-ACCESS accessible-for-notify
    STATUS current
    DESCRIPTION
        "Parameter 'ack-number' in event IPHC.6"
    ::= { iphcEventObjects6 5 }

iphc6-window-size OBJECT-TYPE
    SYNTAX Integer32
    MAX-ACCESS accessible-for-notify
    STATUS current
    DESCRIPTION
        "Parameter 'window-size' in event IPHC.6"
    ::= { iphcEventObjects6 6 }

iphc6-checksum OBJECT-TYPE
    SYNTAX Integer32
    MAX-ACCESS accessible-for-notify
    STATUS current
    DESCRIPTION
        "Parameter 'checksum' in event IPHC.6"
    ::= { iphcEventObjects6 7 }

iphc6-ip-id OBJECT-TYPE
    SYNTAX Integer32
    MAX-ACCESS accessible-for-notify
    STATUS current
    DESCRIPTION
        "Parameter 'ip-id' in event IPHC.6"
    ::= { iphcEventObjects6 8 }

iphc6-pkt-counter OBJECT-TYPE
    SYNTAX Integer32
    MAX-ACCESS accessible-for-notify
    STATUS current
    DESCRIPTION
        "Parameter 'pkt-counter' in event IPHC.6"
    ::= { iphcEventObjects6 9 }

iphcEventObjects7 OBJECT-IDENTITY
    STATUS current
    DESCRIPTION
        "Event IPHC.7
        ."
    ::= { iphcEventsGroup 7 }

iphc7-interface OBJECT-TYPE
    SYNTAX DisplayString
    MAX-ACCESS accessible-for-notify
    STATUS current
    DESCRIPTION
        "Parameter 'interface' in event IPHC.7"
    ::= { iphcEventObjects7 1 }

iphc7-cid OBJECT-TYPE
    SYNTAX Integer32
    MAX-ACCESS accessible-for-notify
    STATUS current
    DESCRIPTION
        "Parameter 'cid' in event IPHC.7"
    ::= { iphcEventObjects7 2 }

iphcEventObjects8 OBJECT-IDENTITY
    STATUS current
    DESCRIPTION
        "Event IPHC.8
        ."
    ::= { iphcEventsGroup 8 }

iphc8-interface OBJECT-TYPE
    SYNTAX DisplayString
    MAX-ACCESS accessible-for-notify
    STATUS current
    DESCRIPTION
        "Parameter 'interface' in event IPHC.8"
    ::= { iphcEventObjects8 1 }

iphc8-cid OBJECT-TYPE
    SYNTAX Integer32
    MAX-ACCESS accessible-for-notify
    STATUS current
    DESCRIPTION
        "Parameter 'cid' in event IPHC.8"
    ::= { iphcEventObjects8 2 }

iphcEventObjects9 OBJECT-IDENTITY
    STATUS current
    DESCRIPTION
        "Event IPHC.9
        ."
    ::= { iphcEventsGroup 9 }

iphc9-interface OBJECT-TYPE
    SYNTAX DisplayString
    MAX-ACCESS accessible-for-notify
    STATUS current
    DESCRIPTION
        "Parameter 'interface' in event IPHC.9"
    ::= { iphcEventObjects9 1 }

iphc9-cid OBJECT-TYPE
    SYNTAX Integer32
    MAX-ACCESS accessible-for-notify
    STATUS current
    DESCRIPTION
        "Parameter 'cid' in event IPHC.9"
    ::= { iphcEventObjects9 2 }

iphc9-flags OBJECT-TYPE
    SYNTAX DisplayString
    MAX-ACCESS accessible-for-notify
    STATUS current
    DESCRIPTION
        "Parameter 'flags' in event IPHC.9"
    ::= { iphcEventObjects9 3 }

iphc9-link-sequence OBJECT-TYPE
    SYNTAX Integer32
    MAX-ACCESS accessible-for-notify
    STATUS current
    DESCRIPTION
        "Parameter 'link-sequence' in event IPHC.9"
    ::= { iphcEventObjects9 4 }

iphc9-ip-id OBJECT-TYPE
    SYNTAX Integer32
    MAX-ACCESS accessible-for-notify
    STATUS current
    DESCRIPTION
        "Parameter 'ip-id' in event IPHC.9"
    ::= { iphcEventObjects9 5 }

iphc9-pkt-counter OBJECT-TYPE
    SYNTAX Integer32
    MAX-ACCESS accessible-for-notify
    STATUS current
    DESCRIPTION
        "Parameter 'pkt-counter' in event IPHC.9"
    ::= { iphcEventObjects9 6 }

iphcEventObjects10 OBJECT-IDENTITY
    STATUS current
    DESCRIPTION
        "Event IPHC.10
        ."
    ::= { iphcEventsGroup 10 }

iphc10-interface OBJECT-TYPE
    SYNTAX DisplayString
    MAX-ACCESS accessible-for-notify
    STATUS current
    DESCRIPTION
        "Parameter 'interface' in event IPHC.10"
    ::= { iphcEventObjects10 1 }

iphc10-cid OBJECT-TYPE
    SYNTAX Integer32
    MAX-ACCESS accessible-for-notify
    STATUS current
    DESCRIPTION
        "Parameter 'cid' in event IPHC.10"
    ::= { iphcEventObjects10 2 }

iphc10-flags OBJECT-TYPE
    SYNTAX DisplayString
    MAX-ACCESS accessible-for-notify
    STATUS current
    DESCRIPTION
        "Parameter 'flags' in event IPHC.10"
    ::= { iphcEventObjects10 3 }

iphc10-link-sequence OBJECT-TYPE
    SYNTAX Integer32
    MAX-ACCESS accessible-for-notify
    STATUS current
    DESCRIPTION
        "Parameter 'link-sequence' in event IPHC.10"
    ::= { iphcEventObjects10 4 }

iphc10-ip-id OBJECT-TYPE
    SYNTAX Integer32
    MAX-ACCESS accessible-for-notify
    STATUS current
    DESCRIPTION
        "Parameter 'ip-id' in event IPHC.10"
    ::= { iphcEventObjects10 5 }

iphc10-pkt-counter OBJECT-TYPE
    SYNTAX Integer32
    MAX-ACCESS accessible-for-notify
    STATUS current
    DESCRIPTION
        "Parameter 'pkt-counter' in event IPHC.10"
    ::= { iphcEventObjects10 6 }

iphcEventObjects11 OBJECT-IDENTITY
    STATUS current
    DESCRIPTION
        "Event IPHC.11
        ."
    ::= { iphcEventsGroup 11 }

iphc11-interface OBJECT-TYPE
    SYNTAX DisplayString
    MAX-ACCESS accessible-for-notify
    STATUS current
    DESCRIPTION
        "Parameter 'interface' in event IPHC.11"
    ::= { iphcEventObjects11 1 }

iphc11-cid OBJECT-TYPE
    SYNTAX Integer32
    MAX-ACCESS accessible-for-notify
    STATUS current
    DESCRIPTION
        "Parameter 'cid' in event IPHC.11"
    ::= { iphcEventObjects11 2 }

iphc11-flags OBJECT-TYPE
    SYNTAX DisplayString
    MAX-ACCESS accessible-for-notify
    STATUS current
    DESCRIPTION
        "Parameter 'flags' in event IPHC.11"
    ::= { iphcEventObjects11 3 }

iphc11-link-sequence OBJECT-TYPE
    SYNTAX Integer32
    MAX-ACCESS accessible-for-notify
    STATUS current
    DESCRIPTION
        "Parameter 'link-sequence' in event IPHC.11"
    ::= { iphcEventObjects11 4 }

iphc11-pkt-counter OBJECT-TYPE
    SYNTAX Integer32
    MAX-ACCESS accessible-for-notify
    STATUS current
    DESCRIPTION
        "Parameter 'pkt-counter' in event IPHC.11"
    ::= { iphcEventObjects11 5 }

iphcEventObjects12 OBJECT-IDENTITY
    STATUS current
    DESCRIPTION
        "Event IPHC.12
        ."
    ::= { iphcEventsGroup 12 }

iphc12-interface OBJECT-TYPE
    SYNTAX DisplayString
    MAX-ACCESS accessible-for-notify
    STATUS current
    DESCRIPTION
        "Parameter 'interface' in event IPHC.12"
    ::= { iphcEventObjects12 1 }

iphc12-cid OBJECT-TYPE
    SYNTAX Integer32
    MAX-ACCESS accessible-for-notify
    STATUS current
    DESCRIPTION
        "Parameter 'cid' in event IPHC.12"
    ::= { iphcEventObjects12 2 }

iphc12-flags OBJECT-TYPE
    SYNTAX DisplayString
    MAX-ACCESS accessible-for-notify
    STATUS current
    DESCRIPTION
        "Parameter 'flags' in event IPHC.12"
    ::= { iphcEventObjects12 3 }

iphc12-link-sequence OBJECT-TYPE
    SYNTAX Integer32
    MAX-ACCESS accessible-for-notify
    STATUS current
    DESCRIPTION
        "Parameter 'link-sequence' in event IPHC.12"
    ::= { iphcEventObjects12 4 }

iphc12-ip-id OBJECT-TYPE
    SYNTAX Integer32
    MAX-ACCESS accessible-for-notify
    STATUS current
    DESCRIPTION
        "Parameter 'ip-id' in event IPHC.12"
    ::= { iphcEventObjects12 5 }

iphc12-pkt-counter OBJECT-TYPE
    SYNTAX Integer32
    MAX-ACCESS accessible-for-notify
    STATUS current
    DESCRIPTION
        "Parameter 'pkt-counter' in event IPHC.12"
    ::= { iphcEventObjects12 6 }

iphcEventObjects13 OBJECT-IDENTITY
    STATUS current
    DESCRIPTION
        "Event IPHC.13
        ."
    ::= { iphcEventsGroup 13 }

iphc13-interface OBJECT-TYPE
    SYNTAX DisplayString
    MAX-ACCESS accessible-for-notify
    STATUS current
    DESCRIPTION
        "Parameter 'interface' in event IPHC.13"
    ::= { iphcEventObjects13 1 }

iphc13-cid OBJECT-TYPE
    SYNTAX Integer32
    MAX-ACCESS accessible-for-notify
    STATUS current
    DESCRIPTION
        "Parameter 'cid' in event IPHC.13"
    ::= { iphcEventObjects13 2 }

iphcEventObjects14 OBJECT-IDENTITY
    STATUS current
    DESCRIPTION
        "Event IPHC.14
        ."
    ::= { iphcEventsGroup 14 }

iphc14-interface OBJECT-TYPE
    SYNTAX DisplayString
    MAX-ACCESS accessible-for-notify
    STATUS current
    DESCRIPTION
        "Parameter 'interface' in event IPHC.14"
    ::= { iphcEventObjects14 1 }

iphc14-cid OBJECT-TYPE
    SYNTAX Integer32
    MAX-ACCESS accessible-for-notify
    STATUS current
    DESCRIPTION
        "Parameter 'cid' in event IPHC.14"
    ::= { iphcEventObjects14 2 }

iphc14-flags OBJECT-TYPE
    SYNTAX DisplayString
    MAX-ACCESS accessible-for-notify
    STATUS current
    DESCRIPTION
        "Parameter 'flags' in event IPHC.14"
    ::= { iphcEventObjects14 3 }

iphc14-link-sequence OBJECT-TYPE
    SYNTAX Integer32
    MAX-ACCESS accessible-for-notify
    STATUS current
    DESCRIPTION
        "Parameter 'link-sequence' in event IPHC.14"
    ::= { iphcEventObjects14 4 }

iphc14-ip-id OBJECT-TYPE
    SYNTAX Integer32
    MAX-ACCESS accessible-for-notify
    STATUS current
    DESCRIPTION
        "Parameter 'ip-id' in event IPHC.14"
    ::= { iphcEventObjects14 5 }

iphc14-pkt-counter OBJECT-TYPE
    SYNTAX Integer32
    MAX-ACCESS accessible-for-notify
    STATUS current
    DESCRIPTION
        "Parameter 'pkt-counter' in event IPHC.14"
    ::= { iphcEventObjects14 6 }

iphcEventObjects15 OBJECT-IDENTITY
    STATUS current
    DESCRIPTION
        "Event IPHC.15
        ."
    ::= { iphcEventsGroup 15 }

iphc15-interface OBJECT-TYPE
    SYNTAX DisplayString
    MAX-ACCESS accessible-for-notify
    STATUS current
    DESCRIPTION
        "Parameter 'interface' in event IPHC.15"
    ::= { iphcEventObjects15 1 }

iphc15-cid OBJECT-TYPE
    SYNTAX Integer32
    MAX-ACCESS accessible-for-notify
    STATUS current
    DESCRIPTION
        "Parameter 'cid' in event IPHC.15"
    ::= { iphcEventObjects15 2 }

iphcEventObjects16 OBJECT-IDENTITY
    STATUS current
    DESCRIPTION
        "Event IPHC.16
        ."
    ::= { iphcEventsGroup 16 }

iphc16-interface OBJECT-TYPE
    SYNTAX DisplayString
    MAX-ACCESS accessible-for-notify
    STATUS current
    DESCRIPTION
        "Parameter 'interface' in event IPHC.16"
    ::= { iphcEventObjects16 1 }

iphc16-cid OBJECT-TYPE
    SYNTAX Integer32
    MAX-ACCESS accessible-for-notify
    STATUS current
    DESCRIPTION
        "Parameter 'cid' in event IPHC.16"
    ::= { iphcEventObjects16 2 }

iphc16-flags OBJECT-TYPE
    SYNTAX DisplayString
    MAX-ACCESS accessible-for-notify
    STATUS current
    DESCRIPTION
        "Parameter 'flags' in event IPHC.16"
    ::= { iphcEventObjects16 3 }

iphc16-link-sequence OBJECT-TYPE
    SYNTAX Integer32
    MAX-ACCESS accessible-for-notify
    STATUS current
    DESCRIPTION
        "Parameter 'link-sequence' in event IPHC.16"
    ::= { iphcEventObjects16 4 }

iphc16-ip-id OBJECT-TYPE
    SYNTAX Integer32
    MAX-ACCESS accessible-for-notify
    STATUS current
    DESCRIPTION
        "Parameter 'ip-id' in event IPHC.16"
    ::= { iphcEventObjects16 5 }

iphc16-pkt-counter OBJECT-TYPE
    SYNTAX Integer32
    MAX-ACCESS accessible-for-notify
    STATUS current
    DESCRIPTION
        "Parameter 'pkt-counter' in event IPHC.16"
    ::= { iphcEventObjects16 6 }

iphcEventObjects17 OBJECT-IDENTITY
    STATUS current
    DESCRIPTION
        "Event IPHC.17
        ."
    ::= { iphcEventsGroup 17 }

iphc17-interface OBJECT-TYPE
    SYNTAX DisplayString
    MAX-ACCESS accessible-for-notify
    STATUS current
    DESCRIPTION
        "Parameter 'interface' in event IPHC.17"
    ::= { iphcEventObjects17 1 }

iphc17-cid OBJECT-TYPE
    SYNTAX Integer32
    MAX-ACCESS accessible-for-notify
    STATUS current
    DESCRIPTION
        "Parameter 'cid' in event IPHC.17"
    ::= { iphcEventObjects17 2 }

iphcEventObjects18 OBJECT-IDENTITY
    STATUS current
    DESCRIPTION
        "Event IPHC.18
        ."
    ::= { iphcEventsGroup 18 }

iphc18-interface OBJECT-TYPE
    SYNTAX DisplayString
    MAX-ACCESS accessible-for-notify
    STATUS current
    DESCRIPTION
        "Parameter 'interface' in event IPHC.18"
    ::= { iphcEventObjects18 1 }

iphc18-cid OBJECT-TYPE
    SYNTAX Integer32
    MAX-ACCESS accessible-for-notify
    STATUS current
    DESCRIPTION
        "Parameter 'cid' in event IPHC.18"
    ::= { iphcEventObjects18 2 }

iphc18-generation OBJECT-TYPE
    SYNTAX Integer32
    MAX-ACCESS accessible-for-notify
    STATUS current
    DESCRIPTION
        "Parameter 'generation' in event IPHC.18"
    ::= { iphcEventObjects18 3 }

iphc18-current-generation OBJECT-TYPE
    SYNTAX Integer32
    MAX-ACCESS accessible-for-notify
    STATUS current
    DESCRIPTION
        "Parameter 'current-generation' in event IPHC.18"
    ::= { iphcEventObjects18 4 }

iphc18-flag-I OBJECT-TYPE
    SYNTAX DisplayString
    MAX-ACCESS accessible-for-notify
    STATUS current
    DESCRIPTION
        "Parameter 'flag-I' in event IPHC.18"
    ::= { iphcEventObjects18 5 }

iphc18-link-sequence OBJECT-TYPE
    SYNTAX Integer32
    MAX-ACCESS accessible-for-notify
    STATUS current
    DESCRIPTION
        "Parameter 'link-sequence' in event IPHC.18"
    ::= { iphcEventObjects18 6 }

iphc18-current-link-sequence OBJECT-TYPE
    SYNTAX Integer32
    MAX-ACCESS accessible-for-notify
    STATUS current
    DESCRIPTION
        "Parameter 'current-link-sequence' in event IPHC.18"
    ::= { iphcEventObjects18 7 }

iphc18-pkt-counter OBJECT-TYPE
    SYNTAX Integer32
    MAX-ACCESS accessible-for-notify
    STATUS current
    DESCRIPTION
        "Parameter 'pkt-counter' in event IPHC.18"
    ::= { iphcEventObjects18 8 }

iphcEventObjects19 OBJECT-IDENTITY
    STATUS current
    DESCRIPTION
        "Event IPHC.19
        ."
    ::= { iphcEventsGroup 19 }

iphc19-interface OBJECT-TYPE
    SYNTAX DisplayString
    MAX-ACCESS accessible-for-notify
    STATUS current
    DESCRIPTION
        "Parameter 'interface' in event IPHC.19"
    ::= { iphcEventObjects19 1 }

iphc19-checksum OBJECT-TYPE
    SYNTAX Integer32
    MAX-ACCESS accessible-for-notify
    STATUS current
    DESCRIPTION
        "Parameter 'checksum' in event IPHC.19"
    ::= { iphcEventObjects19 2 }

iphc19-expected-checksum OBJECT-TYPE
    SYNTAX Integer32
    MAX-ACCESS accessible-for-notify
    STATUS current
    DESCRIPTION
        "Parameter 'expected-checksum' in event IPHC.19"
    ::= { iphcEventObjects19 3 }

iphc19-cid OBJECT-TYPE
    SYNTAX Integer32
    MAX-ACCESS accessible-for-notify
    STATUS current
    DESCRIPTION
        "Parameter 'cid' in event IPHC.19"
    ::= { iphcEventObjects19 4 }

iphcEventObjects20 OBJECT-IDENTITY
    STATUS current
    DESCRIPTION
        "Event IPHC.20
        ."
    ::= { iphcEventsGroup 20 }

iphc20-interface OBJECT-TYPE
    SYNTAX DisplayString
    MAX-ACCESS accessible-for-notify
    STATUS current
    DESCRIPTION
        "Parameter 'interface' in event IPHC.20"
    ::= { iphcEventObjects20 1 }

iphc20-cid OBJECT-TYPE
    SYNTAX Integer32
    MAX-ACCESS accessible-for-notify
    STATUS current
    DESCRIPTION
        "Parameter 'cid' in event IPHC.20"
    ::= { iphcEventObjects20 2 }

iphc20-max-cid OBJECT-TYPE
    SYNTAX Integer32
    MAX-ACCESS accessible-for-notify
    STATUS current
    DESCRIPTION
        "Parameter 'max-cid' in event IPHC.20"
    ::= { iphcEventObjects20 3 }

iphcEventObjects21 OBJECT-IDENTITY
    STATUS current
    DESCRIPTION
        "Event IPHC.21
        ."
    ::= { iphcEventsGroup 21 }

iphc21-interface OBJECT-TYPE
    SYNTAX DisplayString
    MAX-ACCESS accessible-for-notify
    STATUS current
    DESCRIPTION
        "Parameter 'interface' in event IPHC.21"
    ::= { iphcEventObjects21 1 }

iphc21-cid OBJECT-TYPE
    SYNTAX Integer32
    MAX-ACCESS accessible-for-notify
    STATUS current
    DESCRIPTION
        "Parameter 'cid' in event IPHC.21"
    ::= { iphcEventObjects21 2 }

iphcEventObjects22 OBJECT-IDENTITY
    STATUS current
    DESCRIPTION
        "Event IPHC.22
        ."
    ::= { iphcEventsGroup 22 }

iphc22-interface OBJECT-TYPE
    SYNTAX DisplayString
    MAX-ACCESS accessible-for-notify
    STATUS current
    DESCRIPTION
        "Parameter 'interface' in event IPHC.22"
    ::= { iphcEventObjects22 1 }

iphc22-cid OBJECT-TYPE
    SYNTAX Integer32
    MAX-ACCESS accessible-for-notify
    STATUS current
    DESCRIPTION
        "Parameter 'cid' in event IPHC.22"
    ::= { iphcEventObjects22 2 }

iphc22-ip-id OBJECT-TYPE
    SYNTAX Integer32
    MAX-ACCESS accessible-for-notify
    STATUS current
    DESCRIPTION
        "Parameter 'ip-id' in event IPHC.22"
    ::= { iphcEventObjects22 3 }

iphc22-src-ipaddr OBJECT-TYPE
    SYNTAX IpAddress
    MAX-ACCESS accessible-for-notify
    STATUS current
    DESCRIPTION
        "Parameter 'src-ipaddr' in event IPHC.22"
    ::= { iphcEventObjects22 4 }

iphc22-src-port OBJECT-TYPE
    SYNTAX Integer32
    MAX-ACCESS accessible-for-notify
    STATUS current
    DESCRIPTION
        "Parameter 'src-port' in event IPHC.22"
    ::= { iphcEventObjects22 5 }

iphc22-dst-ipaddr OBJECT-TYPE
    SYNTAX IpAddress
    MAX-ACCESS accessible-for-notify
    STATUS current
    DESCRIPTION
        "Parameter 'dst-ipaddr' in event IPHC.22"
    ::= { iphcEventObjects22 6 }

iphc22-dst-port OBJECT-TYPE
    SYNTAX Integer32
    MAX-ACCESS accessible-for-notify
    STATUS current
    DESCRIPTION
        "Parameter 'dst-port' in event IPHC.22"
    ::= { iphcEventObjects22 7 }

iphc22-generation OBJECT-TYPE
    SYNTAX Integer32
    MAX-ACCESS accessible-for-notify
    STATUS current
    DESCRIPTION
        "Parameter 'generation' in event IPHC.22"
    ::= { iphcEventObjects22 8 }

iphc22-cksum OBJECT-TYPE
    SYNTAX Integer32
    MAX-ACCESS accessible-for-notify
    STATUS current
    DESCRIPTION
        "Parameter 'cksum' in event IPHC.22"
    ::= { iphcEventObjects22 9 }

iphc22-flag OBJECT-TYPE
    SYNTAX DisplayString
    MAX-ACCESS accessible-for-notify
    STATUS current
    DESCRIPTION
        "Parameter 'flag' in event IPHC.22"
    ::= { iphcEventObjects22 10 }

iphc22-link-sequence OBJECT-TYPE
    SYNTAX Integer32
    MAX-ACCESS accessible-for-notify
    STATUS current
    DESCRIPTION
        "Parameter 'link-sequence' in event IPHC.22"
    ::= { iphcEventObjects22 11 }

iphcEventObjects23 OBJECT-IDENTITY
    STATUS current
    DESCRIPTION
        "Event IPHC.23
        ."
    ::= { iphcEventsGroup 23 }

iphc23-interface OBJECT-TYPE
    SYNTAX DisplayString
    MAX-ACCESS accessible-for-notify
    STATUS current
    DESCRIPTION
        "Parameter 'interface' in event IPHC.23"
    ::= { iphcEventObjects23 1 }

iphc23-cid OBJECT-TYPE
    SYNTAX Integer32
    MAX-ACCESS accessible-for-notify
    STATUS current
    DESCRIPTION
        "Parameter 'cid' in event IPHC.23"
    ::= { iphcEventObjects23 2 }

iphc23-cause OBJECT-TYPE
    SYNTAX DisplayString
    MAX-ACCESS accessible-for-notify
    STATUS current
    DESCRIPTION
        "Parameter 'cause' in event IPHC.23"
    ::= { iphcEventObjects23 3 }

iphc23-pkt-counter OBJECT-TYPE
    SYNTAX Integer32
    MAX-ACCESS accessible-for-notify
    STATUS current
    DESCRIPTION
        "Parameter 'pkt-counter' in event IPHC.23"
    ::= { iphcEventObjects23 4 }

iphcEventObjects24 OBJECT-IDENTITY
    STATUS current
    DESCRIPTION
        "Event IPHC.24
        ."
    ::= { iphcEventsGroup 24 }

iphc24-interface OBJECT-TYPE
    SYNTAX DisplayString
    MAX-ACCESS accessible-for-notify
    STATUS current
    DESCRIPTION
        "Parameter 'interface' in event IPHC.24"
    ::= { iphcEventObjects24 1 }

iphc24-cid OBJECT-TYPE
    SYNTAX Integer32
    MAX-ACCESS accessible-for-notify
    STATUS current
    DESCRIPTION
        "Parameter 'cid' in event IPHC.24"
    ::= { iphcEventObjects24 2 }

iphc24-pkt-counter OBJECT-TYPE
    SYNTAX Integer32
    MAX-ACCESS accessible-for-notify
    STATUS current
    DESCRIPTION
        "Parameter 'pkt-counter' in event IPHC.24"
    ::= { iphcEventObjects24 3 }

iphcEventObjects25 OBJECT-IDENTITY
    STATUS current
    DESCRIPTION
        "Event IPHC.25
        ."
    ::= { iphcEventsGroup 25 }

iphc25-interface OBJECT-TYPE
    SYNTAX DisplayString
    MAX-ACCESS accessible-for-notify
    STATUS current
    DESCRIPTION
        "Parameter 'interface' in event IPHC.25"
    ::= { iphcEventObjects25 1 }

iphc25-cid OBJECT-TYPE
    SYNTAX Integer32
    MAX-ACCESS accessible-for-notify
    STATUS current
    DESCRIPTION
        "Parameter 'cid' in event IPHC.25"
    ::= { iphcEventObjects25 2 }

iphc25-ip-id OBJECT-TYPE
    SYNTAX Integer32
    MAX-ACCESS accessible-for-notify
    STATUS current
    DESCRIPTION
        "Parameter 'ip-id' in event IPHC.25"
    ::= { iphcEventObjects25 3 }

iphc25-src-ipaddr OBJECT-TYPE
    SYNTAX IpAddress
    MAX-ACCESS accessible-for-notify
    STATUS current
    DESCRIPTION
        "Parameter 'src-ipaddr' in event IPHC.25"
    ::= { iphcEventObjects25 4 }

iphc25-src-port OBJECT-TYPE
    SYNTAX Integer32
    MAX-ACCESS accessible-for-notify
    STATUS current
    DESCRIPTION
        "Parameter 'src-port' in event IPHC.25"
    ::= { iphcEventObjects25 5 }

iphc25-dst-ipaddr OBJECT-TYPE
    SYNTAX IpAddress
    MAX-ACCESS accessible-for-notify
    STATUS current
    DESCRIPTION
        "Parameter 'dst-ipaddr' in event IPHC.25"
    ::= { iphcEventObjects25 6 }

iphc25-dst-port OBJECT-TYPE
    SYNTAX Integer32
    MAX-ACCESS accessible-for-notify
    STATUS current
    DESCRIPTION
        "Parameter 'dst-port' in event IPHC.25"
    ::= { iphcEventObjects25 7 }

iphc25-cksum OBJECT-TYPE
    SYNTAX Integer32
    MAX-ACCESS accessible-for-notify
    STATUS current
    DESCRIPTION
        "Parameter 'cksum' in event IPHC.25"
    ::= { iphcEventObjects25 8 }

iphcEventObjects26 OBJECT-IDENTITY
    STATUS current
    DESCRIPTION
        "Event IPHC.26
        ."
    ::= { iphcEventsGroup 26 }

iphc26-interface OBJECT-TYPE
    SYNTAX DisplayString
    MAX-ACCESS accessible-for-notify
    STATUS current
    DESCRIPTION
        "Parameter 'interface' in event IPHC.26"
    ::= { iphcEventObjects26 1 }

iphc26-cid OBJECT-TYPE
    SYNTAX Integer32
    MAX-ACCESS accessible-for-notify
    STATUS current
    DESCRIPTION
        "Parameter 'cid' in event IPHC.26"
    ::= { iphcEventObjects26 2 }

iphc26-hlen OBJECT-TYPE
    SYNTAX Integer32
    MAX-ACCESS accessible-for-notify
    STATUS current
    DESCRIPTION
        "Parameter 'hlen' in event IPHC.26"
    ::= { iphcEventObjects26 3 }

iphc26-max-hlen OBJECT-TYPE
    SYNTAX Integer32
    MAX-ACCESS accessible-for-notify
    STATUS current
    DESCRIPTION
        "Parameter 'max-hlen' in event IPHC.26"
    ::= { iphcEventObjects26 4 }

iphcEventObjects27 OBJECT-IDENTITY
    STATUS current
    DESCRIPTION
        "Event IPHC.27
        ."
    ::= { iphcEventsGroup 27 }

iphc27-interface OBJECT-TYPE
    SYNTAX DisplayString
    MAX-ACCESS accessible-for-notify
    STATUS current
    DESCRIPTION
        "Parameter 'interface' in event IPHC.27"
    ::= { iphcEventObjects27 1 }

iphc27-cid OBJECT-TYPE
    SYNTAX Integer32
    MAX-ACCESS accessible-for-notify
    STATUS current
    DESCRIPTION
        "Parameter 'cid' in event IPHC.27"
    ::= { iphcEventObjects27 2 }

iphc27-generation OBJECT-TYPE
    SYNTAX Integer32
    MAX-ACCESS accessible-for-notify
    STATUS current
    DESCRIPTION
        "Parameter 'generation' in event IPHC.27"
    ::= { iphcEventObjects27 3 }

iphc27-expected-generation OBJECT-TYPE
    SYNTAX Integer32
    MAX-ACCESS accessible-for-notify
    STATUS current
    DESCRIPTION
        "Parameter 'expected-generation' in event IPHC.27"
    ::= { iphcEventObjects27 4 }

iphcEventObjects29 OBJECT-IDENTITY
    STATUS current
    DESCRIPTION
        "Event IPHC.29
        This message is generated when an packet has an invalid sequence.
        The received sequence, together with the correct sequence,
        are displayed."
    ::= { iphcEventsGroup 29 }

iphc29-interface OBJECT-TYPE
    SYNTAX DisplayString
    MAX-ACCESS accessible-for-notify
    STATUS current
    DESCRIPTION
        "Parameter 'interface' in event IPHC.29"
    ::= { iphcEventObjects29 1 }

iphc29-link-sequence OBJECT-TYPE
    SYNTAX Integer32
    MAX-ACCESS accessible-for-notify
    STATUS current
    DESCRIPTION
        "Parameter 'link-sequence' in event IPHC.29"
    ::= { iphcEventObjects29 2 }

iphc29-expected-link-sequence OBJECT-TYPE
    SYNTAX Integer32
    MAX-ACCESS accessible-for-notify
    STATUS current
    DESCRIPTION
        "Parameter 'expected-link-sequence' in event IPHC.29"
    ::= { iphcEventObjects29 3 }

iphc29-cid OBJECT-TYPE
    SYNTAX Integer32
    MAX-ACCESS accessible-for-notify
    STATUS current
    DESCRIPTION
        "Parameter 'cid' in event IPHC.29"
    ::= { iphcEventObjects29 4 }

iphcEventObjects30 OBJECT-IDENTITY
    STATUS current
    DESCRIPTION
        "Event IPHC.30
        ."
    ::= { iphcEventsGroup 30 }

iphc30-interface OBJECT-TYPE
    SYNTAX DisplayString
    MAX-ACCESS accessible-for-notify
    STATUS current
    DESCRIPTION
        "Parameter 'interface' in event IPHC.30"
    ::= { iphcEventObjects30 1 }

iphc30-cid OBJECT-TYPE
    SYNTAX Integer32
    MAX-ACCESS accessible-for-notify
    STATUS current
    DESCRIPTION
        "Parameter 'cid' in event IPHC.30"
    ::= { iphcEventObjects30 2 }

iphc30-ip-id OBJECT-TYPE
    SYNTAX Integer32
    MAX-ACCESS accessible-for-notify
    STATUS current
    DESCRIPTION
        "Parameter 'ip-id' in event IPHC.30"
    ::= { iphcEventObjects30 3 }

iphc30-src-ipaddr OBJECT-TYPE
    SYNTAX IpAddress
    MAX-ACCESS accessible-for-notify
    STATUS current
    DESCRIPTION
        "Parameter 'src-ipaddr' in event IPHC.30"
    ::= { iphcEventObjects30 4 }

iphc30-src-port OBJECT-TYPE
    SYNTAX Integer32
    MAX-ACCESS accessible-for-notify
    STATUS current
    DESCRIPTION
        "Parameter 'src-port' in event IPHC.30"
    ::= { iphcEventObjects30 5 }

iphc30-dst-ipaddr OBJECT-TYPE
    SYNTAX IpAddress
    MAX-ACCESS accessible-for-notify
    STATUS current
    DESCRIPTION
        "Parameter 'dst-ipaddr' in event IPHC.30"
    ::= { iphcEventObjects30 6 }

iphc30-dst-port OBJECT-TYPE
    SYNTAX Integer32
    MAX-ACCESS accessible-for-notify
    STATUS current
    DESCRIPTION
        "Parameter 'dst-port' in event IPHC.30"
    ::= { iphcEventObjects30 7 }

iphc30-generation OBJECT-TYPE
    SYNTAX Integer32
    MAX-ACCESS accessible-for-notify
    STATUS current
    DESCRIPTION
        "Parameter 'generation' in event IPHC.30"
    ::= { iphcEventObjects30 8 }

iphc30-cksum OBJECT-TYPE
    SYNTAX Integer32
    MAX-ACCESS accessible-for-notify
    STATUS current
    DESCRIPTION
        "Parameter 'cksum' in event IPHC.30"
    ::= { iphcEventObjects30 9 }

iphc30-flag OBJECT-TYPE
    SYNTAX DisplayString
    MAX-ACCESS accessible-for-notify
    STATUS current
    DESCRIPTION
        "Parameter 'flag' in event IPHC.30"
    ::= { iphcEventObjects30 10 }

iphc30-link-sequence OBJECT-TYPE
    SYNTAX Integer32
    MAX-ACCESS accessible-for-notify
    STATUS current
    DESCRIPTION
        "Parameter 'link-sequence' in event IPHC.30"
    ::= { iphcEventObjects30 11 }

iphcEventObjects31 OBJECT-IDENTITY
    STATUS current
    DESCRIPTION
        "Event IPHC.31
        ."
    ::= { iphcEventsGroup 31 }

iphc31-interface OBJECT-TYPE
    SYNTAX DisplayString
    MAX-ACCESS accessible-for-notify
    STATUS current
    DESCRIPTION
        "Parameter 'interface' in event IPHC.31"
    ::= { iphcEventObjects31 1 }

iphc31-cid OBJECT-TYPE
    SYNTAX Integer32
    MAX-ACCESS accessible-for-notify
    STATUS current
    DESCRIPTION
        "Parameter 'cid' in event IPHC.31"
    ::= { iphcEventObjects31 2 }

iphc31-chksum OBJECT-TYPE
    SYNTAX Integer32
    MAX-ACCESS accessible-for-notify
    STATUS current
    DESCRIPTION
        "Parameter 'chksum' in event IPHC.31"
    ::= { iphcEventObjects31 3 }

iphc31-chksumexp OBJECT-TYPE
    SYNTAX Integer32
    MAX-ACCESS accessible-for-notify
    STATUS current
    DESCRIPTION
        "Parameter 'chksumexp' in event IPHC.31"
    ::= { iphcEventObjects31 4 }

iphcEventObjects32 OBJECT-IDENTITY
    STATUS current
    DESCRIPTION
        "Event IPHC.32
        ."
    ::= { iphcEventsGroup 32 }

iphc32-interface OBJECT-TYPE
    SYNTAX DisplayString
    MAX-ACCESS accessible-for-notify
    STATUS current
    DESCRIPTION
        "Parameter 'interface' in event IPHC.32"
    ::= { iphcEventObjects32 1 }

iphc32-cid OBJECT-TYPE
    SYNTAX Integer32
    MAX-ACCESS accessible-for-notify
    STATUS current
    DESCRIPTION
        "Parameter 'cid' in event IPHC.32"
    ::= { iphcEventObjects32 2 }

iphc32-pkt-counter OBJECT-TYPE
    SYNTAX Integer32
    MAX-ACCESS accessible-for-notify
    STATUS current
    DESCRIPTION
        "Parameter 'pkt-counter' in event IPHC.32"
    ::= { iphcEventObjects32 3 }

iphcEventObjects33 OBJECT-IDENTITY
    STATUS current
    DESCRIPTION
        "Event IPHC.33
        ."
    ::= { iphcEventsGroup 33 }

iphc33-interface OBJECT-TYPE
    SYNTAX DisplayString
    MAX-ACCESS accessible-for-notify
    STATUS current
    DESCRIPTION
        "Parameter 'interface' in event IPHC.33"
    ::= { iphcEventObjects33 1 }

iphc33-cid OBJECT-TYPE
    SYNTAX Integer32
    MAX-ACCESS accessible-for-notify
    STATUS current
    DESCRIPTION
        "Parameter 'cid' in event IPHC.33"
    ::= { iphcEventObjects33 2 }

iphc33-pkt-counter OBJECT-TYPE
    SYNTAX Integer32
    MAX-ACCESS accessible-for-notify
    STATUS current
    DESCRIPTION
        "Parameter 'pkt-counter' in event IPHC.33"
    ::= { iphcEventObjects33 3 }

iphcEventObjects34 OBJECT-IDENTITY
    STATUS current
    DESCRIPTION
        "Event IPHC.34
        ."
    ::= { iphcEventsGroup 34 }

iphc34-interface OBJECT-TYPE
    SYNTAX DisplayString
    MAX-ACCESS accessible-for-notify
    STATUS current
    DESCRIPTION
        "Parameter 'interface' in event IPHC.34"
    ::= { iphcEventObjects34 1 }

iphc34-cid OBJECT-TYPE
    SYNTAX Integer32
    MAX-ACCESS accessible-for-notify
    STATUS current
    DESCRIPTION
        "Parameter 'cid' in event IPHC.34"
    ::= { iphcEventObjects34 2 }

iphc34-pkt-counter OBJECT-TYPE
    SYNTAX Integer32
    MAX-ACCESS accessible-for-notify
    STATUS current
    DESCRIPTION
        "Parameter 'pkt-counter' in event IPHC.34"
    ::= { iphcEventObjects34 3 }

iphcEventObjects35 OBJECT-IDENTITY
    STATUS current
    DESCRIPTION
        "Event IPHC.35
        ."
    ::= { iphcEventsGroup 35 }

iphc35-interface OBJECT-TYPE
    SYNTAX DisplayString
    MAX-ACCESS accessible-for-notify
    STATUS current
    DESCRIPTION
        "Parameter 'interface' in event IPHC.35"
    ::= { iphcEventObjects35 1 }

iphc35-rx-tx OBJECT-TYPE
    SYNTAX DisplayString
    MAX-ACCESS accessible-for-notify
    STATUS current
    DESCRIPTION
        "Parameter 'rx/tx' in event IPHC.35"
    ::= { iphcEventObjects35 2 }

iphc35-ietf-compat OBJECT-TYPE
    SYNTAX DisplayString
    MAX-ACCESS accessible-for-notify
    STATUS current
    DESCRIPTION
        "Parameter 'ietf/compat' in event IPHC.35"
    ::= { iphcEventObjects35 3 }

iphc35-tcp-space OBJECT-TYPE
    SYNTAX Integer32
    MAX-ACCESS accessible-for-notify
    STATUS current
    DESCRIPTION
        "Parameter 'tcp-space' in event IPHC.35"
    ::= { iphcEventObjects35 4 }

iphc35-nontcp-space OBJECT-TYPE
    SYNTAX Integer32
    MAX-ACCESS accessible-for-notify
    STATUS current
    DESCRIPTION
        "Parameter 'nontcp-space' in event IPHC.35"
    ::= { iphcEventObjects35 5 }

iphc35-maxheader OBJECT-TYPE
    SYNTAX Integer32
    MAX-ACCESS accessible-for-notify
    STATUS current
    DESCRIPTION
        "Parameter 'maxheader' in event IPHC.35"
    ::= { iphcEventObjects35 6 }

iphc35-maxperiod OBJECT-TYPE
    SYNTAX Integer32
    MAX-ACCESS accessible-for-notify
    STATUS current
    DESCRIPTION
        "Parameter 'maxperiod' in event IPHC.35"
    ::= { iphcEventObjects35 7 }

iphc35-maxtime OBJECT-TYPE
    SYNTAX Integer32
    MAX-ACCESS accessible-for-notify
    STATUS current
    DESCRIPTION
        "Parameter 'maxtime' in event IPHC.35"
    ::= { iphcEventObjects35 8 }

iphcEventObjects36 OBJECT-IDENTITY
    STATUS current
    DESCRIPTION
        "Event IPHC.36
        ."
    ::= { iphcEventsGroup 36 }

iphc36-interface OBJECT-TYPE
    SYNTAX DisplayString
    MAX-ACCESS accessible-for-notify
    STATUS current
    DESCRIPTION
        "Parameter 'interface' in event IPHC.36"
    ::= { iphcEventObjects36 1 }

iphcEventObjects37 OBJECT-IDENTITY
    STATUS current
    DESCRIPTION
        "Event IPHC.37
        ."
    ::= { iphcEventsGroup 37 }

iphc37-interface OBJECT-TYPE
    SYNTAX DisplayString
    MAX-ACCESS accessible-for-notify
    STATUS current
    DESCRIPTION
        "Parameter 'interface' in event IPHC.37"
    ::= { iphcEventObjects37 1 }

iphc37-protocol OBJECT-TYPE
    SYNTAX DisplayString
    MAX-ACCESS accessible-for-notify
    STATUS current
    DESCRIPTION
        "Parameter 'protocol' in event IPHC.37"
    ::= { iphcEventObjects37 2 }

iphc37-cid OBJECT-TYPE
    SYNTAX Integer32
    MAX-ACCESS accessible-for-notify
    STATUS current
    DESCRIPTION
        "Parameter 'cid' in event IPHC.37"
    ::= { iphcEventObjects37 3 }

iphcEventObjects38 OBJECT-IDENTITY
    STATUS current
    DESCRIPTION
        "Event IPHC.38
        ."
    ::= { iphcEventsGroup 38 }

iphc38-interface OBJECT-TYPE
    SYNTAX DisplayString
    MAX-ACCESS accessible-for-notify
    STATUS current
    DESCRIPTION
        "Parameter 'interface' in event IPHC.38"
    ::= { iphcEventObjects38 1 }

iphc38-cid OBJECT-TYPE
    SYNTAX Integer32
    MAX-ACCESS accessible-for-notify
    STATUS current
    DESCRIPTION
        "Parameter 'cid' in event IPHC.38"
    ::= { iphcEventObjects38 2 }

iphc38-ip-id OBJECT-TYPE
    SYNTAX Integer32
    MAX-ACCESS accessible-for-notify
    STATUS current
    DESCRIPTION
        "Parameter 'ip-id' in event IPHC.38"
    ::= { iphcEventObjects38 3 }

iphc38-src-ipaddr OBJECT-TYPE
    SYNTAX IpAddress
    MAX-ACCESS accessible-for-notify
    STATUS current
    DESCRIPTION
        "Parameter 'src-ipaddr' in event IPHC.38"
    ::= { iphcEventObjects38 4 }

iphc38-src-port OBJECT-TYPE
    SYNTAX Integer32
    MAX-ACCESS accessible-for-notify
    STATUS current
    DESCRIPTION
        "Parameter 'src-port' in event IPHC.38"
    ::= { iphcEventObjects38 5 }

iphc38-dst-ipaddr OBJECT-TYPE
    SYNTAX IpAddress
    MAX-ACCESS accessible-for-notify
    STATUS current
    DESCRIPTION
        "Parameter 'dst-ipaddr' in event IPHC.38"
    ::= { iphcEventObjects38 6 }

iphc38-dst-port OBJECT-TYPE
    SYNTAX Integer32
    MAX-ACCESS accessible-for-notify
    STATUS current
    DESCRIPTION
        "Parameter 'dst-port' in event IPHC.38"
    ::= { iphcEventObjects38 7 }

iphc38-cksum OBJECT-TYPE
    SYNTAX Integer32
    MAX-ACCESS accessible-for-notify
    STATUS current
    DESCRIPTION
        "Parameter 'cksum' in event IPHC.38"
    ::= { iphcEventObjects38 8 }

iphcEventObjects39 OBJECT-IDENTITY
    STATUS current
    DESCRIPTION
        "Event IPHC.39
        ."
    ::= { iphcEventsGroup 39 }

iphc39-interface OBJECT-TYPE
    SYNTAX DisplayString
    MAX-ACCESS accessible-for-notify
    STATUS current
    DESCRIPTION
        "Parameter 'interface' in event IPHC.39"
    ::= { iphcEventObjects39 1 }

iphc39-cid OBJECT-TYPE
    SYNTAX Integer32
    MAX-ACCESS accessible-for-notify
    STATUS current
    DESCRIPTION
        "Parameter 'cid' in event IPHC.39"
    ::= { iphcEventObjects39 2 }

iphc39-chksum OBJECT-TYPE
    SYNTAX Integer32
    MAX-ACCESS accessible-for-notify
    STATUS current
    DESCRIPTION
        "Parameter 'chksum' in event IPHC.39"
    ::= { iphcEventObjects39 3 }

iphc39-chksumexp OBJECT-TYPE
    SYNTAX Integer32
    MAX-ACCESS accessible-for-notify
    STATUS current
    DESCRIPTION
        "Parameter 'chksumexp' in event IPHC.39"
    ::= { iphcEventObjects39 4 }

iphcEventObjects40 OBJECT-IDENTITY
    STATUS current
    DESCRIPTION
        "Event IPHC.40
        ."
    ::= { iphcEventsGroup 40 }

iphc40-interface OBJECT-TYPE
    SYNTAX DisplayString
    MAX-ACCESS accessible-for-notify
    STATUS current
    DESCRIPTION
        "Parameter 'interface' in event IPHC.40"
    ::= { iphcEventObjects40 1 }

iphc40-cid OBJECT-TYPE
    SYNTAX Integer32
    MAX-ACCESS accessible-for-notify
    STATUS current
    DESCRIPTION
        "Parameter 'cid' in event IPHC.40"
    ::= { iphcEventObjects40 2 }

iphc40-chksum OBJECT-TYPE
    SYNTAX Integer32
    MAX-ACCESS accessible-for-notify
    STATUS current
    DESCRIPTION
        "Parameter 'chksum' in event IPHC.40"
    ::= { iphcEventObjects40 3 }

iphc40-chksumexp OBJECT-TYPE
    SYNTAX Integer32
    MAX-ACCESS accessible-for-notify
    STATUS current
    DESCRIPTION
        "Parameter 'chksumexp' in event IPHC.40"
    ::= { iphcEventObjects40 4 }

iphcEventObjects41 OBJECT-IDENTITY
    STATUS current
    DESCRIPTION
        "Event IPHC.41
        ."
    ::= { iphcEventsGroup 41 }

iphc41-interface OBJECT-TYPE
    SYNTAX DisplayString
    MAX-ACCESS accessible-for-notify
    STATUS current
    DESCRIPTION
        "Parameter 'interface' in event IPHC.41"
    ::= { iphcEventObjects41 1 }

iphc41-cid OBJECT-TYPE
    SYNTAX Integer32
    MAX-ACCESS accessible-for-notify
    STATUS current
    DESCRIPTION
        "Parameter 'cid' in event IPHC.41"
    ::= { iphcEventObjects41 2 }

iphc41-chksum OBJECT-TYPE
    SYNTAX Integer32
    MAX-ACCESS accessible-for-notify
    STATUS current
    DESCRIPTION
        "Parameter 'chksum' in event IPHC.41"
    ::= { iphcEventObjects41 3 }

iphc41-chksumexp OBJECT-TYPE
    SYNTAX Integer32
    MAX-ACCESS accessible-for-notify
    STATUS current
    DESCRIPTION
        "Parameter 'chksumexp' in event IPHC.41"
    ::= { iphcEventObjects41 4 }

iphcEventObjects42 OBJECT-IDENTITY
    STATUS current
    DESCRIPTION
        "Event IPHC.42
        ."
    ::= { iphcEventsGroup 42 }

iphc42-interface OBJECT-TYPE
    SYNTAX DisplayString
    MAX-ACCESS accessible-for-notify
    STATUS current
    DESCRIPTION
        "Parameter 'interface' in event IPHC.42"
    ::= { iphcEventObjects42 1 }

iphc42-cause OBJECT-TYPE
    SYNTAX DisplayString
    MAX-ACCESS accessible-for-notify
    STATUS current
    DESCRIPTION
        "Parameter 'cause' in event IPHC.42"
    ::= { iphcEventObjects42 2 }

iphcEventObjects43 OBJECT-IDENTITY
    STATUS current
    DESCRIPTION
        "Event IPHC.43
        ."
    ::= { iphcEventsGroup 43 }

iphc43-interface OBJECT-TYPE
    SYNTAX DisplayString
    MAX-ACCESS accessible-for-notify
    STATUS current
    DESCRIPTION
        "Parameter 'interface' in event IPHC.43"
    ::= { iphcEventObjects43 1 }

iphc43-cid OBJECT-TYPE
    SYNTAX Integer32
    MAX-ACCESS accessible-for-notify
    STATUS current
    DESCRIPTION
        "Parameter 'cid' in event IPHC.43"
    ::= { iphcEventObjects43 2 }

iphc43-pps OBJECT-TYPE
    SYNTAX Integer32
    MAX-ACCESS accessible-for-notify
    STATUS current
    DESCRIPTION
        "Parameter 'pps' in event IPHC.43"
    ::= { iphcEventObjects43 3 }

iphcEventObjects44 OBJECT-IDENTITY
    STATUS current
    DESCRIPTION
        "Event IPHC.44
        ."
    ::= { iphcEventsGroup 44 }

iphc44-interface OBJECT-TYPE
    SYNTAX DisplayString
    MAX-ACCESS accessible-for-notify
    STATUS current
    DESCRIPTION
        "Parameter 'interface' in event IPHC.44"
    ::= { iphcEventObjects44 1 }

iphc44-cid OBJECT-TYPE
    SYNTAX Integer32
    MAX-ACCESS accessible-for-notify
    STATUS current
    DESCRIPTION
        "Parameter 'cid' in event IPHC.44"
    ::= { iphcEventObjects44 2 }

iphc44-pps OBJECT-TYPE
    SYNTAX Integer32
    MAX-ACCESS accessible-for-notify
    STATUS current
    DESCRIPTION
        "Parameter 'pps' in event IPHC.44"
    ::= { iphcEventObjects44 3 }

iphcEventObjects45 OBJECT-IDENTITY
    STATUS current
    DESCRIPTION
        "Event IPHC.45
        ."
    ::= { iphcEventsGroup 45 }

iphc45-interface OBJECT-TYPE
    SYNTAX DisplayString
    MAX-ACCESS accessible-for-notify
    STATUS current
    DESCRIPTION
        "Parameter 'interface' in event IPHC.45"
    ::= { iphcEventObjects45 1 }

iphc45-cause OBJECT-TYPE
    SYNTAX DisplayString
    MAX-ACCESS accessible-for-notify
    STATUS current
    DESCRIPTION
        "Parameter 'cause' in event IPHC.45"
    ::= { iphcEventObjects45 2 }

iphcEventObjects46 OBJECT-IDENTITY
    STATUS current
    DESCRIPTION
        "Event IPHC.46
        ."
    ::= { iphcEventsGroup 46 }

iphc46-interface OBJECT-TYPE
    SYNTAX DisplayString
    MAX-ACCESS accessible-for-notify
    STATUS current
    DESCRIPTION
        "Parameter 'interface' in event IPHC.46"
    ::= { iphcEventObjects46 1 }

iphc46-cid OBJECT-TYPE
    SYNTAX Integer32
    MAX-ACCESS accessible-for-notify
    STATUS current
    DESCRIPTION
        "Parameter 'cid' in event IPHC.46"
    ::= { iphcEventObjects46 2 }

iphc46-link-sequence OBJECT-TYPE
    SYNTAX Integer32
    MAX-ACCESS accessible-for-notify
    STATUS current
    DESCRIPTION
        "Parameter 'link-sequence' in event IPHC.46"
    ::= { iphcEventObjects46 3 }


iphcNotification1 NOTIFICATION-TYPE
    OBJECTS { 
              iphc1-interface, 
              iphc1-cid,
              iphc1-cause,
              iphc1-pkt-counter 
            }
    STATUS current
    DESCRIPTION
        "Notification of Event IPHC.1

        Message: '[$1] Encoded FULL-HEADER cid $2, prot NON-TCP, Cause: $3,#$4'

        Parameters list:
              $1: iphc1-interface
              $2: iphc1-cid
              $3: iphc1-cause
              $4: iphc1-pkt-counter

        ."
    ::= { iphcNotificationsPrefix 1 }

iphcNotification2 NOTIFICATION-TYPE
    OBJECTS { 
              iphc2-interface, 
              iphc2-cid,
              iphc2-pkt-counter 
            }
    STATUS current
    DESCRIPTION
        "Notification of Event IPHC.2

        Message: '[$1] Decoded FULL-HEADER cid $2, prot NON-TCP, #$3'

        Parameters list:
              $1: iphc2-interface
              $2: iphc2-cid
              $3: iphc2-pkt-counter

        ."
    ::= { iphcNotificationsPrefix 2 }

iphcNotification3 NOTIFICATION-TYPE
    OBJECTS { 
              iphc3-interface, 
              iphc3-cid,
              iphc3-generation,
              iphc3-flag-D,
              iphc3-link-sequence,
              iphc3-ip-id,
              iphc3-pkt-counter 
            }
    STATUS current
    DESCRIPTION
        "Notification of Event IPHC.3

        Message: '[$1] Encoded COMPRESS-NON-TCP cid $2, generation $3, ($4), link-seq 0x$5, ip-id 0x$6,#$7'

        Parameters list:
              $1: iphc3-interface
              $2: iphc3-cid
              $3: iphc3-generation
              $4: iphc3-flag-D
              $5: iphc3-link-sequence
              $6: iphc3-ip-id
              $7: iphc3-pkt-counter

        ."
    ::= { iphcNotificationsPrefix 3 }

iphcNotification4 NOTIFICATION-TYPE
    OBJECTS { 
              iphc4-interface, 
              iphc4-cid,
              iphc4-generation,
              iphc4-flag-D,
              iphc4-link-sequence,
              iphc4-ip-id,
              iphc4-pkt-counter 
            }
    STATUS current
    DESCRIPTION
        "Notification of Event IPHC.4

        Message: '[$1] Decoded COMPRESS-NON-TCP cid $2, generation $3, ($4), link-seq 0x$5, ip-id 0x$6,#$7'

        Parameters list:
              $1: iphc4-interface
              $2: iphc4-cid
              $3: iphc4-generation
              $4: iphc4-flag-D
              $5: iphc4-link-sequence
              $6: iphc4-ip-id
              $7: iphc4-pkt-counter

        ."
    ::= { iphcNotificationsPrefix 4 }

iphcNotification5 NOTIFICATION-TYPE
    OBJECTS { 
              iphc5-interface, 
              iphc5-cid,
              iphc5-flags,
              iphc5-sequence-number,
              iphc5-ack-number,
              iphc5-window-size,
              iphc5-checksum,
              iphc5-ip-id,
              iphc5-pkt-counter 
            }
    STATUS current
    DESCRIPTION
        "Notification of Event IPHC.5

        Message: '[$1] Encoded COMP-TCP cid $2 ($3) SEQ=$4 ACK=$5 W=$6 CHK=0x$7 ID=0x$8, #$9'

        Parameters list:
              $1: iphc5-interface
              $2: iphc5-cid
              $3: iphc5-flags
              $4: iphc5-sequence-number
              $5: iphc5-ack-number
              $6: iphc5-window-size
              $7: iphc5-checksum
              $8: iphc5-ip-id
              $9: iphc5-pkt-counter

        ."
    ::= { iphcNotificationsPrefix 5 }

iphcNotification6 NOTIFICATION-TYPE
    OBJECTS { 
              iphc6-interface, 
              iphc6-cid,
              iphc6-flags,
              iphc6-sequence-number,
              iphc6-ack-number,
              iphc6-window-size,
              iphc6-checksum,
              iphc6-ip-id,
              iphc6-pkt-counter 
            }
    STATUS current
    DESCRIPTION
        "Notification of Event IPHC.6

        Message: '[$1] Decoded COMP-TCP cid $2 ($3) SEQ=$4 ACK=$5 W=$6 CHK=0x$7 ID=0x$8, #$9'

        Parameters list:
              $1: iphc6-interface
              $2: iphc6-cid
              $3: iphc6-flags
              $4: iphc6-sequence-number
              $5: iphc6-ack-number
              $6: iphc6-window-size
              $7: iphc6-checksum
              $8: iphc6-ip-id
              $9: iphc6-pkt-counter

        ."
    ::= { iphcNotificationsPrefix 6 }

iphcNotification7 NOTIFICATION-TYPE
    OBJECTS { 
              iphc7-interface, 
              iphc7-cid 
            }
    STATUS current
    DESCRIPTION
        "Notification of Event IPHC.7

        Message: '[$1] Encoded COMP-TCP-NO-DELTA cid $2'

        Parameters list:
              $1: iphc7-interface
              $2: iphc7-cid

        ."
    ::= { iphcNotificationsPrefix 7 }

iphcNotification8 NOTIFICATION-TYPE
    OBJECTS { 
              iphc8-interface, 
              iphc8-cid 
            }
    STATUS current
    DESCRIPTION
        "Notification of Event IPHC.8

        Message: '[$1] Decoded COMP-TCP-NO-DELTA cid $2'

        Parameters list:
              $1: iphc8-interface
              $2: iphc8-cid

        ."
    ::= { iphcNotificationsPrefix 8 }

iphcNotification9 NOTIFICATION-TYPE
    OBJECTS { 
              iphc9-interface, 
              iphc9-cid,
              iphc9-flags,
              iphc9-link-sequence,
              iphc9-ip-id,
              iphc9-pkt-counter 
            }
    STATUS current
    DESCRIPTION
        "Notification of Event IPHC.9

        Message: '[$1] Encoded COMP-RTP8 cid $2 ($3), link-seq 0x$4, ip-id 0x$5, #$6'

        Parameters list:
              $1: iphc9-interface
              $2: iphc9-cid
              $3: iphc9-flags
              $4: iphc9-link-sequence
              $5: iphc9-ip-id
              $6: iphc9-pkt-counter

        ."
    ::= { iphcNotificationsPrefix 9 }

iphcNotification10 NOTIFICATION-TYPE
    OBJECTS { 
              iphc10-interface, 
              iphc10-cid,
              iphc10-flags,
              iphc10-link-sequence,
              iphc10-ip-id,
              iphc10-pkt-counter 
            }
    STATUS current
    DESCRIPTION
        "Notification of Event IPHC.10

        Message: '[$1] Decoded COMP-RTP8 cid $2 ($3), link-seq 0x$4, ip-id 0x$5, #$6'

        Parameters list:
              $1: iphc10-interface
              $2: iphc10-cid
              $3: iphc10-flags
              $4: iphc10-link-sequence
              $5: iphc10-ip-id
              $6: iphc10-pkt-counter

        ."
    ::= { iphcNotificationsPrefix 10 }

iphcNotification11 NOTIFICATION-TYPE
    OBJECTS { 
              iphc11-interface, 
              iphc11-cid,
              iphc11-flags,
              iphc11-link-sequence,
              iphc11-pkt-counter 
            }
    STATUS current
    DESCRIPTION
        "Notification of Event IPHC.11

        Message: '[$1] Encoded COMP-RTP16 cid $2 ($3), link-seq 0x$4, #$5'

        Parameters list:
              $1: iphc11-interface
              $2: iphc11-cid
              $3: iphc11-flags
              $4: iphc11-link-sequence
              $5: iphc11-pkt-counter

        ."
    ::= { iphcNotificationsPrefix 11 }

iphcNotification12 NOTIFICATION-TYPE
    OBJECTS { 
              iphc12-interface, 
              iphc12-cid,
              iphc12-flags,
              iphc12-link-sequence,
              iphc12-ip-id,
              iphc12-pkt-counter 
            }
    STATUS current
    DESCRIPTION
        "Notification of Event IPHC.12

        Message: '[$1] Decoded COMP-RTP16 cid $2 ($3), link-seq 0x$4, ip-id 0x$5, #$6'

        Parameters list:
              $1: iphc12-interface
              $2: iphc12-cid
              $3: iphc12-flags
              $4: iphc12-link-sequence
              $5: iphc12-ip-id
              $6: iphc12-pkt-counter

        ."
    ::= { iphcNotificationsPrefix 12 }

iphcNotification13 NOTIFICATION-TYPE
    OBJECTS { 
              iphc13-interface, 
              iphc13-cid 
            }
    STATUS current
    DESCRIPTION
        "Notification of Event IPHC.13

        Message: '[$1] Encoded COMP-UDP8 cid $2'

        Parameters list:
              $1: iphc13-interface
              $2: iphc13-cid

        ."
    ::= { iphcNotificationsPrefix 13 }

iphcNotification14 NOTIFICATION-TYPE
    OBJECTS { 
              iphc14-interface, 
              iphc14-cid,
              iphc14-flags,
              iphc14-link-sequence,
              iphc14-ip-id,
              iphc14-pkt-counter 
            }
    STATUS current
    DESCRIPTION
        "Notification of Event IPHC.14

        Message: '[$1] Decoded COMP-UDP8 cid $2 ($3), link-seq 0x$4, ip-id 0x$5, #$6'

        Parameters list:
              $1: iphc14-interface
              $2: iphc14-cid
              $3: iphc14-flags
              $4: iphc14-link-sequence
              $5: iphc14-ip-id
              $6: iphc14-pkt-counter

        ."
    ::= { iphcNotificationsPrefix 14 }

iphcNotification15 NOTIFICATION-TYPE
    OBJECTS { 
              iphc15-interface, 
              iphc15-cid 
            }
    STATUS current
    DESCRIPTION
        "Notification of Event IPHC.15

        Message: '[$1] Encoded COMP-UDP16 cid $2'

        Parameters list:
              $1: iphc15-interface
              $2: iphc15-cid

        ."
    ::= { iphcNotificationsPrefix 15 }

iphcNotification16 NOTIFICATION-TYPE
    OBJECTS { 
              iphc16-interface, 
              iphc16-cid,
              iphc16-flags,
              iphc16-link-sequence,
              iphc16-ip-id,
              iphc16-pkt-counter 
            }
    STATUS current
    DESCRIPTION
        "Notification of Event IPHC.16

        Message: '[$1] Decoded COMP-UDP16 cid $2 ($3), link-seq 0x$4, ip-id 0x$5, #$6'

        Parameters list:
              $1: iphc16-interface
              $2: iphc16-cid
              $3: iphc16-flags
              $4: iphc16-link-sequence
              $5: iphc16-ip-id
              $6: iphc16-pkt-counter

        ."
    ::= { iphcNotificationsPrefix 16 }

iphcNotification17 NOTIFICATION-TYPE
    OBJECTS { 
              iphc17-interface, 
              iphc17-cid 
            }
    STATUS current
    DESCRIPTION
        "Notification of Event IPHC.17

        Message: '[$1] Decoded COMP-RTP with CSRC list changes not allowed, cid $2'

        Parameters list:
              $1: iphc17-interface
              $2: iphc17-cid

        ."
    ::= { iphcNotificationsPrefix 17 }

iphcNotification18 NOTIFICATION-TYPE
    OBJECTS { 
              iphc18-interface, 
              iphc18-cid,
              iphc18-generation,
              iphc18-current-generation,
              iphc18-flag-I,
              iphc18-link-sequence,
              iphc18-current-link-sequence,
              iphc18-pkt-counter 
            }
    STATUS current
    DESCRIPTION
        "Notification of Event IPHC.18

        Message: '[$1] Decoded CONTEXT-STATE prot NON-TCP cid $2, generation $3 (curr $4), ($5), lnk-seq $6 (curr $7), #$8'

        Parameters list:
              $1: iphc18-interface
              $2: iphc18-cid
              $3: iphc18-generation
              $4: iphc18-current-generation
              $5: iphc18-flag-I
              $6: iphc18-link-sequence
              $7: iphc18-current-link-sequence
              $8: iphc18-pkt-counter

        ."
    ::= { iphcNotificationsPrefix 18 }

iphcNotification19 NOTIFICATION-TYPE
    OBJECTS { 
              iphc19-interface, 
              iphc19-checksum,
              iphc19-expected-checksum,
              iphc19-cid 
            }
    STATUS current
    DESCRIPTION
        "Notification of Event IPHC.19

        Message: '[$1] Decoded bad header cksum 0x$2 (exp 0x$3), cid $4'

        Parameters list:
              $1: iphc19-interface
              $2: iphc19-checksum
              $3: iphc19-expected-checksum
              $4: iphc19-cid

        ."
    ::= { iphcNotificationsPrefix 19 }

iphcNotification20 NOTIFICATION-TYPE
    OBJECTS { 
              iphc20-interface, 
              iphc20-cid,
              iphc20-max-cid 
            }
    STATUS current
    DESCRIPTION
        "Notification of Event IPHC.20

        Message: '[$1] Received context id $2 greated than maximum configured $3'

        Parameters list:
              $1: iphc20-interface
              $2: iphc20-cid
              $3: iphc20-max-cid

        ."
    ::= { iphcNotificationsPrefix 20 }

iphcNotification21 NOTIFICATION-TYPE
    OBJECTS { 
              iphc21-interface, 
              iphc21-cid 
            }
    STATUS current
    DESCRIPTION
        "Notification of Event IPHC.21

        Message: '[$1] Received TCP invalid context id $2'

        Parameters list:
              $1: iphc21-interface
              $2: iphc21-cid

        ."
    ::= { iphcNotificationsPrefix 21 }

iphcNotification22 NOTIFICATION-TYPE
    OBJECTS { 
              iphc22-interface, 
              iphc22-cid,
              iphc22-ip-id,
              iphc22-src-ipaddr,
              iphc22-src-port,
              iphc22-dst-ipaddr,
              iphc22-dst-port,
              iphc22-generation,
              iphc22-cksum,
              iphc22-flag,
              iphc22-link-sequence 
            }
    STATUS current
    DESCRIPTION
        "Notification of Event IPHC.22

        Message: '[$1] Decoded cid $2, prot NON-TCP, ip-id 0x$3, $4/$5 -> $6/$7, generation $8, cksum 0x$9, ($10) link-seq 0x$11'

        Parameters list:
              $1: iphc22-interface
              $2: iphc22-cid
              $3: iphc22-ip-id
              $4: iphc22-src-ipaddr
              $5: iphc22-src-port
              $6: iphc22-dst-ipaddr
              $7: iphc22-dst-port
              $8: iphc22-generation
              $9: iphc22-cksum
              $10: iphc22-flag
              $11: iphc22-link-sequence

        ."
    ::= { iphcNotificationsPrefix 22 }

iphcNotification23 NOTIFICATION-TYPE
    OBJECTS { 
              iphc23-interface, 
              iphc23-cid,
              iphc23-cause,
              iphc23-pkt-counter 
            }
    STATUS current
    DESCRIPTION
        "Notification of Event IPHC.23

        Message: '[$1] Encoded FULL-HEADER cid $2, prot TCP, Cause: $3, #$4'

        Parameters list:
              $1: iphc23-interface
              $2: iphc23-cid
              $3: iphc23-cause
              $4: iphc23-pkt-counter

        ."
    ::= { iphcNotificationsPrefix 23 }

iphcNotification24 NOTIFICATION-TYPE
    OBJECTS { 
              iphc24-interface, 
              iphc24-cid,
              iphc24-pkt-counter 
            }
    STATUS current
    DESCRIPTION
        "Notification of Event IPHC.24

        Message: '[$1] Decoded FULL-HEADER cid $2, prot TCP, #$3'

        Parameters list:
              $1: iphc24-interface
              $2: iphc24-cid
              $3: iphc24-pkt-counter

        ."
    ::= { iphcNotificationsPrefix 24 }

iphcNotification25 NOTIFICATION-TYPE
    OBJECTS { 
              iphc25-interface, 
              iphc25-cid,
              iphc25-ip-id,
              iphc25-src-ipaddr,
              iphc25-src-port,
              iphc25-dst-ipaddr,
              iphc25-dst-port,
              iphc25-cksum 
            }
    STATUS current
    DESCRIPTION
        "Notification of Event IPHC.25

        Message: '[$1] Decoded cid $2, prot TCP, id 0x$3,  $4/$5 -> $6/$7, cksum 0x$8'

        Parameters list:
              $1: iphc25-interface
              $2: iphc25-cid
              $3: iphc25-ip-id
              $4: iphc25-src-ipaddr
              $5: iphc25-src-port
              $6: iphc25-dst-ipaddr
              $7: iphc25-dst-port
              $8: iphc25-cksum

        ."
    ::= { iphcNotificationsPrefix 25 }

iphcNotification26 NOTIFICATION-TYPE
    OBJECTS { 
              iphc26-interface, 
              iphc26-cid,
              iphc26-hlen,
              iphc26-max-hlen 
            }
    STATUS current
    DESCRIPTION
        "Notification of Event IPHC.26

        Message: '[$1] Decoded cid $2, prot TCP, header length too large $3 (max $4)'

        Parameters list:
              $1: iphc26-interface
              $2: iphc26-cid
              $3: iphc26-hlen
              $4: iphc26-max-hlen

        ."
    ::= { iphcNotificationsPrefix 26 }

iphcNotification27 NOTIFICATION-TYPE
    OBJECTS { 
              iphc27-interface, 
              iphc27-cid,
              iphc27-generation,
              iphc27-expected-generation 
            }
    STATUS current
    DESCRIPTION
        "Notification of Event IPHC.27

        Message: '[$1] Decoded cid $2, prot NON-TCP, invalid generation $3 (exp $4)'

        Parameters list:
              $1: iphc27-interface
              $2: iphc27-cid
              $3: iphc27-generation
              $4: iphc27-expected-generation

        ."
    ::= { iphcNotificationsPrefix 27 }

iphcNotification28 NOTIFICATION-TYPE
    STATUS current
    DESCRIPTION
        "Notification of Event IPHC.28

        Message: 'Disable this event to disable event sample mode'

        ."
    ::= { iphcNotificationsPrefix 28 }

iphcNotification29 NOTIFICATION-TYPE
    OBJECTS { 
              iphc29-interface, 
              iphc29-link-sequence,
              iphc29-expected-link-sequence,
              iphc29-cid 
            }
    STATUS current
    DESCRIPTION
        "Notification of Event IPHC.29

        Message: '[$1] Decoded bad link-seq 0x$2 (exp 0x$3), cid $4'

        Parameters list:
              $1: iphc29-interface
              $2: iphc29-link-sequence
              $3: iphc29-expected-link-sequence
              $4: iphc29-cid

        This message is generated when an packet has an invalid sequence.
        The received sequence, together with the correct sequence,
        are displayed."
    ::= { iphcNotificationsPrefix 29 }

iphcNotification30 NOTIFICATION-TYPE
    OBJECTS { 
              iphc30-interface, 
              iphc30-cid,
              iphc30-ip-id,
              iphc30-src-ipaddr,
              iphc30-src-port,
              iphc30-dst-ipaddr,
              iphc30-dst-port,
              iphc30-generation,
              iphc30-cksum,
              iphc30-flag,
              iphc30-link-sequence 
            }
    STATUS current
    DESCRIPTION
        "Notification of Event IPHC.30

        Message: '[$1] Encoded cid $2, prot NON-TCP, id 0x$3, $4/$5 -> $6/$7, generation $8, cksum 0x$9, ($10) link-seq 0x$11'

        Parameters list:
              $1: iphc30-interface
              $2: iphc30-cid
              $3: iphc30-ip-id
              $4: iphc30-src-ipaddr
              $5: iphc30-src-port
              $6: iphc30-dst-ipaddr
              $7: iphc30-dst-port
              $8: iphc30-generation
              $9: iphc30-cksum
              $10: iphc30-flag
              $11: iphc30-link-sequence

        ."
    ::= { iphcNotificationsPrefix 30 }

iphcNotification31 NOTIFICATION-TYPE
    OBJECTS { 
              iphc31-interface, 
              iphc31-cid,
              iphc31-chksum,
              iphc31-chksumexp 
            }
    STATUS current
    DESCRIPTION
        "Notification of Event IPHC.31

        Message: '[$1] Encoded cid $2, prot NON-TCP, detected unexpected checksum change 0x$3 (exp 0x$4)'

        Parameters list:
              $1: iphc31-interface
              $2: iphc31-cid
              $3: iphc31-chksum
              $4: iphc31-chksumexp

        ."
    ::= { iphcNotificationsPrefix 31 }

iphcNotification32 NOTIFICATION-TYPE
    OBJECTS { 
              iphc32-interface, 
              iphc32-cid,
              iphc32-pkt-counter 
            }
    STATUS current
    DESCRIPTION
        "Notification of Event IPHC.32

        Message: '[$1] Decoded CONTEXT-STATE prot TCP cid $2, #$3'

        Parameters list:
              $1: iphc32-interface
              $2: iphc32-cid
              $3: iphc32-pkt-counter

        ."
    ::= { iphcNotificationsPrefix 32 }

iphcNotification33 NOTIFICATION-TYPE
    OBJECTS { 
              iphc33-interface, 
              iphc33-cid,
              iphc33-pkt-counter 
            }
    STATUS current
    DESCRIPTION
        "Notification of Event IPHC.33

        Message: '[$1] Encoded CONTEXT-STATE prot NON-TCP cid $2, #$3'

        Parameters list:
              $1: iphc33-interface
              $2: iphc33-cid
              $3: iphc33-pkt-counter

        ."
    ::= { iphcNotificationsPrefix 33 }

iphcNotification34 NOTIFICATION-TYPE
    OBJECTS { 
              iphc34-interface, 
              iphc34-cid,
              iphc34-pkt-counter 
            }
    STATUS current
    DESCRIPTION
        "Notification of Event IPHC.34

        Message: '[$1] Encoded CONTEXT-STATE prot TCP cid $2, #$3'

        Parameters list:
              $1: iphc34-interface
              $2: iphc34-cid
              $3: iphc34-pkt-counter

        ."
    ::= { iphcNotificationsPrefix 34 }

iphcNotification35 NOTIFICATION-TYPE
    OBJECTS { 
              iphc35-interface, 
              iphc35-rx-tx,
              iphc35-ietf-compat,
              iphc35-tcp-space,
              iphc35-nontcp-space,
              iphc35-maxheader,
              iphc35-maxperiod,
              iphc35-maxtime 
            }
    STATUS current
    DESCRIPTION
        "Notification of Event IPHC.35

        Message: '[$1] Init, $2, $3 format, tcp-space $4, nontcp-space $5, maxheader $6, maxperiod $7, maxtime $8'

        Parameters list:
              $1: iphc35-interface
              $2: iphc35-rx-tx
              $3: iphc35-ietf-compat
              $4: iphc35-tcp-space
              $5: iphc35-nontcp-space
              $6: iphc35-maxheader
              $7: iphc35-maxperiod
              $8: iphc35-maxtime

        ."
    ::= { iphcNotificationsPrefix 35 }

iphcNotification36 NOTIFICATION-TYPE
    OBJECTS { 
              iphc36-interface 
            }
    STATUS current
    DESCRIPTION
        "Notification of Event IPHC.36

        Message: '[$1] Destroy'

        Parameters list:
              $1: iphc36-interface

        ."
    ::= { iphcNotificationsPrefix 36 }

iphcNotification37 NOTIFICATION-TYPE
    OBJECTS { 
              iphc37-interface, 
              iphc37-protocol,
              iphc37-cid 
            }
    STATUS current
    DESCRIPTION
        "Notification of Event IPHC.37

        Message: '[$1] Freeing context state, prot $2, cid $3, due to inactivity'

        Parameters list:
              $1: iphc37-interface
              $2: iphc37-protocol
              $3: iphc37-cid

        ."
    ::= { iphcNotificationsPrefix 37 }

iphcNotification38 NOTIFICATION-TYPE
    OBJECTS { 
              iphc38-interface, 
              iphc38-cid,
              iphc38-ip-id,
              iphc38-src-ipaddr,
              iphc38-src-port,
              iphc38-dst-ipaddr,
              iphc38-dst-port,
              iphc38-cksum 
            }
    STATUS current
    DESCRIPTION
        "Notification of Event IPHC.38

        Message: '[$1] Encoded cid $2, prot TCP, id 0x$3, $4/$5 -> $6/$7, cksum 0x$8'

        Parameters list:
              $1: iphc38-interface
              $2: iphc38-cid
              $3: iphc38-ip-id
              $4: iphc38-src-ipaddr
              $5: iphc38-src-port
              $6: iphc38-dst-ipaddr
              $7: iphc38-dst-port
              $8: iphc38-cksum

        ."
    ::= { iphcNotificationsPrefix 38 }

iphcNotification39 NOTIFICATION-TYPE
    OBJECTS { 
              iphc39-interface, 
              iphc39-cid,
              iphc39-chksum,
              iphc39-chksumexp 
            }
    STATUS current
    DESCRIPTION
        "Notification of Event IPHC.39

        Message: '[$1] Encoded cid $2, prot TCP, detected unexpected checksum change 0x$3 (exp 0x$4)'

        Parameters list:
              $1: iphc39-interface
              $2: iphc39-cid
              $3: iphc39-chksum
              $4: iphc39-chksumexp

        ."
    ::= { iphcNotificationsPrefix 39 }

iphcNotification40 NOTIFICATION-TYPE
    OBJECTS { 
              iphc40-interface, 
              iphc40-cid,
              iphc40-chksum,
              iphc40-chksumexp 
            }
    STATUS current
    DESCRIPTION
        "Notification of Event IPHC.40

        Message: '[$1] Decoded cid $2, prot NON-TCP, detected unexpected checksum change 0x$3 (exp 0x$4)'

        Parameters list:
              $1: iphc40-interface
              $2: iphc40-cid
              $3: iphc40-chksum
              $4: iphc40-chksumexp

        ."
    ::= { iphcNotificationsPrefix 40 }

iphcNotification41 NOTIFICATION-TYPE
    OBJECTS { 
              iphc41-interface, 
              iphc41-cid,
              iphc41-chksum,
              iphc41-chksumexp 
            }
    STATUS current
    DESCRIPTION
        "Notification of Event IPHC.41

        Message: '[$1] Decoded cid $2, prot TCP, detected unexpected checksum change 0x$3 (exp 0x$4)'

        Parameters list:
              $1: iphc41-interface
              $2: iphc41-cid
              $3: iphc41-chksum
              $4: iphc41-chksumexp

        ."
    ::= { iphcNotificationsPrefix 41 }

iphcNotification42 NOTIFICATION-TYPE
    OBJECTS { 
              iphc42-interface, 
              iphc42-cause 
            }
    STATUS current
    DESCRIPTION
        "Notification of Event IPHC.42

        Message: '[$1] UNCOMPRESS, Cause: $2'

        Parameters list:
              $1: iphc42-interface
              $2: iphc42-cause

        ."
    ::= { iphcNotificationsPrefix 42 }

iphcNotification43 NOTIFICATION-TYPE
    OBJECTS { 
              iphc43-interface, 
              iphc43-cid,
              iphc43-pps 
            }
    STATUS current
    DESCRIPTION
        "Notification of Event IPHC.43

        Message: '[$1] Decoded RTP per second stats cid $2, PPS: $3'

        Parameters list:
              $1: iphc43-interface
              $2: iphc43-cid
              $3: iphc43-pps

        ."
    ::= { iphcNotificationsPrefix 43 }

iphcNotification44 NOTIFICATION-TYPE
    OBJECTS { 
              iphc44-interface, 
              iphc44-cid,
              iphc44-pps 
            }
    STATUS current
    DESCRIPTION
        "Notification of Event IPHC.44

        Message: '[$1] Encoded RTP per second stats cid $2, PPS: $3'

        Parameters list:
              $1: iphc44-interface
              $2: iphc44-cid
              $3: iphc44-pps

        ."
    ::= { iphcNotificationsPrefix 44 }

iphcNotification45 NOTIFICATION-TYPE
    OBJECTS { 
              iphc45-interface, 
              iphc45-cause 
            }
    STATUS current
    DESCRIPTION
        "Notification of Event IPHC.45

        Message: '[$1] Decoded DROP PACKET, Cause: $2'

        Parameters list:
              $1: iphc45-interface
              $2: iphc45-cause

        ."
    ::= { iphcNotificationsPrefix 45 }

iphcNotification46 NOTIFICATION-TYPE
    OBJECTS { 
              iphc46-interface, 
              iphc46-cid,
              iphc46-link-sequence 
            }
    STATUS current
    DESCRIPTION
        "Notification of Event IPHC.46

        Message: '[$1] Received NON-TCP invalid context id $2, link-seq 0x$3'

        Parameters list:
              $1: iphc46-interface
              $2: iphc46-cid
              $3: iphc46-link-sequence

        ."
    ::= { iphcNotificationsPrefix 46 }


END
