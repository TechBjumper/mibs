-- file automatically created


TELDAT-TRAP-L2TP-MIB DEFINITIONS ::= BEGIN


IMPORTS
	MODULE-IDENTITY,OBJECT-TYPE,OBJECT-IDENTITY,NOTIFICATION-TYPE,Integer32,IpAddress
		FROM SNMPv2-SMI
	DisplayString
		FROM SNMPv2-TC
	telEventTraps
		FROM TELDAT-MIB;


l2tpTrapsMIB MODULE-IDENTITY
    LAST-UPDATED "201401200930Z"
    ORGANIZATION "Teldat, S.A."
    CONTACT-INFO 
        "Teldat, S.A.
        Customer Service

        Postal: Parque Tecnologico de Madrid
                Tres Cantos 28760
                Madrid, SPAIN

        Tel.: +34 918 076 565

        http://www.teldat.com"
    DESCRIPTION
        "This Module Information Base file is defined for managing received
        SNMP notifications generated by the L2TP event subsystem."
    REVISION "201401200930Z"
    DESCRIPTION "Initial implementation"
        ::= { telEventTraps 172 }


l2tpEventsGroup	OBJECT IDENTIFIER	::= { l2tpTrapsMIB 1 }

l2tpNotifications	OBJECT IDENTIFIER	::= { l2tpTrapsMIB 2 }
l2tpNotificationsPrefix	OBJECT IDENTIFIER	::= { l2tpNotifications 0 }

l2tpEventObjects2 OBJECT-IDENTITY
    STATUS current
    DESCRIPTION
        "Event L2TP.2
        The error printed occurred while reading the configuration."
    ::= { l2tpEventsGroup 2 }

l2tp2-DiagnosticMessage OBJECT-TYPE
    SYNTAX DisplayString
    MAX-ACCESS accessible-for-notify
    STATUS current
    DESCRIPTION
        "Parameter 'DiagnosticMessage' in event L2TP.2"
    ::= { l2tpEventObjects2 1 }

l2tpEventObjects3 OBJECT-IDENTITY
    STATUS current
    DESCRIPTION
        "Event L2TP.3
        A packet has been received from a remote peer. Local Tunnel ID,
        packet type and peer IP address are shown in this message."
    ::= { l2tpEventsGroup 3 }

l2tp3-TunnelID OBJECT-TYPE
    SYNTAX Integer32
    MAX-ACCESS accessible-for-notify
    STATUS current
    DESCRIPTION
        "Parameter 'TunnelID' in event L2TP.3"
    ::= { l2tpEventObjects3 1 }

l2tp3-Packet-type OBJECT-TYPE
    SYNTAX DisplayString
    MAX-ACCESS accessible-for-notify
    STATUS current
    DESCRIPTION
        "Parameter 'Packet-type' in event L2TP.3"
    ::= { l2tpEventObjects3 2 }

l2tp3-RemoteIPAddress OBJECT-TYPE
    SYNTAX IpAddress
    MAX-ACCESS accessible-for-notify
    STATUS current
    DESCRIPTION
        "Parameter 'RemoteIPAddress' in event L2TP.3"
    ::= { l2tpEventObjects3 3 }

l2tpEventObjects4 OBJECT-IDENTITY
    STATUS current
    DESCRIPTION
        "Event L2TP.4
        A packet has been sent to a remote peer. Local Tunnel ID, packet type
        and peer IP address are shown in this message."
    ::= { l2tpEventsGroup 4 }

l2tp4-TunnelID OBJECT-TYPE
    SYNTAX Integer32
    MAX-ACCESS accessible-for-notify
    STATUS current
    DESCRIPTION
        "Parameter 'TunnelID' in event L2TP.4"
    ::= { l2tpEventObjects4 1 }

l2tp4-Packet-type OBJECT-TYPE
    SYNTAX DisplayString
    MAX-ACCESS accessible-for-notify
    STATUS current
    DESCRIPTION
        "Parameter 'Packet-type' in event L2TP.4"
    ::= { l2tpEventObjects4 2 }

l2tp4-RemoteIPAddress OBJECT-TYPE
    SYNTAX IpAddress
    MAX-ACCESS accessible-for-notify
    STATUS current
    DESCRIPTION
        "Parameter 'RemoteIPAddress' in event L2TP.4"
    ::= { l2tpEventObjects4 3 }

l2tpEventObjects5 OBJECT-IDENTITY
    STATUS current
    DESCRIPTION
        "Event L2TP.5
        A new tunnel has been created. Local Tunnel ID is shown in the message."
    ::= { l2tpEventsGroup 5 }

l2tp5-TunnelID OBJECT-TYPE
    SYNTAX Integer32
    MAX-ACCESS accessible-for-notify
    STATUS current
    DESCRIPTION
        "Parameter 'TunnelID' in event L2TP.5"
    ::= { l2tpEventObjects5 1 }

l2tpEventObjects6 OBJECT-IDENTITY
    STATUS current
    DESCRIPTION
        "Event L2TP.6
        The tunnel has changed its state. Local Tunnel ID, old state and new
        state are shown in the message."
    ::= { l2tpEventsGroup 6 }

l2tp6-TunnelID OBJECT-TYPE
    SYNTAX Integer32
    MAX-ACCESS accessible-for-notify
    STATUS current
    DESCRIPTION
        "Parameter 'TunnelID' in event L2TP.6"
    ::= { l2tpEventObjects6 1 }

l2tp6-OldState OBJECT-TYPE
    SYNTAX DisplayString
    MAX-ACCESS accessible-for-notify
    STATUS current
    DESCRIPTION
        "Parameter 'OldState' in event L2TP.6"
    ::= { l2tpEventObjects6 2 }

l2tp6-NewState OBJECT-TYPE
    SYNTAX DisplayString
    MAX-ACCESS accessible-for-notify
    STATUS current
    DESCRIPTION
        "Parameter 'NewState' in event L2TP.6"
    ::= { l2tpEventObjects6 3 }

l2tpEventObjects7 OBJECT-IDENTITY
    STATUS current
    DESCRIPTION
        "Event L2TP.7
        An Start-Control-Connection-Request packet has been received from a
        remote peer. Peer IP address is shown in the message."
    ::= { l2tpEventsGroup 7 }

l2tp7-RemoteIPAddress OBJECT-TYPE
    SYNTAX IpAddress
    MAX-ACCESS accessible-for-notify
    STATUS current
    DESCRIPTION
        "Parameter 'RemoteIPAddress' in event L2TP.7"
    ::= { l2tpEventObjects7 1 }

l2tpEventObjects8 OBJECT-IDENTITY
    STATUS current
    DESCRIPTION
        "Event L2TP.8
        The router is creating the stuctures for a pseudowire."
    ::= { l2tpEventsGroup 8 }

l2tp8-pseudowire-name OBJECT-TYPE
    SYNTAX DisplayString
    MAX-ACCESS accessible-for-notify
    STATUS current
    DESCRIPTION
        "Parameter 'pseudowire-name' in event L2TP.8"
    ::= { l2tpEventObjects8 1 }

l2tp8-associated-interface OBJECT-TYPE
    SYNTAX DisplayString
    MAX-ACCESS accessible-for-notify
    STATUS current
    DESCRIPTION
        "Parameter 'associated-interface' in event L2TP.8"
    ::= { l2tpEventObjects8 2 }

l2tp8-source-ip OBJECT-TYPE
    SYNTAX IpAddress
    MAX-ACCESS accessible-for-notify
    STATUS current
    DESCRIPTION
        "Parameter 'source-ip' in event L2TP.8"
    ::= { l2tpEventObjects8 3 }

l2tp8-destination-ip OBJECT-TYPE
    SYNTAX IpAddress
    MAX-ACCESS accessible-for-notify
    STATUS current
    DESCRIPTION
        "Parameter 'destination-ip' in event L2TP.8"
    ::= { l2tpEventObjects8 4 }

l2tpEventObjects9 OBJECT-IDENTITY
    STATUS current
    DESCRIPTION
        "Event L2TP.9
        The pseudowire associated interface is now UP. The router tries to 
        establish the pseudoeire session."
    ::= { l2tpEventsGroup 9 }

l2tp9-interface-name OBJECT-TYPE
    SYNTAX DisplayString
    MAX-ACCESS accessible-for-notify
    STATUS current
    DESCRIPTION
        "Parameter 'interface-name' in event L2TP.9"
    ::= { l2tpEventObjects9 1 }

l2tp9-pseudowire-name OBJECT-TYPE
    SYNTAX DisplayString
    MAX-ACCESS accessible-for-notify
    STATUS current
    DESCRIPTION
        "Parameter 'pseudowire-name' in event L2TP.9"
    ::= { l2tpEventObjects9 2 }

l2tpEventObjects10 OBJECT-IDENTITY
    STATUS current
    DESCRIPTION
        "Event L2TP.10
        A session already exists for the pseudowire and not need to be created."
    ::= { l2tpEventsGroup 10 }

l2tp10-pseudowire-name OBJECT-TYPE
    SYNTAX DisplayString
    MAX-ACCESS accessible-for-notify
    STATUS current
    DESCRIPTION
        "Parameter 'pseudowire-name' in event L2TP.10"
    ::= { l2tpEventObjects10 1 }

l2tp10-tunnel-id OBJECT-TYPE
    SYNTAX Integer32
    MAX-ACCESS accessible-for-notify
    STATUS current
    DESCRIPTION
        "Parameter 'tunnel-id' in event L2TP.10"
    ::= { l2tpEventObjects10 2 }

l2tp10-session-id OBJECT-TYPE
    SYNTAX Integer32
    MAX-ACCESS accessible-for-notify
    STATUS current
    DESCRIPTION
        "Parameter 'session-id' in event L2TP.10"
    ::= { l2tpEventObjects10 3 }

l2tpEventObjects11 OBJECT-IDENTITY
    STATUS current
    DESCRIPTION
        "Event L2TP.11
        The session has changed its state. Local Tunnel/Session IDs, old state
        and new state are shown in the message."
    ::= { l2tpEventsGroup 11 }

l2tp11-TunnelID OBJECT-TYPE
    SYNTAX Integer32
    MAX-ACCESS accessible-for-notify
    STATUS current
    DESCRIPTION
        "Parameter 'TunnelID' in event L2TP.11"
    ::= { l2tpEventObjects11 1 }

l2tp11-SessionID OBJECT-TYPE
    SYNTAX Integer32
    MAX-ACCESS accessible-for-notify
    STATUS current
    DESCRIPTION
        "Parameter 'SessionID' in event L2TP.11"
    ::= { l2tpEventObjects11 2 }

l2tp11-OldState OBJECT-TYPE
    SYNTAX DisplayString
    MAX-ACCESS accessible-for-notify
    STATUS current
    DESCRIPTION
        "Parameter 'OldState' in event L2TP.11"
    ::= { l2tpEventObjects11 3 }

l2tp11-NewState OBJECT-TYPE
    SYNTAX DisplayString
    MAX-ACCESS accessible-for-notify
    STATUS current
    DESCRIPTION
        "Parameter 'NewState' in event L2TP.11"
    ::= { l2tpEventObjects11 4 }

l2tpEventObjects12 OBJECT-IDENTITY
    STATUS current
    DESCRIPTION
        "Event L2TP.12
        A new session within a tunnel has been created.
        Local Tunnel and Session IDs are shown in the message."
    ::= { l2tpEventsGroup 12 }

l2tp12-TunnelID OBJECT-TYPE
    SYNTAX Integer32
    MAX-ACCESS accessible-for-notify
    STATUS current
    DESCRIPTION
        "Parameter 'TunnelID' in event L2TP.12"
    ::= { l2tpEventObjects12 1 }

l2tp12-SessionID OBJECT-TYPE
    SYNTAX Integer32
    MAX-ACCESS accessible-for-notify
    STATUS current
    DESCRIPTION
        "Parameter 'SessionID' in event L2TP.12"
    ::= { l2tpEventObjects12 2 }

l2tpEventObjects13 OBJECT-IDENTITY
    STATUS current
    DESCRIPTION
        "Event L2TP.13
        The pseudowire cannot be registered in the down net because the net
        does not allowed registration.."
    ::= { l2tpEventsGroup 13 }

l2tp13-pseudowire-name OBJECT-TYPE
    SYNTAX DisplayString
    MAX-ACCESS accessible-for-notify
    STATUS current
    DESCRIPTION
        "Parameter 'pseudowire-name' in event L2TP.13"
    ::= { l2tpEventObjects13 1 }

l2tp13-net-name OBJECT-TYPE
    SYNTAX DisplayString
    MAX-ACCESS accessible-for-notify
    STATUS current
    DESCRIPTION
        "Parameter 'net-name' in event L2TP.13"
    ::= { l2tpEventObjects13 2 }

l2tpEventObjects14 OBJECT-IDENTITY
    STATUS current
    DESCRIPTION
        "Event L2TP.14
        The pseudowire has been successfully created."
    ::= { l2tpEventsGroup 14 }

l2tp14-pseudowire-name OBJECT-TYPE
    SYNTAX DisplayString
    MAX-ACCESS accessible-for-notify
    STATUS current
    DESCRIPTION
        "Parameter 'pseudowire-name' in event L2TP.14"
    ::= { l2tpEventObjects14 1 }

l2tpEventObjects15 OBJECT-IDENTITY
    STATUS current
    DESCRIPTION
        "Event L2TP.15
        The pseudowire can not be created due to one of the following reasons:
        the interface is unkown, there is already a peer registered or an 
        internal error."
    ::= { l2tpEventsGroup 15 }

l2tp15-pseudowire-name OBJECT-TYPE
    SYNTAX DisplayString
    MAX-ACCESS accessible-for-notify
    STATUS current
    DESCRIPTION
        "Parameter 'pseudowire-name' in event L2TP.15"
    ::= { l2tpEventObjects15 1 }

l2tp15-cause-of-error OBJECT-TYPE
    SYNTAX DisplayString
    MAX-ACCESS accessible-for-notify
    STATUS current
    DESCRIPTION
        "Parameter 'cause-of-error' in event L2TP.15"
    ::= { l2tpEventObjects15 2 }

l2tpEventObjects17 OBJECT-IDENTITY
    STATUS current
    DESCRIPTION
        "Event L2TP.17
        A tunnel has been deleted. Local Tunnel ID is shown in the message."
    ::= { l2tpEventsGroup 17 }

l2tp17-TunnelID OBJECT-TYPE
    SYNTAX Integer32
    MAX-ACCESS accessible-for-notify
    STATUS current
    DESCRIPTION
        "Parameter 'TunnelID' in event L2TP.17"
    ::= { l2tpEventObjects17 1 }

l2tpEventObjects18 OBJECT-IDENTITY
    STATUS current
    DESCRIPTION
        "Event L2TP.18
        A session has been deleted. Local Tunnel and Session IDs are shown in
        the message."
    ::= { l2tpEventsGroup 18 }

l2tp18-TunnelID OBJECT-TYPE
    SYNTAX Integer32
    MAX-ACCESS accessible-for-notify
    STATUS current
    DESCRIPTION
        "Parameter 'TunnelID' in event L2TP.18"
    ::= { l2tpEventObjects18 1 }

l2tp18-SessionID OBJECT-TYPE
    SYNTAX Integer32
    MAX-ACCESS accessible-for-notify
    STATUS current
    DESCRIPTION
        "Parameter 'SessionID' in event L2TP.18"
    ::= { l2tpEventObjects18 2 }

l2tpEventObjects19 OBJECT-IDENTITY
    STATUS current
    DESCRIPTION
        "Event L2TP.19
        An L2TP error has occurred. Specific error message follows."
    ::= { l2tpEventsGroup 19 }

l2tp19-ErrorMessage OBJECT-TYPE
    SYNTAX DisplayString
    MAX-ACCESS accessible-for-notify
    STATUS current
    DESCRIPTION
        "Parameter 'ErrorMessage' in event L2TP.19"
    ::= { l2tpEventObjects19 1 }

l2tpEventObjects20 OBJECT-IDENTITY
    STATUS current
    DESCRIPTION
        "Event L2TP.20
        Elastic-store underrun has been detected, the last received packet and a
        copy will be added to the elastic-store buffer."
    ::= { l2tpEventsGroup 20 }

l2tp20-BufferLevel OBJECT-TYPE
    SYNTAX Integer32
    MAX-ACCESS accessible-for-notify
    STATUS current
    DESCRIPTION
        "Parameter 'BufferLevel' in event L2TP.20"
    ::= { l2tpEventObjects20 1 }

l2tpEventObjects21 OBJECT-IDENTITY
    STATUS current
    DESCRIPTION
        "Event L2TP.21
        Elastic-store overrun has been detected, the last received packet will
        be dropped.
        "
    ::= { l2tpEventsGroup 21 }

l2tp21-BufferLevel OBJECT-TYPE
    SYNTAX Integer32
    MAX-ACCESS accessible-for-notify
    STATUS current
    DESCRIPTION
        "Parameter 'BufferLevel' in event L2TP.21"
    ::= { l2tpEventObjects21 1 }

l2tpEventObjects26 OBJECT-IDENTITY
    STATUS current
    DESCRIPTION
        "Event L2TP.26
        A data packet has been received for an L2TP session with no L2TP
        handler. Datagram is discarded."
    ::= { l2tpEventsGroup 26 }

l2tp26-TunnelID OBJECT-TYPE
    SYNTAX Integer32
    MAX-ACCESS accessible-for-notify
    STATUS current
    DESCRIPTION
        "Parameter 'TunnelID' in event L2TP.26"
    ::= { l2tpEventObjects26 1 }

l2tp26-SessionID OBJECT-TYPE
    SYNTAX Integer32
    MAX-ACCESS accessible-for-notify
    STATUS current
    DESCRIPTION
        "Parameter 'SessionID' in event L2TP.26"
    ::= { l2tpEventObjects26 2 }

l2tpEventObjects27 OBJECT-IDENTITY
    STATUS current
    DESCRIPTION
        "Event L2TP.27
        An error has ocurred while sending received L2TP session data through
        its associated PPP/L2TP interface. Data is discarded."
    ::= { l2tpEventsGroup 27 }

l2tp27-TunnelID OBJECT-TYPE
    SYNTAX Integer32
    MAX-ACCESS accessible-for-notify
    STATUS current
    DESCRIPTION
        "Parameter 'TunnelID' in event L2TP.27"
    ::= { l2tpEventObjects27 1 }

l2tp27-SessionID OBJECT-TYPE
    SYNTAX Integer32
    MAX-ACCESS accessible-for-notify
    STATUS current
    DESCRIPTION
        "Parameter 'SessionID' in event L2TP.27"
    ::= { l2tpEventObjects27 2 }

l2tp27-IfcName OBJECT-TYPE
    SYNTAX DisplayString
    MAX-ACCESS accessible-for-notify
    STATUS current
    DESCRIPTION
        "Parameter 'IfcName' in event L2TP.27"
    ::= { l2tpEventObjects27 3 }

l2tp27-L2TP-Session-Name OBJECT-TYPE
    SYNTAX DisplayString
    MAX-ACCESS accessible-for-notify
    STATUS current
    DESCRIPTION
        "Parameter 'L2TP-Session-Name' in event L2TP.27"
    ::= { l2tpEventObjects27 4 }

l2tpEventObjects28 OBJECT-IDENTITY
    STATUS current
    DESCRIPTION
        "Event L2TP.28
        A data packet has been received for an L2TP session and has been sent
        successfully through its associated interface."
    ::= { l2tpEventsGroup 28 }

l2tp28-TunnelID OBJECT-TYPE
    SYNTAX Integer32
    MAX-ACCESS accessible-for-notify
    STATUS current
    DESCRIPTION
        "Parameter 'TunnelID' in event L2TP.28"
    ::= { l2tpEventObjects28 1 }

l2tp28-SessionID OBJECT-TYPE
    SYNTAX Integer32
    MAX-ACCESS accessible-for-notify
    STATUS current
    DESCRIPTION
        "Parameter 'SessionID' in event L2TP.28"
    ::= { l2tpEventObjects28 2 }

l2tp28-L2TP-Session-Name OBJECT-TYPE
    SYNTAX DisplayString
    MAX-ACCESS accessible-for-notify
    STATUS current
    DESCRIPTION
        "Parameter 'L2TP-Session-Name' in event L2TP.28"
    ::= { l2tpEventObjects28 3 }

l2tp28-IfcName OBJECT-TYPE
    SYNTAX DisplayString
    MAX-ACCESS accessible-for-notify
    STATUS current
    DESCRIPTION
        "Parameter 'IfcName' in event L2TP.28"
    ::= { l2tpEventObjects28 4 }

l2tpEventObjects29 OBJECT-IDENTITY
    STATUS current
    DESCRIPTION
        "Event L2TP.29
        A data packet has been received from a interface and has been
        sent successfully through its associated L2TP session."
    ::= { l2tpEventsGroup 29 }

l2tp29-TunnelID OBJECT-TYPE
    SYNTAX Integer32
    MAX-ACCESS accessible-for-notify
    STATUS current
    DESCRIPTION
        "Parameter 'TunnelID' in event L2TP.29"
    ::= { l2tpEventObjects29 1 }

l2tp29-SessionID OBJECT-TYPE
    SYNTAX Integer32
    MAX-ACCESS accessible-for-notify
    STATUS current
    DESCRIPTION
        "Parameter 'SessionID' in event L2TP.29"
    ::= { l2tpEventObjects29 2 }

l2tp29-IfcName OBJECT-TYPE
    SYNTAX DisplayString
    MAX-ACCESS accessible-for-notify
    STATUS current
    DESCRIPTION
        "Parameter 'IfcName' in event L2TP.29"
    ::= { l2tpEventObjects29 3 }

l2tp29-L2TP-Session-Name OBJECT-TYPE
    SYNTAX DisplayString
    MAX-ACCESS accessible-for-notify
    STATUS current
    DESCRIPTION
        "Parameter 'L2TP-Session-Name' in event L2TP.29"
    ::= { l2tpEventObjects29 4 }

l2tpEventObjects30 OBJECT-IDENTITY
    STATUS current
    DESCRIPTION
        "Event L2TP.30
        An error has ocurred while sending received PPP data through
        its associated L2TP session. Data is discarded."
    ::= { l2tpEventsGroup 30 }

l2tp30-TunnelID OBJECT-TYPE
    SYNTAX Integer32
    MAX-ACCESS accessible-for-notify
    STATUS current
    DESCRIPTION
        "Parameter 'TunnelID' in event L2TP.30"
    ::= { l2tpEventObjects30 1 }

l2tp30-SessionID OBJECT-TYPE
    SYNTAX Integer32
    MAX-ACCESS accessible-for-notify
    STATUS current
    DESCRIPTION
        "Parameter 'SessionID' in event L2TP.30"
    ::= { l2tpEventObjects30 2 }

l2tp30-IfcName OBJECT-TYPE
    SYNTAX DisplayString
    MAX-ACCESS accessible-for-notify
    STATUS current
    DESCRIPTION
        "Parameter 'IfcName' in event L2TP.30"
    ::= { l2tpEventObjects30 3 }

l2tp30-L2TP-Session-Name OBJECT-TYPE
    SYNTAX DisplayString
    MAX-ACCESS accessible-for-notify
    STATUS current
    DESCRIPTION
        "Parameter 'L2TP-Session-Name' in event L2TP.30"
    ::= { l2tpEventObjects30 4 }

l2tpEventObjects33 OBJECT-IDENTITY
    STATUS current
    DESCRIPTION
        "Event L2TP.33
        The L2TP virtual interface is unable to get a user or domain from the
        associated PPP interface."
    ::= { l2tpEventsGroup 33 }

l2tp33-L2TPInterface OBJECT-TYPE
    SYNTAX DisplayString
    MAX-ACCESS accessible-for-notify
    STATUS current
    DESCRIPTION
        "Parameter 'L2TPInterface' in event L2TP.33"
    ::= { l2tpEventObjects33 1 }

l2tpEventObjects34 OBJECT-IDENTITY
    STATUS current
    DESCRIPTION
        "Event L2TP.34
        The L2TP virtual interface cannot establish a new L2TP session for this
        user/domain."
    ::= { l2tpEventsGroup 34 }

l2tp34-L2TPInterface OBJECT-TYPE
    SYNTAX DisplayString
    MAX-ACCESS accessible-for-notify
    STATUS current
    DESCRIPTION
        "Parameter 'L2TPInterface' in event L2TP.34"
    ::= { l2tpEventObjects34 1 }

l2tp34-User OBJECT-TYPE
    SYNTAX DisplayString
    MAX-ACCESS accessible-for-notify
    STATUS current
    DESCRIPTION
        "Parameter 'User' in event L2TP.34"
    ::= { l2tpEventObjects34 2 }

l2tpEventObjects35 OBJECT-IDENTITY
    STATUS current
    DESCRIPTION
        "Event L2TP.35
        An L2TP event has occurred. Specific event message follows."
    ::= { l2tpEventsGroup 35 }

l2tp35-EventMessage OBJECT-TYPE
    SYNTAX DisplayString
    MAX-ACCESS accessible-for-notify
    STATUS current
    DESCRIPTION
        "Parameter 'EventMessage' in event L2TP.35"
    ::= { l2tpEventObjects35 1 }

l2tpEventObjects36 OBJECT-IDENTITY
    STATUS current
    DESCRIPTION
        "Event L2TP.36
        An L2TP debug has occurred. Specific debug message follows."
    ::= { l2tpEventsGroup 36 }

l2tp36-DebugMessage OBJECT-TYPE
    SYNTAX DisplayString
    MAX-ACCESS accessible-for-notify
    STATUS current
    DESCRIPTION
        "Parameter 'DebugMessage' in event L2TP.36"
    ::= { l2tpEventObjects36 1 }

l2tpEventObjects37 OBJECT-IDENTITY
    STATUS current
    DESCRIPTION
        "Event L2TP.37
        Shows Attribute Information."
    ::= { l2tpEventsGroup 37 }

l2tp37-AttributeType OBJECT-TYPE
    SYNTAX DisplayString
    MAX-ACCESS accessible-for-notify
    STATUS current
    DESCRIPTION
        "Parameter 'AttributeType' in event L2TP.37"
    ::= { l2tpEventObjects37 1 }

l2tp37-AttributeValue OBJECT-TYPE
    SYNTAX DisplayString
    MAX-ACCESS accessible-for-notify
    STATUS current
    DESCRIPTION
        "Parameter 'AttributeValue' in event L2TP.37"
    ::= { l2tpEventObjects37 2 }

l2tp37-MandatoryYesNo OBJECT-TYPE
    SYNTAX DisplayString
    MAX-ACCESS accessible-for-notify
    STATUS current
    DESCRIPTION
        "Parameter 'MandatoryYesNo' in event L2TP.37"
    ::= { l2tpEventObjects37 3 }

l2tp37-HiddenYesNo OBJECT-TYPE
    SYNTAX DisplayString
    MAX-ACCESS accessible-for-notify
    STATUS current
    DESCRIPTION
        "Parameter 'HiddenYesNo' in event L2TP.37"
    ::= { l2tpEventObjects37 4 }

l2tpEventObjects38 OBJECT-IDENTITY
    STATUS current
    DESCRIPTION
        "Event L2TP.38
        The Tie Breaker has been done and one side has won."
    ::= { l2tpEventsGroup 38 }

l2tp38-who-has-won OBJECT-TYPE
    SYNTAX DisplayString
    MAX-ACCESS accessible-for-notify
    STATUS current
    DESCRIPTION
        "Parameter 'who-has-won' in event L2TP.38"
    ::= { l2tpEventObjects38 1 }

l2tp38-peer-address OBJECT-TYPE
    SYNTAX IpAddress
    MAX-ACCESS accessible-for-notify
    STATUS current
    DESCRIPTION
        "Parameter 'peer-address' in event L2TP.38"
    ::= { l2tpEventObjects38 2 }

l2tpEventObjects39 OBJECT-IDENTITY
    STATUS current
    DESCRIPTION
        "Event L2TP.39
        The session has been rejected because there is no peer with this address and 
        this remote end identifier."
    ::= { l2tpEventsGroup 39 }

l2tp39-tunnel-ID OBJECT-TYPE
    SYNTAX Integer32
    MAX-ACCESS accessible-for-notify
    STATUS current
    DESCRIPTION
        "Parameter 'tunnel-ID' in event L2TP.39"
    ::= { l2tpEventObjects39 1 }

l2tp39-peer-address OBJECT-TYPE
    SYNTAX IpAddress
    MAX-ACCESS accessible-for-notify
    STATUS current
    DESCRIPTION
        "Parameter 'peer-address' in event L2TP.39"
    ::= { l2tpEventObjects39 2 }

l2tp39-remote-end-id-received OBJECT-TYPE
    SYNTAX DisplayString
    MAX-ACCESS accessible-for-notify
    STATUS current
    DESCRIPTION
        "Parameter 'remote-end-id-received' in event L2TP.39"
    ::= { l2tpEventObjects39 3 }

l2tpEventObjects40 OBJECT-IDENTITY
    STATUS current
    DESCRIPTION
        "Event L2TP.40
        The Session Tie Breaker has been done and one side has won."
    ::= { l2tpEventsGroup 40 }

l2tp40-who-has-won OBJECT-TYPE
    SYNTAX DisplayString
    MAX-ACCESS accessible-for-notify
    STATUS current
    DESCRIPTION
        "Parameter 'who-has-won' in event L2TP.40"
    ::= { l2tpEventObjects40 1 }

l2tp40-peer-address OBJECT-TYPE
    SYNTAX IpAddress
    MAX-ACCESS accessible-for-notify
    STATUS current
    DESCRIPTION
        "Parameter 'peer-address' in event L2TP.40"
    ::= { l2tpEventObjects40 2 }

l2tpEventObjects41 OBJECT-IDENTITY
    STATUS current
    DESCRIPTION
        "Event L2TP.41
        One IPoFR packet has been processed"
    ::= { l2tpEventsGroup 41 }

l2tp41-From OBJECT-TYPE
    SYNTAX DisplayString
    MAX-ACCESS accessible-for-notify
    STATUS current
    DESCRIPTION
        "Parameter 'From' in event L2TP.41"
    ::= { l2tpEventObjects41 1 }

l2tp41-To OBJECT-TYPE
    SYNTAX DisplayString
    MAX-ACCESS accessible-for-notify
    STATUS current
    DESCRIPTION
        "Parameter 'To' in event L2TP.41"
    ::= { l2tpEventObjects41 2 }

l2tp41-PacketLength OBJECT-TYPE
    SYNTAX Integer32
    MAX-ACCESS accessible-for-notify
    STATUS current
    DESCRIPTION
        "Parameter 'PacketLength' in event L2TP.41"
    ::= { l2tpEventObjects41 3 }

l2tp41-DCLI OBJECT-TYPE
    SYNTAX Integer32
    MAX-ACCESS accessible-for-notify
    STATUS current
    DESCRIPTION
        "Parameter 'DCLI' in event L2TP.41"
    ::= { l2tpEventObjects41 4 }

l2tp41-IPSource OBJECT-TYPE
    SYNTAX IpAddress
    MAX-ACCESS accessible-for-notify
    STATUS current
    DESCRIPTION
        "Parameter 'IPSource' in event L2TP.41"
    ::= { l2tpEventObjects41 5 }

l2tp41-IPDest OBJECT-TYPE
    SYNTAX IpAddress
    MAX-ACCESS accessible-for-notify
    STATUS current
    DESCRIPTION
        "Parameter 'IPDest' in event L2TP.41"
    ::= { l2tpEventObjects41 6 }

l2tp41-Protocol OBJECT-TYPE
    SYNTAX Integer32
    MAX-ACCESS accessible-for-notify
    STATUS current
    DESCRIPTION
        "Parameter 'Protocol' in event L2TP.41"
    ::= { l2tpEventObjects41 7 }

l2tpEventObjects42 OBJECT-IDENTITY
    STATUS current
    DESCRIPTION
        "Event L2TP.42
        One FR LMI packet has been processed"
    ::= { l2tpEventsGroup 42 }

l2tp42-From OBJECT-TYPE
    SYNTAX DisplayString
    MAX-ACCESS accessible-for-notify
    STATUS current
    DESCRIPTION
        "Parameter 'From' in event L2TP.42"
    ::= { l2tpEventObjects42 1 }

l2tp42-To OBJECT-TYPE
    SYNTAX DisplayString
    MAX-ACCESS accessible-for-notify
    STATUS current
    DESCRIPTION
        "Parameter 'To' in event L2TP.42"
    ::= { l2tpEventObjects42 2 }

l2tp42-PacketLength OBJECT-TYPE
    SYNTAX Integer32
    MAX-ACCESS accessible-for-notify
    STATUS current
    DESCRIPTION
        "Parameter 'PacketLength' in event L2TP.42"
    ::= { l2tpEventObjects42 3 }

l2tp42-DCLI OBJECT-TYPE
    SYNTAX Integer32
    MAX-ACCESS accessible-for-notify
    STATUS current
    DESCRIPTION
        "Parameter 'DCLI' in event L2TP.42"
    ::= { l2tpEventObjects42 4 }

l2tp42-Status-Enquiry OBJECT-TYPE
    SYNTAX DisplayString
    MAX-ACCESS accessible-for-notify
    STATUS current
    DESCRIPTION
        "Parameter 'Status-Enquiry' in event L2TP.42"
    ::= { l2tpEventObjects42 5 }

l2tpEventObjects43 OBJECT-IDENTITY
    STATUS current
    DESCRIPTION
        "Event L2TP.43
        One FR packet has been processed"
    ::= { l2tpEventsGroup 43 }

l2tp43-From OBJECT-TYPE
    SYNTAX DisplayString
    MAX-ACCESS accessible-for-notify
    STATUS current
    DESCRIPTION
        "Parameter 'From' in event L2TP.43"
    ::= { l2tpEventObjects43 1 }

l2tp43-To OBJECT-TYPE
    SYNTAX DisplayString
    MAX-ACCESS accessible-for-notify
    STATUS current
    DESCRIPTION
        "Parameter 'To' in event L2TP.43"
    ::= { l2tpEventObjects43 2 }

l2tp43-PacketLength OBJECT-TYPE
    SYNTAX Integer32
    MAX-ACCESS accessible-for-notify
    STATUS current
    DESCRIPTION
        "Parameter 'PacketLength' in event L2TP.43"
    ::= { l2tpEventObjects43 3 }

l2tp43-DCLI OBJECT-TYPE
    SYNTAX Integer32
    MAX-ACCESS accessible-for-notify
    STATUS current
    DESCRIPTION
        "Parameter 'DCLI' in event L2TP.43"
    ::= { l2tpEventObjects43 4 }

l2tpEventObjects44 OBJECT-IDENTITY
    STATUS current
    DESCRIPTION
        "Event L2TP.44
        One packet has been processed"
    ::= { l2tpEventsGroup 44 }

l2tp44-TunnelName OBJECT-TYPE
    SYNTAX DisplayString
    MAX-ACCESS accessible-for-notify
    STATUS current
    DESCRIPTION
        "Parameter 'TunnelName' in event L2TP.44"
    ::= { l2tpEventObjects44 1 }

l2tp44-From OBJECT-TYPE
    SYNTAX DisplayString
    MAX-ACCESS accessible-for-notify
    STATUS current
    DESCRIPTION
        "Parameter 'From' in event L2TP.44"
    ::= { l2tpEventObjects44 2 }

l2tp44-To OBJECT-TYPE
    SYNTAX DisplayString
    MAX-ACCESS accessible-for-notify
    STATUS current
    DESCRIPTION
        "Parameter 'To' in event L2TP.44"
    ::= { l2tpEventObjects44 3 }

l2tp44-PacketLength OBJECT-TYPE
    SYNTAX Integer32
    MAX-ACCESS accessible-for-notify
    STATUS current
    DESCRIPTION
        "Parameter 'PacketLength' in event L2TP.44"
    ::= { l2tpEventObjects44 4 }

l2tp44-Buffer OBJECT-TYPE
    SYNTAX DisplayString
    MAX-ACCESS accessible-for-notify
    STATUS current
    DESCRIPTION
        "Parameter 'Buffer' in event L2TP.44"
    ::= { l2tpEventObjects44 5 }

l2tpEventObjects45 OBJECT-IDENTITY
    STATUS current
    DESCRIPTION
        "Event L2TP.45
        The time of life of a packet inside the disordered queue has expired,
        the expected packet is considered lost, the packet from the queue is
        extracted and sent throgh the base interface."
    ::= { l2tpEventsGroup 45 }

l2tp45-pckt-sequence-number OBJECT-TYPE
    SYNTAX Integer32
    MAX-ACCESS accessible-for-notify
    STATUS current
    DESCRIPTION
        "Parameter 'pckt-sequence-number' in event L2TP.45"
    ::= { l2tpEventObjects45 1 }

l2tp45-remaining-queue-size OBJECT-TYPE
    SYNTAX Integer32
    MAX-ACCESS accessible-for-notify
    STATUS current
    DESCRIPTION
        "Parameter 'remaining-queue-size' in event L2TP.45"
    ::= { l2tpEventObjects45 2 }

l2tpEventObjects46 OBJECT-IDENTITY
    STATUS current
    DESCRIPTION
        "Event L2TP.46
        And old packet has been received, the router will discard this packet."
    ::= { l2tpEventsGroup 46 }

l2tp46-pckt-sequence-number OBJECT-TYPE
    SYNTAX Integer32
    MAX-ACCESS accessible-for-notify
    STATUS current
    DESCRIPTION
        "Parameter 'pckt-sequence-number' in event L2TP.46"
    ::= { l2tpEventObjects46 1 }

l2tp46-expected-sequence-number OBJECT-TYPE
    SYNTAX Integer32
    MAX-ACCESS accessible-for-notify
    STATUS current
    DESCRIPTION
        "Parameter 'expected-sequence-number' in event L2TP.46"
    ::= { l2tpEventObjects46 2 }

l2tpEventObjects47 OBJECT-IDENTITY
    STATUS current
    DESCRIPTION
        "Event L2TP.47
        We are extracting and sending a packet from the disordered queue because
        it is the following packet of the last sent packet."
    ::= { l2tpEventsGroup 47 }

l2tp47-sequence-number OBJECT-TYPE
    SYNTAX Integer32
    MAX-ACCESS accessible-for-notify
    STATUS current
    DESCRIPTION
        "Parameter 'sequence-number' in event L2TP.47"
    ::= { l2tpEventObjects47 1 }

l2tp47-queue-size OBJECT-TYPE
    SYNTAX Integer32
    MAX-ACCESS accessible-for-notify
    STATUS current
    DESCRIPTION
        "Parameter 'queue-size' in event L2TP.47"
    ::= { l2tpEventObjects47 2 }

l2tpEventObjects48 OBJECT-IDENTITY
    STATUS current
    DESCRIPTION
        "Event L2TP.48
        We are adding a packet to the disordered queue because it is inside the
        receive window."
    ::= { l2tpEventsGroup 48 }

l2tp48-sequence-number OBJECT-TYPE
    SYNTAX Integer32
    MAX-ACCESS accessible-for-notify
    STATUS current
    DESCRIPTION
        "Parameter 'sequence-number' in event L2TP.48"
    ::= { l2tpEventObjects48 1 }

l2tp48-expected-sequence-number OBJECT-TYPE
    SYNTAX Integer32
    MAX-ACCESS accessible-for-notify
    STATUS current
    DESCRIPTION
        "Parameter 'expected-sequence-number' in event L2TP.48"
    ::= { l2tpEventObjects48 2 }

l2tp48-queue-size OBJECT-TYPE
    SYNTAX Integer32
    MAX-ACCESS accessible-for-notify
    STATUS current
    DESCRIPTION
        "Parameter 'queue-size' in event L2TP.48"
    ::= { l2tpEventObjects48 3 }

l2tpEventObjects49 OBJECT-IDENTITY
    STATUS current
    DESCRIPTION
        "Event L2TP.49
        We are adding a packet to the disordered queue because it is inside the
        window."
    ::= { l2tpEventsGroup 49 }

l2tp49-received-sequence-number OBJECT-TYPE
    SYNTAX Integer32
    MAX-ACCESS accessible-for-notify
    STATUS current
    DESCRIPTION
        "Parameter 'received-sequence-number' in event L2TP.49"
    ::= { l2tpEventObjects49 1 }

l2tp49-expected-sequence-number OBJECT-TYPE
    SYNTAX Integer32
    MAX-ACCESS accessible-for-notify
    STATUS current
    DESCRIPTION
        "Parameter 'expected-sequence-number' in event L2TP.49"
    ::= { l2tpEventObjects49 2 }

l2tpEventObjects50 OBJECT-IDENTITY
    STATUS current
    DESCRIPTION
        "Event L2TP.50
        We are flushing the disordered packet queue."
    ::= { l2tpEventsGroup 50 }

l2tp50-sent-sequence-number OBJECT-TYPE
    SYNTAX Integer32
    MAX-ACCESS accessible-for-notify
    STATUS current
    DESCRIPTION
        "Parameter 'sent-sequence-number' in event L2TP.50"
    ::= { l2tpEventObjects50 1 }

l2tp50-remaining-queue-size OBJECT-TYPE
    SYNTAX Integer32
    MAX-ACCESS accessible-for-notify
    STATUS current
    DESCRIPTION
        "Parameter 'remaining-queue-size' in event L2TP.50"
    ::= { l2tpEventObjects50 2 }

l2tpEventObjects51 OBJECT-IDENTITY
    STATUS current
    DESCRIPTION
        "Event L2TP.51
        The pattern insertion structure is being created"
    ::= { l2tpEventsGroup 51 }

l2tp51-interface-name OBJECT-TYPE
    SYNTAX DisplayString
    MAX-ACCESS accessible-for-notify
    STATUS current
    DESCRIPTION
        "Parameter 'interface-name' in event L2TP.51"
    ::= { l2tpEventObjects51 1 }

l2tp51-pseudowire-name OBJECT-TYPE
    SYNTAX DisplayString
    MAX-ACCESS accessible-for-notify
    STATUS current
    DESCRIPTION
        "Parameter 'pseudowire-name' in event L2TP.51"
    ::= { l2tpEventObjects51 2 }

l2tpEventObjects52 OBJECT-IDENTITY
    STATUS current
    DESCRIPTION
        "Event L2TP.52
        The pattern insertion process has succeed"
    ::= { l2tpEventsGroup 52 }

l2tp52-interface-name OBJECT-TYPE
    SYNTAX DisplayString
    MAX-ACCESS accessible-for-notify
    STATUS current
    DESCRIPTION
        "Parameter 'interface-name' in event L2TP.52"
    ::= { l2tpEventObjects52 1 }

l2tp52-pseudowire-name OBJECT-TYPE
    SYNTAX DisplayString
    MAX-ACCESS accessible-for-notify
    STATUS current
    DESCRIPTION
        "Parameter 'pseudowire-name' in event L2TP.52"
    ::= { l2tpEventObjects52 2 }

l2tpEventObjects53 OBJECT-IDENTITY
    STATUS current
    DESCRIPTION
        "Event L2TP.53
        The pattern insertion process has failed"
    ::= { l2tpEventsGroup 53 }

l2tp53-interface-name OBJECT-TYPE
    SYNTAX DisplayString
    MAX-ACCESS accessible-for-notify
    STATUS current
    DESCRIPTION
        "Parameter 'interface-name' in event L2TP.53"
    ::= { l2tpEventObjects53 1 }

l2tp53-pseudowire-name OBJECT-TYPE
    SYNTAX DisplayString
    MAX-ACCESS accessible-for-notify
    STATUS current
    DESCRIPTION
        "Parameter 'pseudowire-name' in event L2TP.53"
    ::= { l2tpEventObjects53 2 }

l2tpEventObjects54 OBJECT-IDENTITY
    STATUS current
    DESCRIPTION
        "Event L2TP.54
        An L2TP event call has occurred. Specific event message follows."
    ::= { l2tpEventsGroup 54 }

l2tp54-EventMessage OBJECT-TYPE
    SYNTAX DisplayString
    MAX-ACCESS accessible-for-notify
    STATUS current
    DESCRIPTION
        "Parameter 'EventMessage' in event L2TP.54"
    ::= { l2tpEventObjects54 1 }

l2tpEventObjects56 OBJECT-IDENTITY
    STATUS current
    DESCRIPTION
        "Event L2TP.56
        Pattern insertion multicast and waiting for establish session"
    ::= { l2tpEventsGroup 56 }

l2tp56-interface-name OBJECT-TYPE
    SYNTAX DisplayString
    MAX-ACCESS accessible-for-notify
    STATUS current
    DESCRIPTION
        "Parameter 'interface-name' in event L2TP.56"
    ::= { l2tpEventObjects56 1 }

l2tp56-pseudowire-name OBJECT-TYPE
    SYNTAX DisplayString
    MAX-ACCESS accessible-for-notify
    STATUS current
    DESCRIPTION
        "Parameter 'pseudowire-name' in event L2TP.56"
    ::= { l2tpEventObjects56 2 }


l2tpNotification1 NOTIFICATION-TYPE
    STATUS current
    DESCRIPTION
        "Notification of Event L2TP.1

        Message: 'L2TP subsystem started successfully.'

        L2TP subsystem started successfully."
    ::= { l2tpNotificationsPrefix 1 }

l2tpNotification2 NOTIFICATION-TYPE
    OBJECTS { 
              l2tp2-DiagnosticMessage 
            }
    STATUS current
    DESCRIPTION
        "Notification of Event L2TP.2

        Message: 'Error reading config: $1'

        Parameters list:
              $1: l2tp2-DiagnosticMessage

        The error printed occurred while reading the configuration."
    ::= { l2tpNotificationsPrefix 2 }

l2tpNotification3 NOTIFICATION-TYPE
    OBJECTS { 
              l2tp3-TunnelID, 
              l2tp3-Packet-type,
              l2tp3-RemoteIPAddress 
            }
    STATUS current
    DESCRIPTION
        "Notification of Event L2TP.3

        Message: 'tunnel $1: Incoming $2 from $3'

        Parameters list:
              $1: l2tp3-TunnelID
              $2: l2tp3-Packet-type
              $3: l2tp3-RemoteIPAddress

        A packet has been received from a remote peer. Local Tunnel ID,
        packet type and peer IP address are shown in this message."
    ::= { l2tpNotificationsPrefix 3 }

l2tpNotification4 NOTIFICATION-TYPE
    OBJECTS { 
              l2tp4-TunnelID, 
              l2tp4-Packet-type,
              l2tp4-RemoteIPAddress 
            }
    STATUS current
    DESCRIPTION
        "Notification of Event L2TP.4

        Message: 'tunnel $1: Outgoing $2 to $3'

        Parameters list:
              $1: l2tp4-TunnelID
              $2: l2tp4-Packet-type
              $3: l2tp4-RemoteIPAddress

        A packet has been sent to a remote peer. Local Tunnel ID, packet type
        and peer IP address are shown in this message."
    ::= { l2tpNotificationsPrefix 4 }

l2tpNotification5 NOTIFICATION-TYPE
    OBJECTS { 
              l2tp5-TunnelID 
            }
    STATUS current
    DESCRIPTION
        "Notification of Event L2TP.5

        Message: 'New tunnel with ID $1 has been created'

        Parameters list:
              $1: l2tp5-TunnelID

        A new tunnel has been created. Local Tunnel ID is shown in the message."
    ::= { l2tpNotificationsPrefix 5 }

l2tpNotification6 NOTIFICATION-TYPE
    OBJECTS { 
              l2tp6-TunnelID, 
              l2tp6-OldState,
              l2tp6-NewState 
            }
    STATUS current
    DESCRIPTION
        "Notification of Event L2TP.6

        Message: 'Tunnel with ID $1 changed state from $2 to $3'

        Parameters list:
              $1: l2tp6-TunnelID
              $2: l2tp6-OldState
              $3: l2tp6-NewState

        The tunnel has changed its state. Local Tunnel ID, old state and new
        state are shown in the message."
    ::= { l2tpNotificationsPrefix 6 }

l2tpNotification7 NOTIFICATION-TYPE
    OBJECTS { 
              l2tp7-RemoteIPAddress 
            }
    STATUS current
    DESCRIPTION
        "Notification of Event L2TP.7

        Message: 'Incoming SCCRQ from $1'

        Parameters list:
              $1: l2tp7-RemoteIPAddress

        An Start-Control-Connection-Request packet has been received from a
        remote peer. Peer IP address is shown in the message."
    ::= { l2tpNotificationsPrefix 7 }

l2tpNotification8 NOTIFICATION-TYPE
    OBJECTS { 
              l2tp8-pseudowire-name, 
              l2tp8-associated-interface,
              l2tp8-source-ip,
              l2tp8-destination-ip 
            }
    STATUS current
    DESCRIPTION
        "Notification of Event L2TP.8

        Message: 'Creating pseudowire $1 interface: $2 source IP: $3 destination IP: $4'

        Parameters list:
              $1: l2tp8-pseudowire-name
              $2: l2tp8-associated-interface
              $3: l2tp8-source-ip
              $4: l2tp8-destination-ip

        The router is creating the stuctures for a pseudowire."
    ::= { l2tpNotificationsPrefix 8 }

l2tpNotification9 NOTIFICATION-TYPE
    OBJECTS { 
              l2tp9-interface-name, 
              l2tp9-pseudowire-name 
            }
    STATUS current
    DESCRIPTION
        "Notification of Event L2TP.9

        Message: 'Associated interface $1 is up, establishing $2'

        Parameters list:
              $1: l2tp9-interface-name
              $2: l2tp9-pseudowire-name

        The pseudowire associated interface is now UP. The router tries to 
        establish the pseudoeire session."
    ::= { l2tpNotificationsPrefix 9 }

l2tpNotification10 NOTIFICATION-TYPE
    OBJECTS { 
              l2tp10-pseudowire-name, 
              l2tp10-tunnel-id,
              l2tp10-session-id 
            }
    STATUS current
    DESCRIPTION
        "Notification of Event L2TP.10

        Message: 'Session already exists for pseudowire $1, tunnel: $2, session id: $3'

        Parameters list:
              $1: l2tp10-pseudowire-name
              $2: l2tp10-tunnel-id
              $3: l2tp10-session-id

        A session already exists for the pseudowire and not need to be created."
    ::= { l2tpNotificationsPrefix 10 }

l2tpNotification11 NOTIFICATION-TYPE
    OBJECTS { 
              l2tp11-TunnelID, 
              l2tp11-SessionID,
              l2tp11-OldState,
              l2tp11-NewState 
            }
    STATUS current
    DESCRIPTION
        "Notification of Event L2TP.11

        Message: 'Session of tunnel $1 with ID $2 changed state from $3 to $4'

        Parameters list:
              $1: l2tp11-TunnelID
              $2: l2tp11-SessionID
              $3: l2tp11-OldState
              $4: l2tp11-NewState

        The session has changed its state. Local Tunnel/Session IDs, old state
        and new state are shown in the message."
    ::= { l2tpNotificationsPrefix 11 }

l2tpNotification12 NOTIFICATION-TYPE
    OBJECTS { 
              l2tp12-TunnelID, 
              l2tp12-SessionID 
            }
    STATUS current
    DESCRIPTION
        "Notification of Event L2TP.12

        Message: 'New session for tunnel $1 with ID $2 has been created'

        Parameters list:
              $1: l2tp12-TunnelID
              $2: l2tp12-SessionID

        A new session within a tunnel has been created.
        Local Tunnel and Session IDs are shown in the message."
    ::= { l2tpNotificationsPrefix 12 }

l2tpNotification13 NOTIFICATION-TYPE
    OBJECTS { 
              l2tp13-pseudowire-name, 
              l2tp13-net-name 
            }
    STATUS current
    DESCRIPTION
        "Notification of Event L2TP.13

        Message: 'The pseudowire $1 cannot be registered at interface $2'

        Parameters list:
              $1: l2tp13-pseudowire-name
              $2: l2tp13-net-name

        The pseudowire cannot be registered in the down net because the net
        does not allowed registration.."
    ::= { l2tpNotificationsPrefix 13 }

l2tpNotification14 NOTIFICATION-TYPE
    OBJECTS { 
              l2tp14-pseudowire-name 
            }
    STATUS current
    DESCRIPTION
        "Notification of Event L2TP.14

        Message: 'Pseudowire $1 was successfully created'

        Parameters list:
              $1: l2tp14-pseudowire-name

        The pseudowire has been successfully created."
    ::= { l2tpNotificationsPrefix 14 }

l2tpNotification15 NOTIFICATION-TYPE
    OBJECTS { 
              l2tp15-pseudowire-name, 
              l2tp15-cause-of-error 
            }
    STATUS current
    DESCRIPTION
        "Notification of Event L2TP.15

        Message: 'Can not create pseudowire $1 due to $2'

        Parameters list:
              $1: l2tp15-pseudowire-name
              $2: l2tp15-cause-of-error

        The pseudowire can not be created due to one of the following reasons:
        the interface is unkown, there is already a peer registered or an 
        internal error."
    ::= { l2tpNotificationsPrefix 15 }

l2tpNotification16 NOTIFICATION-TYPE
    STATUS current
    DESCRIPTION
        "Notification of Event L2TP.16

        Message: '----'

        Reserved for possible future use."
    ::= { l2tpNotificationsPrefix 16 }

l2tpNotification17 NOTIFICATION-TYPE
    OBJECTS { 
              l2tp17-TunnelID 
            }
    STATUS current
    DESCRIPTION
        "Notification of Event L2TP.17

        Message: 'A tunnel with ID $1 has been deleted'

        Parameters list:
              $1: l2tp17-TunnelID

        A tunnel has been deleted. Local Tunnel ID is shown in the message."
    ::= { l2tpNotificationsPrefix 17 }

l2tpNotification18 NOTIFICATION-TYPE
    OBJECTS { 
              l2tp18-TunnelID, 
              l2tp18-SessionID 
            }
    STATUS current
    DESCRIPTION
        "Notification of Event L2TP.18

        Message: 'A session with ID $1/$2 has been deleted'

        Parameters list:
              $1: l2tp18-TunnelID
              $2: l2tp18-SessionID

        A session has been deleted. Local Tunnel and Session IDs are shown in
        the message."
    ::= { l2tpNotificationsPrefix 18 }

l2tpNotification19 NOTIFICATION-TYPE
    OBJECTS { 
              l2tp19-ErrorMessage 
            }
    STATUS current
    DESCRIPTION
        "Notification of Event L2TP.19

        Message: 'L2TP error: $1'

        Parameters list:
              $1: l2tp19-ErrorMessage

        An L2TP error has occurred. Specific error message follows."
    ::= { l2tpNotificationsPrefix 19 }

l2tpNotification20 NOTIFICATION-TYPE
    OBJECTS { 
              l2tp20-BufferLevel 
            }
    STATUS current
    DESCRIPTION
        "Notification of Event L2TP.20

        Message: 'Elastic-store underrun detected, buffer level $1'

        Parameters list:
              $1: l2tp20-BufferLevel

        Elastic-store underrun has been detected, the last received packet and a
        copy will be added to the elastic-store buffer."
    ::= { l2tpNotificationsPrefix 20 }

l2tpNotification21 NOTIFICATION-TYPE
    OBJECTS { 
              l2tp21-BufferLevel 
            }
    STATUS current
    DESCRIPTION
        "Notification of Event L2TP.21

        Message: 'Elastic-store overrun detected, buffer level $1'

        Parameters list:
              $1: l2tp21-BufferLevel

        Elastic-store overrun has been detected, the last received packet will
        be dropped.
        "
    ::= { l2tpNotificationsPrefix 21 }

l2tpNotification22 NOTIFICATION-TYPE
    STATUS current
    DESCRIPTION
        "Notification of Event L2TP.22

        Message: '----'

        Reserved for possible future use."
    ::= { l2tpNotificationsPrefix 22 }

l2tpNotification23 NOTIFICATION-TYPE
    STATUS current
    DESCRIPTION
        "Notification of Event L2TP.23

        Message: '----'

        Reserved for possible future use."
    ::= { l2tpNotificationsPrefix 23 }

l2tpNotification24 NOTIFICATION-TYPE
    STATUS current
    DESCRIPTION
        "Notification of Event L2TP.24

        Message: '----'

        Reserved for possible future use."
    ::= { l2tpNotificationsPrefix 24 }

l2tpNotification25 NOTIFICATION-TYPE
    STATUS current
    DESCRIPTION
        "Notification of Event L2TP.25

        Message: '----'

        Reserved for possible future use."
    ::= { l2tpNotificationsPrefix 25 }

l2tpNotification26 NOTIFICATION-TYPE
    OBJECTS { 
              l2tp26-TunnelID, 
              l2tp26-SessionID 
            }
    STATUS current
    DESCRIPTION
        "Notification of Event L2TP.26

        Message: 'session $1/$2 has no L2TP handler available'

        Parameters list:
              $1: l2tp26-TunnelID
              $2: l2tp26-SessionID

        A data packet has been received for an L2TP session with no L2TP
        handler. Datagram is discarded."
    ::= { l2tpNotificationsPrefix 26 }

l2tpNotification27 NOTIFICATION-TYPE
    OBJECTS { 
              l2tp27-TunnelID, 
              l2tp27-SessionID,
              l2tp27-IfcName,
              l2tp27-L2TP-Session-Name 
            }
    STATUS current
    DESCRIPTION
        "Notification of Event L2TP.27

        Message: 'session $1/$2: error while sending data through $3 interface from $4'

        Parameters list:
              $1: l2tp27-TunnelID
              $2: l2tp27-SessionID
              $3: l2tp27-IfcName
              $4: l2tp27-L2TP-Session-Name

        An error has ocurred while sending received L2TP session data through
        its associated PPP/L2TP interface. Data is discarded."
    ::= { l2tpNotificationsPrefix 27 }

l2tpNotification28 NOTIFICATION-TYPE
    OBJECTS { 
              l2tp28-TunnelID, 
              l2tp28-SessionID,
              l2tp28-L2TP-Session-Name,
              l2tp28-IfcName 
            }
    STATUS current
    DESCRIPTION
        "Notification of Event L2TP.28

        Message: 'session out $1/$2: data received from $3 sent to associated $4 interface'

        Parameters list:
              $1: l2tp28-TunnelID
              $2: l2tp28-SessionID
              $3: l2tp28-L2TP-Session-Name
              $4: l2tp28-IfcName

        A data packet has been received for an L2TP session and has been sent
        successfully through its associated interface."
    ::= { l2tpNotificationsPrefix 28 }

l2tpNotification29 NOTIFICATION-TYPE
    OBJECTS { 
              l2tp29-TunnelID, 
              l2tp29-SessionID,
              l2tp29-IfcName,
              l2tp29-L2TP-Session-Name 
            }
    STATUS current
    DESCRIPTION
        "Notification of Event L2TP.29

        Message: 'session in $1/$2: data received from $3 interface sent to $4 L2TP session'

        Parameters list:
              $1: l2tp29-TunnelID
              $2: l2tp29-SessionID
              $3: l2tp29-IfcName
              $4: l2tp29-L2TP-Session-Name

        A data packet has been received from a interface and has been
        sent successfully through its associated L2TP session."
    ::= { l2tpNotificationsPrefix 29 }

l2tpNotification30 NOTIFICATION-TYPE
    OBJECTS { 
              l2tp30-TunnelID, 
              l2tp30-SessionID,
              l2tp30-IfcName,
              l2tp30-L2TP-Session-Name 
            }
    STATUS current
    DESCRIPTION
        "Notification of Event L2TP.30

        Message: 'session $1/$2: error while sending data from $3 interface to $4 L2TP session'

        Parameters list:
              $1: l2tp30-TunnelID
              $2: l2tp30-SessionID
              $3: l2tp30-IfcName
              $4: l2tp30-L2TP-Session-Name

        An error has ocurred while sending received PPP data through
        its associated L2TP session. Data is discarded."
    ::= { l2tpNotificationsPrefix 30 }

l2tpNotification31 NOTIFICATION-TYPE
    STATUS current
    DESCRIPTION
        "Notification of Event L2TP.31

        Message: '----'

        Reserved for possible future use."
    ::= { l2tpNotificationsPrefix 31 }

l2tpNotification32 NOTIFICATION-TYPE
    STATUS current
    DESCRIPTION
        "Notification of Event L2TP.32

        Message: '----'

        Reserved for possible future use."
    ::= { l2tpNotificationsPrefix 32 }

l2tpNotification33 NOTIFICATION-TYPE
    OBJECTS { 
              l2tp33-L2TPInterface 
            }
    STATUS current
    DESCRIPTION
        "Notification of Event L2TP.33

        Message: '$1 Ifc Cannot get user/domain'

        Parameters list:
              $1: l2tp33-L2TPInterface

        The L2TP virtual interface is unable to get a user or domain from the
        associated PPP interface."
    ::= { l2tpNotificationsPrefix 33 }

l2tpNotification34 NOTIFICATION-TYPE
    OBJECTS { 
              l2tp34-L2TPInterface, 
              l2tp34-User 
            }
    STATUS current
    DESCRIPTION
        "Notification of Event L2TP.34

        Message: '$1 Ifc Cannot establish tunn/sess ($2)'

        Parameters list:
              $1: l2tp34-L2TPInterface
              $2: l2tp34-User

        The L2TP virtual interface cannot establish a new L2TP session for this
        user/domain."
    ::= { l2tpNotificationsPrefix 34 }

l2tpNotification35 NOTIFICATION-TYPE
    OBJECTS { 
              l2tp35-EventMessage 
            }
    STATUS current
    DESCRIPTION
        "Notification of Event L2TP.35

        Message: 'EVENT: $1'

        Parameters list:
              $1: l2tp35-EventMessage

        An L2TP event has occurred. Specific event message follows."
    ::= { l2tpNotificationsPrefix 35 }

l2tpNotification36 NOTIFICATION-TYPE
    OBJECTS { 
              l2tp36-DebugMessage 
            }
    STATUS current
    DESCRIPTION
        "Notification of Event L2TP.36

        Message: 'DEBUG: $1'

        Parameters list:
              $1: l2tp36-DebugMessage

        An L2TP debug has occurred. Specific debug message follows."
    ::= { l2tpNotificationsPrefix 36 }

l2tpNotification37 NOTIFICATION-TYPE
    OBJECTS { 
              l2tp37-AttributeType, 
              l2tp37-AttributeValue,
              l2tp37-MandatoryYesNo,
              l2tp37-HiddenYesNo 
            }
    STATUS current
    DESCRIPTION
        "Notification of Event L2TP.37

        Message: 'AVP:$1,$2 Mandatory:$3, Hidden:$4'

        Parameters list:
              $1: l2tp37-AttributeType
              $2: l2tp37-AttributeValue
              $3: l2tp37-MandatoryYesNo
              $4: l2tp37-HiddenYesNo

        Shows Attribute Information."
    ::= { l2tpNotificationsPrefix 37 }

l2tpNotification38 NOTIFICATION-TYPE
    OBJECTS { 
              l2tp38-who-has-won, 
              l2tp38-peer-address 
            }
    STATUS current
    DESCRIPTION
        "Notification of Event L2TP.38

        Message: 'TIE BREAKER: $1 the Tie Breaker with peer $2'

        Parameters list:
              $1: l2tp38-who-has-won
              $2: l2tp38-peer-address

        The Tie Breaker has been done and one side has won."
    ::= { l2tpNotificationsPrefix 38 }

l2tpNotification39 NOTIFICATION-TYPE
    OBJECTS { 
              l2tp39-tunnel-ID, 
              l2tp39-peer-address,
              l2tp39-remote-end-id-received 
            }
    STATUS current
    DESCRIPTION
        "Notification of Event L2TP.39

        Message: 'tnnl: $1: Rejected session ICRQ, no peer ($2) with Remote End ID: $3'

        Parameters list:
              $1: l2tp39-tunnel-ID
              $2: l2tp39-peer-address
              $3: l2tp39-remote-end-id-received

        The session has been rejected because there is no peer with this address and 
        this remote end identifier."
    ::= { l2tpNotificationsPrefix 39 }

l2tpNotification40 NOTIFICATION-TYPE
    OBJECTS { 
              l2tp40-who-has-won, 
              l2tp40-peer-address 
            }
    STATUS current
    DESCRIPTION
        "Notification of Event L2TP.40

        Message: 'TIE BREAKER: $1 the Session Tie Breaker with peer $2'

        Parameters list:
              $1: l2tp40-who-has-won
              $2: l2tp40-peer-address

        The Session Tie Breaker has been done and one side has won."
    ::= { l2tpNotificationsPrefix 40 }

l2tpNotification41 NOTIFICATION-TYPE
    OBJECTS { 
              l2tp41-From, 
              l2tp41-To,
              l2tp41-PacketLength,
              l2tp41-DCLI,
              l2tp41-IPSource,
              l2tp41-IPDest,
              l2tp41-Protocol 
            }
    STATUS current
    DESCRIPTION
        "Notification of Event L2TP.41

        Message: 'fr data $1->$2, len=$3: dcli=$4, ipsrc=$5, ipdst=$6, prot=$7'

        Parameters list:
              $1: l2tp41-From
              $2: l2tp41-To
              $3: l2tp41-PacketLength
              $4: l2tp41-DCLI
              $5: l2tp41-IPSource
              $6: l2tp41-IPDest
              $7: l2tp41-Protocol

        One IPoFR packet has been processed"
    ::= { l2tpNotificationsPrefix 41 }

l2tpNotification42 NOTIFICATION-TYPE
    OBJECTS { 
              l2tp42-From, 
              l2tp42-To,
              l2tp42-PacketLength,
              l2tp42-DCLI,
              l2tp42-Status-Enquiry 
            }
    STATUS current
    DESCRIPTION
        "Notification of Event L2TP.42

        Message: 'fr lmi data $1->$2, len=$3: dcli=$4 $5'

        Parameters list:
              $1: l2tp42-From
              $2: l2tp42-To
              $3: l2tp42-PacketLength
              $4: l2tp42-DCLI
              $5: l2tp42-Status-Enquiry

        One FR LMI packet has been processed"
    ::= { l2tpNotificationsPrefix 42 }

l2tpNotification43 NOTIFICATION-TYPE
    OBJECTS { 
              l2tp43-From, 
              l2tp43-To,
              l2tp43-PacketLength,
              l2tp43-DCLI 
            }
    STATUS current
    DESCRIPTION
        "Notification of Event L2TP.43

        Message: 'fr data $1->$2, len=$3: dcli=$4'

        Parameters list:
              $1: l2tp43-From
              $2: l2tp43-To
              $3: l2tp43-PacketLength
              $4: l2tp43-DCLI

        One FR packet has been processed"
    ::= { l2tpNotificationsPrefix 43 }

l2tpNotification44 NOTIFICATION-TYPE
    OBJECTS { 
              l2tp44-TunnelName, 
              l2tp44-From,
              l2tp44-To,
              l2tp44-PacketLength,
              l2tp44-Buffer 
            }
    STATUS current
    DESCRIPTION
        "Notification of Event L2TP.44

        Message: 'data remote:$1 $2->$3, len=$4: packet:$5'

        Parameters list:
              $1: l2tp44-TunnelName
              $2: l2tp44-From
              $3: l2tp44-To
              $4: l2tp44-PacketLength
              $5: l2tp44-Buffer

        One packet has been processed"
    ::= { l2tpNotificationsPrefix 44 }

l2tpNotification45 NOTIFICATION-TYPE
    OBJECTS { 
              l2tp45-pckt-sequence-number, 
              l2tp45-remaining-queue-size 
            }
    STATUS current
    DESCRIPTION
        "Notification of Event L2TP.45

        Message: 'Timer expired, sending packet $1, queue size is $2'

        Parameters list:
              $1: l2tp45-pckt-sequence-number
              $2: l2tp45-remaining-queue-size

        The time of life of a packet inside the disordered queue has expired,
        the expected packet is considered lost, the packet from the queue is
        extracted and sent throgh the base interface."
    ::= { l2tpNotificationsPrefix 45 }

l2tpNotification46 NOTIFICATION-TYPE
    OBJECTS { 
              l2tp46-pckt-sequence-number, 
              l2tp46-expected-sequence-number 
            }
    STATUS current
    DESCRIPTION
        "Notification of Event L2TP.46

        Message: 'Old packet $1 received is being discarded, expected $2'

        Parameters list:
              $1: l2tp46-pckt-sequence-number
              $2: l2tp46-expected-sequence-number

        And old packet has been received, the router will discard this packet."
    ::= { l2tpNotificationsPrefix 46 }

l2tpNotification47 NOTIFICATION-TYPE
    OBJECTS { 
              l2tp47-sequence-number, 
              l2tp47-queue-size 
            }
    STATUS current
    DESCRIPTION
        "Notification of Event L2TP.47

        Message: 'Sending packet $1 from disordered queue, queue size is $2'

        Parameters list:
              $1: l2tp47-sequence-number
              $2: l2tp47-queue-size

        We are extracting and sending a packet from the disordered queue because
        it is the following packet of the last sent packet."
    ::= { l2tpNotificationsPrefix 47 }

l2tpNotification48 NOTIFICATION-TYPE
    OBJECTS { 
              l2tp48-sequence-number, 
              l2tp48-expected-sequence-number,
              l2tp48-queue-size 
            }
    STATUS current
    DESCRIPTION
        "Notification of Event L2TP.48

        Message: 'Adding packet $1 to disordered queue, expected $2, queue size is $3'

        Parameters list:
              $1: l2tp48-sequence-number
              $2: l2tp48-expected-sequence-number
              $3: l2tp48-queue-size

        We are adding a packet to the disordered queue because it is inside the
        receive window."
    ::= { l2tpNotificationsPrefix 48 }

l2tpNotification49 NOTIFICATION-TYPE
    OBJECTS { 
              l2tp49-received-sequence-number, 
              l2tp49-expected-sequence-number 
            }
    STATUS current
    DESCRIPTION
        "Notification of Event L2TP.49

        Message: 'Received packet $1 out of window, expected seq num $2'

        Parameters list:
              $1: l2tp49-received-sequence-number
              $2: l2tp49-expected-sequence-number

        We are adding a packet to the disordered queue because it is inside the
        window."
    ::= { l2tpNotificationsPrefix 49 }

l2tpNotification50 NOTIFICATION-TYPE
    OBJECTS { 
              l2tp50-sent-sequence-number, 
              l2tp50-remaining-queue-size 
            }
    STATUS current
    DESCRIPTION
        "Notification of Event L2TP.50

        Message: 'Flushing disordered packet queue, sending packet $1, queue size is $2'

        Parameters list:
              $1: l2tp50-sent-sequence-number
              $2: l2tp50-remaining-queue-size

        We are flushing the disordered packet queue."
    ::= { l2tpNotificationsPrefix 50 }

l2tpNotification51 NOTIFICATION-TYPE
    OBJECTS { 
              l2tp51-interface-name, 
              l2tp51-pseudowire-name 
            }
    STATUS current
    DESCRIPTION
        "Notification of Event L2TP.51

        Message: 'Creating pattern insertion structure for peer ifc=$1 pw=$2'

        Parameters list:
              $1: l2tp51-interface-name
              $2: l2tp51-pseudowire-name

        The pattern insertion structure is being created"
    ::= { l2tpNotificationsPrefix 51 }

l2tpNotification52 NOTIFICATION-TYPE
    OBJECTS { 
              l2tp52-interface-name, 
              l2tp52-pseudowire-name 
            }
    STATUS current
    DESCRIPTION
        "Notification of Event L2TP.52

        Message: 'Pattern insertion process success for peer ifc=$1 pw=$2'

        Parameters list:
              $1: l2tp52-interface-name
              $2: l2tp52-pseudowire-name

        The pattern insertion process has succeed"
    ::= { l2tpNotificationsPrefix 52 }

l2tpNotification53 NOTIFICATION-TYPE
    OBJECTS { 
              l2tp53-interface-name, 
              l2tp53-pseudowire-name 
            }
    STATUS current
    DESCRIPTION
        "Notification of Event L2TP.53

        Message: 'Pattern insertion process fail for peer ifc=$1 pw=$2'

        Parameters list:
              $1: l2tp53-interface-name
              $2: l2tp53-pseudowire-name

        The pattern insertion process has failed"
    ::= { l2tpNotificationsPrefix 53 }

l2tpNotification54 NOTIFICATION-TYPE
    OBJECTS { 
              l2tp54-EventMessage 
            }
    STATUS current
    DESCRIPTION
        "Notification of Event L2TP.54

        Message: 'EVENT CALL: $1'

        Parameters list:
              $1: l2tp54-EventMessage

        An L2TP event call has occurred. Specific event message follows."
    ::= { l2tpNotificationsPrefix 54 }

l2tpNotification55 NOTIFICATION-TYPE
    STATUS current
    DESCRIPTION
        "Notification of Event L2TP.55

        Message: 'EVENT CALL: Disable this event to enable EVENT CALL events'

        Disable this event to enable EVENT CALL events"
    ::= { l2tpNotificationsPrefix 55 }

l2tpNotification56 NOTIFICATION-TYPE
    OBJECTS { 
              l2tp56-interface-name, 
              l2tp56-pseudowire-name 
            }
    STATUS current
    DESCRIPTION
        "Notification of Event L2TP.56

        Message: 'Pattern insertion multicast. Waiting session for peer ifc=$1 pw=$2'

        Parameters list:
              $1: l2tp56-interface-name
              $2: l2tp56-pseudowire-name

        Pattern insertion multicast and waiting for establish session"
    ::= { l2tpNotificationsPrefix 56 }


END
