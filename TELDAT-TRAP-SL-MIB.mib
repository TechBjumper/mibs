-- file automatically created


TELDAT-TRAP-SL-MIB DEFINITIONS ::= BEGIN


IMPORTS
	MODULE-IDENTITY,OBJECT-TYPE,OBJECT-IDENTITY,NOTIFICATION-TYPE,Integer32,IpAddress
		FROM SNMPv2-SMI
	DisplayString
		FROM SNMPv2-TC
	telEventTraps
		FROM TELDAT-MIB;


slTrapsMIB MODULE-IDENTITY
    LAST-UPDATED "201401200930Z"
    ORGANIZATION "Teldat, S.A."
    CONTACT-INFO 
        "Teldat, S.A.
        Customer Service

        Postal: Parque Tecnologico de Madrid
                Tres Cantos 28760
                Madrid, SPAIN

        Tel.: +34 918 076 565

        http://www.teldat.com"
    DESCRIPTION
        "This Module Information Base file is defined for managing received
        SNMP notifications generated by the SL event subsystem."
    REVISION "201401200930Z"
    DESCRIPTION "Initial implementation"
        ::= { telEventTraps 83 }


slEventsGroup	OBJECT IDENTIFIER	::= { slTrapsMIB 1 }

slNotifications	OBJECT IDENTIFIER	::= { slTrapsMIB 2 }
slNotificationsPrefix	OBJECT IDENTIFIER	::= { slNotifications 0 }

slEventObjects1 OBJECT-IDENTITY
    STATUS current
    DESCRIPTION
        "Event SL.1
        A packet buffer was not available when the interface self-test
        needed one."
    ::= { slEventsGroup 1 }

sl1-interface OBJECT-TYPE
    SYNTAX DisplayString
    MAX-ACCESS accessible-for-notify
    STATUS current
    DESCRIPTION
        "Parameter 'interface' in event SL.1"
    ::= { slEventObjects1 1 }

slEventObjects2 OBJECT-IDENTITY
    STATUS current
    DESCRIPTION
        "Event SL.2
        During the self-test, the interface card detected that certain signals
        from modem necessary to indicate that it is present and ready to operate
        were not detectable."
    ::= { slEventsGroup 2 }

sl2-interface OBJECT-TYPE
    SYNTAX DisplayString
    MAX-ACCESS accessible-for-notify
    STATUS current
    DESCRIPTION
        "Parameter 'interface' in event SL.2"
    ::= { slEventObjects2 1 }

slEventObjects3 OBJECT-IDENTITY
    STATUS current
    DESCRIPTION
        "Event SL.3
        During self-test, an Echo Acknowledgement was not received from the
        other end of the line within the timeout period. The network fails
        self-test."
    ::= { slEventsGroup 3 }

sl3-interface OBJECT-TYPE
    SYNTAX DisplayString
    MAX-ACCESS accessible-for-notify
    STATUS current
    DESCRIPTION
        "Parameter 'interface' in event SL.3"
    ::= { slEventObjects3 1 }

slEventObjects4 OBJECT-IDENTITY
    STATUS current
    DESCRIPTION
        "Event SL.4
        A bad length field or truncated packet was detected in a DECnet packet
        on the serial line."
    ::= { slEventsGroup 4 }

sl4-actual-length OBJECT-TYPE
    SYNTAX Integer32
    MAX-ACCESS accessible-for-notify
    STATUS current
    DESCRIPTION
        "Parameter 'actual-length' in event SL.4"
    ::= { slEventObjects4 1 }

sl4-claimed-length OBJECT-TYPE
    SYNTAX Integer32
    MAX-ACCESS accessible-for-notify
    STATUS current
    DESCRIPTION
        "Parameter 'claimed-length' in event SL.4"
    ::= { slEventObjects4 2 }

sl4-interface OBJECT-TYPE
    SYNTAX DisplayString
    MAX-ACCESS accessible-for-notify
    STATUS current
    DESCRIPTION
        "Parameter 'interface' in event SL.4"
    ::= { slEventObjects4 3 }

slEventObjects5 OBJECT-IDENTITY
    STATUS current
    DESCRIPTION
        "Event SL.5
        A network control packet was received with a packet type which did not
        match any known opcode."
    ::= { slEventsGroup 5 }

sl5-opcode OBJECT-TYPE
    SYNTAX Integer32
    MAX-ACCESS accessible-for-notify
    STATUS current
    DESCRIPTION
        "Parameter 'opcode' in event SL.5"
    ::= { slEventObjects5 1 }

sl5-interface OBJECT-TYPE
    SYNTAX DisplayString
    MAX-ACCESS accessible-for-notify
    STATUS current
    DESCRIPTION
        "Parameter 'interface' in event SL.5"
    ::= { slEventObjects5 2 }

slEventObjects6 OBJECT-IDENTITY
    STATUS current
    DESCRIPTION
        "Event SL.6
        A serial line packet was received with a higher level protocol which
        did not match any known protocol."
    ::= { slEventsGroup 6 }

sl6-protocol OBJECT-TYPE
    SYNTAX Integer32
    MAX-ACCESS accessible-for-notify
    STATUS current
    DESCRIPTION
        "Parameter 'protocol' in event SL.6"
    ::= { slEventObjects6 1 }

sl6-interface OBJECT-TYPE
    SYNTAX DisplayString
    MAX-ACCESS accessible-for-notify
    STATUS current
    DESCRIPTION
        "Parameter 'interface' in event SL.6"
    ::= { slEventObjects6 2 }

slEventObjects7 OBJECT-IDENTITY
    STATUS current
    DESCRIPTION
        "Event SL.7
        Self-test is being started on the serial line."
    ::= { slEventsGroup 7 }

sl7-interface OBJECT-TYPE
    SYNTAX DisplayString
    MAX-ACCESS accessible-for-notify
    STATUS current
    DESCRIPTION
        "Parameter 'interface' in event SL.7"
    ::= { slEventObjects7 1 }

slEventObjects8 OBJECT-IDENTITY
    STATUS current
    DESCRIPTION
        "Event SL.8
        An echo request is being sent on the serial line."
    ::= { slEventsGroup 8 }

sl8-interface OBJECT-TYPE
    SYNTAX DisplayString
    MAX-ACCESS accessible-for-notify
    STATUS current
    DESCRIPTION
        "Parameter 'interface' in event SL.8"
    ::= { slEventObjects8 1 }

slEventObjects9 OBJECT-IDENTITY
    STATUS current
    DESCRIPTION
        "Event SL.9
        A test packet has been received on the serial line."
    ::= { slEventsGroup 9 }

sl9-interface OBJECT-TYPE
    SYNTAX DisplayString
    MAX-ACCESS accessible-for-notify
    STATUS current
    DESCRIPTION
        "Parameter 'interface' in event SL.9"
    ::= { slEventObjects9 1 }

slEventObjects10 OBJECT-IDENTITY
    STATUS current
    DESCRIPTION
        "Event SL.10
        An echo acknowledgement packet has been received on the serial line."
    ::= { slEventsGroup 10 }

sl10-interface OBJECT-TYPE
    SYNTAX DisplayString
    MAX-ACCESS accessible-for-notify
    STATUS current
    DESCRIPTION
        "Parameter 'interface' in event SL.10"
    ::= { slEventObjects10 1 }

slEventObjects11 OBJECT-IDENTITY
    STATUS current
    DESCRIPTION
        "Event SL.11
        An echo acknowledgement packet has been received on the serial line."
    ::= { slEventsGroup 11 }

sl11-interface OBJECT-TYPE
    SYNTAX DisplayString
    MAX-ACCESS accessible-for-notify
    STATUS current
    DESCRIPTION
        "Parameter 'interface' in event SL.11"
    ::= { slEventObjects11 1 }

slEventObjects12 OBJECT-IDENTITY
    STATUS current
    DESCRIPTION
        "Event SL.12
        A test packet used for network maintenence is being sent on
        the serial line."
    ::= { slEventsGroup 12 }

sl12-interface OBJECT-TYPE
    SYNTAX DisplayString
    MAX-ACCESS accessible-for-notify
    STATUS current
    DESCRIPTION
        "Parameter 'interface' in event SL.12"
    ::= { slEventObjects12 1 }

slEventObjects13 OBJECT-IDENTITY
    STATUS current
    DESCRIPTION
        "Event SL.13
        A Bridged packet is received on this serial line interface even though
        the Spanning Tree Bridging is not enabled on this interface or STB
        is disabled in the box."
    ::= { slEventsGroup 13 }

sl13-interface OBJECT-TYPE
    SYNTAX DisplayString
    MAX-ACCESS accessible-for-notify
    STATUS current
    DESCRIPTION
        "Parameter 'interface' in event SL.13"
    ::= { slEventObjects13 1 }

slEventObjects14 OBJECT-IDENTITY
    STATUS current
    DESCRIPTION
        "Event SL.14
        Dual Serial Line Interface board firmware download has completed with
        the status shown."
    ::= { slEventsGroup 14 }

sl14-slot-num OBJECT-TYPE
    SYNTAX Integer32
    MAX-ACCESS accessible-for-notify
    STATUS current
    DESCRIPTION
        "Parameter 'slot-num' in event SL.14"
    ::= { slEventObjects14 1 }

sl14-ld-code OBJECT-TYPE
    SYNTAX DisplayString
    MAX-ACCESS accessible-for-notify
    STATUS current
    DESCRIPTION
        "Parameter 'ld-code' in event SL.14"
    ::= { slEventObjects14 2 }

slEventObjects15 OBJECT-IDENTITY
    STATUS current
    DESCRIPTION
        "Event SL.15
        Dual Serial Line Board Power-On Diagnostics status completed with the
        code shown. See Power-On Diagnostics manual for encoding."
    ::= { slEventsGroup 15 }

sl15-slot-num OBJECT-TYPE
    SYNTAX Integer32
    MAX-ACCESS accessible-for-notify
    STATUS current
    DESCRIPTION
        "Parameter 'slot-num' in event SL.15"
    ::= { slEventObjects15 1 }

sl15-pud-stat OBJECT-TYPE
    SYNTAX Integer32
    MAX-ACCESS accessible-for-notify
    STATUS current
    DESCRIPTION
        "Parameter 'pud-stat' in event SL.15"
    ::= { slEventObjects15 2 }

slEventObjects16 OBJECT-IDENTITY
    STATUS current
    DESCRIPTION
        "Event SL.16
        Protocol type like Ethertype, DSAPytype or SNAPtype packet filtered.
        This is due to the user supplied protocol filtering information. (STB)."
    ::= { slEventsGroup 16 }

sl16-protocol-type OBJECT-TYPE
    SYNTAX DisplayString
    MAX-ACCESS accessible-for-notify
    STATUS current
    DESCRIPTION
        "Parameter 'protocol-type' in event SL.16"
    ::= { slEventObjects16 1 }

sl16-protocol OBJECT-TYPE
    SYNTAX Integer32
    MAX-ACCESS accessible-for-notify
    STATUS current
    DESCRIPTION
        "Parameter 'protocol' in event SL.16"
    ::= { slEventObjects16 2 }

sl16-interface OBJECT-TYPE
    SYNTAX DisplayString
    MAX-ACCESS accessible-for-notify
    STATUS current
    DESCRIPTION
        "Parameter 'interface' in event SL.16"
    ::= { slEventObjects16 3 }

slEventObjects17 OBJECT-IDENTITY
    STATUS current
    DESCRIPTION
        "Event SL.17
        Packet dropped as the protocol type is enabled but packet arrived
        as bridged. (STB)."
    ::= { slEventsGroup 17 }

sl17-protocol-type OBJECT-TYPE
    SYNTAX Integer32
    MAX-ACCESS accessible-for-notify
    STATUS current
    DESCRIPTION
        "Parameter 'protocol-type' in event SL.17"
    ::= { slEventObjects17 1 }

sl17-src-addr OBJECT-TYPE
    SYNTAX DisplayString
    MAX-ACCESS accessible-for-notify
    STATUS current
    DESCRIPTION
        "Parameter 'src-addr' in event SL.17"
    ::= { slEventObjects17 2 }

sl17-interface OBJECT-TYPE
    SYNTAX DisplayString
    MAX-ACCESS accessible-for-notify
    STATUS current
    DESCRIPTION
        "Parameter 'interface' in event SL.17"
    ::= { slEventObjects17 3 }

slEventObjects18 OBJECT-IDENTITY
    STATUS current
    DESCRIPTION
        "Event SL.18
        Packet dropped as the protocol filtering applies (STB)."
    ::= { slEventsGroup 18 }

sl18-protocol-type OBJECT-TYPE
    SYNTAX Integer32
    MAX-ACCESS accessible-for-notify
    STATUS current
    DESCRIPTION
        "Parameter 'protocol-type' in event SL.18"
    ::= { slEventObjects18 1 }

sl18-interface OBJECT-TYPE
    SYNTAX DisplayString
    MAX-ACCESS accessible-for-notify
    STATUS current
    DESCRIPTION
        "Parameter 'interface' in event SL.18"
    ::= { slEventObjects18 2 }

slEventObjects19 OBJECT-IDENTITY
    STATUS current
    DESCRIPTION
        "Event SL.19
        The cable and the level converter on the interface are not compatible
        with each other. The self-test will fail."
    ::= { slEventsGroup 19 }

sl19-cable-type OBJECT-TYPE
    SYNTAX DisplayString
    MAX-ACCESS accessible-for-notify
    STATUS current
    DESCRIPTION
        "Parameter 'cable-type' in event SL.19"
    ::= { slEventObjects19 1 }

sl19-level-converter-type OBJECT-TYPE
    SYNTAX DisplayString
    MAX-ACCESS accessible-for-notify
    STATUS current
    DESCRIPTION
        "Parameter 'level-converter-type' in event SL.19"
    ::= { slEventObjects19 2 }

sl19-interface OBJECT-TYPE
    SYNTAX DisplayString
    MAX-ACCESS accessible-for-notify
    STATUS current
    DESCRIPTION
        "Parameter 'interface' in event SL.19"
    ::= { slEventObjects19 3 }

slEventObjects20 OBJECT-IDENTITY
    STATUS current
    DESCRIPTION
        "Event SL.20
        There is an incompatibility between the mode of the cable (DCE or DTE)
        and the type of clocking used. The interface will not be brought up."
    ::= { slEventsGroup 20 }

sl20-cable-type OBJECT-TYPE
    SYNTAX DisplayString
    MAX-ACCESS accessible-for-notify
    STATUS current
    DESCRIPTION
        "Parameter 'cable-type' in event SL.20"
    ::= { slEventObjects20 1 }

sl20-internal-external OBJECT-TYPE
    SYNTAX DisplayString
    MAX-ACCESS accessible-for-notify
    STATUS current
    DESCRIPTION
        "Parameter 'internal-external' in event SL.20"
    ::= { slEventObjects20 2 }

sl20-interface OBJECT-TYPE
    SYNTAX DisplayString
    MAX-ACCESS accessible-for-notify
    STATUS current
    DESCRIPTION
        "Parameter 'interface' in event SL.20"
    ::= { slEventObjects20 3 }

slEventObjects21 OBJECT-IDENTITY
    STATUS current
    DESCRIPTION
        "Event SL.21
        The interface failed self test because at least one of the
        modem signals was off."
    ::= { slEventsGroup 21 }

sl21-cts OBJECT-TYPE
    SYNTAX DisplayString
    MAX-ACCESS accessible-for-notify
    STATUS current
    DESCRIPTION
        "Parameter 'cts' in event SL.21"
    ::= { slEventObjects21 1 }

sl21-dsr OBJECT-TYPE
    SYNTAX DisplayString
    MAX-ACCESS accessible-for-notify
    STATUS current
    DESCRIPTION
        "Parameter 'dsr' in event SL.21"
    ::= { slEventObjects21 2 }

sl21-dcd OBJECT-TYPE
    SYNTAX DisplayString
    MAX-ACCESS accessible-for-notify
    STATUS current
    DESCRIPTION
        "Parameter 'dcd' in event SL.21"
    ::= { slEventObjects21 3 }

sl21-interface OBJECT-TYPE
    SYNTAX DisplayString
    MAX-ACCESS accessible-for-notify
    STATUS current
    DESCRIPTION
        "Parameter 'interface' in event SL.21"
    ::= { slEventObjects21 4 }

slEventObjects22 OBJECT-IDENTITY
    STATUS current
    DESCRIPTION
        "Event SL.22
        A modem status change has occurred. The present state is described."
    ::= { slEventsGroup 22 }

sl22-cts OBJECT-TYPE
    SYNTAX DisplayString
    MAX-ACCESS accessible-for-notify
    STATUS current
    DESCRIPTION
        "Parameter 'cts' in event SL.22"
    ::= { slEventObjects22 1 }

sl22-dsr OBJECT-TYPE
    SYNTAX DisplayString
    MAX-ACCESS accessible-for-notify
    STATUS current
    DESCRIPTION
        "Parameter 'dsr' in event SL.22"
    ::= { slEventObjects22 2 }

sl22-dcd OBJECT-TYPE
    SYNTAX DisplayString
    MAX-ACCESS accessible-for-notify
    STATUS current
    DESCRIPTION
        "Parameter 'dcd' in event SL.22"
    ::= { slEventObjects22 3 }

sl22-interface OBJECT-TYPE
    SYNTAX DisplayString
    MAX-ACCESS accessible-for-notify
    STATUS current
    DESCRIPTION
        "Parameter 'interface' in event SL.22"
    ::= { slEventObjects22 4 }

slEventObjects23 OBJECT-IDENTITY
    STATUS current
    DESCRIPTION
        "Event SL.23
        The interface was brought down because one of the modem signals was off."
    ::= { slEventsGroup 23 }

sl23-cts OBJECT-TYPE
    SYNTAX DisplayString
    MAX-ACCESS accessible-for-notify
    STATUS current
    DESCRIPTION
        "Parameter 'cts' in event SL.23"
    ::= { slEventObjects23 1 }

sl23-dsr OBJECT-TYPE
    SYNTAX DisplayString
    MAX-ACCESS accessible-for-notify
    STATUS current
    DESCRIPTION
        "Parameter 'dsr' in event SL.23"
    ::= { slEventObjects23 2 }

sl23-dcd OBJECT-TYPE
    SYNTAX DisplayString
    MAX-ACCESS accessible-for-notify
    STATUS current
    DESCRIPTION
        "Parameter 'dcd' in event SL.23"
    ::= { slEventObjects23 3 }

sl23-interface OBJECT-TYPE
    SYNTAX DisplayString
    MAX-ACCESS accessible-for-notify
    STATUS current
    DESCRIPTION
        "Parameter 'interface' in event SL.23"
    ::= { slEventObjects23 4 }

slEventObjects24 OBJECT-IDENTITY
    STATUS current
    DESCRIPTION
        "Event SL.24
        The user-configured frame size for this interface is larger than
        the maximum that is allowed for the particular serial line device.
        The size is reduced to the largest allowable one."
    ::= { slEventsGroup 24 }

sl24-configured-size OBJECT-TYPE
    SYNTAX Integer32
    MAX-ACCESS accessible-for-notify
    STATUS current
    DESCRIPTION
        "Parameter 'configured-size' in event SL.24"
    ::= { slEventObjects24 1 }

sl24-maximum-size OBJECT-TYPE
    SYNTAX Integer32
    MAX-ACCESS accessible-for-notify
    STATUS current
    DESCRIPTION
        "Parameter 'maximum-size' in event SL.24"
    ::= { slEventObjects24 2 }

sl24-interface OBJECT-TYPE
    SYNTAX DisplayString
    MAX-ACCESS accessible-for-notify
    STATUS current
    DESCRIPTION
        "Parameter 'interface' in event SL.24"
    ::= { slEventObjects24 3 }

slEventObjects25 OBJECT-IDENTITY
    STATUS current
    DESCRIPTION
        "Event SL.25
        A bad length field or truncated packet was detected in a SRT bridge
        packet."
    ::= { slEventsGroup 25 }

sl25-actual-length OBJECT-TYPE
    SYNTAX Integer32
    MAX-ACCESS accessible-for-notify
    STATUS current
    DESCRIPTION
        "Parameter 'actual-length' in event SL.25"
    ::= { slEventObjects25 1 }

sl25-claimed-length OBJECT-TYPE
    SYNTAX Integer32
    MAX-ACCESS accessible-for-notify
    STATUS current
    DESCRIPTION
        "Parameter 'claimed-length' in event SL.25"
    ::= { slEventObjects25 2 }

sl25-interface OBJECT-TYPE
    SYNTAX DisplayString
    MAX-ACCESS accessible-for-notify
    STATUS current
    DESCRIPTION
        "Parameter 'interface' in event SL.25"
    ::= { slEventObjects25 3 }

slEventObjects26 OBJECT-IDENTITY
    STATUS current
    DESCRIPTION
        "Event SL.26
        An Incoming Serial Line packet is shorter than a minimally required
        Serial Line header. Such packet can not be processed and hence freed."
    ::= { slEventsGroup 26 }

sl26-actual-length OBJECT-TYPE
    SYNTAX Integer32
    MAX-ACCESS accessible-for-notify
    STATUS current
    DESCRIPTION
        "Parameter 'actual-length' in event SL.26"
    ::= { slEventObjects26 1 }

sl26-interface OBJECT-TYPE
    SYNTAX DisplayString
    MAX-ACCESS accessible-for-notify
    STATUS current
    DESCRIPTION
        "Parameter 'interface' in event SL.26"
    ::= { slEventObjects26 2 }

slEventObjects27 OBJECT-IDENTITY
    STATUS current
    DESCRIPTION
        "Event SL.27
        There is no level converter on this port of the Quad Serial Line card.
        The self-test will fail, and future self-tests will be cancelled."
    ::= { slEventsGroup 27 }

sl27-interface OBJECT-TYPE
    SYNTAX DisplayString
    MAX-ACCESS accessible-for-notify
    STATUS current
    DESCRIPTION
        "Parameter 'interface' in event SL.27"
    ::= { slEventObjects27 1 }

slEventObjects28 OBJECT-IDENTITY
    STATUS current
    DESCRIPTION
        "Event SL.28
        There is a level converter of an unknown type on this port of
        the Quad Serial Line card. The self-test will fail, and future
        self-tests will be cancelled."
    ::= { slEventsGroup 28 }

sl28-converter-type OBJECT-TYPE
    SYNTAX Integer32
    MAX-ACCESS accessible-for-notify
    STATUS current
    DESCRIPTION
        "Parameter 'converter-type' in event SL.28"
    ::= { slEventObjects28 1 }

sl28-interface OBJECT-TYPE
    SYNTAX DisplayString
    MAX-ACCESS accessible-for-notify
    STATUS current
    DESCRIPTION
        "Parameter 'interface' in event SL.28"
    ::= { slEventObjects28 2 }

slEventObjects29 OBJECT-IDENTITY
    STATUS current
    DESCRIPTION
        "Event SL.29
        The user-configured frame size for this interface is smaller than
        the minimum that is required for the particular serial line device.
        The size is increased to the minimum allowable one."
    ::= { slEventsGroup 29 }

sl29-configured-size OBJECT-TYPE
    SYNTAX Integer32
    MAX-ACCESS accessible-for-notify
    STATUS current
    DESCRIPTION
        "Parameter 'configured-size' in event SL.29"
    ::= { slEventObjects29 1 }

sl29-minimum-size OBJECT-TYPE
    SYNTAX Integer32
    MAX-ACCESS accessible-for-notify
    STATUS current
    DESCRIPTION
        "Parameter 'minimum-size' in event SL.29"
    ::= { slEventObjects29 2 }

sl29-interface OBJECT-TYPE
    SYNTAX DisplayString
    MAX-ACCESS accessible-for-notify
    STATUS current
    DESCRIPTION
        "Parameter 'interface' in event SL.29"
    ::= { slEventObjects29 3 }

slEventObjects30 OBJECT-IDENTITY
    STATUS current
    DESCRIPTION
        "Event SL.30
        The maintenance routine is attempting to send a maintenance frame for
        Proteon Serial data-link, but the buffer for sending this has not been
        freed since the previous maintenance. If this happens 3 times in a row,
        maintenance will fail at the other end of the serial line."
    ::= { slEventsGroup 30 }

sl30-interface OBJECT-TYPE
    SYNTAX DisplayString
    MAX-ACCESS accessible-for-notify
    STATUS current
    DESCRIPTION
        "Parameter 'interface' in event SL.30"
    ::= { slEventObjects30 1 }

slEventObjects31 OBJECT-IDENTITY
    STATUS current
    DESCRIPTION
        "Event SL.31
        A buffer could not be allocated when needed to read the statistics
        counters from the Dual Serial interface.
        The counters should be successfully updated at the next maintenance,
        4 seconds later."
    ::= { slEventsGroup 31 }

sl31-interface OBJECT-TYPE
    SYNTAX DisplayString
    MAX-ACCESS accessible-for-notify
    STATUS current
    DESCRIPTION
        "Parameter 'interface' in event SL.31"
    ::= { slEventObjects31 1 }

slEventObjects32 OBJECT-IDENTITY
    STATUS current
    DESCRIPTION
        "Event SL.32
        The allocation of a packet buffer for a DNX 300 serial line failed.
        This may be due to a shortage of either buffer memory or heap memory.
        (See the output of ELS messages GW.061, GW.063, and GW.064).
        The interface will still try and come up, but with a reduced number of
        receive packet buffers."
    ::= { slEventsGroup 32 }

sl32-buffer-number OBJECT-TYPE
    SYNTAX Integer32
    MAX-ACCESS accessible-for-notify
    STATUS current
    DESCRIPTION
        "Parameter 'buffer-number' in event SL.32"
    ::= { slEventObjects32 1 }

sl32-interface OBJECT-TYPE
    SYNTAX DisplayString
    MAX-ACCESS accessible-for-notify
    STATUS current
    DESCRIPTION
        "Parameter 'interface' in event SL.32"
    ::= { slEventObjects32 2 }

slEventObjects33 OBJECT-IDENTITY
    STATUS current
    DESCRIPTION
        "Event SL.33
        A packet buffer was allocated for the DNX 300 serial line, but that
        buffer crossed a 64 Kbyte memory boundary in the buffer memory. Since
        all of the receive buffers for a DNX 300 serial line must be
        in the same 64 Kbyte buffer memory packet, that buffer will be ignored,
        and no further buffers will be allocated for the device. The interface
        will still try and come up, but with a reduced number of receive packet
        buffers."
    ::= { slEventsGroup 33 }

sl33-buffer-number OBJECT-TYPE
    SYNTAX Integer32
    MAX-ACCESS accessible-for-notify
    STATUS current
    DESCRIPTION
        "Parameter 'buffer-number' in event SL.33"
    ::= { slEventObjects33 1 }

sl33-interface OBJECT-TYPE
    SYNTAX DisplayString
    MAX-ACCESS accessible-for-notify
    STATUS current
    DESCRIPTION
        "Parameter 'interface' in event SL.33"
    ::= { slEventObjects33 2 }

slEventObjects34 OBJECT-IDENTITY
    STATUS current
    DESCRIPTION
        "Event SL.34
        The system does not detect an adapter cable in the network interface
        port. Self-test will fail."
    ::= { slEventsGroup 34 }

sl34-interface OBJECT-TYPE
    SYNTAX DisplayString
    MAX-ACCESS accessible-for-notify
    STATUS current
    DESCRIPTION
        "Parameter 'interface' in event SL.34"
    ::= { slEventObjects34 1 }

slEventObjects35 OBJECT-IDENTITY
    STATUS current
    DESCRIPTION
        "Event SL.35
        A protocol that cannot be bridged by Proteon Serial Line's PSEUDO-
        ETHERNET bridging method has been configured over an interface
        using PSL PSEUDO-ETH."
    ::= { slEventsGroup 35 }

sl35-protocol-name OBJECT-TYPE
    SYNTAX DisplayString
    MAX-ACCESS accessible-for-notify
    STATUS current
    DESCRIPTION
        "Parameter 'protocol-name' in event SL.35"
    ::= { slEventObjects35 1 }

sl35-protocol-number OBJECT-TYPE
    SYNTAX Integer32
    MAX-ACCESS accessible-for-notify
    STATUS current
    DESCRIPTION
        "Parameter 'protocol-number' in event SL.35"
    ::= { slEventObjects35 2 }

sl35-interface OBJECT-TYPE
    SYNTAX DisplayString
    MAX-ACCESS accessible-for-notify
    STATUS current
    DESCRIPTION
        "Parameter 'interface' in event SL.35"
    ::= { slEventObjects35 3 }

slEventObjects36 OBJECT-IDENTITY
    STATUS current
    DESCRIPTION
        "Event SL.36
        The interface is on mode loopback or echo and the timeout as expired."
    ::= { slEventsGroup 36 }

sl36-interface OBJECT-TYPE
    SYNTAX DisplayString
    MAX-ACCESS accessible-for-notify
    STATUS current
    DESCRIPTION
        "Parameter 'interface' in event SL.36"
    ::= { slEventObjects36 1 }


slNotification1 NOTIFICATION-TYPE
    OBJECTS { 
              sl1-interface 
            }
    STATUS current
    DESCRIPTION
        "Notification of Event SL.1

        Message: 'no buffer available for selftest interface $1'

        Parameters list:
              $1: sl1-interface

        A packet buffer was not available when the interface self-test
        needed one."
    ::= { slNotificationsPrefix 1 }

slNotification2 NOTIFICATION-TYPE
    OBJECTS { 
              sl2-interface 
            }
    STATUS current
    DESCRIPTION
        "Notification of Event SL.2

        Message: 'modem error with no DCD/DTS detected during selftest interface $1'

        Parameters list:
              $1: sl2-interface

        During the self-test, the interface card detected that certain signals
        from modem necessary to indicate that it is present and ready to operate
        were not detectable."
    ::= { slNotificationsPrefix 2 }

slNotification3 NOTIFICATION-TYPE
    OBJECTS { 
              sl3-interface 
            }
    STATUS current
    DESCRIPTION
        "Notification of Event SL.3

        Message: 'no echo acknowledgement received, timeout selftest interface $1'

        Parameters list:
              $1: sl3-interface

        During self-test, an Echo Acknowledgement was not received from the
        other end of the line within the timeout period. The network fails
        self-test."
    ::= { slNotificationsPrefix 3 }

slNotification4 NOTIFICATION-TYPE
    OBJECTS { 
              sl4-actual-length, 
              sl4-claimed-length,
              sl4-interface 
            }
    STATUS current
    DESCRIPTION
        "Notification of Event SL.4

        Message: 'bad length in DECNet packet actual $1 claimed $2 interface $3'

        Parameters list:
              $1: sl4-actual-length
              $2: sl4-claimed-length
              $3: sl4-interface

        A bad length field or truncated packet was detected in a DECnet packet
        on the serial line."
    ::= { slNotificationsPrefix 4 }

slNotification5 NOTIFICATION-TYPE
    OBJECTS { 
              sl5-opcode, 
              sl5-interface 
            }
    STATUS current
    DESCRIPTION
        "Notification of Event SL.5

        Message: 'bad received packet header opcode $1 interface $2'

        Parameters list:
              $1: sl5-opcode
              $2: sl5-interface

        A network control packet was received with a packet type which did not
        match any known opcode."
    ::= { slNotificationsPrefix 5 }

slNotification6 NOTIFICATION-TYPE
    OBJECTS { 
              sl6-protocol, 
              sl6-interface 
            }
    STATUS current
    DESCRIPTION
        "Notification of Event SL.6

        Message: 'bad received packet header protocol $1 interface $2'

        Parameters list:
              $1: sl6-protocol
              $2: sl6-interface

        A serial line packet was received with a higher level protocol which
        did not match any known protocol."
    ::= { slNotificationsPrefix 6 }

slNotification7 NOTIFICATION-TYPE
    OBJECTS { 
              sl7-interface 
            }
    STATUS current
    DESCRIPTION
        "Notification of Event SL.7

        Message: 'start selftest interface $1'

        Parameters list:
              $1: sl7-interface

        Self-test is being started on the serial line."
    ::= { slNotificationsPrefix 7 }

slNotification8 NOTIFICATION-TYPE
    OBJECTS { 
              sl8-interface 
            }
    STATUS current
    DESCRIPTION
        "Notification of Event SL.8

        Message: 'send echo packet interface $1'

        Parameters list:
              $1: sl8-interface

        An echo request is being sent on the serial line."
    ::= { slNotificationsPrefix 8 }

slNotification9 NOTIFICATION-TYPE
    OBJECTS { 
              sl9-interface 
            }
    STATUS current
    DESCRIPTION
        "Notification of Event SL.9

        Message: 'receive test packet interface $1'

        Parameters list:
              $1: sl9-interface

        A test packet has been received on the serial line."
    ::= { slNotificationsPrefix 9 }

slNotification10 NOTIFICATION-TYPE
    OBJECTS { 
              sl10-interface 
            }
    STATUS current
    DESCRIPTION
        "Notification of Event SL.10

        Message: 'receive echo acknowledgement packet interface $1'

        Parameters list:
              $1: sl10-interface

        An echo acknowledgement packet has been received on the serial line."
    ::= { slNotificationsPrefix 10 }

slNotification11 NOTIFICATION-TYPE
    OBJECTS { 
              sl11-interface 
            }
    STATUS current
    DESCRIPTION
        "Notification of Event SL.11

        Message: 'receive echo request packet interface $1'

        Parameters list:
              $1: sl11-interface

        An echo acknowledgement packet has been received on the serial line."
    ::= { slNotificationsPrefix 11 }

slNotification12 NOTIFICATION-TYPE
    OBJECTS { 
              sl12-interface 
            }
    STATUS current
    DESCRIPTION
        "Notification of Event SL.12

        Message: 'sending maintenance test packet interface $1'

        Parameters list:
              $1: sl12-interface

        A test packet used for network maintenence is being sent on
        the serial line."
    ::= { slNotificationsPrefix 12 }

slNotification13 NOTIFICATION-TYPE
    OBJECTS { 
              sl13-interface 
            }
    STATUS current
    DESCRIPTION
        "Notification of Event SL.13

        Message: 'Dropping the received Spanning Tree Bridged packet but bridging is disabled on interface $1'

        Parameters list:
              $1: sl13-interface

        A Bridged packet is received on this serial line interface even though
        the Spanning Tree Bridging is not enabled on this interface or STB
        is disabled in the box."
    ::= { slNotificationsPrefix 13 }

slNotification14 NOTIFICATION-TYPE
    OBJECTS { 
              sl14-slot-num, 
              sl14-ld-code 
            }
    STATUS current
    DESCRIPTION
        "Notification of Event SL.14

        Message: 'Dual Serial Line board in slot $1 firmware download $2'

        Parameters list:
              $1: sl14-slot-num
              $2: sl14-ld-code

        Dual Serial Line Interface board firmware download has completed with
        the status shown."
    ::= { slNotificationsPrefix 14 }

slNotification15 NOTIFICATION-TYPE
    OBJECTS { 
              sl15-slot-num, 
              sl15-pud-stat 
            }
    STATUS current
    DESCRIPTION
        "Notification of Event SL.15

        Message: 'Dual Serial Line board slot $1 Power-On Diagnostics status $2'

        Parameters list:
              $1: sl15-slot-num
              $2: sl15-pud-stat

        Dual Serial Line Board Power-On Diagnostics status completed with the
        code shown. See Power-On Diagnostics manual for encoding."
    ::= { slNotificationsPrefix 15 }

slNotification16 NOTIFICATION-TYPE
    OBJECTS { 
              sl16-protocol-type, 
              sl16-protocol,
              sl16-interface 
            }
    STATUS current
    DESCRIPTION
        "Notification of Event SL.16

        Message: '$1 type pakcet filtered for protocol = $2 interface $3'

        Parameters list:
              $1: sl16-protocol-type
              $2: sl16-protocol
              $3: sl16-interface

        Protocol type like Ethertype, DSAPytype or SNAPtype packet filtered.
        This is due to the user supplied protocol filtering information. (STB)."
    ::= { slNotificationsPrefix 16 }

slNotification17 NOTIFICATION-TYPE
    OBJECTS { 
              sl17-protocol-type, 
              sl17-src-addr,
              sl17-interface 
            }
    STATUS current
    DESCRIPTION
        "Notification of Event SL.17

        Message: 'Dropped, protocol = $1 enabled but packet arrived as bridged from address $2, interface $3'

        Parameters list:
              $1: sl17-protocol-type
              $2: sl17-src-addr
              $3: sl17-interface

        Packet dropped as the protocol type is enabled but packet arrived
        as bridged. (STB)."
    ::= { slNotificationsPrefix 17 }

slNotification18 NOTIFICATION-TYPE
    OBJECTS { 
              sl18-protocol-type, 
              sl18-interface 
            }
    STATUS current
    DESCRIPTION
        "Notification of Event SL.18

        Message: 'Dropped, dsap = $1, Protocol filtreing applies, interface $2'

        Parameters list:
              $1: sl18-protocol-type
              $2: sl18-interface

        Packet dropped as the protocol filtering applies (STB)."
    ::= { slNotificationsPrefix 18 }

slNotification19 NOTIFICATION-TYPE
    OBJECTS { 
              sl19-cable-type, 
              sl19-level-converter-type,
              sl19-interface 
            }
    STATUS current
    DESCRIPTION
        "Notification of Event SL.19

        Message: 'Cable of type $1 is not compatible with level converter of type $2, interface $3'

        Parameters list:
              $1: sl19-cable-type
              $2: sl19-level-converter-type
              $3: sl19-interface

        The cable and the level converter on the interface are not compatible
        with each other. The self-test will fail."
    ::= { slNotificationsPrefix 19 }

slNotification20 NOTIFICATION-TYPE
    OBJECTS { 
              sl20-cable-type, 
              sl20-internal-external,
              sl20-interface 
            }
    STATUS current
    DESCRIPTION
        "Notification of Event SL.20

        Message: '$1 cable cannot be used with $2 clocking enabled, interface $3'

        Parameters list:
              $1: sl20-cable-type
              $2: sl20-internal-external
              $3: sl20-interface

        There is an incompatibility between the mode of the cable (DCE or DTE)
        and the type of clocking used. The interface will not be brought up."
    ::= { slNotificationsPrefix 20 }

slNotification21 NOTIFICATION-TYPE
    OBJECTS { 
              sl21-cts, 
              sl21-dsr,
              sl21-dcd,
              sl21-interface 
            }
    STATUS current
    DESCRIPTION
        "Notification of Event SL.21

        Message: 'Self test failed because of modem status, CTS = $1, DSR = $2, DCD = $3, ifc $4'

        Parameters list:
              $1: sl21-cts
              $2: sl21-dsr
              $3: sl21-dcd
              $4: sl21-interface

        The interface failed self test because at least one of the
        modem signals was off."
    ::= { slNotificationsPrefix 21 }

slNotification22 NOTIFICATION-TYPE
    OBJECTS { 
              sl22-cts, 
              sl22-dsr,
              sl22-dcd,
              sl22-interface 
            }
    STATUS current
    DESCRIPTION
        "Notification of Event SL.22

        Message: 'Modem status change CTS = $1, DSR = $2, DCD = $3, on interface $4'

        Parameters list:
              $1: sl22-cts
              $2: sl22-dsr
              $3: sl22-dcd
              $4: sl22-interface

        A modem status change has occurred. The present state is described."
    ::= { slNotificationsPrefix 22 }

slNotification23 NOTIFICATION-TYPE
    OBJECTS { 
              sl23-cts, 
              sl23-dsr,
              sl23-dcd,
              sl23-interface 
            }
    STATUS current
    DESCRIPTION
        "Notification of Event SL.23

        Message: 'Interface down because of modem status, CTS = $1, DSR = $2, DCD = $3, ifc $4'

        Parameters list:
              $1: sl23-cts
              $2: sl23-dsr
              $3: sl23-dcd
              $4: sl23-interface

        The interface was brought down because one of the modem signals was off."
    ::= { slNotificationsPrefix 23 }

slNotification24 NOTIFICATION-TYPE
    OBJECTS { 
              sl24-configured-size, 
              sl24-maximum-size,
              sl24-interface 
            }
    STATUS current
    DESCRIPTION
        "Notification of Event SL.24

        Message: 'Configured frame size of $1 bytes too large, reducing to $2 bytes, interface $3'

        Parameters list:
              $1: sl24-configured-size
              $2: sl24-maximum-size
              $3: sl24-interface

        The user-configured frame size for this interface is larger than
        the maximum that is allowed for the particular serial line device.
        The size is reduced to the largest allowable one."
    ::= { slNotificationsPrefix 24 }

slNotification25 NOTIFICATION-TYPE
    OBJECTS { 
              sl25-actual-length, 
              sl25-claimed-length,
              sl25-interface 
            }
    STATUS current
    DESCRIPTION
        "Notification of Event SL.25

        Message: 'bad length in SRT packet actual $1 claimed $2 interface $3'

        Parameters list:
              $1: sl25-actual-length
              $2: sl25-claimed-length
              $3: sl25-interface

        A bad length field or truncated packet was detected in a SRT bridge
        packet."
    ::= { slNotificationsPrefix 25 }

slNotification26 NOTIFICATION-TYPE
    OBJECTS { 
              sl26-actual-length, 
              sl26-interface 
            }
    STATUS current
    DESCRIPTION
        "Notification of Event SL.26

        Message: 'Packet received is shorter than Serial line header, actual $1 interface $2'

        Parameters list:
              $1: sl26-actual-length
              $2: sl26-interface

        An Incoming Serial Line packet is shorter than a minimally required
        Serial Line header. Such packet can not be processed and hence freed."
    ::= { slNotificationsPrefix 26 }

slNotification27 NOTIFICATION-TYPE
    OBJECTS { 
              sl27-interface 
            }
    STATUS current
    DESCRIPTION
        "Notification of Event SL.27

        Message: 'No level converter, disabling interface $1'

        Parameters list:
              $1: sl27-interface

        There is no level converter on this port of the Quad Serial Line card.
        The self-test will fail, and future self-tests will be cancelled."
    ::= { slNotificationsPrefix 27 }

slNotification28 NOTIFICATION-TYPE
    OBJECTS { 
              sl28-converter-type, 
              sl28-interface 
            }
    STATUS current
    DESCRIPTION
        "Notification of Event SL.28

        Message: 'Unknown level converter type $1, disabling interface $2'

        Parameters list:
              $1: sl28-converter-type
              $2: sl28-interface

        There is a level converter of an unknown type on this port of
        the Quad Serial Line card. The self-test will fail, and future
        self-tests will be cancelled."
    ::= { slNotificationsPrefix 28 }

slNotification29 NOTIFICATION-TYPE
    OBJECTS { 
              sl29-configured-size, 
              sl29-minimum-size,
              sl29-interface 
            }
    STATUS current
    DESCRIPTION
        "Notification of Event SL.29

        Message: 'Configured frame size of $1 bytes too small, increasing to $2 bytes, interface $3'

        Parameters list:
              $1: sl29-configured-size
              $2: sl29-minimum-size
              $3: sl29-interface

        The user-configured frame size for this interface is smaller than
        the minimum that is required for the particular serial line device.
        The size is increased to the minimum allowable one."
    ::= { slNotificationsPrefix 29 }

slNotification30 NOTIFICATION-TYPE
    OBJECTS { 
              sl30-interface 
            }
    STATUS current
    DESCRIPTION
        "Notification of Event SL.30

        Message: 'Maintenance buffer busy, interface $1'

        Parameters list:
              $1: sl30-interface

        The maintenance routine is attempting to send a maintenance frame for
        Proteon Serial data-link, but the buffer for sending this has not been
        freed since the previous maintenance. If this happens 3 times in a row,
        maintenance will fail at the other end of the serial line."
    ::= { slNotificationsPrefix 30 }

slNotification31 NOTIFICATION-TYPE
    OBJECTS { 
              sl31-interface 
            }
    STATUS current
    DESCRIPTION
        "Notification of Event SL.31

        Message: 'No packet for reading counters, interface $1'

        Parameters list:
              $1: sl31-interface

        A buffer could not be allocated when needed to read the statistics
        counters from the Dual Serial interface.
        The counters should be successfully updated at the next maintenance,
        4 seconds later."
    ::= { slNotificationsPrefix 31 }

slNotification32 NOTIFICATION-TYPE
    OBJECTS { 
              sl32-buffer-number, 
              sl32-interface 
            }
    STATUS current
    DESCRIPTION
        "Notification of Event SL.32

        Message: 'Packet buffer allocation number $1 failed, interface $2'

        Parameters list:
              $1: sl32-buffer-number
              $2: sl32-interface

        The allocation of a packet buffer for a DNX 300 serial line failed.
        This may be due to a shortage of either buffer memory or heap memory.
        (See the output of ELS messages GW.061, GW.063, and GW.064).
        The interface will still try and come up, but with a reduced number of
        receive packet buffers."
    ::= { slNotificationsPrefix 32 }

slNotification33 NOTIFICATION-TYPE
    OBJECTS { 
              sl33-buffer-number, 
              sl33-interface 
            }
    STATUS current
    DESCRIPTION
        "Notification of Event SL.33

        Message: 'Packet buffer number $1 crossed 64 Kbyte page boundary, dropped, ifc $2'

        Parameters list:
              $1: sl33-buffer-number
              $2: sl33-interface

        A packet buffer was allocated for the DNX 300 serial line, but that
        buffer crossed a 64 Kbyte memory boundary in the buffer memory. Since
        all of the receive buffers for a DNX 300 serial line must be
        in the same 64 Kbyte buffer memory packet, that buffer will be ignored,
        and no further buffers will be allocated for the device. The interface
        will still try and come up, but with a reduced number of receive packet
        buffers."
    ::= { slNotificationsPrefix 33 }

slNotification34 NOTIFICATION-TYPE
    OBJECTS { 
              sl34-interface 
            }
    STATUS current
    DESCRIPTION
        "Notification of Event SL.34

        Message: 'No cable installed or installed cable broken or non-compatible, interface $1'

        Parameters list:
              $1: sl34-interface

        The system does not detect an adapter cable in the network interface
        port. Self-test will fail."
    ::= { slNotificationsPrefix 34 }

slNotification35 NOTIFICATION-TYPE
    OBJECTS { 
              sl35-protocol-name, 
              sl35-protocol-number,
              sl35-interface 
            }
    STATUS current
    DESCRIPTION
        "Notification of Event SL.35

        Message: 'Protocol $1 ($2) can not be bridged over Proteon Serial Line using the pseudo-ethernet bridging method.  Interface $3'

        Parameters list:
              $1: sl35-protocol-name
              $2: sl35-protocol-number
              $3: sl35-interface

        A protocol that cannot be bridged by Proteon Serial Line's PSEUDO-
        ETHERNET bridging method has been configured over an interface
        using PSL PSEUDO-ETH."
    ::= { slNotificationsPrefix 35 }

slNotification36 NOTIFICATION-TYPE
    OBJECTS { 
              sl36-interface 
            }
    STATUS current
    DESCRIPTION
        "Notification of Event SL.36

        Message: 'warning: test on ifc $1'

        Parameters list:
              $1: sl36-interface

        The interface is on mode loopback or echo and the timeout as expired."
    ::= { slNotificationsPrefix 36 }


END
