-- file automatically created


TELDAT-TRAP-AAA-MIB DEFINITIONS ::= BEGIN


IMPORTS
	MODULE-IDENTITY,OBJECT-TYPE,OBJECT-IDENTITY,NOTIFICATION-TYPE,Integer32,IpAddress
		FROM SNMPv2-SMI
	DisplayString
		FROM SNMPv2-TC
	telEventTraps
		FROM TELDAT-MIB;


aaaTrapsMIB MODULE-IDENTITY
    LAST-UPDATED "201401200930Z"
    ORGANIZATION "Teldat, S.A."
    CONTACT-INFO 
        "Teldat, S.A.
        Customer Service

        Postal: Parque Tecnologico de Madrid
                Tres Cantos 28760
                Madrid, SPAIN

        Tel.: +34 918 076 565

        http://www.teldat.com"
    DESCRIPTION
        "This Module Information Base file is defined for managing received
        SNMP notifications generated by the AAA event subsystem."
    REVISION "201401200930Z"
    DESCRIPTION "Initial implementation"
        ::= { telEventTraps 226 }


aaaEventsGroup	OBJECT IDENTIFIER	::= { aaaTrapsMIB 1 }

aaaNotifications	OBJECT IDENTIFIER	::= { aaaTrapsMIB 2 }
aaaNotificationsPrefix	OBJECT IDENTIFIER	::= { aaaNotifications 0 }

aaaEventObjects1 OBJECT-IDENTITY
    STATUS current
    DESCRIPTION
        "Event AAA.1
        Generic abnormal internal error message."
    ::= { aaaEventsGroup 1 }

aaa1-message OBJECT-TYPE
    SYNTAX DisplayString
    MAX-ACCESS accessible-for-notify
    STATUS current
    DESCRIPTION
        "Parameter 'message' in event AAA.1"
    ::= { aaaEventObjects1 1 }

aaaEventObjects2 OBJECT-IDENTITY
    STATUS current
    DESCRIPTION
        "Event AAA.2
        Generic usual internal error message."
    ::= { aaaEventsGroup 2 }

aaa2-message OBJECT-TYPE
    SYNTAX DisplayString
    MAX-ACCESS accessible-for-notify
    STATUS current
    DESCRIPTION
        "Parameter 'message' in event AAA.2"
    ::= { aaaEventObjects2 1 }

aaaEventObjects3 OBJECT-IDENTITY
    STATUS current
    DESCRIPTION
        "Event AAA.3
        Generic abnormal external error message."
    ::= { aaaEventsGroup 3 }

aaa3-message OBJECT-TYPE
    SYNTAX DisplayString
    MAX-ACCESS accessible-for-notify
    STATUS current
    DESCRIPTION
        "Parameter 'message' in event AAA.3"
    ::= { aaaEventObjects3 1 }

aaaEventObjects4 OBJECT-IDENTITY
    STATUS current
    DESCRIPTION
        "Event AAA.4
        Generic usual external error message."
    ::= { aaaEventsGroup 4 }

aaa4-message OBJECT-TYPE
    SYNTAX DisplayString
    MAX-ACCESS accessible-for-notify
    STATUS current
    DESCRIPTION
        "Parameter 'message' in event AAA.4"
    ::= { aaaEventObjects4 1 }

aaaEventObjects5 OBJECT-IDENTITY
    STATUS current
    DESCRIPTION
        "Event AAA.5
        Generic comment on abnormal information message."
    ::= { aaaEventsGroup 5 }

aaa5-message OBJECT-TYPE
    SYNTAX DisplayString
    MAX-ACCESS accessible-for-notify
    STATUS current
    DESCRIPTION
        "Parameter 'message' in event AAA.5"
    ::= { aaaEventObjects5 1 }

aaaEventObjects6 OBJECT-IDENTITY
    STATUS current
    DESCRIPTION
        "Event AAA.6
        Generic comment on usual information message."
    ::= { aaaEventsGroup 6 }

aaa6-message OBJECT-TYPE
    SYNTAX DisplayString
    MAX-ACCESS accessible-for-notify
    STATUS current
    DESCRIPTION
        "Parameter 'message' in event AAA.6"
    ::= { aaaEventObjects6 1 }

aaaEventObjects7 OBJECT-IDENTITY
    STATUS current
    DESCRIPTION
        "Event AAA.7
        Generic packet trace message."
    ::= { aaaEventsGroup 7 }

aaa7-message OBJECT-TYPE
    SYNTAX DisplayString
    MAX-ACCESS accessible-for-notify
    STATUS current
    DESCRIPTION
        "Parameter 'message' in event AAA.7"
    ::= { aaaEventObjects7 1 }

aaaEventObjects8 OBJECT-IDENTITY
    STATUS current
    DESCRIPTION
        "Event AAA.8
        Generic abnormal operation trace message."
    ::= { aaaEventsGroup 8 }

aaa8-message OBJECT-TYPE
    SYNTAX DisplayString
    MAX-ACCESS accessible-for-notify
    STATUS current
    DESCRIPTION
        "Parameter 'message' in event AAA.8"
    ::= { aaaEventObjects8 1 }

aaaEventObjects9 OBJECT-IDENTITY
    STATUS current
    DESCRIPTION
        "Event AAA.9
        Generic usual operation trace message."
    ::= { aaaEventsGroup 9 }

aaa9-message OBJECT-TYPE
    SYNTAX DisplayString
    MAX-ACCESS accessible-for-notify
    STATUS current
    DESCRIPTION
        "Parameter 'message' in event AAA.9"
    ::= { aaaEventObjects9 1 }

aaaEventObjects10 OBJECT-IDENTITY
    STATUS current
    DESCRIPTION
        "Event AAA.10
        The generic event level is wrong."
    ::= { aaaEventsGroup 10 }

aaa10-event-level OBJECT-TYPE
    SYNTAX Integer32
    MAX-ACCESS accessible-for-notify
    STATUS current
    DESCRIPTION
        "Parameter 'event-level' in event AAA.10"
    ::= { aaaEventObjects10 1 }

aaa10-message OBJECT-TYPE
    SYNTAX DisplayString
    MAX-ACCESS accessible-for-notify
    STATUS current
    DESCRIPTION
        "Parameter 'message' in event AAA.10"
    ::= { aaaEventObjects10 2 }

aaaEventObjects11 OBJECT-IDENTITY
    STATUS current
    DESCRIPTION
        "Event AAA.11
        AAA authentication has been initilized by the specified service"
    ::= { aaaEventsGroup 11 }

aaa11-module OBJECT-TYPE
    SYNTAX DisplayString
    MAX-ACCESS accessible-for-notify
    STATUS current
    DESCRIPTION
        "Parameter 'module' in event AAA.11"
    ::= { aaaEventObjects11 1 }

aaa11-service OBJECT-TYPE
    SYNTAX DisplayString
    MAX-ACCESS accessible-for-notify
    STATUS current
    DESCRIPTION
        "Parameter 'service' in event AAA.11"
    ::= { aaaEventObjects11 2 }

aaa11-privLvl OBJECT-TYPE
    SYNTAX DisplayString
    MAX-ACCESS accessible-for-notify
    STATUS current
    DESCRIPTION
        "Parameter 'privLvl' in event AAA.11"
    ::= { aaaEventObjects11 3 }

aaaEventObjects12 OBJECT-IDENTITY
    STATUS current
    DESCRIPTION
        "Event AAA.12
        We are looking for the method with number methodNumber."
    ::= { aaaEventsGroup 12 }

aaa12-methodNumber OBJECT-TYPE
    SYNTAX Integer32
    MAX-ACCESS accessible-for-notify
    STATUS current
    DESCRIPTION
        "Parameter 'methodNumber' in event AAA.12"
    ::= { aaaEventObjects12 1 }

aaa12-service OBJECT-TYPE
    SYNTAX DisplayString
    MAX-ACCESS accessible-for-notify
    STATUS current
    DESCRIPTION
        "Parameter 'service' in event AAA.12"
    ::= { aaaEventObjects12 2 }

aaa12-module OBJECT-TYPE
    SYNTAX DisplayString
    MAX-ACCESS accessible-for-notify
    STATUS current
    DESCRIPTION
        "Parameter 'module' in event AAA.12"
    ::= { aaaEventObjects12 3 }

aaa12-privLvl OBJECT-TYPE
    SYNTAX DisplayString
    MAX-ACCESS accessible-for-notify
    STATUS current
    DESCRIPTION
        "Parameter 'privLvl' in event AAA.12"
    ::= { aaaEventObjects12 4 }

aaaEventObjects13 OBJECT-IDENTITY
    STATUS current
    DESCRIPTION
        "Event AAA.13
        The specified service has not got associated methods list."
    ::= { aaaEventsGroup 13 }

aaa13-service OBJECT-TYPE
    SYNTAX DisplayString
    MAX-ACCESS accessible-for-notify
    STATUS current
    DESCRIPTION
        "Parameter 'service' in event AAA.13"
    ::= { aaaEventObjects13 1 }

aaa13-module OBJECT-TYPE
    SYNTAX DisplayString
    MAX-ACCESS accessible-for-notify
    STATUS current
    DESCRIPTION
        "Parameter 'module' in event AAA.13"
    ::= { aaaEventObjects13 2 }

aaa13-privLvl OBJECT-TYPE
    SYNTAX DisplayString
    MAX-ACCESS accessible-for-notify
    STATUS current
    DESCRIPTION
        "Parameter 'privLvl' in event AAA.13"
    ::= { aaaEventObjects13 3 }

aaa13-default OBJECT-TYPE
    SYNTAX DisplayString
    MAX-ACCESS accessible-for-notify
    STATUS current
    DESCRIPTION
        "Parameter 'default' in event AAA.13"
    ::= { aaaEventObjects13 4 }

aaaEventObjects14 OBJECT-IDENTITY
    STATUS current
    DESCRIPTION
        "Event AAA.14
        The specified service has got an associated methods list."
    ::= { aaaEventsGroup 14 }

aaa14-methodsList OBJECT-TYPE
    SYNTAX DisplayString
    MAX-ACCESS accessible-for-notify
    STATUS current
    DESCRIPTION
        "Parameter 'methodsList' in event AAA.14"
    ::= { aaaEventObjects14 1 }

aaa14-service OBJECT-TYPE
    SYNTAX DisplayString
    MAX-ACCESS accessible-for-notify
    STATUS current
    DESCRIPTION
        "Parameter 'service' in event AAA.14"
    ::= { aaaEventObjects14 2 }

aaa14-module OBJECT-TYPE
    SYNTAX DisplayString
    MAX-ACCESS accessible-for-notify
    STATUS current
    DESCRIPTION
        "Parameter 'module' in event AAA.14"
    ::= { aaaEventObjects14 3 }

aaa14-privLvl OBJECT-TYPE
    SYNTAX DisplayString
    MAX-ACCESS accessible-for-notify
    STATUS current
    DESCRIPTION
        "Parameter 'privLvl' in event AAA.14"
    ::= { aaaEventObjects14 4 }

aaaEventObjects15 OBJECT-IDENTITY
    STATUS current
    DESCRIPTION
        "Event AAA.15
        The specified Methods list doesn't exist."
    ::= { aaaEventsGroup 15 }

aaa15-methodsList OBJECT-TYPE
    SYNTAX DisplayString
    MAX-ACCESS accessible-for-notify
    STATUS current
    DESCRIPTION
        "Parameter 'methodsList' in event AAA.15"
    ::= { aaaEventObjects15 1 }

aaaEventObjects16 OBJECT-IDENTITY
    STATUS current
    DESCRIPTION
        "Event AAA.16
        The specified Methods list exists."
    ::= { aaaEventsGroup 16 }

aaa16-methodsList OBJECT-TYPE
    SYNTAX DisplayString
    MAX-ACCESS accessible-for-notify
    STATUS current
    DESCRIPTION
        "Parameter 'methodsList' in event AAA.16"
    ::= { aaaEventObjects16 1 }

aaaEventObjects17 OBJECT-IDENTITY
    STATUS current
    DESCRIPTION
        "Event AAA.17
        Found the specified servers group."
    ::= { aaaEventsGroup 17 }

aaa17-groupName OBJECT-TYPE
    SYNTAX DisplayString
    MAX-ACCESS accessible-for-notify
    STATUS current
    DESCRIPTION
        "Parameter 'groupName' in event AAA.17"
    ::= { aaaEventObjects17 1 }

aaa17-numberOfServers OBJECT-TYPE
    SYNTAX Integer32
    MAX-ACCESS accessible-for-notify
    STATUS current
    DESCRIPTION
        "Parameter 'numberOfServers' in event AAA.17"
    ::= { aaaEventObjects17 2 }

aaaEventObjects18 OBJECT-IDENTITY
    STATUS current
    DESCRIPTION
        "Event AAA.18
        The specified server ID doesn't exist."
    ::= { aaaEventsGroup 18 }

aaa18-serverID OBJECT-TYPE
    SYNTAX DisplayString
    MAX-ACCESS accessible-for-notify
    STATUS current
    DESCRIPTION
        "Parameter 'serverID' in event AAA.18"
    ::= { aaaEventObjects18 1 }

aaaEventObjects19 OBJECT-IDENTITY
    STATUS current
    DESCRIPTION
        "Event AAA.19
        Found a method."
    ::= { aaaEventsGroup 19 }

aaa19-methodType OBJECT-TYPE
    SYNTAX DisplayString
    MAX-ACCESS accessible-for-notify
    STATUS current
    DESCRIPTION
        "Parameter 'methodType' in event AAA.19"
    ::= { aaaEventObjects19 1 }

aaa19-methodsList OBJECT-TYPE
    SYNTAX DisplayString
    MAX-ACCESS accessible-for-notify
    STATUS current
    DESCRIPTION
        "Parameter 'methodsList' in event AAA.19"
    ::= { aaaEventObjects19 2 }

aaaEventObjects20 OBJECT-IDENTITY
    STATUS current
    DESCRIPTION
        "Event AAA.20
        Showing a method."
    ::= { aaaEventsGroup 20 }

aaa20-methodType OBJECT-TYPE
    SYNTAX DisplayString
    MAX-ACCESS accessible-for-notify
    STATUS current
    DESCRIPTION
        "Parameter 'methodType' in event AAA.20"
    ::= { aaaEventObjects20 1 }

aaa20-serverInfo OBJECT-TYPE
    SYNTAX DisplayString
    MAX-ACCESS accessible-for-notify
    STATUS current
    DESCRIPTION
        "Parameter 'serverInfo' in event AAA.20"
    ::= { aaaEventObjects20 2 }

aaaEventObjects21 OBJECT-IDENTITY
    STATUS current
    DESCRIPTION
        "Event AAA.21
        The required method not found for this service."
    ::= { aaaEventsGroup 21 }

aaa21-methodNumber OBJECT-TYPE
    SYNTAX Integer32
    MAX-ACCESS accessible-for-notify
    STATUS current
    DESCRIPTION
        "Parameter 'methodNumber' in event AAA.21"
    ::= { aaaEventObjects21 1 }

aaa21-service OBJECT-TYPE
    SYNTAX DisplayString
    MAX-ACCESS accessible-for-notify
    STATUS current
    DESCRIPTION
        "Parameter 'service' in event AAA.21"
    ::= { aaaEventObjects21 2 }

aaa21-module OBJECT-TYPE
    SYNTAX DisplayString
    MAX-ACCESS accessible-for-notify
    STATUS current
    DESCRIPTION
        "Parameter 'module' in event AAA.21"
    ::= { aaaEventObjects21 3 }

aaa21-privLvl OBJECT-TYPE
    SYNTAX DisplayString
    MAX-ACCESS accessible-for-notify
    STATUS current
    DESCRIPTION
        "Parameter 'privLvl' in event AAA.21"
    ::= { aaaEventObjects21 4 }

aaaEventObjects22 OBJECT-IDENTITY
    STATUS current
    DESCRIPTION
        "Event AAA.22
        The specified service is not configured to use the module."
    ::= { aaaEventsGroup 22 }

aaa22-service OBJECT-TYPE
    SYNTAX DisplayString
    MAX-ACCESS accessible-for-notify
    STATUS current
    DESCRIPTION
        "Parameter 'service' in event AAA.22"
    ::= { aaaEventObjects22 1 }

aaa22-module OBJECT-TYPE
    SYNTAX DisplayString
    MAX-ACCESS accessible-for-notify
    STATUS current
    DESCRIPTION
        "Parameter 'module' in event AAA.22"
    ::= { aaaEventObjects22 2 }

aaa22-privLvl OBJECT-TYPE
    SYNTAX DisplayString
    MAX-ACCESS accessible-for-notify
    STATUS current
    DESCRIPTION
        "Parameter 'privLvl' in event AAA.22"
    ::= { aaaEventObjects22 3 }

aaaEventObjects24 OBJECT-IDENTITY
    STATUS current
    DESCRIPTION
        "Event AAA.24
        A user logged in successfully via specified protocol (console, telnet,
        ssh, etc.)"
    ::= { aaaEventsGroup 24 }

aaa24-protocol OBJECT-TYPE
    SYNTAX DisplayString
    MAX-ACCESS accessible-for-notify
    STATUS current
    DESCRIPTION
        "Parameter 'protocol' in event AAA.24"
    ::= { aaaEventObjects24 1 }

aaa24-user-name OBJECT-TYPE
    SYNTAX DisplayString
    MAX-ACCESS accessible-for-notify
    STATUS current
    DESCRIPTION
        "Parameter 'user-name' in event AAA.24"
    ::= { aaaEventObjects24 2 }

aaa24-source-id OBJECT-TYPE
    SYNTAX DisplayString
    MAX-ACCESS accessible-for-notify
    STATUS current
    DESCRIPTION
        "Parameter 'source-id' in event AAA.24"
    ::= { aaaEventObjects24 3 }

aaaEventObjects25 OBJECT-IDENTITY
    STATUS current
    DESCRIPTION
        "Event AAA.25
        A user login attempt failed via specified protocol (console, telnet,
        ssh, etc.)"
    ::= { aaaEventsGroup 25 }

aaa25-protocol OBJECT-TYPE
    SYNTAX DisplayString
    MAX-ACCESS accessible-for-notify
    STATUS current
    DESCRIPTION
        "Parameter 'protocol' in event AAA.25"
    ::= { aaaEventObjects25 1 }

aaa25-user-name OBJECT-TYPE
    SYNTAX DisplayString
    MAX-ACCESS accessible-for-notify
    STATUS current
    DESCRIPTION
        "Parameter 'user-name' in event AAA.25"
    ::= { aaaEventObjects25 2 }

aaa25-source-id OBJECT-TYPE
    SYNTAX DisplayString
    MAX-ACCESS accessible-for-notify
    STATUS current
    DESCRIPTION
        "Parameter 'source-id' in event AAA.25"
    ::= { aaaEventObjects25 3 }

aaaEventObjects26 OBJECT-IDENTITY
    STATUS current
    DESCRIPTION
        "Event AAA.26
        The process for this module was successful"
    ::= { aaaEventsGroup 26 }

aaa26-service OBJECT-TYPE
    SYNTAX DisplayString
    MAX-ACCESS accessible-for-notify
    STATUS current
    DESCRIPTION
        "Parameter 'service' in event AAA.26"
    ::= { aaaEventObjects26 1 }

aaa26-module OBJECT-TYPE
    SYNTAX DisplayString
    MAX-ACCESS accessible-for-notify
    STATUS current
    DESCRIPTION
        "Parameter 'module' in event AAA.26"
    ::= { aaaEventObjects26 2 }

aaa26-privLvl OBJECT-TYPE
    SYNTAX DisplayString
    MAX-ACCESS accessible-for-notify
    STATUS current
    DESCRIPTION
        "Parameter 'privLvl' in event AAA.26"
    ::= { aaaEventObjects26 3 }

aaaEventObjects27 OBJECT-IDENTITY
    STATUS current
    DESCRIPTION
        "Event AAA.27
        The process for this module was unsuccessful"
    ::= { aaaEventsGroup 27 }

aaa27-service OBJECT-TYPE
    SYNTAX DisplayString
    MAX-ACCESS accessible-for-notify
    STATUS current
    DESCRIPTION
        "Parameter 'service' in event AAA.27"
    ::= { aaaEventObjects27 1 }

aaa27-module OBJECT-TYPE
    SYNTAX DisplayString
    MAX-ACCESS accessible-for-notify
    STATUS current
    DESCRIPTION
        "Parameter 'module' in event AAA.27"
    ::= { aaaEventObjects27 2 }

aaa27-privLvl OBJECT-TYPE
    SYNTAX DisplayString
    MAX-ACCESS accessible-for-notify
    STATUS current
    DESCRIPTION
        "Parameter 'privLvl' in event AAA.27"
    ::= { aaaEventObjects27 3 }

aaaEventObjects28 OBJECT-IDENTITY
    STATUS current
    DESCRIPTION
        "Event AAA.28
        Looking for a method in a methods list"
    ::= { aaaEventsGroup 28 }

aaa28-service1 OBJECT-TYPE
    SYNTAX DisplayString
    MAX-ACCESS accessible-for-notify
    STATUS current
    DESCRIPTION
        "Parameter 'service1' in event AAA.28"
    ::= { aaaEventObjects28 1 }

aaa28-module1 OBJECT-TYPE
    SYNTAX DisplayString
    MAX-ACCESS accessible-for-notify
    STATUS current
    DESCRIPTION
        "Parameter 'module1' in event AAA.28"
    ::= { aaaEventObjects28 2 }

aaa28-service2 OBJECT-TYPE
    SYNTAX DisplayString
    MAX-ACCESS accessible-for-notify
    STATUS current
    DESCRIPTION
        "Parameter 'service2' in event AAA.28"
    ::= { aaaEventObjects28 3 }

aaa28-module2 OBJECT-TYPE
    SYNTAX DisplayString
    MAX-ACCESS accessible-for-notify
    STATUS current
    DESCRIPTION
        "Parameter 'module2' in event AAA.28"
    ::= { aaaEventObjects28 4 }

aaaEventObjects29 OBJECT-IDENTITY
    STATUS current
    DESCRIPTION
        "Event AAA.29
        The method was found in the methods list"
    ::= { aaaEventsGroup 29 }

aaa29-service1 OBJECT-TYPE
    SYNTAX DisplayString
    MAX-ACCESS accessible-for-notify
    STATUS current
    DESCRIPTION
        "Parameter 'service1' in event AAA.29"
    ::= { aaaEventObjects29 1 }

aaa29-module1 OBJECT-TYPE
    SYNTAX DisplayString
    MAX-ACCESS accessible-for-notify
    STATUS current
    DESCRIPTION
        "Parameter 'module1' in event AAA.29"
    ::= { aaaEventObjects29 2 }

aaa29-service2 OBJECT-TYPE
    SYNTAX DisplayString
    MAX-ACCESS accessible-for-notify
    STATUS current
    DESCRIPTION
        "Parameter 'service2' in event AAA.29"
    ::= { aaaEventObjects29 3 }

aaa29-module2 OBJECT-TYPE
    SYNTAX DisplayString
    MAX-ACCESS accessible-for-notify
    STATUS current
    DESCRIPTION
        "Parameter 'module2' in event AAA.29"
    ::= { aaaEventObjects29 4 }

aaa29-position OBJECT-TYPE
    SYNTAX Integer32
    MAX-ACCESS accessible-for-notify
    STATUS current
    DESCRIPTION
        "Parameter 'position' in event AAA.29"
    ::= { aaaEventObjects29 5 }

aaaEventObjects30 OBJECT-IDENTITY
    STATUS current
    DESCRIPTION
        "Event AAA.30
        The method was not found in the methods list"
    ::= { aaaEventsGroup 30 }

aaa30-service1 OBJECT-TYPE
    SYNTAX DisplayString
    MAX-ACCESS accessible-for-notify
    STATUS current
    DESCRIPTION
        "Parameter 'service1' in event AAA.30"
    ::= { aaaEventObjects30 1 }

aaa30-module1 OBJECT-TYPE
    SYNTAX DisplayString
    MAX-ACCESS accessible-for-notify
    STATUS current
    DESCRIPTION
        "Parameter 'module1' in event AAA.30"
    ::= { aaaEventObjects30 2 }

aaa30-service2 OBJECT-TYPE
    SYNTAX DisplayString
    MAX-ACCESS accessible-for-notify
    STATUS current
    DESCRIPTION
        "Parameter 'service2' in event AAA.30"
    ::= { aaaEventObjects30 3 }

aaa30-module2 OBJECT-TYPE
    SYNTAX DisplayString
    MAX-ACCESS accessible-for-notify
    STATUS current
    DESCRIPTION
        "Parameter 'module2' in event AAA.30"
    ::= { aaaEventObjects30 4 }

aaaEventObjects31 OBJECT-IDENTITY
    STATUS current
    DESCRIPTION
        "Event AAA.31
        There isn't method used"
    ::= { aaaEventsGroup 31 }

aaa31-service1 OBJECT-TYPE
    SYNTAX DisplayString
    MAX-ACCESS accessible-for-notify
    STATUS current
    DESCRIPTION
        "Parameter 'service1' in event AAA.31"
    ::= { aaaEventObjects31 1 }

aaa31-module1 OBJECT-TYPE
    SYNTAX DisplayString
    MAX-ACCESS accessible-for-notify
    STATUS current
    DESCRIPTION
        "Parameter 'module1' in event AAA.31"
    ::= { aaaEventObjects31 2 }

aaa31-service2 OBJECT-TYPE
    SYNTAX DisplayString
    MAX-ACCESS accessible-for-notify
    STATUS current
    DESCRIPTION
        "Parameter 'service2' in event AAA.31"
    ::= { aaaEventObjects31 3 }

aaa31-module2 OBJECT-TYPE
    SYNTAX DisplayString
    MAX-ACCESS accessible-for-notify
    STATUS current
    DESCRIPTION
        "Parameter 'module2' in event AAA.31"
    ::= { aaaEventObjects31 4 }

aaaEventObjects32 OBJECT-IDENTITY
    STATUS current
    DESCRIPTION
        "Event AAA.32
        The attribute has been established"
    ::= { aaaEventsGroup 32 }

aaa32-attribute OBJECT-TYPE
    SYNTAX DisplayString
    MAX-ACCESS accessible-for-notify
    STATUS current
    DESCRIPTION
        "Parameter 'attribute' in event AAA.32"
    ::= { aaaEventObjects32 1 }

aaa32-service OBJECT-TYPE
    SYNTAX DisplayString
    MAX-ACCESS accessible-for-notify
    STATUS current
    DESCRIPTION
        "Parameter 'service' in event AAA.32"
    ::= { aaaEventObjects32 2 }

aaaEventObjects33 OBJECT-IDENTITY
    STATUS current
    DESCRIPTION
        "Event AAA.33
        The attribute couldn't be established"
    ::= { aaaEventsGroup 33 }

aaa33-attribute OBJECT-TYPE
    SYNTAX DisplayString
    MAX-ACCESS accessible-for-notify
    STATUS current
    DESCRIPTION
        "Parameter 'attribute' in event AAA.33"
    ::= { aaaEventObjects33 1 }

aaa33-service OBJECT-TYPE
    SYNTAX DisplayString
    MAX-ACCESS accessible-for-notify
    STATUS current
    DESCRIPTION
        "Parameter 'service' in event AAA.33"
    ::= { aaaEventObjects33 2 }

aaaEventObjects34 OBJECT-IDENTITY
    STATUS current
    DESCRIPTION
        "Event AAA.34
        The AVP value is wrong"
    ::= { aaaEventsGroup 34 }

aaa34-value OBJECT-TYPE
    SYNTAX DisplayString
    MAX-ACCESS accessible-for-notify
    STATUS current
    DESCRIPTION
        "Parameter 'value' in event AAA.34"
    ::= { aaaEventObjects34 1 }

aaa34-attribute OBJECT-TYPE
    SYNTAX DisplayString
    MAX-ACCESS accessible-for-notify
    STATUS current
    DESCRIPTION
        "Parameter 'attribute' in event AAA.34"
    ::= { aaaEventObjects34 2 }

aaaEventObjects35 OBJECT-IDENTITY
    STATUS current
    DESCRIPTION
        "Event AAA.35
        There's no local function defined for the service"
    ::= { aaaEventsGroup 35 }

aaa35-service OBJECT-TYPE
    SYNTAX DisplayString
    MAX-ACCESS accessible-for-notify
    STATUS current
    DESCRIPTION
        "Parameter 'service' in event AAA.35"
    ::= { aaaEventObjects35 1 }

aaa35-module OBJECT-TYPE
    SYNTAX DisplayString
    MAX-ACCESS accessible-for-notify
    STATUS current
    DESCRIPTION
        "Parameter 'module' in event AAA.35"
    ::= { aaaEventObjects35 2 }

aaaEventObjects36 OBJECT-IDENTITY
    STATUS current
    DESCRIPTION
        "Event AAA.36
        The specified server is not responding"
    ::= { aaaEventsGroup 36 }

aaa36-sever OBJECT-TYPE
    SYNTAX IpAddress
    MAX-ACCESS accessible-for-notify
    STATUS current
    DESCRIPTION
        "Parameter 'sever' in event AAA.36"
    ::= { aaaEventObjects36 1 }

aaa36-port OBJECT-TYPE
    SYNTAX Integer32
    MAX-ACCESS accessible-for-notify
    STATUS current
    DESCRIPTION
        "Parameter 'port' in event AAA.36"
    ::= { aaaEventObjects36 2 }

aaaEventObjects38 OBJECT-IDENTITY
    STATUS current
    DESCRIPTION
        "Event AAA.38
        Accounting request has been received from the accounting dispatcher queue"
    ::= { aaaEventsGroup 38 }

aaa38-request-type OBJECT-TYPE
    SYNTAX DisplayString
    MAX-ACCESS accessible-for-notify
    STATUS current
    DESCRIPTION
        "Parameter 'request-type' in event AAA.38"
    ::= { aaaEventObjects38 1 }

aaaEventObjects39 OBJECT-IDENTITY
    STATUS current
    DESCRIPTION
        "Event AAA.39
        Accounting dispatcher task not created. Request could not be sent"
    ::= { aaaEventsGroup 39 }

aaa39-state OBJECT-TYPE
    SYNTAX DisplayString
    MAX-ACCESS accessible-for-notify
    STATUS current
    DESCRIPTION
        "Parameter 'state' in event AAA.39"
    ::= { aaaEventObjects39 1 }

aaa39-type OBJECT-TYPE
    SYNTAX DisplayString
    MAX-ACCESS accessible-for-notify
    STATUS current
    DESCRIPTION
        "Parameter 'type' in event AAA.39"
    ::= { aaaEventObjects39 2 }

aaaEventObjects40 OBJECT-IDENTITY
    STATUS current
    DESCRIPTION
        "Event AAA.40
        Accounting request has been sent to the accounting dispatcher queue"
    ::= { aaaEventsGroup 40 }

aaa40-type OBJECT-TYPE
    SYNTAX DisplayString
    MAX-ACCESS accessible-for-notify
    STATUS current
    DESCRIPTION
        "Parameter 'type' in event AAA.40"
    ::= { aaaEventObjects40 1 }

aaaEventObjects41 OBJECT-IDENTITY
    STATUS current
    DESCRIPTION
        "Event AAA.41
        Accounting dispatcher task has been created"
    ::= { aaaEventsGroup 41 }

aaa41-ptr OBJECT-TYPE
    SYNTAX Integer32
    MAX-ACCESS accessible-for-notify
    STATUS current
    DESCRIPTION
        "Parameter 'ptr' in event AAA.41"
    ::= { aaaEventObjects41 1 }

aaaEventObjects42 OBJECT-IDENTITY
    STATUS current
    DESCRIPTION
        "Event AAA.42
        Current configuration has blocked the request"
    ::= { aaaEventsGroup 42 }

aaa42-service OBJECT-TYPE
    SYNTAX DisplayString
    MAX-ACCESS accessible-for-notify
    STATUS current
    DESCRIPTION
        "Parameter 'service' in event AAA.42"
    ::= { aaaEventObjects42 1 }

aaa42-module OBJECT-TYPE
    SYNTAX DisplayString
    MAX-ACCESS accessible-for-notify
    STATUS current
    DESCRIPTION
        "Parameter 'module' in event AAA.42"
    ::= { aaaEventObjects42 2 }

aaa42-action OBJECT-TYPE
    SYNTAX DisplayString
    MAX-ACCESS accessible-for-notify
    STATUS current
    DESCRIPTION
        "Parameter 'action' in event AAA.42"
    ::= { aaaEventObjects42 3 }

aaaEventObjects43 OBJECT-IDENTITY
    STATUS current
    DESCRIPTION
        "Event AAA.43
        The accounting request has been queued"
    ::= { aaaEventsGroup 43 }

aaa43-service OBJECT-TYPE
    SYNTAX DisplayString
    MAX-ACCESS accessible-for-notify
    STATUS current
    DESCRIPTION
        "Parameter 'service' in event AAA.43"
    ::= { aaaEventObjects43 1 }

aaa43-module OBJECT-TYPE
    SYNTAX DisplayString
    MAX-ACCESS accessible-for-notify
    STATUS current
    DESCRIPTION
        "Parameter 'module' in event AAA.43"
    ::= { aaaEventObjects43 2 }

aaa43-action OBJECT-TYPE
    SYNTAX DisplayString
    MAX-ACCESS accessible-for-notify
    STATUS current
    DESCRIPTION
        "Parameter 'action' in event AAA.43"
    ::= { aaaEventObjects43 3 }

aaa43-id OBJECT-TYPE
    SYNTAX Integer32
    MAX-ACCESS accessible-for-notify
    STATUS current
    DESCRIPTION
        "Parameter 'id' in event AAA.43"
    ::= { aaaEventObjects43 4 }

aaa43-userName OBJECT-TYPE
    SYNTAX DisplayString
    MAX-ACCESS accessible-for-notify
    STATUS current
    DESCRIPTION
        "Parameter 'userName' in event AAA.43"
    ::= { aaaEventObjects43 5 }

aaa43-port OBJECT-TYPE
    SYNTAX DisplayString
    MAX-ACCESS accessible-for-notify
    STATUS current
    DESCRIPTION
        "Parameter 'port' in event AAA.43"
    ::= { aaaEventObjects43 6 }

aaa43-remoteAddr OBJECT-TYPE
    SYNTAX DisplayString
    MAX-ACCESS accessible-for-notify
    STATUS current
    DESCRIPTION
        "Parameter 'remoteAddr' in event AAA.43"
    ::= { aaaEventObjects43 7 }

aaaEventObjects44 OBJECT-IDENTITY
    STATUS current
    DESCRIPTION
        "Event AAA.44
        The accounting request has been queued"
    ::= { aaaEventsGroup 44 }

aaa44-service OBJECT-TYPE
    SYNTAX DisplayString
    MAX-ACCESS accessible-for-notify
    STATUS current
    DESCRIPTION
        "Parameter 'service' in event AAA.44"
    ::= { aaaEventObjects44 1 }

aaa44-module OBJECT-TYPE
    SYNTAX DisplayString
    MAX-ACCESS accessible-for-notify
    STATUS current
    DESCRIPTION
        "Parameter 'module' in event AAA.44"
    ::= { aaaEventObjects44 2 }

aaa44-action OBJECT-TYPE
    SYNTAX DisplayString
    MAX-ACCESS accessible-for-notify
    STATUS current
    DESCRIPTION
        "Parameter 'action' in event AAA.44"
    ::= { aaaEventObjects44 3 }

aaa44-id OBJECT-TYPE
    SYNTAX Integer32
    MAX-ACCESS accessible-for-notify
    STATUS current
    DESCRIPTION
        "Parameter 'id' in event AAA.44"
    ::= { aaaEventObjects44 4 }

aaa44-avpNumber OBJECT-TYPE
    SYNTAX Integer32
    MAX-ACCESS accessible-for-notify
    STATUS current
    DESCRIPTION
        "Parameter 'avpNumber' in event AAA.44"
    ::= { aaaEventObjects44 5 }

aaa44-avpString OBJECT-TYPE
    SYNTAX DisplayString
    MAX-ACCESS accessible-for-notify
    STATUS current
    DESCRIPTION
        "Parameter 'avpString' in event AAA.44"
    ::= { aaaEventObjects44 6 }

aaaEventObjects45 OBJECT-IDENTITY
    STATUS current
    DESCRIPTION
        "Event AAA.45
        The accounting dispatcher is ready, it is waiting for requests"
    ::= { aaaEventsGroup 45 }

aaa45-ptr OBJECT-TYPE
    SYNTAX Integer32
    MAX-ACCESS accessible-for-notify
    STATUS current
    DESCRIPTION
        "Parameter 'ptr' in event AAA.45"
    ::= { aaaEventObjects45 1 }

aaaEventObjects46 OBJECT-IDENTITY
    STATUS current
    DESCRIPTION
        "Event AAA.46
        Accounting request could not be sent"
    ::= { aaaEventsGroup 46 }

aaa46-reason OBJECT-TYPE
    SYNTAX DisplayString
    MAX-ACCESS accessible-for-notify
    STATUS current
    DESCRIPTION
        "Parameter 'reason' in event AAA.46"
    ::= { aaaEventObjects46 1 }

aaaEventObjects48 OBJECT-IDENTITY
    STATUS current
    DESCRIPTION
        "Event AAA.48
        The path of the command will be used"
    ::= { aaaEventsGroup 48 }

aaa48-service OBJECT-TYPE
    SYNTAX DisplayString
    MAX-ACCESS accessible-for-notify
    STATUS current
    DESCRIPTION
        "Parameter 'service' in event AAA.48"
    ::= { aaaEventObjects48 1 }

aaa48-module OBJECT-TYPE
    SYNTAX DisplayString
    MAX-ACCESS accessible-for-notify
    STATUS current
    DESCRIPTION
        "Parameter 'module' in event AAA.48"
    ::= { aaaEventObjects48 2 }


aaaNotification1 NOTIFICATION-TYPE
    OBJECTS { 
              aaa1-message 
            }
    STATUS current
    DESCRIPTION
        "Notification of Event AAA.1

        Message: '$1'

        Parameters list:
              $1: aaa1-message

        Generic abnormal internal error message."
    ::= { aaaNotificationsPrefix 1 }

aaaNotification2 NOTIFICATION-TYPE
    OBJECTS { 
              aaa2-message 
            }
    STATUS current
    DESCRIPTION
        "Notification of Event AAA.2

        Message: '$1'

        Parameters list:
              $1: aaa2-message

        Generic usual internal error message."
    ::= { aaaNotificationsPrefix 2 }

aaaNotification3 NOTIFICATION-TYPE
    OBJECTS { 
              aaa3-message 
            }
    STATUS current
    DESCRIPTION
        "Notification of Event AAA.3

        Message: '$1'

        Parameters list:
              $1: aaa3-message

        Generic abnormal external error message."
    ::= { aaaNotificationsPrefix 3 }

aaaNotification4 NOTIFICATION-TYPE
    OBJECTS { 
              aaa4-message 
            }
    STATUS current
    DESCRIPTION
        "Notification of Event AAA.4

        Message: '$1'

        Parameters list:
              $1: aaa4-message

        Generic usual external error message."
    ::= { aaaNotificationsPrefix 4 }

aaaNotification5 NOTIFICATION-TYPE
    OBJECTS { 
              aaa5-message 
            }
    STATUS current
    DESCRIPTION
        "Notification of Event AAA.5

        Message: '$1'

        Parameters list:
              $1: aaa5-message

        Generic comment on abnormal information message."
    ::= { aaaNotificationsPrefix 5 }

aaaNotification6 NOTIFICATION-TYPE
    OBJECTS { 
              aaa6-message 
            }
    STATUS current
    DESCRIPTION
        "Notification of Event AAA.6

        Message: '$1'

        Parameters list:
              $1: aaa6-message

        Generic comment on usual information message."
    ::= { aaaNotificationsPrefix 6 }

aaaNotification7 NOTIFICATION-TYPE
    OBJECTS { 
              aaa7-message 
            }
    STATUS current
    DESCRIPTION
        "Notification of Event AAA.7

        Message: '$1'

        Parameters list:
              $1: aaa7-message

        Generic packet trace message."
    ::= { aaaNotificationsPrefix 7 }

aaaNotification8 NOTIFICATION-TYPE
    OBJECTS { 
              aaa8-message 
            }
    STATUS current
    DESCRIPTION
        "Notification of Event AAA.8

        Message: '$1'

        Parameters list:
              $1: aaa8-message

        Generic abnormal operation trace message."
    ::= { aaaNotificationsPrefix 8 }

aaaNotification9 NOTIFICATION-TYPE
    OBJECTS { 
              aaa9-message 
            }
    STATUS current
    DESCRIPTION
        "Notification of Event AAA.9

        Message: '$1'

        Parameters list:
              $1: aaa9-message

        Generic usual operation trace message."
    ::= { aaaNotificationsPrefix 9 }

aaaNotification10 NOTIFICATION-TYPE
    OBJECTS { 
              aaa10-event-level, 
              aaa10-message 
            }
    STATUS current
    DESCRIPTION
        "Notification of Event AAA.10

        Message: 'Bad generic event level ($1) ($2)'

        Parameters list:
              $1: aaa10-event-level
              $2: aaa10-message

        The generic event level is wrong."
    ::= { aaaNotificationsPrefix 10 }

aaaNotification11 NOTIFICATION-TYPE
    OBJECTS { 
              aaa11-module, 
              aaa11-service,
              aaa11-privLvl 
            }
    STATUS current
    DESCRIPTION
        "Notification of Event AAA.11

        Message: 'Module '$1' initialized from '$2', level $3'

        Parameters list:
              $1: aaa11-module
              $2: aaa11-service
              $3: aaa11-privLvl

        AAA authentication has been initilized by the specified service"
    ::= { aaaNotificationsPrefix 11 }

aaaNotification12 NOTIFICATION-TYPE
    OBJECTS { 
              aaa12-methodNumber, 
              aaa12-service,
              aaa12-module,
              aaa12-privLvl 
            }
    STATUS current
    DESCRIPTION
        "Notification of Event AAA.12

        Message: 'Looking for method $1 for '$2 $3' level $4'

        Parameters list:
              $1: aaa12-methodNumber
              $2: aaa12-service
              $3: aaa12-module
              $4: aaa12-privLvl

        We are looking for the method with number methodNumber."
    ::= { aaaNotificationsPrefix 12 }

aaaNotification13 NOTIFICATION-TYPE
    OBJECTS { 
              aaa13-service, 
              aaa13-module,
              aaa13-privLvl,
              aaa13-default 
            }
    STATUS current
    DESCRIPTION
        "Notification of Event AAA.13

        Message: 'No methods list associated with '$1 $2' level $3. Using '$4''

        Parameters list:
              $1: aaa13-service
              $2: aaa13-module
              $3: aaa13-privLvl
              $4: aaa13-default

        The specified service has not got associated methods list."
    ::= { aaaNotificationsPrefix 13 }

aaaNotification14 NOTIFICATION-TYPE
    OBJECTS { 
              aaa14-methodsList, 
              aaa14-service,
              aaa14-module,
              aaa14-privLvl 
            }
    STATUS current
    DESCRIPTION
        "Notification of Event AAA.14

        Message: 'Methods list '$1' associated with '$2 $3' level $4'

        Parameters list:
              $1: aaa14-methodsList
              $2: aaa14-service
              $3: aaa14-module
              $4: aaa14-privLvl

        The specified service has got an associated methods list."
    ::= { aaaNotificationsPrefix 14 }

aaaNotification15 NOTIFICATION-TYPE
    OBJECTS { 
              aaa15-methodsList 
            }
    STATUS current
    DESCRIPTION
        "Notification of Event AAA.15

        Message: 'Methods list '$1' doesn't exist'

        Parameters list:
              $1: aaa15-methodsList

        The specified Methods list doesn't exist."
    ::= { aaaNotificationsPrefix 15 }

aaaNotification16 NOTIFICATION-TYPE
    OBJECTS { 
              aaa16-methodsList 
            }
    STATUS current
    DESCRIPTION
        "Notification of Event AAA.16

        Message: 'Found methods list '$1''

        Parameters list:
              $1: aaa16-methodsList

        The specified Methods list exists."
    ::= { aaaNotificationsPrefix 16 }

aaaNotification17 NOTIFICATION-TYPE
    OBJECTS { 
              aaa17-groupName, 
              aaa17-numberOfServers 
            }
    STATUS current
    DESCRIPTION
        "Notification of Event AAA.17

        Message: 'Found servers group '$1' with $2 server[s]'

        Parameters list:
              $1: aaa17-groupName
              $2: aaa17-numberOfServers

        Found the specified servers group."
    ::= { aaaNotificationsPrefix 17 }

aaaNotification18 NOTIFICATION-TYPE
    OBJECTS { 
              aaa18-serverID 
            }
    STATUS current
    DESCRIPTION
        "Notification of Event AAA.18

        Message: 'Server ID '$1' doesn't exist'

        Parameters list:
              $1: aaa18-serverID

        The specified server ID doesn't exist."
    ::= { aaaNotificationsPrefix 18 }

aaaNotification19 NOTIFICATION-TYPE
    OBJECTS { 
              aaa19-methodType, 
              aaa19-methodsList 
            }
    STATUS current
    DESCRIPTION
        "Notification of Event AAA.19

        Message: 'Found '$1' method in methods list '$2''

        Parameters list:
              $1: aaa19-methodType
              $2: aaa19-methodsList

        Found a method."
    ::= { aaaNotificationsPrefix 19 }

aaaNotification20 NOTIFICATION-TYPE
    OBJECTS { 
              aaa20-methodType, 
              aaa20-serverInfo 
            }
    STATUS current
    DESCRIPTION
        "Notification of Event AAA.20

        Message: 'Using method '$1' ($2)'

        Parameters list:
              $1: aaa20-methodType
              $2: aaa20-serverInfo

        Showing a method."
    ::= { aaaNotificationsPrefix 20 }

aaaNotification21 NOTIFICATION-TYPE
    OBJECTS { 
              aaa21-methodNumber, 
              aaa21-service,
              aaa21-module,
              aaa21-privLvl 
            }
    STATUS current
    DESCRIPTION
        "Notification of Event AAA.21

        Message: 'No method $1 found for '$2 $3' level $4'

        Parameters list:
              $1: aaa21-methodNumber
              $2: aaa21-service
              $3: aaa21-module
              $4: aaa21-privLvl

        The required method not found for this service."
    ::= { aaaNotificationsPrefix 21 }

aaaNotification22 NOTIFICATION-TYPE
    OBJECTS { 
              aaa22-service, 
              aaa22-module,
              aaa22-privLvl 
            }
    STATUS current
    DESCRIPTION
        "Notification of Event AAA.22

        Message: ''$1' is not configured to use '$2' level $3'

        Parameters list:
              $1: aaa22-service
              $2: aaa22-module
              $3: aaa22-privLvl

        The specified service is not configured to use the module."
    ::= { aaaNotificationsPrefix 22 }

aaaNotification23 NOTIFICATION-TYPE
    STATUS current
    DESCRIPTION
        "Notification of Event AAA.23

        Message: 'No local access restriction'

        There is no local access restriction."
    ::= { aaaNotificationsPrefix 23 }

aaaNotification24 NOTIFICATION-TYPE
    OBJECTS { 
              aaa24-protocol, 
              aaa24-user-name,
              aaa24-source-id 
            }
    STATUS current
    DESCRIPTION
        "Notification of Event AAA.24

        Message: 'Login successful via $1 user $2 from source $3'

        Parameters list:
              $1: aaa24-protocol
              $2: aaa24-user-name
              $3: aaa24-source-id

        A user logged in successfully via specified protocol (console, telnet,
        ssh, etc.)"
    ::= { aaaNotificationsPrefix 24 }

aaaNotification25 NOTIFICATION-TYPE
    OBJECTS { 
              aaa25-protocol, 
              aaa25-user-name,
              aaa25-source-id 
            }
    STATUS current
    DESCRIPTION
        "Notification of Event AAA.25

        Message: 'Login failed via $1 user $2 from source $3'

        Parameters list:
              $1: aaa25-protocol
              $2: aaa25-user-name
              $3: aaa25-source-id

        A user login attempt failed via specified protocol (console, telnet,
        ssh, etc.)"
    ::= { aaaNotificationsPrefix 25 }

aaaNotification26 NOTIFICATION-TYPE
    OBJECTS { 
              aaa26-service, 
              aaa26-module,
              aaa26-privLvl 
            }
    STATUS current
    DESCRIPTION
        "Notification of Event AAA.26

        Message: ''$1 $2' level $3: successful'

        Parameters list:
              $1: aaa26-service
              $2: aaa26-module
              $3: aaa26-privLvl

        The process for this module was successful"
    ::= { aaaNotificationsPrefix 26 }

aaaNotification27 NOTIFICATION-TYPE
    OBJECTS { 
              aaa27-service, 
              aaa27-module,
              aaa27-privLvl 
            }
    STATUS current
    DESCRIPTION
        "Notification of Event AAA.27

        Message: ''$1 $2' level $3: unsuccessful'

        Parameters list:
              $1: aaa27-service
              $2: aaa27-module
              $3: aaa27-privLvl

        The process for this module was unsuccessful"
    ::= { aaaNotificationsPrefix 27 }

aaaNotification28 NOTIFICATION-TYPE
    OBJECTS { 
              aaa28-service1, 
              aaa28-module1,
              aaa28-service2,
              aaa28-module2 
            }
    STATUS current
    DESCRIPTION
        "Notification of Event AAA.28

        Message: 'Checking if the method used in '$1 $2' is valid for '$3 $4''

        Parameters list:
              $1: aaa28-service1
              $2: aaa28-module1
              $3: aaa28-service2
              $4: aaa28-module2

        Looking for a method in a methods list"
    ::= { aaaNotificationsPrefix 28 }

aaaNotification29 NOTIFICATION-TYPE
    OBJECTS { 
              aaa29-service1, 
              aaa29-module1,
              aaa29-service2,
              aaa29-module2,
              aaa29-position 
            }
    STATUS current
    DESCRIPTION
        "Notification of Event AAA.29

        Message: 'Method used in '$1 $2' is valid for '$3 $4' (position $5)'

        Parameters list:
              $1: aaa29-service1
              $2: aaa29-module1
              $3: aaa29-service2
              $4: aaa29-module2
              $5: aaa29-position

        The method was found in the methods list"
    ::= { aaaNotificationsPrefix 29 }

aaaNotification30 NOTIFICATION-TYPE
    OBJECTS { 
              aaa30-service1, 
              aaa30-module1,
              aaa30-service2,
              aaa30-module2 
            }
    STATUS current
    DESCRIPTION
        "Notification of Event AAA.30

        Message: 'Method used in '$1 $2' doesn't exist for '$3 $4''

        Parameters list:
              $1: aaa30-service1
              $2: aaa30-module1
              $3: aaa30-service2
              $4: aaa30-module2

        The method was not found in the methods list"
    ::= { aaaNotificationsPrefix 30 }

aaaNotification31 NOTIFICATION-TYPE
    OBJECTS { 
              aaa31-service1, 
              aaa31-module1,
              aaa31-service2,
              aaa31-module2 
            }
    STATUS current
    DESCRIPTION
        "Notification of Event AAA.31

        Message: 'Method used in '$1 $2' cannot be used for '$3 $4''

        Parameters list:
              $1: aaa31-service1
              $2: aaa31-module1
              $3: aaa31-service2
              $4: aaa31-module2

        There isn't method used"
    ::= { aaaNotificationsPrefix 31 }

aaaNotification32 NOTIFICATION-TYPE
    OBJECTS { 
              aaa32-attribute, 
              aaa32-service 
            }
    STATUS current
    DESCRIPTION
        "Notification of Event AAA.32

        Message: 'Attribute '$1' has been established for '$2''

        Parameters list:
              $1: aaa32-attribute
              $2: aaa32-service

        The attribute has been established"
    ::= { aaaNotificationsPrefix 32 }

aaaNotification33 NOTIFICATION-TYPE
    OBJECTS { 
              aaa33-attribute, 
              aaa33-service 
            }
    STATUS current
    DESCRIPTION
        "Notification of Event AAA.33

        Message: 'Attribute '$1' couldn't be established for '$2''

        Parameters list:
              $1: aaa33-attribute
              $2: aaa33-service

        The attribute couldn't be established"
    ::= { aaaNotificationsPrefix 33 }

aaaNotification34 NOTIFICATION-TYPE
    OBJECTS { 
              aaa34-value, 
              aaa34-attribute 
            }
    STATUS current
    DESCRIPTION
        "Notification of Event AAA.34

        Message: 'Invalid value '$1' for attribute '$2''

        Parameters list:
              $1: aaa34-value
              $2: aaa34-attribute

        The AVP value is wrong"
    ::= { aaaNotificationsPrefix 34 }

aaaNotification35 NOTIFICATION-TYPE
    OBJECTS { 
              aaa35-service, 
              aaa35-module 
            }
    STATUS current
    DESCRIPTION
        "Notification of Event AAA.35

        Message: 'No local function defined for '$1 $2''

        Parameters list:
              $1: aaa35-service
              $2: aaa35-module

        There's no local function defined for the service"
    ::= { aaaNotificationsPrefix 35 }

aaaNotification36 NOTIFICATION-TYPE
    OBJECTS { 
              aaa36-sever, 
              aaa36-port 
            }
    STATUS current
    DESCRIPTION
        "Notification of Event AAA.36

        Message: 'Server $1:$2 is not responding'

        Parameters list:
              $1: aaa36-sever
              $2: aaa36-port

        The specified server is not responding"
    ::= { aaaNotificationsPrefix 36 }

aaaNotification37 NOTIFICATION-TYPE
    STATUS current
    DESCRIPTION
        "Notification of Event AAA.37

        Message: 'No Radius authorization request needed, using authentication request'

        No Radius authorization request needed, using the authentication request"
    ::= { aaaNotificationsPrefix 37 }

aaaNotification38 NOTIFICATION-TYPE
    OBJECTS { 
              aaa38-request-type 
            }
    STATUS current
    DESCRIPTION
        "Notification of Event AAA.38

        Message: 'Received '$1' request from accounting dispatcher queue'

        Parameters list:
              $1: aaa38-request-type

        Accounting request has been received from the accounting dispatcher queue"
    ::= { aaaNotificationsPrefix 38 }

aaaNotification39 NOTIFICATION-TYPE
    OBJECTS { 
              aaa39-state, 
              aaa39-type 
            }
    STATUS current
    DESCRIPTION
        "Notification of Event AAA.39

        Message: 'Accounting dispatcher task state: '$1'. Request '$2' could not be sent'

        Parameters list:
              $1: aaa39-state
              $2: aaa39-type

        Accounting dispatcher task not created. Request could not be sent"
    ::= { aaaNotificationsPrefix 39 }

aaaNotification40 NOTIFICATION-TYPE
    OBJECTS { 
              aaa40-type 
            }
    STATUS current
    DESCRIPTION
        "Notification of Event AAA.40

        Message: 'Request '$1' sent to accounting dispatcher queue'

        Parameters list:
              $1: aaa40-type

        Accounting request has been sent to the accounting dispatcher queue"
    ::= { aaaNotificationsPrefix 40 }

aaaNotification41 NOTIFICATION-TYPE
    OBJECTS { 
              aaa41-ptr 
            }
    STATUS current
    DESCRIPTION
        "Notification of Event AAA.41

        Message: 'Accounting dispatcher task created (0x$1)'

        Parameters list:
              $1: aaa41-ptr

        Accounting dispatcher task has been created"
    ::= { aaaNotificationsPrefix 41 }

aaaNotification42 NOTIFICATION-TYPE
    OBJECTS { 
              aaa42-service, 
              aaa42-module,
              aaa42-action 
            }
    STATUS current
    DESCRIPTION
        "Notification of Event AAA.42

        Message: 'Current configuration has blocked '$1 $2 $3' request'

        Parameters list:
              $1: aaa42-service
              $2: aaa42-module
              $3: aaa42-action

        Current configuration has blocked the request"
    ::= { aaaNotificationsPrefix 42 }

aaaNotification43 NOTIFICATION-TYPE
    OBJECTS { 
              aaa43-service, 
              aaa43-module,
              aaa43-action,
              aaa43-id,
              aaa43-userName,
              aaa43-port,
              aaa43-remoteAddr 
            }
    STATUS current
    DESCRIPTION
        "Notification of Event AAA.43

        Message: 'Queuing '$1 $2 $3' request $4 (user '$5', port '$6', rem-addr '$7')'

        Parameters list:
              $1: aaa43-service
              $2: aaa43-module
              $3: aaa43-action
              $4: aaa43-id
              $5: aaa43-userName
              $6: aaa43-port
              $7: aaa43-remoteAddr

        The accounting request has been queued"
    ::= { aaaNotificationsPrefix 43 }

aaaNotification44 NOTIFICATION-TYPE
    OBJECTS { 
              aaa44-service, 
              aaa44-module,
              aaa44-action,
              aaa44-id,
              aaa44-avpNumber,
              aaa44-avpString 
            }
    STATUS current
    DESCRIPTION
        "Notification of Event AAA.44

        Message: 'Queuing '$1 $2 $3' request $4 (AVP[$5] '$6')'

        Parameters list:
              $1: aaa44-service
              $2: aaa44-module
              $3: aaa44-action
              $4: aaa44-id
              $5: aaa44-avpNumber
              $6: aaa44-avpString

        The accounting request has been queued"
    ::= { aaaNotificationsPrefix 44 }

aaaNotification45 NOTIFICATION-TYPE
    OBJECTS { 
              aaa45-ptr 
            }
    STATUS current
    DESCRIPTION
        "Notification of Event AAA.45

        Message: 'Accounting dispatcher ready, waiting for requests (0x$1)'

        Parameters list:
              $1: aaa45-ptr

        The accounting dispatcher is ready, it is waiting for requests"
    ::= { aaaNotificationsPrefix 45 }

aaaNotification46 NOTIFICATION-TYPE
    OBJECTS { 
              aaa46-reason 
            }
    STATUS current
    DESCRIPTION
        "Notification of Event AAA.46

        Message: 'Accounting request could not be sent: $1'

        Parameters list:
              $1: aaa46-reason

        Accounting request could not be sent"
    ::= { aaaNotificationsPrefix 46 }

aaaNotification47 NOTIFICATION-TYPE
    STATUS current
    DESCRIPTION
        "Notification of Event AAA.47

        Message: 'No local authorization restriction'

        There is no local authorization restriction."
    ::= { aaaNotificationsPrefix 47 }

aaaNotification48 NOTIFICATION-TYPE
    OBJECTS { 
              aaa48-service, 
              aaa48-module 
            }
    STATUS current
    DESCRIPTION
        "Notification of Event AAA.48

        Message: ''$1 $2' will use the path of the command'

        Parameters list:
              $1: aaa48-service
              $2: aaa48-module

        The path of the command will be used"
    ::= { aaaNotificationsPrefix 48 }


END
