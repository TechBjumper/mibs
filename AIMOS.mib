--
-- AIMOS.my
-- MIB generated by MG-SOFT Visual MIB Builder 2013 Version 9.0  Build 452
-- Thursday, September 20, 2012 at 16:12:14
--

  AIMOS DEFINITIONS ::= BEGIN
 
    IMPORTS
      OBJECT-GROUP, MODULE-COMPLIANCE, NOTIFICATION-GROUP      
        FROM SNMPv2-CONF      
      zeroDotZero, mib-2, enterprises, TimeTicks, Integer32, 
      Unsigned32, OBJECT-TYPE, MODULE-IDENTITY, OBJECT-IDENTITY, NOTIFICATION-TYPE      
        FROM SNMPv2-SMI      
      DisplayString, RowPointer, TEXTUAL-CONVENTION      
        FROM SNMPv2-TC;
  
  
    aimos MODULE-IDENTITY 
      LAST-UPDATED "200207121645Z"
      ORGANIZATION 
        "Andrew Wireless Systems GmbH"
      CONTACT-INFO 
        "Name:  Michael Jelich
        Postal: Andrew Wireless Systems GmbH
                Industriering 10
                D-86675 Buchdorf
                Germany
        Phone:  +49 9099 69-0
        Fax:    +49 9099 69-140
        eMail:  WIsupport.germany@Andrew.com
                http://www.andrew.com"
      DESCRIPTION 
        "The MIB is divided into ranges with different rights of access, in order not
        to grant any person access to the entire data. The protected main part of the
        information is located in the branch aimosObjects and can be accessed only
        after an authorising of the user, called login.
        
        The areas are accessible as follows:
        . The public area aimosPublic is accessible without any restrictions.It serves
          mainly to prepare the login procedure.
        
        . aimosLogin can be accessed only with special community names generated by the
          A.I.M.O.S. SNMP Agent. Here the login takes place. This authorising takes place
          via username and password. A valid user/password combination combined with a
          community name generated by the agent is called a session after the login has
          take place. The main part of the MIB (off aimosObjects downward) is permitted
          only within a valid session.
        
        . aimosObjects contains the objects of the managed network elements. This area
          is accessible only after a successful login (that is within a valid session)
        
        . aimosNotifications contains objects, which concern the alarm notifications.
        
        . aimosGroups and aimosCompliances satisfies SNMP requirements.
        "
      REVISION "200207072130Z"
      DESCRIPTION 
        "1.0.0.0
        Release Q0215RHA"
      REVISION "200207291500Z"
      DESCRIPTION 
        "1.0.0.1
        Release Q0215RHB"
      REVISION "200302031628Z"
      DESCRIPTION 
        "1.0.0.111
        Release Q0215RHD_DRAFT
        Modifications:
        - Textual convention TruthValue replaced by Boolean
        - Modified OrgLevel enumeration
        - Right renamed to RightArea
        - aimosRoleRight renamed to aimosRoleRightArea
        - aimosOMCVersion changed to aimosOMCConnectorVersion
        - MIB-2 (1.3.6.1.2.1.1) not imported but directly implemented
        - aimosPhoneBookActive and aimosPhoneBookLastNotificationID was added
        - Format of PhonebookAddress was modified (from 6 bytes to 21 bytes) and renamed (to IPAddressAndPort)
        - aimosUserPasswordAge added
        - aimosPhoneBookActive added
        - aimosPhoneBookLastNotificationID added
        - ProbableCause: values 58 to 65 moved to 100 to 107
        - aimosAlarmLogTrapID renamed to aimosAlarmLogPhoneBookID
        - added aimosBandNetworkStandard and aimosBandName
        - aimosMasterPBKMU renamed to aimosMasterAddress
        - aimosMasterPBKOMC renamed to aimosMasterCommunicationID
        - renamed NSB to NSO
        - removed aimosMasterMaxMNP
        - last digit of the OID's of RDN, SDN, IdentNo, SerialNo, TrapInfo, Location, AnyText and MapXY changed to 2 to 9 (aimosUnitManagement)
        - added aimosSubRackV1Table
        - removed aimosNextMasterID
        - aimosMasterGUID, aimosMasterAddress, aimosMasterCommunicationID moved from aimosMasterUnitTable to aimosMasterUnitV1Table"
      REVISION "200304071523Z"
      DESCRIPTION 
        "1.0.0.113
        Release Q0215RHD_DRAFT
        Modifications:
        - added aimosAcknowledgementOID
        - added aimosShutDownDelay
        - added aimosPhoneBookAlarmListResync
        - renamed aimosAlarmListDemand to aimosAlarmListResync
        - added aimosAlarmListRebuild
        - SNMPState renamed to AgentState
        - renamed alarmHasGone to alarmAutoClear
        - renamed alarmAcknowledged to alarmManualClear"
      REVISION "200304281048Z"
      DESCRIPTION 
        "1.0.0.114
        Release Q0215RHD_DRAFT
        Modifications:
        - added textual convention PasswordStandard
        - added aimosPasswordStandard
        - added Textual Convention ClearMode
        - aimosAlarmExpectAutoClear (boolean) renamed to aimosAlarmClearMode (ClearMode)
        - added aimosNextMasterID
        - added Textual Convention MasterState
        - aimosMasterV1Address renamed to aimosMasterAddress
        - added aimosMasterState
        - aimosCableCodeTable and aimosCableUsageTable are implemented"
      REVISION "200305071218Z"
      DESCRIPTION 
        "1.0.0.115
        Release Q0215RHD_DRAFT
        Modifications:
        - BTS-Entries removed
        - Sector-Entries removed
        - aimosMasterV1GUID renamed to aimosMasterGUID
        - aimosMasterV1CommunicationID renamed to aimosMasterCommunicationID
        - added aimosSubRackMapXY, aimosGSMNSOMapXY, aimosUMTSNSOMapXY
        - added some named values to textual convention MasterState
        - aimosPreLogin renamed to aimosPublic
        - aimosSessionTimeOut added
        - minor changes (modified descriptions, access-rights)"
      REVISION "200308061446Z"
      DESCRIPTION 
        "1.1.0.111
        Release Q0215RHD_DRAFT
        Modifications:
        - aimosSessionTimeout added
        - aimosOrgPassword deleted
        - aimosOrgNextBTSID deleted
        - aimosOrgNextSectorID deleted
        - aimosRoleMinOrgLevel deleted
        - aimosNextCommunicationTypeID deleted
        - aimosCommunicationTypeTable deleted
        - aimosPhoneBookCommunicationType deleted
        - aimosAlarmForwarding changed to aimosAlarmForwardingType.
          old: 0=off, 1=on
          new: 0=off, 1=use V1 trap, 2=use V2 notification
        - aimosMasterGUID added
        - aimosMasterLoginUserName added
        - aimosMasterLoginPassword added
        - aimosSubRackMapXY added
        - aimosGSMNSOMapXY added
        - aimosUMTSNSOMapXY added
        - aimosBTSTable deleted
        - aimosSectorTable deleted, new is aimosNextMasterLoginUser
        - aimosSectorUsageTable deleted, new is aimosNextMasterLoginPassword
        - in each ...V1-Table a new index (...ValueSource) was added
          e.g. aimosMasterV1ValueSource in aimosMasterUnitV1Table.
          Therefore it was here unfortunately inevitable that the following
          OIDs are changed.
        - aimosMasterV1GUID deleted
        - aimosMasterV1CommunicationID deleted
        - aimosNextCommunicationID deleted
        - aimosCommunicationTable deleted"
      REVISION "200308121724Z"
      DESCRIPTION 
        "1.1.0.112
        Release Q0215RHD_DRAFT
        Modifications:
        - TextualConventions added:
          - ControllerPassword
          - WeekMinutes
          - UnitReference
          - CableID
          - NSOID
        - first login after software installation implemented
        - aimosSessionTimeout is now of type WeekMinutes
        - aimosNextMasterLoginUserName moved to aimosUnitiallyMasterLoginUserName
        - aimosNextMasterLoginPassword moved to aimosInitiallyMasterLoginPassword
        - aimosNextMasterID and aimosMasterID are now of type MasterID
        - aimosNextCableID and aimosCableID are now of type CableID
        - aimosMasterLoginPassword is now of type ControllerPassword
        - aimosCableUsageUnitReference renamed to aimosCableUsageRemoteUnitReference
        - Heartbeat implemented (aimosMasterV1HeartbeatInterval, -Overtime and -Time added)"
      REVISION "200308271009Z"
      DESCRIPTION 
        "1.1.1.100
        Release Q0215RHD
        Modifications:
        - added aimosOMCConnectorAddress
        - aimosMasterOID, aimosSubRackOID and aimosRemoteOID changed from OBJECT IDENTIFIER to RowPointer
        - aimosGSMNSOOID and aimosGSMNSOOIDData changed from OBJECT IDENTIFIER to RowPointer
        - aimosUMTSNSOOID and aimosUMTSNSOOIDData changed from OBJECT IDENTIFIER to RowPointer
        - mandatory objects (sysUpTime, aimosTrapOID and aimosTrapEnterprise) removed from all NOTIFICATION-TYPE's OBJECTS clause"
      REVISION "200312191220Z"
      DESCRIPTION 
        "1.2.0.102
        Release Q0215RHE
        Modifications:
        - added textual convention InterfaceType
        - added textual convention AlarmForwardingType
        - fixed the description to UTCTime (value is 15 character clear text instead of 10 character binary
        - fixed the description to LocalTime (value is 19 character clear text instead of 12 character binary
        - default time format is local time
        - added aimosPhoneBookInterfaceType
        - added aimosPhoneBookAckCapability
        - objects regarding the amplifiers were renamed (UMTS, DCM, GSM to Amp1, Amp2, Amp3). Their meanings and object IDs are unchanged.
        - added aimosSubRackV1AmplifierBandNamesAge
        - added aimosSubRackV1Amplifier1BandName to aimosSubRackV1Amplifier3BandName
        - ProbableCause: values 100 to 107 moved back to 58 to 65
        - added a lot of descriptions"
      REVISION "200406161020Z"
      DESCRIPTION 
        "1.3.0.100
        Release Q0215RHF
        Modifications:
        - last change of UTCTime and LocalTime revoked
        - added textual convention TimeDisplayFormat
        - added aimosPhoneBookTimeDisplayFormat"
      REVISION "200407051020Z"
      DESCRIPTION 
        "1.3.0.103
        Release Q0215RHF
        Modifications:
        - changed each name MIDAS to the new brand name AIMOS
        - notification type RightAreas is supplemented by some new numbers
        - added object aimosCurrentTime
        - added object aimosWorkShiftHeartBeatInterval
        - added object aimosWorkShiftHeartBeatRecipientList
        - added aimosHeartBeat notification type"
      REVISION "200506161310Z"
      DESCRIPTION 
        "1.5.0.102
        Release Q0215RHG
        Modifications:
        - changed Mikom to Andrew
        - changed AIMOS to A.I.M.O.S."
      REVISION "200509261305Z"
      DESCRIPTION 
        "1.6.1.100
        Release Q0215RHH
        Modifications
        - added coverageNetworkManagementManualDelete to RightArea
        - added coverageNetworkManagementMapView to RightArea
        - added coverageNetworkManagementManualClear to RightArea
        - added unitList to RightArea"
      REVISION "200606221339Z"
      DESCRIPTION 
        "1.7.2.100
        Release Q0215RHI
        Modifications:
        - syntax names starting with lower case letters corrected ('SEQUENCE OF aaa' changed to 'SEQUENCE OF Aaa')
        - objects with underscore in its name removed:
          - aimosUMTSNSODataV1AnyData_ToBeDefined (not implemented until now)
          - aimosUMTSNSOV1AnyData_ToBeDefined (not implemented until now)
        - name of default value of aimosPhoneBookInterfaceType corrected (from ifDefault to ifMIBDefault)
        "
      REVISION "200611221707Z"
      DESCRIPTION 
        "1.9.0.100
        Release Q0215RHJ
        Modifications:
        - added jobMonitor and watchDog to TC RightArea
        - removed aimosUMTSNSODataV1AnyData_ToBeDefined and aimosUMTSNSOV1AnyData_ToBeDefined from aimosUMTSNSOV1Group
        - name of default value of aimosPhoneBookInterfaceType corrected (from ifDefault to ifMIBDefault) - was still wrong"
      REVISION "200911231640Z"
      DESCRIPTION 
        "2.4.0.100
        Release Q0215RHL
        Modifications:
        At time the MIB was designed only MMR was available. The yore network structure of the MMR 
        lead to the design of Trap Info fields. The Cable Trap Info was never implemented.
        
        From SNMP Manager's point of view it was somewhat complicated to extract the Trap Info from 
        notification objects, whereas the Trap Info for later introduced Network Element types 
        beneath the MMR (the Alarm Boards for example) where never forwarded with notifications.
        
        In V2.4.0 the SNMP Manager is provided with the Network Element's Trap Info, Component Name, 
        Location and Unique System ID in the former aimosAlarmListCustomer...Info fields. 
        
        Therefore the following object names change:
        - aimosAlarmListCustomerMasterInfo  -> aimosAlarmListTrapInfo
        - aimosAlarmListCustomerSubRackInfo -> aimosAlarmListComponentName
        - aimosAlarmListCustomerCableInfo   -> aimosAlarmListLocation
        - aimosAlarmListCustomerRemoteInfo  -> aimosAlarmListUniqueSystemID
        
        The same applies to the Alarm Log:
        - aimosAlarmLogCustomerMasterInfo  -> aimosAlarmLogTrapInfo
        - aimosAlarmLogCustomerSubRackInfo -> aimosAlarmLogComponentName
        - aimosAlarmLogCustomerCableInfo   -> aimosAlarmLogLocation
        - aimosAlarmLogCustomerRemoteInfo  -> aimosAlarmLogUniqueSystemID
        
        Additionally the notifications aimosAlarmNew, aimosAlarmChanged (still not used) as well 
        as aimosAlarmCleared are changed to contain the new object names.
        
        The old MIB design remains available in the '%AIMOS_ROOT%\MIB\LEGACY\AIMOS.MY'-MIB-File. 
        The A.I.M.O.S. SNMP Agent can be set to act as it did until V2.3 by means of the A.I.M.O.S. 
        Config-Tool: Set 'MIB supported by the Agent' to 'A.I.M.O.S. Legacy'."
      REVISION "201006171647Z"
      DESCRIPTION 
        "2.5.0.100
        Release Q0215RHM
        Modifications:
        aimosLoginPhoneBookID added to aimosLogin branch"
      REVISION "201009281501Z"
      DESCRIPTION 
        "2.6.0.100
        Release Q0215RHN
        Added Textual Conventions:
        - GeographicPositionFormat
        - GPSPosition
        Extended Textual Conventions:
        - RightArea enlarged by logManager right
        New objects:
        - aimosPhoneBookGeographicPositionFormat
        - aimosAlarmListRaiseLatitude
        - aimosAlarmListRaiseLongitude
        - aimosAlarmListClearLatitude
        - aimosAlarmListClearLongitude
        - aimosAlarmLogRaiseLatitude
        - aimosAlarmLogRaiseLongitude
        - aimosAlarmLogClearLatitude
        - aimosAlarmLogClearLongitude"
      REVISION "201103221832Z"
      DESCRIPTION 
        "2.7.0.100 - MBa:
        Release Q0215RHO
        Extended Textual Conventions:
        - RightArea enlarged by scheduler right
        - RightArea enlarged by reporting right
        - PasswordStandard enlarged by upperCase(5) to numericAndSpecialAndUpperCaseAndLowerCase(11)"
      REVISION "201105271146Z"
      DESCRIPTION 
        "2.8.0.100
        Release Q0215RHP
        Added aimosNEOperations
        Extended Textual Convention RightArea by performanceManager right
        Changed Textual Convention RightArea: fixed scheduler right value"
      REVISION "201112201011Z"
      DESCRIPTION 
        "2.9.0.100
        Release Q0215RHQ
        Added recognition support:
        - new textual convention RecognitionState
        - new notification aimosAlarmRecognized
        - new object aimosPhoneBookRecognitionTraps
        - new object aimosAlarmListRecognitionState
        - new object aimosAlarmListRecognitionUser
        - new object aimosAlarmListRecognitionTime
        - new object aimosAlarmLogRecognitionState
        - new object aimosAlarmLogRecognitionUser
        - new object aimosAlarmLogRecognitionTime"
      ::= { mikom 201 }

    
  
--
-- Textual conventions
--
  
    SystemAvailability ::= TEXTUAL-CONVENTION
      STATUS current
      DESCRIPTION 
        "SystemAvailability is in later released versions of the agent needed for system
        backup and restore purposes. It has the syntax INTEGER with the following
        named values:
        . inaccessible(0)              not used yet
        . accessible(1)                login is possible
        . exclusiveAccessRequested(2)  not used yet
        . exclusiveAccess(3)           not used yet
        "
      SYNTAX INTEGER
        {
        inaccessible(0),
        accessible(1),
        exclusiveAccessRequested(2),
        exclusiveAccess(3)
        }

    Community ::= TEXTUAL-CONVENTION
      STATUS current
      DESCRIPTION 
        "Community is an OCTET STRING with up to 40 characters each being in range from
        32 to 126 (' ' <space> to '~' <tilde>)."
      SYNTAX OCTET STRING (SIZE (1..40))

    UserName ::= TEXTUAL-CONVENTION
      STATUS current
      DESCRIPTION 
        "UserName is an OCTET STRING having up to 40 characters used in order to
        represent uniquely user names.
        
        Each character must be in range from 32 to 126 (' ' <space> to '~' <tilde>)."
      SYNTAX OCTET STRING (SIZE (1..40))

    PasswordString ::= TEXTUAL-CONVENTION
      STATUS current
      DESCRIPTION 
        "PasswordString is an OCTET STRING with at least 5 up to 40 characters each
        being in a range from 32 to 126 (' ' <space> to '~' <tilde>).
        
        Each response to objects of type PasswordString will be a sequence of '*'."
      SYNTAX OCTET STRING (SIZE (5..100))

    LoginState ::= TEXTUAL-CONVENTION
      STATUS current
      DESCRIPTION 
        "LoginState is an INTEGER value used in order to indicate the login state with
        the following named values:
        
        . disconnected(0)     no access to OID's beneath aimosObjects
        
        . connected(1)        access to all OID's of A.I.M.O.S. MIB (according to the
                              authorisation level of the user logged in)
        
        . refused(2)          the password or wrong, access rights like disconnected(0)
        
        . canceled(3)         Session has been inactive too long, access rights like
                              disconnected(0)
        
        . passwordExpired(4)  the password is expired. The user needs to assign a new
                              password to aimosLoginPassword in order to login."
      SYNTAX INTEGER
        {
        disconnected(0),
        connected(1),
        refused(2),
        canceled(3),
        passwordExpired(4)
        }

    OrgID ::= TEXTUAL-CONVENTION
      STATUS current
      DESCRIPTION 
        "The OrgID is an Unsigned32 value with a fixed length of 6 digits and the range
        from 200.000 to 799.299 used in order to represent organisation IDs.
        It contains:
        . MCC (mobile country code 3 digits)
        . TelCo/provider flag (1 digit)
        . MNC (mobile network code) or consecutive numbering (2 digits)
        
        TelCo/Provider flag	Description
              0                 TelCo
              1                 TelCo in the role of a provider
              2                 provider
          3,4,5,6,7,8           Reserved
              9                 manufacturer
        
        Mikom is responsible to provide theses numbers."
      SYNTAX Unsigned32 (200000..799299)

    Version ::= TEXTUAL-CONVENTION
      STATUS current
      DESCRIPTION 
        "Version is an OCTET STRING with at least 3 up to 13 characters in the format
        n.n.n.n (e.g. 1.0.5.328) denoting the hierarchical nested major and minor
        version, release, and build identification."
      SYNTAX OCTET STRING (SIZE (3..15))

    SDN ::= TEXTUAL-CONVENTION
      STATUS current
      DESCRIPTION 
        "The SDN is an OCTET STRING having up to 80 characters used in order to
        represent system distinguished names.
        
        Each character must be in range from 32 to 126 (' ' <space> to '~' <tilde>)."
      SYNTAX OCTET STRING (SIZE (4..80))

    TimeFormat ::= TEXTUAL-CONVENTION
      STATUS current
      DESCRIPTION 
        "TimeFormat is an INTEGER used in order to indicate the time format for date
        and time values with the following named values:
        . utcTimeFormat(0)    Coordinated Universal Time (UTC),
                              also known as Greenwich Mean Time (GMT)
        . localTimeFormat(1)  local time of the machine"
      SYNTAX INTEGER
        {
        utcTimeFormat(0),
        localTimeFormat(1)
        }

    PasswordStandard ::= TEXTUAL-CONVENTION
      STATUS current
      DESCRIPTION 
        "PasswordStandard is an INTEGER value used in order to indicate the password
        security level by the following named values (the description indicates in each
        case, which character must be contained, so that a password is valid):
        . normal(0)              any printable character
        . numbers(1)             at least one number
        . specials(2)            at least one special character
        . numbersOrSpecials(3)   at least one number or special character
        . numbersAndSpecials(4)  at least one number and one special character
        . upperCase(5)
        . lowerCase(6)
        . upperCaseAndLowerCase(7)
        . upperCaseAndLowerCaseAndNumeric(8)
        . upperCaseAndLowerCaseAndSpecial(9)
        . upperCaseAndLowerCaseAndNumericOrSpecial(10)
        . numericAndSpecialAndUpperCaseAndLowerCase(11)
        
        Special characters are as follows:
         and double quotation marks"
      SYNTAX INTEGER
        {
        normal(0),
        numbers(1),
        specials(2),
        numbersOrSpecials(3),
        numbersAndSpecials(4),
        upperCase(5),
        lowerCase(6),
        upperCaseAndLowerCase(7),
        upperCaseAndLowerCaseAndNumeric(8),
        upperCaseAndLowerCaseAndSpecial(9),
        upperCaseAndLowerCaseAndNumericOrSpecial(10),
        numericAndSpecialAndUpperCaseAndLowerCase(11)
        }

    WeekMinutes ::= TEXTUAL-CONVENTION
      STATUS current
      DESCRIPTION 
        "WeekMinutes is an Unsigned32 value within the range from 0 to 10.080 used in
        order to represent an amount of minutes for up to one week."
      SYNTAX Unsigned32 (0..10080)

    IPAddressAndPort ::= TEXTUAL-CONVENTION
      STATUS current
      DESCRIPTION 
        "IPAddressAndPort is an OCTET STRING with at least 7 up to 21 characters used in
        order to represent an IP address and its IP/UDP port number in the following
        format:
        
          a.b.c.d:port, e.g.: 192.168.1.54:162
        
        If the port number is omitted, then also the colon must be omitted."
      SYNTAX OCTET STRING (SIZE (7..21))

    VariableTime ::= TEXTUAL-CONVENTION
      DISPLAY-HINT 
        "2d-1d-1d,1d:1d:1d,1a1d:1d"
      STATUS current
      DESCRIPTION 
        "VariableTime is an OCTET STRING with up to 28 characters used in order to
        represent date and time values. Two objects have influence on coding the
        values:
        . aimosTimeFormat specifies whether times are coded in UTC or in local time
        . aimosPhoneBookTimeDisplayFormat specifies whether the times are coded in OSI
          or SNMP manner. In addition it can be specified whether the information has to
          be handed over in binary form or as (un-)formatted text.
          Refer to the description of the textual convention TimeDisplayFormat for more
          information about that.
        
        The display hint is accordingly to the system default osiBinary(1)."
      SYNTAX OCTET STRING (SIZE (0..28))

    Text ::= TEXTUAL-CONVENTION
      STATUS current
      DESCRIPTION 
        "Text is an OCTET STRING with up to 100 characters having
        each character in a range from 32 to 126 (' ' <space> to '~' <tilde>)."
      SYNTAX OCTET STRING (SIZE (0..100))

    OrgLevel ::= TEXTUAL-CONVENTION
      STATUS current
      DESCRIPTION 
        "OrgLevel is an INTEGER used in order to indicate the role the organisation is
        playing in the A.I.M.O.S. system with the following named values:
        . indeterminate(0)  not used
        . telco(1)          organisation is a TelCo
        . provider(2)       organisation is a provider
        . manufacturer(3)   organisation is the manufacturer
        "
      SYNTAX INTEGER
        {
        indeterminate(0),
        telco(1),
        provider(2),
        manufacturer(3)
        }

    MCC ::= TEXTUAL-CONVENTION
      STATUS current
      DESCRIPTION 
        "MCC is an Unsigned32 value within the range from 200 to 799 used in order to
        represent Mobile Country Codes."
      SYNTAX Unsigned32 (200..799)

    MNC ::= TEXTUAL-CONVENTION
      STATUS current
      DESCRIPTION 
        "MNC is an Unsigned32 value within the range from 0 to 99 used in order to
        represent Mobile Network Codes."
      SYNTAX Integer32 (0..99)

    Boolean ::= TEXTUAL-CONVENTION
      STATUS current
      DESCRIPTION 
        "Boolean is an INTEGER used in order to represent a boolean value by the named
        values of
        . false(0)
        . true(1)"
      SYNTAX INTEGER
        {
        false(0),
        true(1)
        }

    DistinguishedNameSeparator ::= TEXTUAL-CONVENTION
      STATUS current
      DESCRIPTION 
        ""
      SYNTAX	OCTET STRING (SIZE (1))

    DistinguishedNameHierarchySymbol ::= TEXTUAL-CONVENTION
      STATUS current
      DESCRIPTION 
        ""
      SYNTAX OCTET STRING (SIZE (1))

    CableCodeConcatenator ::= TEXTUAL-CONVENTION
      STATUS current
      DESCRIPTION 
        "CableCodeConcatenator is an OCTET STRING with a fixed length of 1 character
        used in order to concatenate Cable Codes."
      SYNTAX OCTET STRING (SIZE (1))

    TableIndex ::= TEXTUAL-CONVENTION
      STATUS current
      DESCRIPTION 
        "TableIndex is an Unsigned32 value within the range from 1 to 2^32-1 used for
        table indexing."
      SYNTAX Unsigned32 (1..2147483647)

    RightArea ::= TEXTUAL-CONVENTION
      STATUS current
      DESCRIPTION 
        "RightArea is an INTEGER used in order to indicate the controller right with
        the following named values:
        . factorySettings(2000)
        . accountManagement(2100)
        . northboundManagement(2200)
        . connectivityManagement(2300)
        . scheduler(2325)
        . jobMonitor(2350)
        . logManager(2375)
        . coverageNetworkManagementGeneral(2400)
        . coverageNetworkManagementConfiguration(2500)
        . coverageNetworkManagementManualDelete(2550)
        . coverageNetworkManagementMaintenance(2600)
        . coverageNetworkManagementMapView(2630)
        . coverageNetworkManagementManualClear(2660)
        . coverageNetworkManagementSupervision(2700)
        . coverageNetworkManagementTopology(2800)
        . performanceManager(2925)
        . reporting(2950)
        . sessionManagement(3000)
        . unitList(3100)
        . watchDog(3200)
        
        
        The values below 2000 are only used before software version 1.3.
        
        organizationProfilesManagement(2900) ist not used as of 2.7.0"
      SYNTAX INTEGER
        {
        administrationAlarms(100),
        administrationFolder(200),
        administrationMCAccounts(300),
        administrationMC(400),
        administrationOMCAccounts(500),
        administrationOMC(600),
        administrationSNMPNorthbound(700),
        administrationSNMPSouthbound(800),
        controlAlarmSystem(900),
        controlDeviceParameter(1000),
        fileUploadDownload(1100),
        factorySettings(2000),
        accountManagement(2100),
        northboundManagement(2200),
        connectivityManagement(2300),
        scheduler(2325),
        jobMonitor(2350),
        logManager(2375),
        coverageNetworkManagementGeneral(2400),
        coverageNetworkManagementConfiguration(2500),
        coverageNetworkManagementManualDelete(2550),
        coverageNetworkManagementMaintenance(2600),
        coverageNetworkManagementMapView(2630),
        coverageNetworkManagementManualClear(2660),
        coverageNetworkManagementSupervision(2700),
        coverageNetworkManagementTopology(2800),
        organizationProfilesManagement(2900),
        performanceManager(2925),
        reporting(2950),
        sessionManagement(3000),
        unitList(3100),
        watchDog(3200)
        }

    AccessRight ::= TEXTUAL-CONVENTION
      STATUS current
      DESCRIPTION 
        "AccessRight is an INTEGER used in order to indicate the access rights of an
        user with the following named values:
        . noAccess(0)   used in order to delete entries in aimosRoleRightTable
        . readOnly(1)   updates are prohibited
        . readWrite(2)  updates are allowed"
      SYNTAX INTEGER
        {
        noAccess(0),
        readOnly(1),
        readWrite(2)
        }

    ControllerPassword ::= TEXTUAL-CONVENTION
      STATUS current
      DESCRIPTION 
        "ControllerPassword is a OCTET STRING with the following requirements:
        . it consists of at least 6, but at the most 8 characters
        . it contains at least one capital letter in the range from A to Z
        . it contains at least one small letter in the range from a to z
        . it contains at least one number
        . it contains no other characters than the ones listed above (A-Z, a-z, 0-9)"
      SYNTAX OCTET STRING (SIZE (6..8))

    NetworkStandard ::= TEXTUAL-CONVENTION
      STATUS current
      DESCRIPTION 
        "NetworkStandard is an INTEGER used in order to indicate a network standards
        with the following named values:
        . umts(1)  UMTS
        . dcs(2)   GSM1800
        . gsm(3)   GSM900"
      SYNTAX INTEGER
        {
        umts(1),
        dcs(2),
        gsm(3)
        }

    FrequencyRange ::= TEXTUAL-CONVENTION
      STATUS current
      DESCRIPTION 
        "FrequencyRange is an Unsigned32 value within the range from
        400.000 to 2.400.000 used in order to represent radio frequency values in kHz."
      SYNTAX Unsigned32 (400000..2400000)

    ARFCN ::= TEXTUAL-CONVENTION
      STATUS current
      DESCRIPTION 
        "ARFCN is an Unsigned32 value within the range from 0 to 16.383 used in order to
        represent the absolute radio frequency channel number."
      SYNTAX Unsigned32 (0..16383)

    AlarmID ::= TEXTUAL-CONVENTION
      STATUS current
      DESCRIPTION 
        "AlarmID is an INTEGER used in order to indicate the kind of alarm."
      SYNTAX INTEGER
        {
        alarmAC(1),
        alarmALC(2),
        alarmAmplifier(3),
        alarmAmplifierCurrent(4),
        alarmAttSet(5),
        alarmAutoLeveling(6),
        alarmAuxSet(7),
        alarmBitErrorRate(8),
        alarmBooster(9),
        alarmBus(10),
        alarmChannel(11),
        alarmCellLost(13),
        alarmConnection(15),
        alarmControlBoard(16),
        alarmConvBias(17),
        alarmConverter(18),
        alarmCellStatusChanged(19),
        alarmCurrent(20),
        alarmCurrentFail(21),
        alarmDistribution(22),
        alarmDistributor(23),
        alarmDoorOpen(24),
        alarmDriverAmp(25),
        alarmEnergyCellTemp(26),
        alarmEnergyCellVoltage(27),
        alarmExternalInput(28),
        alarmFan(29),
        alarmHeartBeat(30),
        alarmICEOscilPower(31),
        alarmInputPower(32),
        alarmMIB(33),
        alarmMicrowaveLock(34),
        alarmOperatorRequired(35),
        alarmOptic(36),
        alarmOpticCurrent(37),
        alarmOscillator(38),
        alarmPA(39),
        alarmPasswordWrong(40),
        alarmPowerAmplifier(41),
        alarmPowerOut(42),
        alarmPowerOutBelowLimit(43),
        alarmPowerOutLow(44),
        alarmPowerSupply(45),
        alarmPreAmplifier(46),
        alarmRelay(47),
        alarmRFPath(48),
        alarmRSSI(49),
        alarmRSSILow(50),
        alarmRxLevelHigh(51),
        alarmRxLevelLow(52),
        alarmSolarVoltage(53),
        alarmSummarizer(54),
        alarmSynthesizerCurrent(55),
        alarmSynthesizer(56),
        alarmSystemModule(57),
        alarmSystemTemp(58),
        alarmUnitUnavailable(59),
        alarmVSWR(60),
        alarmAutoLevelingOutOfRange(61),
        alarmOMC(62),
        alarmHeartbeatMissing(63),
        alarmIPP(64),
        alarmCommonPilotChannelHigh(65),
        alarmCommonPilotChannelLow(66),
        alarmTemperatureStage1(67),
        alarmTemperatureStage2(68),
        alarmCurrent2(69),
        alarmInvalidLogin(70),
        alarmChannelNew(71),
        alarmChannelLost(72),
        alarmChannelAllocationChanged(73),
        alarmUMTSRxLevelHigh(74),
        alarmUMTSRxLevelLow(75),
        alarmUMTSCodePowerLow(76),
        alarmUMTSCPICHEnergyToNoiseRatioLow(77),
        alarmUMTSCPICHCodePowerHigh(78),
        alarmUMTSCPICHCodePowerLow(79),
        alarmUMTSBCHBlockErrorRateHigh(80),
        alarmUMTSPSCCodePowerLow(81),
        alarmUMTSChannelLost(82),
        alarmAlarmlistDeleted(83),
        alarmDataOutOfSequence(84),
        alarmExternalOutput(85),
        alarmGsmNso(86)
        }

    EventType ::= TEXTUAL-CONVENTION
      STATUS current
      DESCRIPTION 
        "EventType is an INTEGER used in order to indicate the event type of an alarm by
        the following named values:
        . communications(1)
        . qualityOfService(2)
        . processingError(3)
        . equipment(4)
        . environmental(5)"
      SYNTAX INTEGER
        {
        communications(1),
        qualityOfService(2),
        processingError(3),
        equipment(4),
        environmental(5)
        }

    Severity ::= TEXTUAL-CONVENTION
      STATUS current
      DESCRIPTION 
        "Severity is an INTEGER used in order to indicate the relative level of urgency
        for operator attention by the following named values:
        . indeterminate(0)
        . critical(1)
        . major(2)
        . minor(3)
        . warning(4)
        . cleared(5)
        . information(6)
        
        Values from indeterminate(0) to cleared(5) are defined in accordance with the
        ITU-T recommendations X.733.
        
        The value information(6) is a Mikom extension. However, for compatibility
        reasons the SNMP Agent can be forced to treat information(6) like warning(4) by
        means of aimosAlarmDefaultSeverity."
      SYNTAX INTEGER
        {
        indeterminate(0),
        critical(1),
        major(2),
        minor(3),
        warning(4),
        cleared(5),
        information(6)
        }

    ClearMode ::= TEXTUAL-CONVENTION
      STATUS current
      DESCRIPTION 
        "ClearMode is an INTEGER used in order to indicate how an alarm gets cleared by the following named values:
        
        . indeterminate(0)  not used
        
        . autoClear(1)      if the alarm condition does not exist any longer, a
                            aimosAlarmCleared notification will be emitted by the system
        
        . manualClear(2)    the alarm remains active until aimosAlarmListClearReason is
                            set to manualCleared(2)
        
        . clearOnAck(3)     after acknowledgement of the aimosAlarmNew notification the
                            system will emit a aimosAlarmCleared notification. If the
                            acknowledgement to that notification is done, the alarm is
                            cleared and will be removed from the alarm list
        
        . ackIsClear(4)     after acknowledgement of the aimosAlarmNew notification the
                            alarm is cleared and will be removed from the alarm list"
      SYNTAX INTEGER
        {
        indeterminate(0),
        autoClear(1),
        manualClear(2),
        clearOnAck(3),
        ackIsClear(4)
        }

    AlarmValue ::= TEXTUAL-CONVENTION
      STATUS current
      DESCRIPTION 
        "AlarmValue is an Unsigned32 value within the range from 0 to 9.999.999 used in
        order to provide an alarm dependent value."
      SYNTAX Unsigned32 (0..9999999)

    PhoneBookEntry ::= TEXTUAL-CONVENTION
      STATUS current
      DESCRIPTION 
        "PhoneBookEntry is an OCTET STRING with a length of at least 1 up to 100
        characters used in order to give a phonebook entry a name.
        
        The name must start with a letter and each character must be in range 32 to 126
        (' ' <space> to '~' <tilde>)."
      SYNTAX OCTET STRING (SIZE (1..100))

    OperationMode ::= TEXTUAL-CONVENTION
      STATUS current
      DESCRIPTION 
        "OperationMode is an INTEGER used in order to indicate the operation mode by
        the following named values:
        . idle(0)      no operation takes place at present
        . stopping(1)  the operation is terminating
        . stop(2)      used in order to terminate the operation
        . running(3)   the operation takes place at present
        . starting(4)  the operation is starting
        . start(5)     used in order to start the operation
        
        If operation mode is idle(0), it can be set to start(5). The system then will
        change the value to starting(4) until the operation is running. In that case it
        goes into running(3) state.
        
        If operation mode is running(3), it can be set to stop(2). The system then will
        change the value to stopping(1), stops the operation and then change the value
        to idle(0).
        
        Only the values start(5) and stop(2) can be set.
        These values will never be reported on get requests."
      SYNTAX INTEGER
        {
        idle(0),
        stopping(1),
        stop(2),
        running(3),
        starting(4),
        start(5)
        }

    InterfaceType ::= TEXTUAL-CONVENTION
      STATUS current
      DESCRIPTION 
        "InterfaceType is an INTEGER used in order to indicate the kind of alarm
        forwarding expected by the SNMP Manager by the following named values:
        
        . ifMIBDefault(0)     currently the same as ifAimos(5)
        
        . ifOMC3Default(1)    force alarm forwarding as used in OMC 3 with the standard
                              interface. The alarms sent away are always SNMPv1 traps
        
        . ifOMC3Nokia(2)      force alarm forwarding as used in OMC 3 with the Nokia
                              interface. The alarms sent away are always SNMPv1 traps
        
        . ifNE3S(3)           force alarm forwarding as defined in the Nokia Enhanced
                              SNMP Solution Suite (NE3S). The decision made by means of
                              the object aimosAlarmForwardingType determines whether an
                              alarm is sent away as SNMPv1 trap or as SNMPv2 notification
        
        . ifAimosObsolete(4)  force alarm forwarding as defined in the first releases of
                              the aimos MIB. The alarms sent away are always SNMPv2
                              notifications.
        
        . ifAimos(5)          alarm forwarding as defined by the MIB. The decision made
                              by means of the object aimosAlarmForwardingType determines
                              whether an alarm is sent away as SNMPv1 trap or as SNMPv2
                              notification."
      SYNTAX INTEGER
        {
        ifMIBDefault(0),
        ifOMC3Default(1),
        ifOMC3Nokia(2),
        ifNE3S(3),
        ifAimosObsolete(4),
        ifAimos(5)
        }

    TimeDisplayFormat ::= TEXTUAL-CONVENTION
      STATUS current
      DESCRIPTION 
        "TimeDisplayFormat is an INTEGER used in order to indicate of how date and time
        values are transmitted in objects of type VariableTime are encoded by the SNMP
        agent. This will be done using one of the following named values:
        
        . default(0)       using default(0) is equal to using osiBinary(1) unless
                           aimosPhoneBookInterfaceType is set to ifAimosObsolete(4).
                           In the latter case it's equal to using osiText(2) instead.
        
        . osiBinary(1)     specifies that the textual conventions UTCTime or LocalTime
                           (depending on the decision made by means of aimosTimeFormat)
                           shall be used as defined.
                           This is the system default unless aimosPhoneBookInterfaceType
                           is set to ifAimosObsolete(4).
        
        . osiText(2)       specifies that the textual conventions UTCTime or LocalTime
                           (depending on the decision made by means of aimosTimeFormat)
                           shall be used. The only exception is that the values are not
                           encoded binary, but in text format. I.e., as an example, the
                           year is not encoded in two octets, but in four. The format
                           is YYYYMMDDHHMMSS+/-HHMM, the length is 19 octets.
                           If aimosTimeFormat is set to utcTimeFormat(0), the timezone
                           information is not present and a 'Z' letter is following the
                           seconds instead of the +/- sign. In the latter case the length
                           is reduced to 15 octets (YYYYMMDDHHMMSS'Z').
                           This is the system default if aimosPhoneBookInterfaceType is
                           set to ifAimosObsolete(4).
        
        . osiFormatted(3)  this option resembles osiText(2), except that instead of
                           unformated text formatted text is used. Due to the inserted
                           formattings the size increases to
                           - 26 octets, if aimosTimeFormat is set to localTimeFormat(1)
                             (the format used is YYYY-MM-DD,HH:MM:SS,+/-HH:MM)
                           - 20 octets, if aimosTimeFormat is set to utcTimeFormat(0)
                             (the format used is YYYY-MM-DD,HH:MM:SS'Z')
        
        . snmpBinary(4)    specifies that the textual convention SNMPv2-TC.DateAndTime
                           shall be used as defined. If aimosTimeFormat is set to
                           utcTimeFormat(0), then the timezone information (fields 8-10)
                           is not present.
        
        . snmpText(5)      specifies that the textual convention SNMPv2-TC.DateAndTime
                           shall be used. The only exception is that the values are not
                           encoded binary, but in text format. I.e., as an example, the
                           year is not encoded in two octets, but in four. The format
                           is YYYYMMDDHHMMSSD+/-HHMM, the length is 20 octets.
                           If aimosTimeFormat is set to utcTimeFormat(0) then the
                           timezone information is not present. In the latter case its
                           length is reduced to 15 octets (YYYYMMDDHHMMSSD).
        
        . snmpFormatted(6) this option resembles snmpText(5), except that instead of
                           unformated text formatted text is used. Due to the inserted
                           formattings the size increases to
                           - 28 octets, if aimosTimeFormat is set to localTimeFormat(1)
                             (the format used is YYYY-MM-DD,HH:MM:SS.D,+/-HH:MM)
                           - 21 octets, if aimosTimeFormat is set to utcTimeFormat(0)
                             (the format used is YYYY-MM-DD,HH:MM:SS.D)
        
        . windows(7)       date and time values are formatted as defined in the windows
                           country settings. The short date format and the long time
                           formats are used, separated by a blank."
      SYNTAX INTEGER
        {
        default(0),
        osiBinary(1),
        osiText(2),
        osiFormatted(3),
        snmpBinary(4),
        snmpText(5),
        snmpFormatted(6),
        windows(7)
        }

    AcknowledgementState ::= TEXTUAL-CONVENTION
      STATUS current
      DESCRIPTION 
        "AcknowledgementState is an INTEGER used in order to indicate the acknowledgement
        state of an alarm by the following named values:
        . indeterminate(0)   corresponds to X.733, however in A.I.M.O.S. not used
        . unacknowledged(1)
        . acknowledged(2)"
      SYNTAX INTEGER
        {
        indeterminate(0),
        unacknowledged(1),
        acknowledged(2)
        }

    ProbableCause ::= TEXTUAL-CONVENTION
      STATUS current
      DESCRIPTION 
        "ProbableCause is an INTEGER used in order to indicate the ITU-T Recommendation
        X.733 clause 8.1.2.1 conform probable cause of an alarm."
      SYNTAX INTEGER
        {
        unknown(0),
        adapterError(1),
        applicationSubsystemFailure(2),
        bandwidthReduced(3),
        callEstablishmentError(4),
        communicationsProtocolError(5),
        communicationsSubsystemFailure(6),
        configurationOrCustomizationError(7),
        congestion(8),
        corruptData(9),
        cpuCyclesLimitExceeded(10),
        dTEDCEInterfaceError(11),
        dataSetOrModemError(12),
        degradedSignal(13),
        enclosureDoorOpen(14),
        equipmentMalfunction(15),
        excessiveVibration(16),
        fileError(17),
        fireDetected(18),
        floodDetected(19),
        framingError(20),
        heatingOrVentialtionOrCoolingSystemProblem(21),
        humidityUnacceptable(22),
        inputOutputDeviceError(23),
        inputDeviceError(24),
        lANError(25),
        leakDetected(26),
        localNodeTransmissionError(27),
        lossOfFrame(28),
        lossOfSignal(29),
        materialSupplyExhausted(30),
        multiplexerProblem(31),
        outOfMemory(32),
        outputDeviceError(33),
        performanceDegraded(34),
        powerProblem(35),
        pressureUnacceptable(36),
        processorProblem(37),
        pumpFailure(38),
        queueSizeExceeded(39),
        receiveFailure(40),
        receiverFailure(41),
        remoteNodeTransmissionError(42),
        resourceAtOrNearingCapacity(43),
        responseTimeExcessive(44),
        retransmissionRateExcessive(45),
        softwareError(46),
        softwareProgramAbnormallyTerminated(47),
        softwareProgramError(48),
        storageCapacityProblem(49),
        temperatureUnacceptable(50),
        thresholdCrossed(51),
        timingProblem(52),
        toxicLeakDetected(53),
        transmitFailure(54),
        transmitterFailure(55),
        underlyingResourceUnavailable(56),
        versionMismatch(57),
        snmpTrapColdStart(100),
        snmpTrapWarmStart(101),
        snmpTrapLinkDown(102),
        snmpTrapLinkUp(103),
        snmpTrapAuthenticationFailure(104),
        snmpTrapEgpNeighborloss(105),
        snmpTrapEnterpriseSpecific(106),
        snmpTrapLinkUpDown(107)
        }

    SpecificProblem ::= TEXTUAL-CONVENTION
      STATUS current
      DESCRIPTION 
        "SpecificProblem is an Unsigned32 value within a range from 0 to 9.999 used in
        order to classify the fault situation as defined in ITU-T Recommendation X.733
        clause 8.1.2.2."
      SYNTAX Unsigned32 (0..9999)

    TrendIndication ::= TEXTUAL-CONVENTION
      STATUS current
      DESCRIPTION 
        "TrendIndication is an INTEGER used in order to indicate the ISO/IEC 10164-4,
        Chapter 8.1.2.6 conform trend indication of an alarm by the following named
        values:
        . lessSevere(0)
        . noChange(1)
        . moreSevere(2)"
      SYNTAX INTEGER
        {
        lessSevere(0),
        noChange(1),
        moreSevere(2)
        }

    ClearReason ::= TEXTUAL-CONVENTION
      STATUS current
      DESCRIPTION 
        "ClearReason is an INTEGER used in order to indicate the reason of an alarm is
        going cleared by the following named values:
        . stillActive(0)       what it says: the alarm is not cleared yet
        . autoCleared(1)       the alarm was cleared by the system
        . manualCleared(2)     the alarm was cleared by assigning manualCleared(2) to
                               aimosAlarmListClearReason
        . objectDeleted(3)     corresponds to X.733, however in A.I.M.O.S. not used
        . objectConfigured(4)  corresponds to X.733, however in A.I.M.O.S. not used
        . alarmListRebuild(5)  the alarm was rejected by an Alarm List Rebuild process
        . alarmChanged(6)      corresponds to X.733, however in A.I.M.O.S. not used"
      SYNTAX INTEGER
        {
        stillActive(0),
        autoCleared(1),
        manualCleared(2),
        objectDeleted(3),
        objectConfigured(4),
        alarmListRebuild(5),
        alarmChanged(6)
        }

    AlarmForwardingType ::= TEXTUAL-CONVENTION
      STATUS current
      DESCRIPTION 
        "AlarmForwardingType is an INTEGER used in order to indicate the type of alarm
        forwarding by the following named values:
        . disabled(0)  alarm forwarding is disabled
        . snmpV1(1)    alarm forwarding is using the TRAP-TYPE construct
        . snmpV2c(2)   alarm forwarding is using the NOTIFICATION-TYPE construct"
      SYNTAX INTEGER
        {
        disabled(0),
        snmpV1(1),
        snmpV2c(2)
        }

    MasterID ::= TEXTUAL-CONVENTION
      STATUS current
      DESCRIPTION 
        "MasterID is an Unsigned32 value within the range from 1 to 9.999 used in order
        to uniquely identify Master Units, each containing up to 13 Racks.
        
        While each Master Unit contains exact one Master Controller it is also used in
        order to identify Master Controllers."
      SYNTAX Unsigned32 (1..9999)

    RDN ::= TEXTUAL-CONVENTION
      STATUS current
      DESCRIPTION 
        "RDN is an OCTET STRING with up to 16 characters used in order to represent a
        relative distinguished name. The RDN uniquely identifies the unit within its
        parent. Each character must be in range 32 to 126 (' ' <space> to '~' <tilde>)."
      SYNTAX OCTET STRING (SIZE (4..16))

    IdentNo ::= TEXTUAL-CONVENTION
      STATUS current
      DESCRIPTION 
        "IdentNo is an OCTET STRING with up to 10 characters used in order to
        represent the Mikom Ident-No."
      SYNTAX OCTET STRING (SIZE (0..10))

    SerialNo ::= TEXTUAL-CONVENTION
      STATUS current
      DESCRIPTION 
        "SerialNo is an OCTET STRING with up to 10 characters used in order to
        represent the Mikom Serial-No of the device."
      SYNTAX OCTET STRING (SIZE (0..10))

    Coordinates ::= TEXTUAL-CONVENTION
      STATUS current
      DESCRIPTION 
        "Coordinates is an OCTET STRING with at least 3 up to 21 characters holding two
        values divided by a slash. The first one represents the x-coordinate and the
        other one represents the y-coordinate of a map position value."
      SYNTAX OCTET STRING (SIZE (0 | 3..21))

    MasterState ::= TEXTUAL-CONVENTION
      STATUS current
      DESCRIPTION 
        "MasterState is an INTEGER value used in order to indicate the state of
        system integration with the following named values:
        
        . indeterminate(0)          not used
        
        . requestGUID(1)            used in order to inquire the Master Controller's
                                    GUID
        
        . performGUIDRequest(2)     indicates that a GUID inquiry takes place
        
        . missingGUID(3)            indicates that a GUID could not be determined
        
        . requestNetInfo(4)         used in order to inquire the Master Controller's
                                    equipment structure and status information
        
        . performNetInfoRequest(5)  indicates that an inquiry of the equipment structure
                                    and status information takes place
        
        . missingNetInfo(6)         indicates that the equipment structure and/or status
                                    information could not be determined
        
        . properlySet(7)            indicates that the Master Controller is properly
                                    integrated in the system
        
        Only requestGUID(1) and requestNetInfo(4) are values, which can be assigned at
        OID's of the type MasterState. The remaining values can be returned in inquiries."
      SYNTAX INTEGER
        {
        indeterminate(0),
        requestGUID(1),
        performGUIDRequest(2),
        missingGUID(3),
        requestNetInfo(4),
        performNetInfoRequest(5),
        missingNetInfo(6),
        properlySet(7)
        }

    GUID ::= TEXTUAL-CONVENTION
      STATUS current
      DESCRIPTION 
        "GUID is an OCTET STRING with a fixed length of 38 character used in order to
        represent a Microsoft Windows GUID in printable format."
      SYNTAX OCTET STRING (SIZE (38))

    SubRackID ::= TEXTUAL-CONVENTION
      STATUS current
      DESCRIPTION 
        "SubRackID is an Unsigned32 value within the range from 1 to 124 used in
        order to represent the unique key for SubRack Master Units, each contained
        in one Master Unit and connected to some Remote Units."
      SYNTAX Unsigned32 (1..124)

    RemoteID ::= TEXTUAL-CONVENTION
      STATUS current
      DESCRIPTION 
        "RemoteID is an Unsigned32 value with the range from 1 to 4 used in order to
        represent the unique key for a Remote Unit."
      SYNTAX Unsigned32 (1..4)

    NSOID ::= TEXTUAL-CONVENTION
      STATUS current
      DESCRIPTION 
        "NSOID is an Unsigned32 value used in order to represent the unique key for
        GSM NSO's, each connected to one Remote Unit."
      SYNTAX Unsigned32 (1)

    CableID ::= TEXTUAL-CONVENTION
      STATUS current
      DESCRIPTION 
        "CableID is an Unsigned32 value within the range from 1 to 2^32-1 used in order
        to represent the unique key for cables, which are used for interconnection
        between Remote Units and SubRack Master Units."
      SYNTAX Unsigned32 (1..2147483647)

    CableCode ::= TEXTUAL-CONVENTION
      STATUS current
      DESCRIPTION 
        "CableCode is an OCTET STRING with a length of up to 40 characters used in order
        to represent the custom cable code, to which the fibre belongs.
        
        Each character must be in range 32 to 126 (' ' <space> to '~' <tilde>)."
      SYNTAX OCTET STRING (SIZE (1..40))

    UnitReference ::= TEXTUAL-CONVENTION
      STATUS current
      DESCRIPTION 
        "UnitReference is an Unsigned32 value that can be used for a system-wide unique
        identification of each individual unit.
        
        Contrary to this the textual conventions MasterID, SubRackID, RemoteID and NSOID
        only identify the corresponding unit types within their superior level."
      SYNTAX Unsigned32 (1..2147483647)

    ValueSource ::= TEXTUAL-CONVENTION
      STATUS current
      DESCRIPTION 
        "ValueSource is an INTEGER used in order to indicate the value to be
        addressed with the following named values:
        . actualValue(1)   the current value
        . cachedValue(2)   the most recent read value
        . desiredValue(3)  a desired value, not set yet
        "
      SYNTAX INTEGER
        {
        actualValue(1),
        cachedValue(2),
        desiredValue(3)
        }

    Attenuation ::= TEXTUAL-CONVENTION
      STATUS current
      DESCRIPTION 
        "Attenuation is an Unsigned32 value within the range from 0 to 30 used in order
        to provide an attenuation value in dB."
      SYNTAX Integer32 (0..30)

    GainOffset ::= TEXTUAL-CONVENTION
      STATUS current
      DESCRIPTION 
        "GainOffset is an Unsigned32 value within the range from 0 to 30 used in order to
        provide an gain offset value."
      SYNTAX Integer32 (-9..9)

    TemperatureStatus ::= TEXTUAL-CONVENTION
      STATUS current
      DESCRIPTION 
        "TemperatureStatus is an Unsigned32 value within the range from -55 to 125
        used in order to represent the current temperature value in degrees centigrade."
      SYNTAX Integer32 (-55..125)

    NominalTemperature ::= TEXTUAL-CONVENTION
      STATUS current
      DESCRIPTION 
        "NominalTemperature is an Unsigned32 value within the range from 40 to 65
        used in order to adjust the desired temperature value in degrees centigrade."
      SYNTAX Integer32 (40..65)

    AmplifierPower ::= TEXTUAL-CONVENTION
      STATUS current
      DESCRIPTION 
        "AmplifierPower is an Unsigned32 value within the range from -640 to 635
        used in order to represent the power value in tenth of dB in steps of 0.5 dB.
        I.e., valid values are 5,10,15,..."
      SYNTAX Integer32 (-640..635)

    ALCThreshold ::= TEXTUAL-CONVENTION
      STATUS current
      DESCRIPTION 
        "ALCThreshold is an Unsigned32 value within the range from 0 to 255 used in order
        to represent ALC Threshold values."
      SYNTAX Unsigned32 (0..255)

    OpticalLoss ::= TEXTUAL-CONVENTION
      STATUS current
      DESCRIPTION 
        "OpticalLoss is an Unsigned32 value within the range from -640 to 635 used in
        order to represent the optical loss value in tenth of dB."
      SYNTAX Integer32 (-640..635)

    BER ::= TEXTUAL-CONVENTION
      STATUS current
      DESCRIPTION 
        "BER is an Unsigned32 value within the range from 0 to 254 used in order to
        represent the bit error rate in tenth of dB."
      SYNTAX Unsigned32 (0..254)

    LAC ::= TEXTUAL-CONVENTION
      STATUS current
      DESCRIPTION 
        "Location Area CodeLAC is an Unsigned32 value within the range from 1 to 65.533
        used in order to represent the location area code."
      SYNTAX Unsigned32 (1..65533)

    CI ::= TEXTUAL-CONVENTION
      STATUS current
      DESCRIPTION 
        "CI is an Unsigned32 value within the range from 0 to 65.535 used in order to
        represent the cell identifier."
      SYNTAX Unsigned32 (0..65535)

    CellStatus ::= TEXTUAL-CONVENTION
      STATUS current
      DESCRIPTION 
        "CellStatus is an INTEGER used in order to indicate the cell status by the
        following named values:
        . cellSuitable(0)
        . cellLowPriority(1)
        . cellBarred(2)
        . cellLowLevel(3)
        . cellForbidden(4)
        . cellOther(5)"
      SYNTAX INTEGER
        {
        cellSuitable(0),
        cellLowPriority(1),
        cellBarred(2),
        cellLowLevel(3),
        cellForbidden(4),
        cellOther(5)
        }

    AgentState ::= TEXTUAL-CONVENTION
      STATUS current
      DESCRIPTION 
        "AgentState is an INTEGER value used in order to indicate what the A.I.M.O.S. SNMP
        Agent is about to do by the following named values:
        . snmpColdStart(1)  the agent was started and is now running
        . snmpPause(2)      not yet used
        . snmpResume(3)     not yet used
        . snmpShutDown(4)   the A.I.M.O.S. SNMP Agent is terminated shortly
        "
      SYNTAX INTEGER
        {
        snmpColdStart(1),
        snmpPause(2),
        snmpResume(3),
        snmpShutDown(4)
        }

    UTCTime ::= TEXTUAL-CONVENTION
      DISPLAY-HINT 
        "2d-1d-1d,1d:1d:1d1a"
      STATUS current
      DESCRIPTION 
        "UTCTime is an OCTET STRING having 8 octets used in order to represent date and
        time values in UTC time format. This format consists of the following fields:
        
        field  octets  contents                  range
        -----  ------  --------                  -----
          1      1-2   year                      0..2999
          2       3    month                     1..12
          3       4    day                       1..31
          4       5    hour                      0..23
          5       6    minutes                   0..59
          6       7    seconds                   0..59
          7       8    fixed character           Z
        
        For example, Tuesday May 26, 1992 at 1:30:15 PM MESZ would be displayed as:
        
        	1992-05-26,11:30:15Z
        
        In order to convert the value to local time, you have to add time zone bias and
        if necessary daylight bias.
        
        In the example above, MESZ has a time zone bias of +1 and a daylight bias of +1.
        So if you add 2 hours to 11:30:15, you'll get 1:30:15 PM."
      SYNTAX OCTET STRING (SIZE (8))

    LocalTime ::= TEXTUAL-CONVENTION
      DISPLAY-HINT 
        "2d-1d-1d,1d:1d:1d,1a1d:1d"
      STATUS current
      DESCRIPTION 
        "LocalTime is an OCTET STRING having 10 octets used in order to represent date
        and time values in local time format. It consists of the following fields:
        
        field  octets  contents                  range
        -----  ------  --------                  -----
          1      1-2   year                      0..2999
          2       3    month                     1..12
          3       4    day                       1..31
          4       5    hour                      0..23
          5       6    minutes                   0..59
          6       7    seconds                   0..59
          7       8    direction from UTC        '+' / '-'
          8       9    hours from UTC            0..13
          9      10    minutes from UTC          0..59
        
        For example, Tuesday May 26, 1992 at 1:30:15 PM MESZ would be displayed as:
        
        	1992-05-26,13:30:15,+02:00
        
        In order to convert the value to UTC time, you have to subtract the time zone
        bias and daylight bias provided with the value above.
        
        In the example above, the bias is +2 hours.
        So if you subtract 2 hours from 13:30:15, you'll get 11:30:15 UTC time."
      SYNTAX OCTET STRING (SIZE (10))

    GeographicPositionFormat ::= TEXTUAL-CONVENTION
      STATUS current
      DESCRIPTION 
        "Four formats are available:
        
          degreeMinuteSecond(0) shows degrees, minutes and seconds 
               decimalSecond(1) shows degrees, minutes and decimal seconds 
               decimalMinute(2) shows degrees and decimal minutes
               decimalDegree(3) shows decimal degrees
                 SignedValue(4) shows an unformatted value (negative value indicates S/W)
        
        Following an example for the different formats of one single GPS position:
        
          degreeMinuteSecond(0) = 35o 43' 0'' N 81o 19' 1'' W
               decimalSecond(1) = 35o 42' 59.59'' N 81o 19' 1.19'' W
               decimalMinute(2) = 35o 42.99318' N 81o 19.01982' W
               decimalDegree(3) = 35.716553o N 81.316997o W
                 SignedValue(4) = 35.716553 -81.316997  
        "
      SYNTAX INTEGER
        {
        degreeMinuteSecond(0),
        decimalSecond(1),
        decimalMinute(2),
        decimalDegree(3),
        signedValue(4)
        }

    GPSPosition ::= TEXTUAL-CONVENTION
      STATUS current
      DESCRIPTION 
        "GPSPosition is an OCTET STRING with a length of up to 30 characters 
        indicating either a latitude or a longitude.
        
        The format used is determined by aimosPhoneBookGeographicPositionFormat.
        "
      SYNTAX OCTET STRING (SIZE (0..30))

    NEOperationStatus ::= TEXTUAL-CONVENTION
      STATUS current
      DESCRIPTION 
        "NEOperationStatus is an INTEGER used in order to indicate the status of a 
        Network Element Operation by the following named values:
        
        . neoNone(0)                Network Element does not support this Operation
        . neoIdle(1)                no operation submitted since Agent Startup
        . neoSubmit(2)              used in order to submit an operation
        . neoQueued(3)              an operation is queued to the Connector
        . neoPhysicalConnecting(4)  attempting to connect the NE
        . neoPhysicalConnected(5)   NE has been connected
        . neoWaitingForSession(6)   attempting to establish a session with the NE
        . neoSessionEstablished(7)  NE session has been established
        . neoStarted(8)             NE performs the requested operation
        . neoSucceeded(9)           operation finished successful
        . neoFailed(10)             operation has failed
        
        
        If NEOperationStatus is either neoIdle(1), neoSucceeded(9) or neoFailed(10) an 
        object of this type can be set to neoSubmit(2) in order to request the execution 
        of a Network Element Operation. 
        
        neoSubmit(2) is the only writeable value; it will never be reported on get requests.
        
        If NEOperationStatus is neoNone(0) this Network Element does not support the
        Network Element Operation. Therefore it cannot be set to neoSubmit(2)."
      SYNTAX INTEGER
        {
        neoNone(0),
        neoIdle(1),
        neoSubmit(2),
        neoQueued(3),
        neoPhysicalConnecting(4),
        neoPhysicalConnected(5),
        neoWaitingForSession(6),
        neoSessionEstablished(7),
        neoStarted(8),
        neoSucceeded(9),
        neoFailed(10)
        }

    RecognitionState ::= TEXTUAL-CONVENTION
      STATUS current
      DESCRIPTION 
        "RecognitionState is an INTEGER used in order to indicate the recognition
        state of an alarm by the following named values:
        . indeterminate(0)
        . unrecognized(1)
        . recognized(2)"
      SYNTAX INTEGER
        {
        indeterminate(0),
        unrecognized(1),
        recognized(2)
        }

  
--
-- Node definitions
--
  
    system OBJECT IDENTIFIER ::= { mib-2 1 }

    
    sysDescr OBJECT-TYPE
      SYNTAX DisplayString
      MAX-ACCESS read-only
      STATUS current
      DESCRIPTION
        "A textual description of the entity.  This value should
        include the full name and version identification of the
        system's hardware type, software operating-system, and
        networking software."
      REFERENCE
        "MDS=TMDSMIB2"
      ::= { system 1 }

    
    sysObjectID OBJECT-TYPE
      SYNTAX OBJECT IDENTIFIER
      MAX-ACCESS read-only
      STATUS current
      DESCRIPTION
        "The vendor's authoritative identification of the network
        management subsystem contained in the entity.  This value is
        allocated within the SMI enterprises subtree (1.3.6.1.4.1)
        and provides an easy and unambiguous means for determining
        `what kind of box' is being managed.  For example, if vendor
        `Flintstones, Inc.' was assigned the subtree
        1.3.6.1.4.1.4242, it could assign the identifier
        1.3.6.1.4.1.4242.1.1 to its `Fred Router'."
      REFERENCE
        "MDS=TMDSMIB2"
      ::= { system 2 }

    
    sysUpTime OBJECT-TYPE
      SYNTAX TimeTicks
      MAX-ACCESS read-only
      STATUS current
      DESCRIPTION
        "The time (in hundredths of a second) since the network
        management portion of the system was last re-initialized."
      REFERENCE
        "MDS=TMDSMIB2"
      ::= { system 3 }

    
    sysContact OBJECT-TYPE
      SYNTAX DisplayString
      MAX-ACCESS read-write
      STATUS current
      DESCRIPTION
        "The textual identification of the contact person for this
        managed node, together with information on how to contact
        this person.  If no contact information is known, the value
        is the zero-length string."
      REFERENCE
        "MDS=TMDSMIB2"
      ::= { system 4 }

    
    sysName OBJECT-TYPE
      SYNTAX DisplayString
      MAX-ACCESS read-write
      STATUS current
      DESCRIPTION
        "An administratively-assigned name for this managed node.
        By convention, this is the node's fully-qualified domain
        name.  If the name is unknown, the value is the zero-length
        string."
      REFERENCE
        "MDS=TMDSMIB2"
      ::= { system 5 }

    
    sysLocation OBJECT-TYPE
      SYNTAX DisplayString
      MAX-ACCESS read-write
      STATUS current
      DESCRIPTION
        "The physical location of this node (e.g., `telephone
        closet, 3rd floor').  If the location is unknown, the value
        is the zero-length string."
      REFERENCE
        "MDS=TMDSMIB2"
      ::= { system 6 }

    
    mikom OBJECT-IDENTITY
      STATUS current
      DESCRIPTION 
        "Root of Andrew Wireless Systems GmbH"
      REFERENCE 
        "Name=Michael.Jelich@andrew.com"
      ::= { enterprises 6408 }

    
    aimosPublic OBJECT-IDENTITY
      STATUS current
      DESCRIPTION 
        "Before an user is able to login to the A.I.M.O.S. SNMP Agent, some preconditions
        must be fulfilled, which are located beneath aimosPublic and explained below.
        This branch is accessible with SNMP community set to public.
        "
      ::= { aimos 1 }

    
    aimosSystemAvailability OBJECT-TYPE
      SYNTAX SystemAvailability
      MAX-ACCESS read-only
      STATUS current
      DESCRIPTION
        "aimosSystemAvailability of type SystemAvailability gives information about system
        login possibility. The required value to be able to login is accessible(1). The
        first version of the A.I.M.O.S. SNMP Agent will report this value only.
        
        If the agent itself is not reachable by the SNMP protocol, then the manager will
        get a timeout error.
        "
      REFERENCE
        "MDS=TMDSPreLogin
        Tag=1"
      ::= { aimosPublic 1 }

    
    aimosCommunity OBJECT-TYPE
      SYNTAX Community
      MAX-ACCESS read-only
      STATUS current
      DESCRIPTION
        "aimosCommunity of type Community issues a Community-Name required for the
        communication with the A.I.M.O.S. SNMP Agent. The Community public only allows
        access to the aimosPublic area.
        
        The validity of a Community-Name expires, when
        . it has no longer been used for a certain time (s. aimosSessionTimeout)
        . the logoff followed the login (s. aimosLoginState)
        . the A.I.M.O.S. SNMP Agent Windows NT service is closed.
        
        Accessing the aimosCommunity object with the Community public (or an invalid
        Community-Name) returns a Community-Name with a random combination of characters.
        The object aimosCommunityLength determines the length of this character chain.
        Only Community-Names created in this way are accepted by the A.I.M.O.S. SNMP Agent.
        
        An access to aimosCommunity using a valid generated Community-Name (instead of
        public) provides no new name but the Community-Name used in the query.
        "
      REFERENCE
        "MDS=TMDSPreLogin
        Tag=2"
      ::= { aimosPublic 2 }

    
    aimosCommunityLength OBJECT-TYPE
      SYNTAX Unsigned32 (1..40)
      UNITS "Character"
      MAX-ACCESS read-write
      STATUS current
      DESCRIPTION
        "aimosCommunityLength is an Unsigned32 value in the range of 1 to 40 which states
        the length of community names being generated on reading of aimosCommunity.
        
        The provider is allowed to adjust this value, in order to manipulate the
        foreseeableness of the community names and therefore increase or decrease the
        security level. Although this value is in the public area (and could be read from
        everyone), a modification can take place only in a valid Session, i.e., with a
        community name, to which a valid login took place.
        "
      REFERENCE
        "MDS=TMDSPreLogin
        Tag=3"
      DEFVAL { 8 }
      ::= { aimosPublic 3 }

    
    aimosMinPasswordLength OBJECT-TYPE
      SYNTAX Unsigned32 (5..40)
      UNITS "Character"
      MAX-ACCESS read-write
      STATUS current
      DESCRIPTION
        "aimosMinPasswordLength is an Unsigned32 value in the range of 5 to 40 which
        states the requirement for the length of passwords.
        
        The provider is allowed to adjust this value, in order to manipulate the password
        security level. Although this value is in the public area (and could be read from
        everyone), a modification can take place only in a valid Session, i.e., with a
        community name, to which a valid login took place.
        "
      REFERENCE
        "MDS=TMDSPreLogin
        Tag=4"
      DEFVAL { 6 }
      ::= { aimosPublic 4 }

    
    aimosLogin OBJECT-IDENTITY
      STATUS current
      DESCRIPTION 
        "The aimosLogin branch carries the leafs for logging in as a specific user.
        
        As above-mentioned access to the branch aimosLogin is only permitted with SNMP
        community set to a value published by aimosCommunity.
        
        Login process is performed by the following actions:
        . Get SNMP community string from aimosCommunity using public as community name.
          Use this community name in further SNMP requests.
        . Set the user name in aimosLoginUserName (use the new community name!)
        . Set the corresponding password in aimosLoginPassword expect in the case of the
          first login after software installation.
          In that case a text in the following format has to be used as password:
                 nnnnnn xxxx xxxx xxxx xxxx xxxx aaaaaaa
           where n is the OrgID
                 x is the license key
                 a is the license extra data (may be omitted)
        . Set aimosLoginState to connected(1).
        . Check the current aimosLoginState.
          . If login was successful, then it is set to connected(1) state.
          . If the password is wrong, then it is set to refused(2) state.
          . If passwordExpired(4) is returned, the password has expired.
        
        Password expiration
        ===================
        All passwords are valid for an amount of days. This period of time is specified
        in aimosPasswordExpirationPeriod. If a password was unchanged for more than the
        specified number of days, then the password expires. Existing Sessions are not
        affected by the password expiration.
        
        When a password has expired, no login can be made for the corresponding user
        account, until the user has defined a new password.
        
        The new password has to be assigned to aimosLoginPassword in order to complete
        the login process. If the new password is permissible then
        . this password is stored in aimosUserPassword and has to be used in the future
        . and aimosLoginState gets connected(1).
        
        The default password (start) is expired by default. I.e., if the default password
        is used for login, the user needs to advise a new password as mentioned above.
        
        Due to the
        . minimum password length requirements (aimosMinPasswordLength)
        . or the reusability of passwords (aimosPasswordReuseCounter)
        . as well as the requirements on password security (aimosPasswordStandard)
        it may be possible, that the new password is not acceptable by the A.I.M.O.S. SNMP
        Agent. In that case, the password remains expired and the user is required to
        . devise another password and repeat this procedure until aimosLoginState gets
          connected(1)
        . or cancel the login process by setting aimosLoginState to disconnected(0)
        
        Logout
        ======
        Set aimosLoginState to disconnected(0) in order to log out. After log out the
        community name is invalid and therefore aimosLoginState gets canceled(3).
        If you need to log in again, then you have to request for a new community name
        by the steps described above."
      ::= { aimos 2 }

    
    aimosLoginUserName OBJECT-TYPE
      SYNTAX UserName
      MAX-ACCESS read-write
      STATUS current
      DESCRIPTION
        "aimosLoginUserName of type UserName is provided to record the username for login
        purposes. The username is a predefined user account or a user account created by
        the provider.
        
        When setting the Username the following SNMP ErrorStatus-values may be returned:
        . noAccess(6)            either the Organisation to which the Username belongs
                                 is deactivated (via aimosOrgActive) or the user account
                                 itself is deactivated (via aimosUserActive)
        . wrongLength(8)         the TextualConvention of this object specifies, that
                                 Usernames must be 1 to 40 characters long. If this
                                 condition is not fulfilled, the Username assignment is
                                 answered by this SNMP ErrorStatus.
        . wrongValue(10)         the Username is unknown
        . authorizationError(16) an invalid Community-Name was used
        . notWritable(17)        after a successful login the aimosLoginUserName can no
                                 longer be changed
        
        "
      REFERENCE
        "MDS=TMDSLogin
        Tag=1"
      ::= { aimosLogin 1 }

    
    aimosLoginPassword OBJECT-TYPE
      SYNTAX PasswordString
      MAX-ACCESS read-write
      STATUS current
      DESCRIPTION
        "aimosLoginPassword of type PasswordString serves to record the password of the
        user. Here, the user must enter the password assigned to the user account by one
        of the following three processes:
        . A password can be assigned when a user account is created.
        . If no password was explicitly assigned during the creation of the user account,
          the implicitly assigned default password is start. In such a case this password
          must uniquely be used for the first login.
        . Passwords expire after a certain interval (see aimosPasswordExpirationPeriod).
          If a password is expired, the user has to define a new one.
        
        A password assignment may result in one of the following SNMP ErrorStatus values:
        . wrongLength(8)         the TextualConvention of this object specifies the
                                 length of a password to range from 5 to 40 characters.
                                 The Provider may specify a higher minimum length via the
                                 object aimosMinPasswordLength. If one of the two length
                                 requirements is not kept, the password assignment will
                                 be denied with this SNMP ErrorStatus.
        . wrongEncoding(9)       the object aimosPasswordStandard specifies which
                                 characters may be used for a password. If this
                                 requirement is not kept, the password assignment will
                                 be denied with this SNMP ErrorStatus.
        . wrongValue(10)         this SNMP ErrorStatus message follows either after a
                                 trial to assign the standard password start as new
                                 password or when the password for the first login after
                                 software installation is an invalid OrgID
        . authorizationError(16) an invalid Community-Name was used
        . notWritable(17)        after a successful login the aimosLoginPassword can no
                                 longer be changed
        "
      REFERENCE
        "MDS=TMDSLogin
        Tag=2"
      ::= { aimosLogin 2 }

    
    aimosLoginState OBJECT-TYPE
      SYNTAX LoginState
      MAX-ACCESS read-write
      STATUS current
      DESCRIPTION
        "The aimosLoginState of type LoginState is used in order to accomplish the login
        process, as its value is set to connected(1).
        
        If its value is set to disconnected(0), then the user logs off and the community
        name is invalidated. Therefore it cannot be reused.
        
        In addition it serves to indicate the status of login success. To any time this
        object may emit one of the following values:
        . disconnected(0)    if access to the MIB (except the branches aimosPublic and
                             aimosLogin) is not allowed with the community name currently
                             used
        . connected(1)       if login was successful and access is permitted to the
                             entire MIB
        . refused(2)         if the password is wrong. Enter the correct password in
                             aimosLoginPassword and try to set aimosLoginState to
                             connected(1) again
        . canceled(3)        if the community name is invalidated by setting
                             aimosLoginState to disconnected(0) or due to missing traffic
                             for a certain period of time
        . passwordExpired(4) if password is expired.
        
        Setting the LoginState may result in one of the following SNMP ErrorStatus-values
        . noAccess(6)            This SNMP ErrorStatus will be returned by the A.I.M.O.S.
                                 SNMP Agent if a login failed more than three times in a
                                 row due to a wrong password. When such 'hacking' is
                                 discovered, the account will be locked for a period of
                                 30 minutes.
        . wrongValue(10)         Only the two values disconnected(0) and connected(1) may
                                 be assigned. All other values are only important for
                                 read access.
        . inconsistentValue(12)  This SNMP ErrorStatus will be returned by the A.I.M.O.S.
                                 SNMP Agent if an expired password is used to try and set
                                 the aimosLoginState to connected(1). In such a case,
                                 however, the A.I.M.O.S. SNMP Agent expects that either
                                 the new password is assigned by aimosLoginPassword or a
                                 logout by assigning aimosLoginState disconnected(0).
        . authorizationError(16) An invalid Community-Name was used.
        "
      REFERENCE
        "MDS=TMDSLogin
        Tag=3"
      ::= { aimosLogin 3 }

    
    aimosLoginOrgID OBJECT-TYPE
      SYNTAX OrgID
      MAX-ACCESS read-only
      STATUS current
      DESCRIPTION
        "aimosLoginOrgID of type OrgID contains the organisation ID of the organisation
        of the user after successful login."
      REFERENCE
        "MDS=TMDSLogin
        Tag=4"
      ::= { aimosLogin 4 }

    
    aimosLoginPhoneBookID OBJECT-TYPE
      SYNTAX Unsigned32
      MAX-ACCESS read-write
      STATUS current
      DESCRIPTION
        "After a successful login the AIMOS SNMP Agent attempts to recognize the SNMP Managers 
        aimosLoginPhonebookID by means of its IP Address.
        
        In case the aimosPhoneBookTable contains a unique representation if this IP Address the
        aimosLoginPhoneBookID of type Unsigned32 contains the appropriate aimosPhoneBookID.
        If not this value is 0,
        
        In any case this value can be set to (overridden with) a valid aimosLoginPhoneBookID.
        
        The value here is used in two cases:
        1. starting an Alarm List Resync (see description to aimosAlarmListResync)
        2. walking the aimosAlarmListTable (see its description for further details)"
      REFERENCE
        "MDS=TMDSLogin
        Tag=5"
      ::= { aimosLogin 5 }

    
    aimosObjects OBJECT-IDENTITY
      STATUS current
      DESCRIPTION 
        "The branch aimosObjects is accessible only after a successful login."
      REFERENCE 
        "MDS=TMDSDefault
        MIS=TMISDefault"
      ::= { aimos 3 }

    
    aimosSystemManagement OBJECT-IDENTITY
      STATUS current
      DESCRIPTION 
        "In this section, system-wide parameters are described. Only the provider is
        responsible for and allowed to change most of the contents of the listed MIB
        branch. Changes, which are made here may have sometimes crucial influence on the
        behaviour of the A.I.M.O.S. SNMP Agent. Thus be careful with changes in this
        section.
        "
      REFERENCE 
        "DB:SMNG"
      ::= { aimosObjects 1 }

    
    aimosMIBVersion OBJECT-TYPE
      SYNTAX Version
      MAX-ACCESS read-only
      STATUS current
      DESCRIPTION
        "This object is a read-only value of type Version representing the version of the
        MIB file."
      REFERENCE
        "MDS=TMDSSystemParams
        Tag=1"
      ::= { aimosSystemManagement 1 }

    
    aimosAgentVersion OBJECT-TYPE
      SYNTAX Version
      MAX-ACCESS read-only
      STATUS current
      DESCRIPTION
        "This object is a read-only value of type Version showing the software version of
        the A.I.M.O.S. SNMP Agent."
      REFERENCE
        "MDS=TMDSSystemParams
        Tag=2"
      ::= { aimosSystemManagement 2 }

    
    aimosOMCConnectorVersion OBJECT-TYPE
      SYNTAX Version
      MAX-ACCESS read-only
      STATUS current
      DESCRIPTION
        "This object is a read-only value of type Version displaying the software version
        of the OMC Connector."
      REFERENCE
        "MDS=TMDSSystemParams
        Tag=3"
      ::= { aimosSystemManagement 3 }

    
    aimosTrapOID OBJECT-TYPE
      SYNTAX OBJECT IDENTIFIER
      MAX-ACCESS accessible-for-notify
      STATUS current
      DESCRIPTION
        "This object of type OBJECT IDENTIFIER references the OID of the corresponding
        trap type listed in aimosNotifications, if aimosPhoneBookInterfaceType is set to
        ifAimosObsolete(4). The entry is accessible in notifications only.
        
        If aimosPhoneBookInterfaceType is not set to ifAimosObsolete(4), then the object
        snmpTrapOID is used in the notifications instead."
      ::= { aimosSystemManagement 4 }

    
    aimosOMCSDN OBJECT-TYPE
      SYNTAX SDN
      MAX-ACCESS read-write
      STATUS current
      DESCRIPTION
        "This object of type SDN is the system distinguished name of the OMC which is
        designated to uniquely identify this OMC within an organisation.
        E.g.: The third OMC in the network supervision may have an SDN of OMC=3.
        
        Changing the class name (preceding the equality mark) affect only the current
        organisation, while changing the instance number (after the equality mark) will
        affect each organisation. That's the reason, why TelCo's must not change the
        instance number."
      REFERENCE
        "MDS=TMDSSystemParams
        Tag=5"
      ::= { aimosSystemManagement 5 }

    
    aimosOMCName OBJECT-TYPE
      SYNTAX OCTET STRING (SIZE (1..40))
      MAX-ACCESS read-write
      STATUS current
      DESCRIPTION
        "This object of type Text with up to 40 characters is provided to assign a free
        definable name for the OMC, e.g. 'A.I.M.O.S. OMC - North'.
        It makes only sense if you have more than one A.I.M.O.S. OMC.
        
        Changes, which are made here, affect all organisations.
        That's why TelCo's are not allowed to make any changes here.
        "
      REFERENCE
        "MDS=TMDSSystemParams
        Tag=6"
      ::= { aimosSystemManagement 6 }

    
    aimosTimeFormat OBJECT-TYPE
      SYNTAX TimeFormat
      MAX-ACCESS read-write
      STATUS current
      DESCRIPTION
        "This object of type TimeFormat determines of how date and time values of type
        VariableTime (e.g. aimosAlarmListEventTime) will be published by the SNMP Agent.
        This would be either UTCTime or LocalTime. The latter one is the default setting.
        
        Changes made here affect only the current organisation."
      REFERENCE
        "MDS=TMDSSystemParams
        Tag=7"
      DEFVAL { localTimeFormat }
      ::= { aimosSystemManagement 7 }

    
    aimosPasswordExpirationPeriod OBJECT-TYPE
      SYNTAX Unsigned32 (0..365)
      UNITS "days"
      MAX-ACCESS read-write
      STATUS current
      DESCRIPTION
        "This object of type Unsigned32 within a range from 0 to 365 days decides the
        period of days after that passwords will expire.
        
        A value of 0 indicates, that the password will never expire; use this value in
        order to disable the password expiration facility.
        
        If a password is expired, then login is prevented by the A.I.M.O.S. SNMP Agent
        until a new password is assigned to aimosLoginPassword.
        
        Changes, which are made here, affect all organisations.
        That's why TelCo's are not allowed to make any changes here.
        "
      REFERENCE
        "MDS=TMDSSystemParams
        Tag=8"
      ::= { aimosSystemManagement 8 }

    
    aimosPasswordReuseCounter OBJECT-TYPE
      SYNTAX Unsigned32 (1..255)
      MAX-ACCESS read-write
      STATUS current
      DESCRIPTION
        "This object of type Unsigned32 with a range from 1 to 255 denotes the number
        of distinguished passwords, that must be used, before a specific one can be
        repeatedly used.
        
        A value of 3 indicates, that the 3 recent used passwords must be different to
        the new one. I.e., the user may have a list of 4 passwords used in circulation.
        
        Changes, which are made here, affect all organisations.
        That's why TelCo's are not allowed to make any changes here."
      REFERENCE
        "MDS=TMDSSystemParams
        Tag=9"
      ::= { aimosSystemManagement 9 }

    
    aimosPasswordStandard OBJECT-TYPE
      SYNTAX PasswordStandard
      MAX-ACCESS read-write
      STATUS current
      DESCRIPTION
        "This object of type PasswordStandard determines if any numeric or special
        character is required in valid password creation.
        
        Existing passwords are not affected by changes made here.
        
        Changes, which are made here, affect all organisations.
        That's why TelCo's are not allowed to make any changes here."
      REFERENCE
        "MDS=TMDSSystemParams
        Tag=10"
      ::= { aimosSystemManagement 10 }

    
    aimosSessionTimeout OBJECT-TYPE
      SYNTAX WeekMinutes
      UNITS "minutes"
      MAX-ACCESS read-write
      STATUS current
      DESCRIPTION
        "A Session is rejected after a certain time of inactivity. This object provides
        the means to adjust this period in minutes.
        
        Set this object to zero in order to disable the idle timeout facility.
        
        Changes, which are made here, affect all organisations.
        That's why TelCo's are not allowed to make any changes here."
      REFERENCE
        "MDS=TMDSSystemParams
        Tag=11"
      DEFVAL { 10 }
      ::= { aimosSystemManagement 11 }

    
    aimosOMCConnectorAddress OBJECT-TYPE
      SYNTAX IPAddressAndPort
      MAX-ACCESS read-write
      STATUS current
      DESCRIPTION
        "This object contains the IP address and the port that serves to access the OMC
        Connector. This information is required for creating Master Controllers.
        
        The value of this object is pre-set with the IP address determined by the
        A.I.M.O.S. SNMP Agent and the port set via the OMC Connector Setup. If the PC on
        which the A.I.M.O.S. SNMP Agent and the OMC Connector are running has several IP
        addresses, the selection made by the A.I.M.O.S. SNMP Agent might be wrong. In such
        a case the IP address can be changed. Since the port number is derived from the
        OMC Connector Setup, it cannot be changed, here. It should be left out when the IP
        address is changed.
        "
      REFERENCE
        "MDS=TMDSSystemParams
        Tag=12"
      ::= { aimosSystemManagement 12 }

    
    aimosCurrentTime OBJECT-TYPE
      SYNTAX VariableTime
      MAX-ACCESS read-only
      STATUS current
      DESCRIPTION
        "This object of type VariableTime is used in heartbeat notifications and states
        the heartbeat notifications event time.
        This object also states the current time of the A.I.M.O.S. SNMP Agent."
      REFERENCE
        "MDS=TMDSSystemParams
        Tag=13"
      ::= { aimosSystemManagement 13 }

    
    aimosUserManagement OBJECT-IDENTITY
      STATUS current
      DESCRIPTION 
        "The user management contains all access authorisation related data of
        organisations and its user accounts.
        
        Each organisation may have user accounts. An user account is required
        in order to get access to the A.I.M.O.S. SNMP Agent. An user account having
        the required rights can be used in order to create further user accounts
        with similar or less access rights.
        
        Read and write access rights are defined per area and are combined in
        'roles'. The access rights of a user account are determined by assigning
        it to a certain role.
        
        The system is shipped with predefined organisations, user accounts, roles
        and its right assignments. Nevertheless the provider is responsible for the
        user management.
        "
      ::= { aimosObjects 2 }

    
    aimosOrgTable OBJECT-TYPE
      SYNTAX SEQUENCE OF AimosOrgEntry
      MAX-ACCESS not-accessible
      STATUS current
      DESCRIPTION
        "Informations about organizations. A organization is a company having a
        relationship with A.I.M.O.S.. Relationship can be one of the following:
        - manufacturer
        - provider
        - telco
        
        There is always exact one manufacturer and one provider.
        It's up to the provider to complete this table with one entry for each mobile
        network provider (telco) using his A.I.M.O.S. service.
        
        Users with aimosOrgLevel=telco are not allowed to modify contents of this table
        except of aimosOrgText and aimosOrgActiveWorkShiftID
        
        Insert rows: set aimosOrgName.<MIKOM provided OrgID> to the organisation's name
        Delete rows: set aimosOrgName.<aimosOrgID> to 'delete' (without quotation marks).
        
        TelCo's are not allowed to insert or delete rows."
      REFERENCE
        "DB:GRP"
      ::= { aimosUserManagement 1 }

    
    aimosOrgEntry OBJECT-TYPE
      SYNTAX AimosOrgEntry
      MAX-ACCESS not-accessible
      STATUS current
      DESCRIPTION
        "see description for table entry..."
      REFERENCE
        "MDS=TMDSOrgTable
        MIS=TMISOrgTable"
      INDEX { aimosOrgID }
      ::= { aimosOrgTable 1 }

    
    AimosOrgEntry ::=
      SEQUENCE { 
        aimosOrgID
          OrgID,
        aimosOrgName
          OCTET STRING,
        aimosOrgText
          Text,
        aimosOrgLevel
          OrgLevel,
        aimosOrgMCC
          MCC,
        aimosOrgMNC
          MNC,
        aimosOrgActive
          Boolean,
        aimosOrgDNSeparator
          DistinguishedNameSeparator,
        aimosOrgDNConcatenator
          DistinguishedNameHierarchySymbol,
        aimosOrgCCConcatenator
          CableCodeConcatenator,
        aimosOrgActiveWorkShiftID
          TableIndex,
        aimosOrgNextUserID
          TableIndex,
        aimosOrgNextWorkShiftID
          TableIndex,
        aimosOrgNextAlarmRecipientListID
          TableIndex,
        aimosOrgNextPhoneBookID
          TableIndex
       }

    aimosOrgID OBJECT-TYPE
      SYNTAX OrgID
      MAX-ACCESS read-only
      STATUS current
      DESCRIPTION
        "This object is a Mikom provided world-wide unique identification number of an
        organisation of type OrgID."
      ::= { aimosOrgEntry 1 }

    
    aimosOrgName OBJECT-TYPE
      SYNTAX OCTET STRING (SIZE (1..40))
      MAX-ACCESS read-write
      STATUS current
      DESCRIPTION
        "This object offers the possibility to designate the organisation mentioned
        in aimosOrgID.
        
        Set this value to 'delete' (without quotation marks) in order to delete this
        table entry."
      ::= { aimosOrgEntry 2 }

    
    aimosOrgText OBJECT-TYPE
      SYNTAX Text
      MAX-ACCESS read-write
      STATUS current
      DESCRIPTION
        "This object gives each organisation the possibility to configure a piece of text."
      ::= { aimosOrgEntry 4 }

    
    aimosOrgLevel OBJECT-TYPE
      SYNTAX OrgLevel
      MAX-ACCESS read-only
      STATUS current
      DESCRIPTION
        "This object of type OrgLevel denotes the role of the organisation.
        Possible values are manufacturer(0), provider(1) and telco(2)."
      DEFVAL { telco }
      ::= { aimosOrgEntry 5 }

    
    aimosOrgMCC OBJECT-TYPE
      SYNTAX MCC
      MAX-ACCESS read-only
      STATUS current
      DESCRIPTION
        "This object of type MCC is the mobile country code of a TelCo organisation.
        Manufacturer and provider have the MCC of its country."
      ::= { aimosOrgEntry 6 }

    
    aimosOrgMNC OBJECT-TYPE
      SYNTAX MNC
      MAX-ACCESS read-only
      STATUS current
      DESCRIPTION
        "This object of type MNC is the mobile network code of a TelCo organisation.
        Manufacturer and provider have a MNC of 0 (zero)."
      ::= { aimosOrgEntry 7 }

    
    aimosOrgActive OBJECT-TYPE
      SYNTAX Boolean
      MAX-ACCESS read-write
      STATUS current
      DESCRIPTION
        "This object sets the activity state of an organisation. An organisation account
        is activated by writing true and deactivated by writing false to this object.
        
        Users of a deactivated organisations are not allowed to login. Existing Sessions
        are not affected by organisation deactivation."
      DEFVAL { true }
      ::= { aimosOrgEntry 8 }

    
    aimosOrgDNSeparator OBJECT-TYPE
      SYNTAX DistinguishedNameSeparator
      MAX-ACCESS read-write
      STATUS current
      DESCRIPTION
        "This object of type DistinguishedNameSeparator separates the
        Distinguished Names into object type and object instance.
        E.g.:
        . 3GPP recommends equality mark (RU=17)
        . Nokia NetAct recommends hyphen (RU-17)
        
        Factory setting is an equality mark (=)."
      DEFVAL { "=" }
      ::= { aimosOrgEntry 9 }

    
    aimosOrgDNConcatenator OBJECT-TYPE
      SYNTAX DistinguishedNameHierarchySymbol
      MAX-ACCESS read-write
      STATUS current
      DESCRIPTION
        "This object of type DistinguishedNameHierarchySymbol divides
        System Distinguished Names in its parts, the Relative Distinguished Names.
        E.g.:
        . 3GPP recommends comma (OMC=1,MC=4,SRMU=17)
        . Nokia NetAct recommends slash mark (OMC-1/MC-4/SRMU-17)
        
        Factory setting is a comma (,)."
      DEFVAL { "," }
      ::= { aimosOrgEntry 10 }

    
    aimosOrgCCConcatenator OBJECT-TYPE
      SYNTAX CableCodeConcatenator
      MAX-ACCESS read-write
      STATUS current
      DESCRIPTION
        "This object of type CableCodeConcatenator is used in
        aimosAlarmListCustomerCableInfo for concatenation of Cable Codes.
        
        Mikom default is a comma."
      DEFVAL { "," }
      ::= { aimosOrgEntry 11 }

    
    aimosOrgActiveWorkShiftID OBJECT-TYPE
      SYNTAX TableIndex
      MAX-ACCESS read-write
      STATUS current
      DESCRIPTION
        "This object denotes the active work shift for delegation of alarms.
        The description for aimosWorkShiftTable contains more about work shifts."
      DEFVAL { 1 }
      ::= { aimosOrgEntry 12 }

    
    aimosOrgNextUserID OBJECT-TYPE
      SYNTAX TableIndex
      MAX-ACCESS read-only
      STATUS current
      DESCRIPTION
        "Provides the aimosUserID to be used in creating a new user account
        (aimosUserTable)."
      ::= { aimosOrgEntry 13 }

    
    aimosOrgNextWorkShiftID OBJECT-TYPE
      SYNTAX TableIndex
      MAX-ACCESS read-only
      STATUS current
      DESCRIPTION
        "Provides the aimosWorkShiftID to be used in creating a new work shift
        (aimosWorkShiftTable)."
      ::= { aimosOrgEntry 14 }

    
    aimosOrgNextAlarmRecipientListID OBJECT-TYPE
      SYNTAX TableIndex
      MAX-ACCESS read-only
      STATUS current
      DESCRIPTION
        "Provides the aimosAlarmRecipientListID to be used in creating a new alarm
        recipient list (aimosAlarmRecipientListTable)."
      ::= { aimosOrgEntry 15 }

    
    aimosOrgNextPhoneBookID OBJECT-TYPE
      SYNTAX TableIndex
      MAX-ACCESS read-only
      STATUS current
      DESCRIPTION
        "Provides the aimosPhoneBookID to be used in creating a new phone book entry
        (aimosPhoneBookTable)."
      ::= { aimosOrgEntry 16 }

    
    aimosUserTable OBJECT-TYPE
      SYNTAX SEQUENCE OF AimosUserEntry
      MAX-ACCESS not-accessible
      STATUS current
      DESCRIPTION
        "This table holds user related data. A user is a employee of a organization having
        an login account.
        
        This table is indexed by aimosOrgID and aimosUserID. Nevertheless aimosUserID is
        a unique number within one OMC aimosOrgID is included in indexing because of
        access rights.
        
        Insert rows: set aimosUserName.<aimosOrgID>.<value of aimosOrgNextUserID> to
                     user's name
        Delete rows: set aimosUserName.<aimosOrgID>.<aimosUserID> to 'delete' (without
                     quotation marks)"
      REFERENCE
        "DB:USR"
      ::= { aimosUserManagement 2 }

    
    aimosUserEntry OBJECT-TYPE
      SYNTAX AimosUserEntry
      MAX-ACCESS not-accessible
      STATUS current
      DESCRIPTION
        "see description for table entry..."
      REFERENCE
        "MDS=TMDSUserTable
        MIS=TMISUserTable"
      INDEX { aimosOrgID, aimosUserID }
      ::= { aimosUserTable 1 }

    
    AimosUserEntry ::=
      SEQUENCE { 
        aimosUserID
          TableIndex,
        aimosUserName
          UserName,
        aimosUserPassword
          PasswordString,
        aimosUserText
          Text,
        aimosUserRoleID
          TableIndex,
        aimosUserActive
          Boolean,
        aimosUserPasswordAge
          VariableTime
       }

    aimosUserID OBJECT-TYPE
      SYNTAX TableIndex
      MAX-ACCESS read-only
      STATUS current
      DESCRIPTION
        "This object is numbered consecutively. aimosOrgNextUserID tells you the value to
        be used in row/user creation."
      ::= { aimosUserEntry 1 }

    
    aimosUserName OBJECT-TYPE
      SYNTAX UserName
      MAX-ACCESS read-write
      STATUS current
      DESCRIPTION
        "This object of type UserName hosts the users name. A user name can be used once
        in the OMC. Therefore it is advisable to prefix the user name with an
        organisation sign (e.g. 'D1 - Meier').
        
        Changing the user name will reset the aimosUserPassword to the default password
        (start).
        
        Setting this value to delete deletes this table entry (the user account)."
      ::= { aimosUserEntry 2 }

    
    aimosUserPassword OBJECT-TYPE
      SYNTAX PasswordString
      MAX-ACCESS read-write
      STATUS current
      DESCRIPTION
        "This object of type PasswordString is the password for an user account required
        in order to login into the OMC. The default password is start. During the first
        login attempt using the default password the user needs to change the password.
        
        Each user is allowed to change its own password by means of
        . set aimosLoginPassword (if aimosLoginState is refused) or
        . set this object (if aimosLoginState is connected)
        to the new password. The user does not need to have readWrite(2) access to the
        RightArea administrationOMCAccounts(500) in order to change its own password.
        This access right is required in order to set the password of any user account."
      DEFVAL { "start" }
      ::= { aimosUserEntry 3 }

    
    aimosUserText OBJECT-TYPE
      SYNTAX Text
      MAX-ACCESS read-write
      STATUS current
      DESCRIPTION
        "This object of type Text gives the possibility to configure a piece of text."
      ::= { aimosUserEntry 4 }

    
    aimosUserRoleID OBJECT-TYPE
      SYNTAX TableIndex
      MAX-ACCESS read-write
      STATUS current
      DESCRIPTION
        "With this object a certain role is assigned to a user account. Thus, via the
        table aimosRoleRightTable the User is granted the rights that are assigned to
        this role.
        
        The default value (0) is an illegal role ID, thus the user is by default not
        assigned to any role and couldn't access the MIB except the public and login
        area."
      DEFVAL { 0 }
      ::= { aimosUserEntry 5 }

    
    aimosUserActive OBJECT-TYPE
      SYNTAX Boolean
      MAX-ACCESS read-write
      STATUS current
      DESCRIPTION
        "This object activates and deactivates an user account.
        If set to true the account is active and the user is able to log in,
        otherwise (false) no log in is possible.
        
        Existing Sessions are not affected by user deactivation."
      DEFVAL { true }
      ::= { aimosUserEntry 6 }

    
    aimosUserPasswordAge OBJECT-TYPE
      SYNTAX VariableTime
      MAX-ACCESS read-only
      STATUS current
      DESCRIPTION
        "This object states the time when the password was most recently changed."
      ::= { aimosUserEntry 7 }

    
    aimosNextRoleID OBJECT-TYPE
      SYNTAX TableIndex
      MAX-ACCESS read-only
      STATUS current
      DESCRIPTION
        "This object is used in order to produce new roles within the aimosRoleTable.
        Its value has to be used as the identifier (aimosRoleID) of the new role."
      REFERENCE
        "MDS=TMDSNextID
        Tag=1"
      ::= { aimosUserManagement 3 }

    
    aimosRoleTable OBJECT-TYPE
      SYNTAX SEQUENCE OF AimosRoleEntry
      MAX-ACCESS not-accessible
      STATUS current
      DESCRIPTION
        "Access control is made using roles. A role is a synonym for a certain
        combination of read and write access rights (AccessRight) to certain areas
        (RightArea). A role could be called e.g. 'admin' or 'alarm manager'.
        This table, indexed by aimosRoleID, contains a list of that roles.
        
        By assigning a role to a User via aimosUserRoleID, the read and write access
        rights connected to this role will be granted to the user account.
        
        Insert rows: set aimosRoleOwner.<value of aimosNextRoleID> to the aimosOrgID of
                     the role's owner
        Delete rows: set aimosRoleName.<aimosRoleID> to 'delete' (without quotation
                     marks)
        
        TelCo's are not allowed to insert or delete rows."
      ::= { aimosUserManagement 4 }

    
    aimosRoleEntry OBJECT-TYPE
      SYNTAX AimosRoleEntry
      MAX-ACCESS not-accessible
      STATUS current
      DESCRIPTION
        "see description for table entry..."
      REFERENCE
        "MDS=TMDSRoleTable
        MIS=TMISRoleTable"
      INDEX { aimosRoleID }
      ::= { aimosRoleTable 1 }

    
    AimosRoleEntry ::=
      SEQUENCE { 
        aimosRoleID
          TableIndex,
        aimosRoleName
          OCTET STRING
       }

    aimosRoleID OBJECT-TYPE
      SYNTAX TableIndex
      MAX-ACCESS read-only
      STATUS current
      DESCRIPTION
        "This object is numbered consecutively. Zero value is not allowed.
        aimosNextRoleID tells you the ID to be used in row creation."
      ::= { aimosRoleEntry 1 }

    
    aimosRoleName OBJECT-TYPE
      SYNTAX OCTET STRING (SIZE (1..40))
      MAX-ACCESS read-write
      STATUS current
      DESCRIPTION
        "This object contains a name for the role with up to 40 characters.
        The table entry is deleted by setting this value to delete.
        "
      ::= { aimosRoleEntry 2 }

    
    aimosRoleRightTable OBJECT-TYPE
      SYNTAX SEQUENCE OF AimosRoleRightEntry
      MAX-ACCESS not-accessible
      STATUS current
      DESCRIPTION
        "Access control is made using roles. A role is a synonym for a certain
        combination of read and write access rights (AccessRight) to certain areas
        (RightArea). A role could be called e.g. 'admin' or 'alarm manager'.
        
        In this table, indexed by aimosRoleID and aimosRoleRightArea, the RightArea's of
        the Controller are assigned to the roles listed in the aimosRoleTable.
        
        Insert rows: set aimosRoleRightAccess.<aimosRoleID>.<aimosRoleRight> to readOnly/
                     readWrite
        Delete rows: set aimosRoleRightAccess.<aimosRoleID>.<aimosRoleRight> to noAccess
        
        TelCo's are not allowed to insert or delete rows."
      ::= { aimosUserManagement 5 }

    
    aimosRoleRightEntry OBJECT-TYPE
      SYNTAX AimosRoleRightEntry
      MAX-ACCESS not-accessible
      STATUS current
      DESCRIPTION
        "see description for table entry..."
      REFERENCE
        "MDS=TMDSRoleRightTable
        MIS=TMISRoleRightTable"
      INDEX { aimosRoleID, aimosRoleRightArea }
      ::= { aimosRoleRightTable 1 }

    
    AimosRoleRightEntry ::=
      SEQUENCE { 
        aimosRoleRightArea
          RightArea,
        aimosRoleRightAccess
          AccessRight
       }

    aimosRoleRightArea OBJECT-TYPE
      SYNTAX RightArea
      MAX-ACCESS read-only
      STATUS current
      DESCRIPTION
        "This object of type RightArea determines the right area arised from the
        controller software to be attached to a particular role identified by
        the index object aimosRoleID."
      ::= { aimosRoleRightEntry 1 }

    
    aimosRoleRightAccess OBJECT-TYPE
      SYNTAX AccessRight
      MAX-ACCESS read-write
      STATUS current
      DESCRIPTION
        "This object of type AccessRight determines whether read, write or no access to
        a specific RightArea has to be assigned to the affected role.
        
        Write access includes read access.
        Setting this value to noAccess deletes this entry.
        "
      ::= { aimosRoleRightEntry 2 }

    
    aimosInitiallyMasterLoginUserName OBJECT-TYPE
      SYNTAX OCTET STRING (SIZE (1..20))
      MAX-ACCESS read-write
      STATUS current
      DESCRIPTION
        "When a new Master Controller is created by making a new entry into the table
        aimosMasterUnitTable, the A.I.M.O.S. SNMP Agent requires a pre-setting for the
        object aimosMasterLoginUserName. This pre-setting is provided by this object.
        
        It is of the UserName type and must consist at least of one character and 20
        characters at the most. The pre-setting is Owner.
        
        Changing the aimosInitiallyMasterLoginUserName has no effect on already existing
        user accounts on the Master Units."
      REFERENCE
        "MDS=TMDSSystemParams
        Tag=1001"
      ::= { aimosUserManagement 6 }

    
    aimosInitiallyMasterLoginPassword OBJECT-TYPE
      SYNTAX ControllerPassword
      MAX-ACCESS read-write
      STATUS current
      DESCRIPTION
        "When a new Master Controller is created by making a new entry into the table
        aimosMasterUnitTable, the A.I.M.O.S. SNMP Agent requires a pre-setting for the
        object aimosMasterLoginPassword. This pre-setting is provided by this object.
        
        It is of the ControllerPassword type and must consist of small and capital
        letters (a-z) as well as numbers. Other characters are not allowed.
        
        The password can be read, but the A.I.M.O.S. SNMP Agent only displays star marks
        (*) instead of the actual password. The pre-setting is Apwd4own.
        
        Changing the aimosInitiallyMasterLoginPassword has no effect on already existing
        user accounts on the Master Units."
      REFERENCE
        "MDS=TMDSSystemParams
        Tag=1002"
      ::= { aimosUserManagement 7 }

    
    aimosBandManagement OBJECT-IDENTITY
      STATUS current
      DESCRIPTION 
        "Band Management is provided for allocation of radio frequencies to
        mobile network companies (TelCo's).
        "
      ::= { aimosObjects 3 }

    
    aimosBandTable OBJECT-TYPE
      SYNTAX SEQUENCE OF AimosBandEntry
      MAX-ACCESS not-accessible
      STATUS current
      DESCRIPTION
        "This table, indexed by aimosBandID, configures the characteristics of each
        RF band. This set up is done by Mikom.
        
        Insert rows: must only be done by Mikom
        Delete rows: must only be done by Mikom"
      REFERENCE
        "DB:RFB"
      ::= { aimosBandManagement 1 }

    
    aimosBandEntry OBJECT-TYPE
      SYNTAX AimosBandEntry
      MAX-ACCESS not-accessible
      STATUS current
      DESCRIPTION
        "see description for table entry..."
      REFERENCE
        "MIS=TMISBandTable
        MDS=TMDSBandTable"
      INDEX { aimosBandID }
      ::= { aimosBandTable 1 }

    
    AimosBandEntry ::=
      SEQUENCE { 
        aimosBandID
          NetworkStandard,
        aimosBandDLmin
          FrequencyRange,
        aimosBandDLmax
          FrequencyRange,
        aimosBandULFrequencyGap
          Unsigned32,
        aimosBandULChannelGap
          ARFCN
       }

    aimosBandID OBJECT-TYPE
      SYNTAX NetworkStandard
      MAX-ACCESS read-only
      STATUS current
      DESCRIPTION
        "This object of type NetworkStandard determines the network standard of the band
        to which this entry belongs to."
      ::= { aimosBandEntry 1 }

    
    aimosBandDLmin OBJECT-TYPE
      SYNTAX FrequencyRange
      UNITS "kHz"
      MAX-ACCESS read-only
      STATUS current
      DESCRIPTION
        "This object of type FrequencyRange is the lowest DL frequency (kHz) possible
        in a specific band."
      ::= { aimosBandEntry 2 }

    
    aimosBandDLmax OBJECT-TYPE
      SYNTAX FrequencyRange
      UNITS "kHz"
      MAX-ACCESS read-only
      STATUS current
      DESCRIPTION
        "This object of type FrequencyRange is the highest DL frequency (kHz) possible
        in a specific band."
      ::= { aimosBandEntry 3 }

    
    aimosBandULFrequencyGap OBJECT-TYPE
      SYNTAX Unsigned32 (10000..95000)
      UNITS "kHz"
      MAX-ACCESS read-only
      STATUS current
      DESCRIPTION
        "This object of type Unsigned32 with a range from 10000 to 95000 represents the
        frequency gap in kHz between UL and DL.
        
        Uplink frequency = downlink frequency - gap."
      ::= { aimosBandEntry 4 }

    
    aimosBandULChannelGap OBJECT-TYPE
      SYNTAX ARFCN
      MAX-ACCESS read-only
      STATUS current
      DESCRIPTION
        "This object of type ARFCN represents the ARFCN gap between UL and DL.
        
        Uplink ARFCN = downlink ARFCN - gap."
      ::= { aimosBandEntry 5 }

    
    aimosBandCalculationTable OBJECT-TYPE
      SYNTAX SEQUENCE OF AimosBandCalculationEntry
      MAX-ACCESS not-accessible
      STATUS current
      DESCRIPTION
        "Frequency calculation for any ARFCN can be done by the following formula:
        
        fDL(ARFCN) = fStart + fBandWidth * (ARFCN-aOffset)
        
        This table contains the information required to calculate the frequency for any
        ARFCN for any network band. E.g.: the formula for Extended GSM900 is
        
        fDL(ARFCN) = 935000 + 200 * (ARFCN - 1024)
        
        Determination of frequency for ARFCN 1023 in E-GSM900 is realised by the
        following formula:
        
        fDL(1023) = 935.000 + 200 * (1023 - 1024) = 934.800 kHz
        
        Insert rows: must only be done by Mikom
        Delete rows: must only be done by Mikom"
      REFERENCE
        "DB:RFBC"
      ::= { aimosBandManagement 2 }

    
    aimosBandCalculationEntry OBJECT-TYPE
      SYNTAX AimosBandCalculationEntry
      MAX-ACCESS not-accessible
      STATUS current
      DESCRIPTION
        "see description for table entry..."
      REFERENCE
        "MIS=TMISBandCalculationTable
        MDS=TMDSBandCalculationTable"
      INDEX { aimosBandID, aimosBandCalculationID }
      ::= { aimosBandCalculationTable 1 }

    
    AimosBandCalculationEntry ::=
      SEQUENCE { 
        aimosBandCalculationID
          TableIndex,
        aimosBandCalculationMin
          ARFCN,
        aimosBandCalculationMax
          ARFCN,
        aimosBandCalculationFormulaStart
          FrequencyRange,
        aimosBandCalculationFormulaBandWidth
          Integer32,
        aimosBandCalculationFormulaOffset
          ARFCN
       }

    aimosBandCalculationID OBJECT-TYPE
      SYNTAX TableIndex (1..5)
      MAX-ACCESS read-only
      STATUS current
      DESCRIPTION
        "Enumerated consecutively."
      ::= { aimosBandCalculationEntry 1 }

    
    aimosBandCalculationMin OBJECT-TYPE
      SYNTAX ARFCN
      MAX-ACCESS read-only
      STATUS current
      DESCRIPTION
        "First ARFCN for wich the aimosBandCalculationFormula-leafs are valid."
      ::= { aimosBandCalculationEntry 2 }

    
    aimosBandCalculationMax OBJECT-TYPE
      SYNTAX ARFCN
      MAX-ACCESS read-only
      STATUS current
      DESCRIPTION
        "Last ARFCN for wich the aimosBandCalculationFormula-leafs are valid."
      ::= { aimosBandCalculationEntry 3 }

    
    aimosBandCalculationFormulaStart OBJECT-TYPE
      SYNTAX FrequencyRange
      UNITS "kHz"
      MAX-ACCESS read-only
      STATUS current
      DESCRIPTION
        "You can calculate the frequency for any ARFCN with the following formula:
        
        fDL(ARFCN) = aimosBandCalculationFormulaStart
                   + aimosBandCalculationFormulaGap *
                     (ARFCN-aimosBandCalculationFormulaOffset)
        
        Example: formula for Extended GSM 900 is 935000 + 200 * (ARFCN - 1024)
        
        Determine frequency of ARFCN 1023 in E-GSM900:
        
        fDL(1023) = 935.000 + 200 * (1023 - 1024) = 934.800 kHz
        
        In this example aimosBandCalculationFormulaStart must have the value 935000."
      ::= { aimosBandCalculationEntry 4 }

    
    aimosBandCalculationFormulaBandWidth OBJECT-TYPE
      SYNTAX Integer32 (25..2500)
      UNITS "kHz"
      MAX-ACCESS read-only
      STATUS current
      DESCRIPTION
        "You can calculate the frequency for any ARFCN with the following formula:
        
        fDL(ARFCN) = aimosBandCalculationFormulaStart
                   + aimosBandCalculationFormulaGap *
                     (ARFCN-aimosBandCalculationFormulaOffset)
        
        Example: formula for Extended GSM 900 is 935000 + 200 * (ARFCN - 1024)
        
        Determine frequency of ARFCN 1023 in E-GSM900:
        
        fDL(1023) = 935.000 + 200 * (1023 - 1024) = 934.800 kHz
        
        In this example aimosBandCalculationFormulaGap must have the value 200."
      ::= { aimosBandCalculationEntry 5 }

    
    aimosBandCalculationFormulaOffset OBJECT-TYPE
      SYNTAX ARFCN
      MAX-ACCESS read-only
      STATUS current
      DESCRIPTION
        "You can calculate the frequency for any ARFCN with the following formula:
        
        fDL(ARFCN) = aimosBandCalculationFormulaStart
                   + aimosBandCalculationFormulaGap *
                     (ARFCN-aimosBandCalculationFormulaOffset)
        
        Example: formula for Extended GSM 900 is 935000 + 200 * (ARFCN - 1024)
        
        Determine frequency of ARFCN 1023 in E-GSM900:
        
        fDL(1023) = 935.000 + 200 * (1023 - 1024) = 934.800 kHz
        
        In this example aimosBandCalculationFormulaOffset must have the value 1024."
      ::= { aimosBandCalculationEntry 6 }

    
    aimosLicenseeTable OBJECT-TYPE
      SYNTAX SEQUENCE OF AimosLicenseeEntry
      MAX-ACCESS not-accessible
      STATUS current
      DESCRIPTION
        "This table is indexed by aimosOrgID, aimosBandID and aimosLicenseeFirstARFCN and
        shows information about frequencies licensed by Mobile Network Providers.
        
        Insert rows: set aimosLicenseeARFCNCount.<aimosOrgID>.<aimosBandID>.
                     <aimosLicenseeFirstARFCN> to the number of channels in band
                     aimosBandID starting with aimosLicenseeFirstARFCN used by aimosOrgID
        Delete rows: set aimosLicenseeARFCNCount.<aimosOrgID>.<aimosBandID>.
                     <aimosLicenseeFirstARFCN> to zero
        
        TelCo's are not allowed to insert or delete rows."
      REFERENCE
        "DB:MNCC"
      ::= { aimosBandManagement 3 }

    
    aimosLicenseeEntry OBJECT-TYPE
      SYNTAX AimosLicenseeEntry
      MAX-ACCESS not-accessible
      STATUS current
      DESCRIPTION
        "see description for table entry..."
      REFERENCE
        "MIS=TMISLicenseeTable
        MDS=TMDSLicenseeTable"
      INDEX { aimosOrgID, aimosBandID, aimosLicenseeFirstARFCN }
      ::= { aimosLicenseeTable 1 }

    
    AimosLicenseeEntry ::=
      SEQUENCE { 
        aimosLicenseeFirstARFCN
          ARFCN,
        aimosLicenseeARFCNCount
          ARFCN
       }

    aimosLicenseeFirstARFCN OBJECT-TYPE
      SYNTAX ARFCN
      MAX-ACCESS read-only
      STATUS current
      DESCRIPTION
        "This object of type ARFCN is the first ARFCN of an licensed interval.
        The size of an ARFCN interval is specified by aimosLicenseeARFCNCount."
      ::= { aimosLicenseeEntry 1 }

    
    aimosLicenseeARFCNCount OBJECT-TYPE
      SYNTAX ARFCN
      MAX-ACCESS read-write
      STATUS current
      DESCRIPTION
        "this object of type ARFCN represents the size of each ARFCN interval.
        The last ARFCN of an ARFCN interval is calculated by the following formula:
        
          last ARFCN = aimosLicenseeFirstARFCN+aimosLicenseeARFCNCount-1.
        
        Set this value to 0 (zero) to delete this table entry.
        "
      ::= { aimosLicenseeEntry 2 }

    
    aimosFrequencyTable OBJECT-TYPE
      SYNTAX SEQUENCE OF AimosFrequencyEntry
      MAX-ACCESS not-accessible
      STATUS current
      DESCRIPTION
        "This table is indexed by aimosBandID and aimosFrequencyARFCN and
        tells you per radio frequency channel number its radio frequency and licensee
        (identified by its aimosOrgID).
        
        Insert rows: not applicable (calculated by contents of aimosBandCalculationTable)
        Delete rows: not applicable (calculated by contents of aimosBandCalculationTable)
        "
      REFERENCE
        "DB:-"
      ::= { aimosBandManagement 4 }

    
    aimosFrequencyEntry OBJECT-TYPE
      SYNTAX AimosFrequencyEntry
      MAX-ACCESS not-accessible
      STATUS current
      DESCRIPTION
        "see description for table entry..."
      INDEX { aimosBandID, aimosFrequencyARFCN }
      ::= { aimosFrequencyTable 1 }

    
    AimosFrequencyEntry ::=
      SEQUENCE { 
        aimosFrequencyARFCN
          ARFCN,
        aimosFrequencyValue
          FrequencyRange,
        aimosFrequencyOwner
          OrgID
       }

    aimosFrequencyARFCN OBJECT-TYPE
      SYNTAX ARFCN
      MAX-ACCESS read-only
      STATUS current
      DESCRIPTION
        "This object of type ARFCN is the index of this table."
      ::= { aimosFrequencyEntry 1 }

    
    aimosFrequencyValue OBJECT-TYPE
      SYNTAX FrequencyRange
      UNITS "kHz"
      MAX-ACCESS read-only
      STATUS current
      DESCRIPTION
        "This object of type FrequencyRange returns the frequency in kHz for
        aimosFrequencyARFCN."
      ::= { aimosFrequencyEntry 2 }

    
    aimosFrequencyOwner OBJECT-TYPE
      SYNTAX OrgID
      MAX-ACCESS read-only
      STATUS current
      DESCRIPTION
        "This object of type OrgID returns the organisation ID of the TelCo owning the
        license for this frequency/ARFCN."
      ::= { aimosFrequencyEntry 3 }

    
    aimosARFCNTable OBJECT-TYPE
      SYNTAX SEQUENCE OF AimosARFCNEntry
      MAX-ACCESS not-accessible
      STATUS current
      DESCRIPTION
        "This table is indexed by aimosBandID and aimosARFCNFrequency and
        tells you per radio frequency its radio frequency channel number and licensee
        (identified by its aimosOrgID).
        
        Insert rows: not applicable (calculated by contents of aimosBandCalculationTable)
        Delete rows: not applicable (calculated by contents of aimosBandCalculationTable)
        "
      REFERENCE
        "DB:-"
      ::= { aimosBandManagement 5 }

    
    aimosARFCNEntry OBJECT-TYPE
      SYNTAX AimosARFCNEntry
      MAX-ACCESS not-accessible
      STATUS current
      DESCRIPTION
        "see description for table entry..."
      INDEX { aimosBandID, aimosARFCNFrequency }
      ::= { aimosARFCNTable 1 }

    
    AimosARFCNEntry ::=
      SEQUENCE { 
        aimosARFCNFrequency
          FrequencyRange,
        aimosARFCNValue
          ARFCN,
        aimosARFCNOwner
          OrgID
       }

    aimosARFCNFrequency OBJECT-TYPE
      SYNTAX FrequencyRange
      UNITS "kHz"
      MAX-ACCESS read-only
      STATUS current
      DESCRIPTION
        "This object of type FrequencyRange is the index (kHz) of this table."
      ::= { aimosARFCNEntry 1 }

    
    aimosARFCNValue OBJECT-TYPE
      SYNTAX ARFCN
      MAX-ACCESS read-only
      STATUS current
      DESCRIPTION
        "This object of type ARFCN returns the ARFCN
        that corresponds to aimosARFCNFrequency."
      ::= { aimosARFCNEntry 2 }

    
    aimosARFCNOwner OBJECT-TYPE
      SYNTAX OrgID
      MAX-ACCESS read-only
      STATUS current
      DESCRIPTION
        "This object of type OrgID returns the organisation ID
        of the TelCo owning the license for this ARFCN/frequency."
      ::= { aimosARFCNEntry 3 }

    
    aimosAlarmManagement OBJECT-IDENTITY
      STATUS current
      DESCRIPTION 
        "This is a short introduction in order to help you understand how the A.I.M.O.S.
        SNMP Agent realises SNMP alarm forwarding. When the A.I.M.O.S. SNMP Agent is
        informed about a failure in the monitored system, it must find out which SNMP
        Managers will have to get an alarm message. Each SNMP Manager who is to get the
        alarm message, requires an entry in the aimosPhoneBookTable. This entry contains
        the IP address used for alarm forwarding.
        
        Prior to the explanation on how the A.I.M.O.S. SNMP Agent determines the list of
        phone book entries which have to be informed about an active alarm, the three
        aspects with a decisive influence on this determination will be explained in
        the following:
        
        . Alarms with similar characteristics will be put together in alarm groups.
          The alarm groups defined in the system are listed in the table
          aimosAlarmGroupTable. Via aimosAlarmAlarmGroupID each alarm is assigned to
          exactly one alarm group.
        
        . The Provider can create work shifts and determine various alarm distribution
          rules in dependence of each work shift. The work shifts defined in the system
          are listed in the table aimosWorkShiftTable. The currently active work shift
          is set by each Organisation itself using the object aimosOrgActiveWorkShiftID
          in the aimosOrgTable.
        
        . The third point of influence are the alarm recipient lists. Each Organisation
          defines its own alarm recipient lists by adding the according entries to the
          table aimosAlarmRecipientListTable. For each alarm recipient list the phone
          book entries assigned to it are listed in the
          aimosAlarmRecipientListMemberTable. One phone book entry (i.e. one SNMP
          Manager) can be assigned to several alarm recipient lists simultaneously.
        
        In order to get the list of SNMP Managers that have to be informed, the A.I.M.O.S.
        SNMP Agent proceeds as follows:
        
        . The A.I.M.O.S. SNMP Agent checks the aimosAlarmConfigTable, and uses the object
          aimosAlarmAlarmGroupID in order to find out to which alarm group the alarm
          belongs.
        
        . Next, it determines which Organisations are authorised to receive alarms of
          this alarm group. This information is laid down in the table
          aimosAlarmGroupAllowedOrgTable.
        
        . The A.I.M.O.S. SNMP Agent checks the value of aimosAlarmForwardingType of each
          affected organisation in order to determine the organisations having alarm
          forwarding enabled as well as the kind of alarm forwarding to be used (SNMPv1
          trap or SNMPv2c notification).
        
        . For each Organisation that is allowed (allowed org) and enabled (alarm
          forwarding enabled) to receive alarms, the current work shift is identified via
          the object aimosOrgActiveWorkShiftID.
        
        . The table aimosAlarmDistributionPlanTable now shows which alarm recipient
          lists have to be used. The table provides one alarm recipient list per
          Organisation, AlarmGroup and work shift. If there is no entry for a certain
          combination, no alarm will be sent. If there is an entry, each member of the
          alarm recipient list (aimosAlarmRecipientListMemberTable) will receive an
          alarm notification, unless a phone book entry was deactivated via
          aimosPhoneBookActive.
        
        After the alarm recipients have been identified, the various counters required
        for sending traps must be identified:
        
        . The aimosAlarmListAlarmEventID identifies the cause leading to the dispatch
          of a aimosAlarmNew or a aimosAlarmChanged notification to one or more SNMP
          Managers. Here, the counter will be increased by one for each cause. If the
          cause leads to sending a aimosAlarmCleared notification, the counter will not
          be increased. Instead, the count of the according aimosAlarmNew or (if present)
          the latest aimosAlarmChanged notification will be used.
        
        . The aimosAlarmListID is identical to the aimosAlarmListAlarmEventID, as long
          as the aimosAlarmChanged alarm has not been implemented.
        
        . The aimosAlarmTrapID uniquely identifies each notification that was not sent
          to an SNMP Manager.
        
        . Each SNMP Manager can rely on the aimosAlarmTrapNotificationID to have a
          continuous numeration. If not, one notification got lost.
        
        At long last the A.I.M.O.S. SNMP Agent have to collect some information required
        to provide the notifications:
        
        . The A.I.M.O.S. SNMP Agent have to inspect the aimosAlarmConfigTable (and in a
          future version of the A.I.M.O.S. SNMP Agent the aimosAlarmSeverityRangeTable) to
          determine the alarms severity (in the future version for each organisation).
        
        . The A.I.M.O.S. SNMP Agent collects the organisation specific customer device
          information to be provided with the notification by means of the values of
          aimosMasterTrapInfo, aimosSubRackTrapInfo, aimosRemoteTrapInfo and
          aimosCableTrapInfo.
        
        Now the A.I.M.O.S. SNMP Agent has collected all information required for SNMP
        alarm forwarding. The A.I.M.O.S. SNMP Agent will now perform the following actions:
        
        . Create one entry per organisation in the alarm list (aimosAlarmListTable)
          using the organisations ID (aimosOrgID) and the alarm List ID
          (aimosAlarmListID) as index.
        
        . Send one SNMP notification to each manager discovered by the steps mentioned
          above and create for each notification one entry in the trap list
          (aimosAlarmTrapTable) using the organisations ID (aimosOrgID), the alarm List
          ID (aimosAlarmListID) and the trap ID (aimosAlarmTrapID) as index.
        
        Each manager have to acknowledge the received notifications by means of setting
        aimosAlarmTrapAcknowledgementState using its organisation ID (aimosOrgID), the
        alarm list ID (aimosAlarmListID) and the alarm trap ID (aimosAlarmTrapID) to
        acknowledged(2).
        
        After having emitted the alarm notification, the A.I.M.O.S. SNMP Agent expects an
        acknowledgement within a certain interval, that can be specified (in seconds) in
        aimosAlarmAckExpectInterval. If there is no such acknowledgement, the A.I.M.O.S.
        SNMP Agent will continue to emit the alarm until the acknowledgement is received.
        
        The notification remains in the alarm list
        . as long as the based alarm event is active or
        . if at least one notification related to the alarm event is not yet acknowledged
          by at least one of the involved SNMP Managers.
        
        The entries in the trap table (aimosAlarmTrapTable) are earlier removed: If a
        manager has performed the required acknowledgements, its entries in the trap
        table are removed.
        After remove from the trap and alarm list table, the removed entries are
        available in the alarm log (aimosAlarmLogTable). The specific alarm event ID
        will not be used again unless an alarm list rebuild resets the counter to zero
        or the wrap value (2^32-1) is reached. If a similar or even the same alarm event
        occurs again (after the old one gets cleared), than the notification will not
        contain the formerly used alarm event ID but a new one."
      ::= { aimosObjects 4 }

    
    aimosNextAlarmGroupID OBJECT-TYPE
      SYNTAX TableIndex
      MAX-ACCESS read-only
      STATUS current
      DESCRIPTION
        "This object is needed in addition of alarm groups to the aimosAlarmGroupTable.
        Its value has to be used as the identifier (aimosAlarmGroupID) of the new alarm
        group."
      REFERENCE
        "MDS=TMDSNextID
        Tag=2"
      ::= { aimosAlarmManagement 1 }

    
    aimosAlarmGroupTable OBJECT-TYPE
      SYNTAX SEQUENCE OF AimosAlarmGroupEntry
      MAX-ACCESS not-accessible
      STATUS current
      DESCRIPTION
        "This table is indexed by aimosAlarmGroupID and lists the alarm groups available
        in the system. Alarm groups provides the means to collect alarms with similar
        characteristics.
        
        Insert rows: set aimosAlarmGroupName.<value of aimosNextAlarmGroupID> to any text
        Delete rows: set aimosAlarmGroupName.<aimosAlarmGroupID> to 'delete' (without
                     quotation marks)
        
        TelCo's are not allowed to insert or delete rows."
      ::= { aimosAlarmManagement 2 }

    
    aimosAlarmGroupEntry OBJECT-TYPE
      SYNTAX AimosAlarmGroupEntry
      MAX-ACCESS not-accessible
      STATUS current
      DESCRIPTION
        "see description for table entry..."
      REFERENCE
        "MIS=TMISAlarmGroupTable
        MDS=TMDSAlarmGroupTable"
      INDEX { aimosAlarmGroupID }
      ::= { aimosAlarmGroupTable 1 }

    
    AimosAlarmGroupEntry ::=
      SEQUENCE { 
        aimosAlarmGroupID
          TableIndex,
        aimosAlarmGroupName
          OCTET STRING
       }

    aimosAlarmGroupID OBJECT-TYPE
      SYNTAX TableIndex
      MAX-ACCESS read-only
      STATUS current
      DESCRIPTION
        "This object is numbered consecutively.
        
        aimosNextAlarmGroupID tells you the ID to be used in row creation."
      ::= { aimosAlarmGroupEntry 1 }

    
    aimosAlarmGroupName OBJECT-TYPE
      SYNTAX OCTET STRING (SIZE (1..50))
      MAX-ACCESS read-write
      STATUS current
      DESCRIPTION
        "This object contains a name for the alarm group with up to 50 characters.
        
        Set this value to 'delete' (without quotation marks) in order to delete
        this table entry/alarm group.
        
        Changes, which are made here, affect all organizations.
        That's why TelCo's are not allowed to make any changes here."
      ::= { aimosAlarmGroupEntry 2 }

    
    aimosAlarmGroupAllowedOrgTable OBJECT-TYPE
      SYNTAX SEQUENCE OF AimosAlarmGroupAllowedOrgEntry
      MAX-ACCESS not-accessible
      STATUS current
      DESCRIPTION
        "This table serves to specify the organisations that will be authorised to
        receive alarms of a certain alarm group. Organisations not listed in this table
        cannot have entries in the table aimosAlarmDistributionPlanTable, which excludes
        them from alarm distribution.
        
        Only the provider is allowed to modify the contents of this table.
        
        Insert rows: set aimosAlarmGroupAllowedOrgActive.<aimosOrgID>.<aimosAlarmGroupID>
                     to true
        Delete rows: set aimosAlarmGroupAllowedOrgActive.<aimosOrgID>.<aimosAlarmGroupID>
                     to false
        
        TelCo's are not allowed to insert or delete rows."
      ::= { aimosAlarmManagement 3 }

    
    aimosAlarmGroupAllowedOrgEntry OBJECT-TYPE
      SYNTAX AimosAlarmGroupAllowedOrgEntry
      MAX-ACCESS not-accessible
      STATUS current
      DESCRIPTION
        "see description for table entry..."
      REFERENCE
        "MIS=TMISAlarmGroupAllowedOrgTable
        MDS=TMDSAlarmGroupAllowedOrgTable"
      INDEX { aimosOrgID, aimosAlarmGroupID }
      ::= { aimosAlarmGroupAllowedOrgTable 1 }

    
    AimosAlarmGroupAllowedOrgEntry ::=
      SEQUENCE { 
        aimosAlarmGroupAllowedOrgActive
          Boolean
       }

    aimosAlarmGroupAllowedOrgActive OBJECT-TYPE
      SYNTAX Boolean
      MAX-ACCESS read-write
      STATUS current
      DESCRIPTION
        "This object is used for row creation and deletion.
        
        An existing table entry denotes, that the corresponding organisation is allowed
        to receive alarms collected in a specific alarm group.
        
        Due to the way of row deletion there will never be a table entry with a value
        of false in aimosAlarmGroupAllowedOrgActive.
        
        TelCo's are not allowed to make any changes."
      ::= { aimosAlarmGroupAllowedOrgEntry 1 }

    
    aimosAlarmConfigTable OBJECT-TYPE
      SYNTAX SEQUENCE OF AimosAlarmConfigEntry
      MAX-ACCESS not-accessible
      STATUS current
      DESCRIPTION
        "With this table, indexed by aimosAlarmID, alarms can be configured. E.g. the
        Severity or the assignment to a certain alarm group can be specified here.
        
        Insert rows: must only be done by Mikom
        Delete rows: must only be done by Mikom"
      ::= { aimosAlarmManagement 4 }

    
    aimosAlarmConfigEntry OBJECT-TYPE
      SYNTAX AimosAlarmConfigEntry
      MAX-ACCESS not-accessible
      STATUS current
      DESCRIPTION
        "see description for table entry..."
      REFERENCE
        "MIS=TMISAlarmConfigTable
        MDS=TMDSAlarmConfigTable"
      INDEX { aimosAlarmID }
      ::= { aimosAlarmConfigTable 1 }

    
    AimosAlarmConfigEntry ::=
      SEQUENCE { 
        aimosAlarmID
          AlarmID,
        aimosAlarmDescription
          Text,
        aimosAlarmEventType
          EventType,
        aimosAlarmDefaultSeverity
          Severity,
        aimosAlarmSeverityMin
          Severity,
        aimosAlarmAlarmGroupID
          TableIndex,
        aimosAlarmClearMode
          ClearMode
       }

    aimosAlarmID OBJECT-TYPE
      SYNTAX AlarmID
      MAX-ACCESS read-only
      STATUS current
      DESCRIPTION
        "The aimosAlarmID of type AlarmID uniquely identifies the type of alarm."
      ::= { aimosAlarmConfigEntry 1 }

    
    aimosAlarmDescription OBJECT-TYPE
      SYNTAX Text
      MAX-ACCESS read-only
      STATUS current
      DESCRIPTION
        "This object holds a short explanation of the type of alarm."
      ::= { aimosAlarmConfigEntry 2 }

    
    aimosAlarmEventType OBJECT-TYPE
      SYNTAX EventType
      MAX-ACCESS read-only
      STATUS current
      DESCRIPTION
        "The aimosAlarmEventType of type EventType categorises the alarm."
      DEFVAL { communications }
      ::= { aimosAlarmConfigEntry 3 }

    
    aimosAlarmDefaultSeverity OBJECT-TYPE
      SYNTAX Severity
      MAX-ACCESS read-write
      STATUS current
      DESCRIPTION
        "This object of type Severity denotes the default severity of an alarm. Use the
        value indeterminate(0) in order to disable the alarm forwarding for this kind
        of alarms.
        
        Default severity is used, if organisation specific alarm severity configuration
        is not defined by aimosAlarmSeverityRangeTable.
        
        Changes, which are made here, affect all organizations.
        That's why TelCo's are not allowed to make any changes here."
      DEFVAL { critical }
      ::= { aimosAlarmConfigEntry 4 }

    
    aimosAlarmSeverityMin OBJECT-TYPE
      SYNTAX Severity
      MAX-ACCESS read-only
      STATUS current
      DESCRIPTION
        "This object of type Severity determines the at least allowed configurable
        severity in aimosAlarmDefaultSeverity and aimosAlarmSeverityRangeTable."
      DEFVAL { warning }
      ::= { aimosAlarmConfigEntry 5 }

    
    aimosAlarmAlarmGroupID OBJECT-TYPE
      SYNTAX TableIndex
      MAX-ACCESS read-write
      STATUS current
      DESCRIPTION
        "This object holds the Alarm Group assignment (aimosAlarmGroupID).
        
        Changes, which are made here, affect all organizations.
        That's why TelCo's are not allowed to make any changes here."
      ::= { aimosAlarmConfigEntry 6 }

    
    aimosAlarmClearMode OBJECT-TYPE
      SYNTAX ClearMode
      MAX-ACCESS read-write
      STATUS current
      DESCRIPTION
        "This object of type ClearMode informs you of how an alarm gets cleared.
        
        Changes, which are made here, affect all organizations.
        That's why TelCo's are not allowed to make any changes here."
      ::= { aimosAlarmConfigEntry 7 }

    
    aimosAlarmSeverityRangeTable OBJECT-TYPE
      SYNTAX SEQUENCE OF AimosAlarmSeverityRangeEntry
      MAX-ACCESS not-accessible
      STATUS deprecated
      DESCRIPTION
        "This table holds organisation specific data of alarm severity configuration.
        
        Insert rows: set aimosAlarmSeverityRangeSeverity.<aimosOrgID>.<aimosAlarmID>.
                     <aimosAlarmSeverityRangeMinValue>.<aimosAlarmSeverityRangeMaxValue>
                     to any severity value but indeterminate
        Delete rows: set aimosAlarmSeverityRangeSeverity.<aimosOrgID>.<aimosAlarmID>.
                     <aimosAlarmSeverityRangeMinValue>.<aimosAlarmSeverityRangeMaxValue>
                     to severity indeterminate
        
        This table is not yet supported !"
      ::= { aimosAlarmManagement 5 }

    
    aimosAlarmSeverityRangeEntry OBJECT-TYPE
      SYNTAX AimosAlarmSeverityRangeEntry
      MAX-ACCESS not-accessible
      STATUS deprecated
      DESCRIPTION
        "see description for table entry..."
      INDEX { aimosOrgID, aimosAlarmID, aimosAlarmSeverityRangeMinValue, aimosAlarmSeverityRangeMaxValue }
      ::= { aimosAlarmSeverityRangeTable 1 }

    
    AimosAlarmSeverityRangeEntry ::=
      SEQUENCE { 
        aimosAlarmSeverityRangeMinValue
          AlarmValue,
        aimosAlarmSeverityRangeMaxValue
          AlarmValue,
        aimosAlarmSeverityRangeSeverity
          Severity
       }

    aimosAlarmSeverityRangeMinValue OBJECT-TYPE
      SYNTAX AlarmValue
      MAX-ACCESS read-only
      STATUS deprecated
      DESCRIPTION
        "Low value causing a defined severity."
      ::= { aimosAlarmSeverityRangeEntry 1 }

    
    aimosAlarmSeverityRangeMaxValue OBJECT-TYPE
      SYNTAX AlarmValue
      MAX-ACCESS read-only
      STATUS deprecated
      DESCRIPTION
        "High value causing a defined severity."
      ::= { aimosAlarmSeverityRangeEntry 2 }

    
    aimosAlarmSeverityRangeSeverity OBJECT-TYPE
      SYNTAX Severity
      MAX-ACCESS read-write
      STATUS deprecated
      DESCRIPTION
        "aimosAlarmSeverityRangeSeverity of type Severity holds the severity to be used
        in alarm notifications if the alarm value is within the range from
        aimosAlarmSeverityRangeMinValue to aimosAlarmSeverityRangeMaxValue, both of type
        AlarmValue.
        
        Use the value indeterminate(0) in order to delete the table entry.
        
        If there is no appropriate entry for a specific Alarm ID,
        then aimosAlarmDefaultSeverity determines the severity of the alarm."
      ::= { aimosAlarmSeverityRangeEntry 3 }

    
    aimosWorkShiftTable OBJECT-TYPE
      SYNTAX SEQUENCE OF AimosWorkShiftEntry
      MAX-ACCESS not-accessible
      STATUS current
      DESCRIPTION
        "Alarm distribution depends on work shifts:
        . This table holds the available work shift ID's and names.
        . aimosOrgActiveWorkShiftID determines the active work shift per each
          organisation.
        . The table aimosAlarmDistributionPlanTable is indexed by aimosWorkShiftID and
          therefore it holds one alarm recipient list per work shift.
        
        In this way it is possible to activate another alarm distribution list via
        simply switching the current work shift.
        
        Insert rows: set aimosWorkShiftName.<aimosOrgID>.
                     <value of aimosOrgNextWorkShiftID>
                     to any text
        Delete rows: set aimosWorkShiftName.<aimosOrgID>.<aimosWorkShiftID> to 'delete'
                     (without quotation marks)"
      ::= { aimosAlarmManagement 6 }

    
    aimosWorkShiftEntry OBJECT-TYPE
      SYNTAX AimosWorkShiftEntry
      MAX-ACCESS not-accessible
      STATUS current
      DESCRIPTION
        "see description for table entry..."
      REFERENCE
        "MIS=TMISWorkShiftTable
        MDS=TMDSWorkShiftTable"
      INDEX { aimosOrgID, aimosWorkShiftID }
      ::= { aimosWorkShiftTable 1 }

    
    AimosWorkShiftEntry ::=
      SEQUENCE { 
        aimosWorkShiftID
          TableIndex,
        aimosWorkShiftName
          OCTET STRING,
        aimosWorkShiftHeartbeatInterval
          WeekMinutes,
        aimosWorkShiftHeartbeatRecipientList
          TableIndex
       }

    aimosWorkShiftID OBJECT-TYPE
      SYNTAX TableIndex
      MAX-ACCESS read-only
      STATUS current
      DESCRIPTION
        "This object is numbered consecutively.
        
        aimosOrgNextWorkShiftID tells you the ID to be used in row creation."
      ::= { aimosWorkShiftEntry 1 }

    
    aimosWorkShiftName OBJECT-TYPE
      SYNTAX OCTET STRING (SIZE (1..40))
      MAX-ACCESS read-write
      STATUS current
      DESCRIPTION
        "This object contains a name for the work shift with up to 40 characters.
        
        Set this value to 'delete' (without quotation marks) in order to delete
        this table entry/work shift."
      ::= { aimosWorkShiftEntry 2 }

    
    aimosWorkShiftHeartbeatInterval OBJECT-TYPE
      SYNTAX WeekMinutes
      UNITS "minutes"
      MAX-ACCESS read-write
      STATUS current
      DESCRIPTION
        "This object is intended to specify the interval in minutes, after that the
        A.I.M.O.S. SNMP Agent will emit a heartbeat notification to one or more SNMP
        Manager. Use aimosWorkShiftHeartbeatRecipientList in order to define that SNMP
        Managers.
        
        This interval is only used, if the affected work shift is activated (i.e. the
        value of aimosOrgActiveWorkShiftID is set to the affected aimosWorkShiftID).
        
        If either aimosWorkShiftHeartbeatInterval or aimosWorkShiftHeartbeatRecipientList
        is set to 0, no heartbeat notification will be emitted."
      DEFVAL { 0 }
      ::= { aimosWorkShiftEntry 3 }

    
    aimosWorkShiftHeartbeatRecipientList OBJECT-TYPE
      SYNTAX TableIndex
      MAX-ACCESS read-write
      STATUS current
      DESCRIPTION
        "This object is intended to specify the Alarm Recipient List which has to be used
        if the A.I.M.O.S. SNMP Agent emits heartbeat notifications. Each member of the
        specified Alarm Recipient List (specified via aimosAlarmRecipientListMemberTable)
        will receive a heartbeat notification every [aimosWorkShiftHeartbeatInterval]
        minutes.
        
        This Recipient List is only used, if the affected work shift is activated (i.e.
        the value of aimosOrgActiveWorkShiftID is set to the affected aimosWorkShiftID).
        
        If either aimosWorkShiftHeartbeatInterval or aimosWorkShiftHeartbeatRecipientList
        is set to 0, no heartbeat notification will be emitted."
      DEFVAL { 0 }
      ::= { aimosWorkShiftEntry 4 }

    
    aimosAlarmDistributionPlanTable OBJECT-TYPE
      SYNTAX SEQUENCE OF AimosAlarmDistributionPlanEntry
      MAX-ACCESS not-accessible
      STATUS current
      DESCRIPTION
        "This table, indexed by aimosOrgID, aimosAlarmGroupID and aimosWorkShiftID, holds
        the alarm recipient list to be used for sending alarms of a certain Alarm Group
        if a certain work shift is active. Each organisation may have different settings.
        Each member of the discovered alarm recipient lists will get the notification.
        
        The organization must be allowed to receive alarms of the specific Alarm Group,
        thus there must be an appropriate entry in the aimosAlarmGroupAllowedOrgTable.
        
        Insert rows: set aimosAlarmDistributionPlanRecipientListID.<aimosOrgID>.
                     <aimosAlarmGroupID>.<aimosWorkShiftID> to a valid
                     aimosAlarmRecipientListID
        Delete rows: set aimosAlarmDistributionPlanRecipientListID.<aimosOrgID>.
                     <aimosAlarmGroupID>.<aimosWorkShiftID> to zero
        
        Example:
        ========
        An organisation with OrgID 262299 wants
        . recipient list 1 to be used for alarms of alarm group 2 during work shift 1
        . recipient list 4 to be used for alarms of alarm group 2 during work shift 2
        
        Two entries are needed in this table:
        . aimosAlarmDistributionPlanRecipientListID.262299.2.1 set to 1
        . aimosAlarmDistributionPlanRecipientListID.262299.2.2 set to 4"
      ::= { aimosAlarmManagement 7 }

    
    aimosAlarmDistributionPlanEntry OBJECT-TYPE
      SYNTAX AimosAlarmDistributionPlanEntry
      MAX-ACCESS not-accessible
      STATUS current
      DESCRIPTION
        "see description for table entry..."
      REFERENCE
        "MIS=TMISAlarmDistributionPlanTable
        MDS=TMDSAlarmDistributionPlanTable"
      INDEX { aimosOrgID, aimosAlarmGroupID, aimosWorkShiftID }
      ::= { aimosAlarmDistributionPlanTable 1 }

    
    AimosAlarmDistributionPlanEntry ::=
      SEQUENCE { 
        aimosAlarmDistributionPlanRecipientListID
          Unsigned32
       }

    aimosAlarmDistributionPlanRecipientListID OBJECT-TYPE
      SYNTAX Unsigned32
      MAX-ACCESS read-write
      STATUS current
      DESCRIPTION
        "This objects value is the recipient lists ID (aimosAlarmRecipientListID) that
        will be bound up with the aimosAlarmGroupID and aimosWorkShiftID for aimosOrgID.
        
        The corresponding organisation must be allowed to receive alarms of the
        specified Alarm Group, thus there must be an appropriate entry in the
        aimosAlarmGroupAllowedOrgTable.
        
        Set the value to 0 (zero) in order to delete this table entry."
      ::= { aimosAlarmDistributionPlanEntry 1 }

    
    aimosAlarmRecipientListTable OBJECT-TYPE
      SYNTAX SEQUENCE OF AimosAlarmRecipientListEntry
      MAX-ACCESS not-accessible
      STATUS current
      DESCRIPTION
        "This table holds the names and IDs of available alarm recipient lists for each
        organization. It is indexed by aimosOrgID and aimosAlarmRecipientListID.
        
        Insert rows: set aimosAlarmRecipientListName.<aimosOrgID>.<value of
                     aimosOrgNextAlarmRecipientListID> to the recipient list's name
        Delete rows: set aimosAlarmRecipientListName.<aimosOrgID>.
                     <aimosAlarmRecipientListID> to 'delete' (without quotation marks)"
      ::= { aimosAlarmManagement 8 }

    
    aimosAlarmRecipientListEntry OBJECT-TYPE
      SYNTAX AimosAlarmRecipientListEntry
      MAX-ACCESS not-accessible
      STATUS current
      DESCRIPTION
        "see description for table entry..."
      REFERENCE
        "MIS=TMISRecipientListTable
        MDS=TMDSRecipientListTable"
      INDEX { aimosOrgID, aimosAlarmRecipientListID }
      ::= { aimosAlarmRecipientListTable 1 }

    
    AimosAlarmRecipientListEntry ::=
      SEQUENCE { 
        aimosAlarmRecipientListID
          TableIndex,
        aimosAlarmRecipientListName
          OCTET STRING
       }

    aimosAlarmRecipientListID OBJECT-TYPE
      SYNTAX TableIndex
      MAX-ACCESS read-only
      STATUS current
      DESCRIPTION
        "This object is numbered consecutively within one organisation.
        
        aimosOrgNextAlarmRecipientListID tells you the value to be used in alarm
        recipient list creation. The value of 0 (zero) must not be used here.
        "
      ::= { aimosAlarmRecipientListEntry 1 }

    
    aimosAlarmRecipientListName OBJECT-TYPE
      SYNTAX OCTET STRING (SIZE (1..50))
      MAX-ACCESS read-write
      STATUS current
      DESCRIPTION
        "This object is just a name with a maximum length of 50 characters
        for the alarm recipient list.
        
        Set this value to 'delete' (without quotation marks) in order to delete
        this table entry."
      ::= { aimosAlarmRecipientListEntry 2 }

    
    aimosPhoneBookTable OBJECT-TYPE
      SYNTAX SEQUENCE OF AimosPhoneBookEntry
      MAX-ACCESS not-accessible
      STATUS current
      DESCRIPTION
        "This table gives IP addresses and IP ports of alarm recipients (SNMP Manager)
        a name and classifies its communication type.
        
        Insert rows: set aimosPhoneBookAddress.<aimosOrgID>.<value of
                     aimosOrgNextPhoneBookID> to any IP address and port
        Delete rows: set aimosPhoneBookAddress.<aimosOrgID>.<aimosPhoneBookID> to
                     'delete' (without quotation marks)"
      ::= { aimosAlarmManagement 11 }

    
    aimosPhoneBookEntry OBJECT-TYPE
      SYNTAX AimosPhoneBookEntry
      MAX-ACCESS not-accessible
      STATUS current
      DESCRIPTION
        "see description for table entry..."
      REFERENCE
        "MIS=TMISPhoneBookTable
        MDS=TMDSPhoneBookTable"
      INDEX { aimosOrgID, aimosPhoneBookID }
      ::= { aimosPhoneBookTable 1 }

    
    AimosPhoneBookEntry ::=
      SEQUENCE { 
        aimosPhoneBookID
          TableIndex,
        aimosPhoneBookName
          PhoneBookEntry,
        aimosPhoneBookAddress
          IPAddressAndPort,
        aimosPhoneBookActive
          Boolean,
        aimosPhoneBookLastNotificationID
          Unsigned32,
        aimosPhoneBookAlarmListResync
          OperationMode,
        aimosPhoneBookInterfaceType
          InterfaceType,
        aimosPhoneBookAckCapability
          Boolean,
        aimosPhoneBookTimeDisplayFormat
          TimeDisplayFormat,
        aimosPhoneBookGeographicPositionFormat
          GeographicPositionFormat,
        aimosPhoneBookRecognitionTraps
          Boolean
       }

    aimosPhoneBookID OBJECT-TYPE
      SYNTAX TableIndex
      MAX-ACCESS read-only
      STATUS current
      DESCRIPTION
        "This object is numbered consecutively within one organisation.
        
        aimosOrgNextPhoneBookID tells you the value to be used in phone book entry
        creation."
      ::= { aimosPhoneBookEntry 1 }

    
    aimosPhoneBookName OBJECT-TYPE
      SYNTAX PhoneBookEntry
      MAX-ACCESS read-write
      STATUS current
      DESCRIPTION
        "This object of type PhoneBookEntry is a name for the phone book entry
        helping to disclose its identity. This name should be unique."
      DEFVAL { "<ID>" }
      ::= { aimosPhoneBookEntry 2 }

    
    aimosPhoneBookAddress OBJECT-TYPE
      SYNTAX IPAddressAndPort
      MAX-ACCESS read-write
      STATUS current
      DESCRIPTION
        "This object of type IPAddressAndPort hold the IP address and IP port number.
        The port number may be omitted in set requests, if the port number is the default
        port number for SNMP traps (162).
        
        Set this value to 'delete' (without quotation marks) in order to delete
        the phone book entry. Phone book entries currently used in the alarm
        list/log cannot be removed."
      ::= { aimosPhoneBookEntry 3 }

    
    aimosPhoneBookActive OBJECT-TYPE
      SYNTAX Boolean
      MAX-ACCESS read-write
      STATUS current
      DESCRIPTION
        "This object is used in order to deactivate a phone book entry for a short
        period of time. Inactive phone book entries are excluded from alarm distribution
        even if they have entries in the aimosAlarmDistributionPlanTable."
      DEFVAL { true }
      ::= { aimosPhoneBookEntry 5 }

    
    aimosPhoneBookLastNotificationID OBJECT-TYPE
      SYNTAX Unsigned32
      MAX-ACCESS read-write
      STATUS current
      DESCRIPTION
        "This object denotes the notification ID used in the most recent trap for the
        specific SNMP Manager. The NotificationID of the next trap that is generated
        will be 1 higher. The wrap value is 2^32-1."
      DEFVAL { 0 }
      ::= { aimosPhoneBookEntry 6 }

    
    aimosPhoneBookAlarmListResync OBJECT-TYPE
      SYNTAX OperationMode
      MAX-ACCESS read-write
      STATUS current
      DESCRIPTION
        "This object of type OperationMode is provided to give each SNMP Manager the
        ability to synchronise its alarm table. Setting this value to start(5) will
        start the alarm list synchronisation process."
      ::= { aimosPhoneBookEntry 7 }

    
    aimosPhoneBookInterfaceType OBJECT-TYPE
      SYNTAX InterfaceType
      MAX-ACCESS read-write
      STATUS current
      DESCRIPTION
        "This object of type InterfaceType is provided in order to define the kind of
        alarm forwarding. Leave this object on its default value unless you want to
        force the SNMP Agent to use an older type of alarm forwarding for compatibility
        reasons.
        
        The aimos interface was adapted in order to remain conformal with SNMP.
        The differences between ifAimosObsolete(4) and ifAimos(5) are as follows:
        
        --------------------------------------------------------------------------------
        topic                 ifAimosObsolete            ifAimos
        ================================================================================
        trap object (second   1.3.6.1.4.1.6408.201.3.1.4 1.3.6.1.6.3.1.1.4.1.0
        object in alarm       AIMOS.aimosTrapOID         SNMPV2-MIB.snmpTrapOID.0
        notifications)
        --------------------------------------------------------------------------------
        enterprise object     1.3.6.1.4.1.6408.201.4.3.0 1.3.6.1.6.3.1.1.4.3.0
        (the last object in   AIMOS.aimosTrapEnterprise  SNMPV2-MIB.snmpTrapEnterprise.0
        alarm notifications)
        --------------------------------------------------------------------------------
        enterprise name (the  1.3.6.1.4.1.6408           1.3.6.1.4.1.6408.201.4
        alarm notifications   mikom                      AIMOS.aimosNotifications
        last objects value)
        --------------------------------------------------------------------------------
        instance identifiers  each objects instance      each object has its real
        in alarm              except aimosTrapOID is 0   instance identifier
        notifications objects
        --------------------------------------------------------------------------------
        
        The ifOMC3... interfaces are implemented only for compatibility reasons to the
        Mikom OMC Version 3. They are described in the documentation to that OMC.
        The Nokia interface is described in documents available from Nokia."
      DEFVAL { ifMIBDefault }
      ::= { aimosPhoneBookEntry 8 }

    
    aimosPhoneBookAckCapability OBJECT-TYPE
      SYNTAX Boolean
      MAX-ACCESS read-write
      STATUS current
      DESCRIPTION
        "This object is provided in order to state the SNMP Managers ability to perform
        an acknowledgement.
        . If this object is set to true (default), then the SNMP Agent expects an
          acknowledgement for each trap sent out. Each trap will be periodically re-send
          until achnowledgement is detected.
        . This object has to be set to false in the case of the inability of the SNMP
          Manager to maintain the acknowledgement process. In that case the SNMP Agent
          doesn't expect an acknowledgement. Therefore each trap is sent out nonrecurring
          and - since SNMP is based on UDP - traps may be lost!"
      DEFVAL { true }
      ::= { aimosPhoneBookEntry 9 }

    
    aimosPhoneBookTimeDisplayFormat OBJECT-TYPE
      SYNTAX TimeDisplayFormat
      MAX-ACCESS read-write
      STATUS current
      DESCRIPTION
        "This object of type TimeDisplayFormat is provided in order to define ofhow
        date and time values (in objects of type VariableTime) inquired by an GET
        request or shipped within alarm notifications have to be encoded by the SNMP
        agent.
        
        Each SNMP manager may make its own setting if system default is not acceptable.
        The system default is default(0). It is treated as
        . osiBinary(1) unless aimosPhoneBookInterfaceType is set to ifAimosObsolete(4)
        . osiText(2) if aimosPhoneBookInterfaceType is set to ifAimosObsolete(4)"
      DEFVAL { default }
      ::= { aimosPhoneBookEntry 10 }

    
    aimosPhoneBookGeographicPositionFormat OBJECT-TYPE
      SYNTAX GeographicPositionFormat
      MAX-ACCESS read-write
      STATUS current
      DESCRIPTION
        "This object defines the format to be used for objects with textual convention
        GPSPosition. 
        
        These are as follows:
        . aimosAlarmListRaiseLatitude
        . aimosAlarmListRaiseLongitude
        . aimosAlarmListClearLatitude
        . aimosAlarmListClearLongitude
        . aimosAlarmLogRaiseLatitude
        . aimosAlarmLogRaiseLongitude
        . aimosAlarmLogClearLatitude
        . aimosAlarmLogClearLongitude"
      ::= { aimosPhoneBookEntry 11 }

    
    aimosPhoneBookRecognitionTraps OBJECT-TYPE
      SYNTAX Boolean
      MAX-ACCESS read-write
      STATUS current
      DESCRIPTION
        "This object provides means to state whether or not the SNMP Manager 
        desires the SNMP Agent to sent a aimosAlarmRecognized trap in case an 
        alarms recognition state changes from unrecognized(1) to recognized(2).
        
        Please see also the description to aimosAlarmListRecognitionState."
      ::= { aimosPhoneBookEntry 12 }

    
    aimosAlarmRecipientListMemberTable OBJECT-TYPE
      SYNTAX SEQUENCE OF AimosAlarmRecipientListMemberEntry
      MAX-ACCESS not-accessible
      STATUS current
      DESCRIPTION
        "This table determines the members of a certain alarm recipient list.
        All active members of an Alarm Recipient List receive the alarm notifications
        assigned to this list via the table aimosAlarmDistributionPlanTable.
        
        Insert rows: set aimosAlarmRecipientListMemberActive.<aimosOrgID>.
                     <aimosAlarmRecipientListID>.<aimosPhoneBookID> to true
        Delete rows: set aimosAlarmRecipientListMemberActive.<aimosOrgID>.
                     <aimosAlarmRecipientListID>.<aimosPhoneBookID> to false"
      ::= { aimosAlarmManagement 12 }

    
    aimosAlarmRecipientListMemberEntry OBJECT-TYPE
      SYNTAX AimosAlarmRecipientListMemberEntry
      MAX-ACCESS not-accessible
      STATUS current
      DESCRIPTION
        "see description for table entry..."
      REFERENCE
        "MIS=TMISRecipientListMemberTable
        MDS=TMDSRecipientListMemberTable"
      INDEX { aimosOrgID, aimosAlarmRecipientListID, aimosPhoneBookID }
      ::= { aimosAlarmRecipientListMemberTable 1 }

    
    AimosAlarmRecipientListMemberEntry ::=
      SEQUENCE { 
        aimosAlarmRecipientListMemberActive
          Boolean
       }

    aimosAlarmRecipientListMemberActive OBJECT-TYPE
      SYNTAX Boolean
      MAX-ACCESS read-write
      STATUS current
      DESCRIPTION
        "This object is used for row creation and deletion. Due to the way of row
        deletion there will never be an object in this table having a value of false.
        
        An existing table entry denotes, that the corresponding phone book entry is
        assigned to the specific alarm recipient list. Thus it become a member of the
        alarm recipient list and with it a recipient of the alarms assigned to the alarm
        recipient list. If the phone book entry is deactivated via aimosPhoneBookActive,
        no traps will be sent to this recipient.
        
        Set this value to false in order to delete a table entry."
      ::= { aimosAlarmRecipientListMemberEntry 1 }

    
    aimosAlarmTrapTable OBJECT-TYPE
      SYNTAX SEQUENCE OF AimosAlarmTrapEntry
      MAX-ACCESS not-accessible
      STATUS current
      DESCRIPTION
        "This table is indexed by aimosOrgID, aimosAlarmTrapID and aimosAlarmListID and
        contains a list of all traps sent out by the agent to a specific SNMP Manager
        identified by its phone book entry.
        
        Insert rows: must only be done by system
        Delete rows: must only be done by system"
      ::= { aimosAlarmManagement 13 }

    
    aimosAlarmTrapEntry OBJECT-TYPE
      SYNTAX AimosAlarmTrapEntry
      MAX-ACCESS not-accessible
      STATUS current
      DESCRIPTION
        "see description for table entry..."
      REFERENCE
        "MIS=TMISAlarmTrapTable
        MDS=TMDSAlarmTrapTable"
      INDEX { aimosOrgID, aimosAlarmTrapID, aimosAlarmListID }
      ::= { aimosAlarmTrapTable 1 }

    
    AimosAlarmTrapEntry ::=
      SEQUENCE { 
        aimosAlarmTrapID
          TableIndex,
        aimosAlarmTrapNotificationID
          Unsigned32,
        aimosAlarmTrapPhonebookID
          TableIndex,
        aimosAlarmTrapAcknowledgementState
          AcknowledgementState,
        aimosAlarmTrapAcknowledgementUser
          UserName,
        aimosAlarmTrapAcknowledgementTime
          VariableTime
       }

    aimosAlarmTrapID OBJECT-TYPE
      SYNTAX TableIndex
      MAX-ACCESS read-only
      STATUS current
      DESCRIPTION
        "This object is an unique identifier for a trap on SNMP Agent side and is used in
        alarm acknowledgement.
        
        Even if its value is consecutive numbered on agent side, it could seem to the
        SNMP Manager in such a way as if the values may be gappy. This will be regularly
        the case if more than one alarm receiver is present.
        
        This value is reset to 0 on alarm list rebuild.
        
        The wrap value is 2^32-1. "
      ::= { aimosAlarmTrapEntry 1 }

    
    aimosAlarmTrapNotificationID OBJECT-TYPE
      SYNTAX Unsigned32
      MAX-ACCESS read-only
      STATUS current
      DESCRIPTION
        "This object is incremented consecutively for each notification sent out to a
        particular SNMP Manager. Thus every SNMP Manager (identified by its phone book
        entry) will have consecutively numbered values in all received notifications and
        therefore its value can be used in order to recognise missing notifications.
        
        The wrap value is 2^32-1.
        
        An Alarm List Resync will reset the current SNMP Managers notification ID,
        whereas an alarm list rebuild will reset the corresponding notification ID
        of each SNMP Manager.
        "
      ::= { aimosAlarmTrapEntry 2 }

    
    aimosAlarmTrapPhonebookID OBJECT-TYPE
      SYNTAX TableIndex
      MAX-ACCESS read-only
      STATUS current
      DESCRIPTION
        "This object is the SNMP Managers aimosPhoneBookID
        to which the notification was directed to."
      ::= { aimosAlarmTrapEntry 3 }

    
    aimosAlarmTrapAcknowledgementState OBJECT-TYPE
      SYNTAX AcknowledgementState
      MAX-ACCESS read-write
      STATUS current
      DESCRIPTION
        "This object of type AcknowledgementState states whether or not the 
        alarm was acknowledged. It is the only writeable value in this table.
        
        Acknowledgement will be done by setting this value to acknowledged(2).
        
        The term acknowledgement is pertaining to the SNMP protocol: 
        it provides means for the SNMP manager to acknowledge trap receipt.
        
        On the other hand the similar sounding term 'recognition' is used to 
        indicate an 'I have seen the alarm and will take care about it'. 
        The latter one is also available via the AIMOS_Visu's Supervision page."
      ::= { aimosAlarmTrapEntry 4 }

    
    aimosAlarmTrapAcknowledgementUser OBJECT-TYPE
      SYNTAX UserName
      MAX-ACCESS read-only
      STATUS current
      DESCRIPTION
        "This object holds the user who has acknowledged the alarm.
        This object is empty if the alarm is not yet acknowledged."
      ::= { aimosAlarmTrapEntry 5 }

    
    aimosAlarmTrapAcknowledgementTime OBJECT-TYPE
      SYNTAX VariableTime
      MAX-ACCESS read-only
      STATUS current
      DESCRIPTION
        "This object of type VariableTime holds the time of acknowledgement.
        This object is empty if the alarm is not yet acknowledged."
      ::= { aimosAlarmTrapEntry 6 }

    
    aimosAlarmListTable OBJECT-TYPE
      SYNTAX SEQUENCE OF AimosAlarmListEntry
      MAX-ACCESS not-accessible
      STATUS current
      DESCRIPTION
        "This table contains a list of active alarms. This table is indexed by aimosOrgID
        and aimosAlarmListID; i.e. the table is organisation specific and, thus has
        entries for each concerned organisation.
        
        Each aimosAlarmNew and aimosAlarmChanged notification generates a new entry for
        each Organisation receiving the alarm. aimosAlarmCleared notifications forwarded
        by the agent to any manager do not create another entry, but make an amendment
        to existing ones.
        
        The entries remain in the list
        . as long as the corresponding alarm situation still exists or
        . if any manager of a specific organisation has not yet acknowledged required
          notifications related to the specific alarm situation.
        
        Insert rows: must only be done by system
        Delete rows: must only be done by system
        
        
        The value stored in aimosLoginPhoneBookID affects this table in the following way:
        - if aimosLoginPhoneBookID is a valid aimosPhoneBookID, then only alarms forwarded 
          to the corresponding SNMP Manager are listed in aimosAlarmListTable
         
        - if aimosLoginPhoneBookID is an invalid aimosPhoneBookID, this table is empty
        
        - if aimosLoginPhoneBookID is 0 this table is complete / not filtered
        "
      ::= { aimosAlarmManagement 14 }

    
    aimosAlarmListEntry OBJECT-TYPE
      SYNTAX AimosAlarmListEntry
      MAX-ACCESS not-accessible
      STATUS current
      DESCRIPTION
        "see description for table entry..."
      REFERENCE
        "MIS=TMISAlarmListTable
        MDS=TMDSAlarmListTable"
      INDEX { aimosOrgID, aimosAlarmListID }
      ::= { aimosAlarmListTable 1 }

    
    AimosAlarmListEntry ::=
      SEQUENCE { 
        aimosAlarmListID
          TableIndex,
        aimosAlarmListAlarmEventID
          Unsigned32,
        aimosAlarmListAlarmID
          AlarmID,
        aimosAlarmListEventType
          EventType,
        aimosAlarmListEventTime
          VariableTime,
        aimosAlarmListProbableCause
          ProbableCause,
        aimosAlarmListSpecificProblem
          SpecificProblem,
        aimosAlarmListSeverity
          Severity,
        aimosAlarmListTrendIndication
          TrendIndication,
        aimosAlarmListAdditionalText
          Text,
        aimosAlarmListSDN
          SDN,
        aimosAlarmListTrapInfo
          Text,
        aimosAlarmListComponentName
          Text,
        aimosAlarmListLocation
          Text,
        aimosAlarmListUniqueSystemID
          Text,
        aimosAlarmListClearReason
          ClearReason,
        aimosAlarmListClearTime
          VariableTime,
        aimosAlarmListRaiseLatitude
          GPSPosition,
        aimosAlarmListRaiseLongitude
          GPSPosition,
        aimosAlarmListClearLatitude
          GPSPosition,
        aimosAlarmListClearLongitude
          GPSPosition,
        aimosAlarmListRecognitionState
          RecognitionState,
        aimosAlarmListRecognitionUser
          UserName,
        aimosAlarmListRecognitionTime
          VariableTime
       }

    aimosAlarmListID OBJECT-TYPE
      SYNTAX TableIndex
      MAX-ACCESS read-only
      STATUS current
      DESCRIPTION
        "This object is the consecutive numbering of all alarm notifications of the
        A.I.M.O.S. SNMP Agent forwarded to any manager. A notification forwarded to more
        than one SNMP Manager will contain identical aimosAlarmListID's.
        
        When an alarm list rebuild is initiated by a SNMP Manager then the
        alarm list ID is reset.
        The alarm list ID is not reset, if a SNMP Manager starts an Alarm List Resync.
        
        The wrap value is 2^32-1."
      ::= { aimosAlarmListEntry 1 }

    
    aimosAlarmListAlarmEventID OBJECT-TYPE
      SYNTAX Unsigned32
      MAX-ACCESS read-only
      STATUS current
      DESCRIPTION
        "This object's Unsigned32 value is incremented by one for each alarm notification
        except aimosAlarmChanged and aimosAlarmCleared. Alarm changed notifications and
        alarm clear notifications are correlated with alarm new notifications by the
        aimosAlarmListAlarmEventID.
        
        When an alarm list rebuild is initiated by a SNMP Manager then the
        alarm event ID is reset.
        The alarm event ID is not reset, if a SNMP Manager starts an Alarm List Resync.
        
        The wrap value is 2^32-1."
      ::= { aimosAlarmListEntry 2 }

    
    aimosAlarmListAlarmID OBJECT-TYPE
      SYNTAX AlarmID
      MAX-ACCESS read-only
      STATUS current
      DESCRIPTION
        "This object of type AlarmID designates the alarm kind."
      ::= { aimosAlarmListEntry 3 }

    
    aimosAlarmListEventType OBJECT-TYPE
      SYNTAX EventType
      MAX-ACCESS read-only
      STATUS current
      DESCRIPTION
        "The Event Type categorises the alarm."
      ::= { aimosAlarmListEntry 4 }

    
    aimosAlarmListEventTime OBJECT-TYPE
      SYNTAX VariableTime
      MAX-ACCESS read-only
      STATUS current
      DESCRIPTION
        "This object of type VariableTime states when the alarm condition appeared or (in
        the case of an aimosAlarmCleared notification) when the alarm condition is gone."
      ::= { aimosAlarmListEntry 5 }

    
    aimosAlarmListProbableCause OBJECT-TYPE
      SYNTAX ProbableCause
      MAX-ACCESS read-only
      STATUS current
      DESCRIPTION
        "This object of type ProbableCause defines further qualification of an alarm than
        aimosAlarmListEventType."
      ::= { aimosAlarmListEntry 6 }

    
    aimosAlarmListSpecificProblem OBJECT-TYPE
      SYNTAX SpecificProblem
      MAX-ACCESS read-only
      STATUS current
      DESCRIPTION
        "This object of type SpecificProblem is a fault specific value used in order to
        classify the fault situation. It provides further qualification of the alarm
        than probable cause and is defined in accordance with definitions given in
        ITU-T Recommendation X.733 clause 8.1.2.2."
      ::= { aimosAlarmListEntry 7 }

    
    aimosAlarmListSeverity OBJECT-TYPE
      SYNTAX Severity
      MAX-ACCESS read-only
      STATUS current
      DESCRIPTION
        "This object of type Severity defines severity levels, which provide an
        indication of how it is perceived that the capability of the managed
        object has been affected."
      ::= { aimosAlarmListEntry 8 }

    
    aimosAlarmListTrendIndication OBJECT-TYPE
      SYNTAX TrendIndication
      MAX-ACCESS read-only
      STATUS current
      DESCRIPTION
        "This object of type TrendIndication specifies the current severity trend
        of the managed object."
      ::= { aimosAlarmListEntry 9 }

    
    aimosAlarmListAdditionalText OBJECT-TYPE
      SYNTAX Text
      MAX-ACCESS read-only
      STATUS current
      DESCRIPTION
        "This object allows a free form text description to be reported.
        It contains a formatted description of the alarm and, should the
        occasion arise, includes alarm values."
      ::= { aimosAlarmListEntry 10 }

    
    aimosAlarmListSDN OBJECT-TYPE
      SYNTAX SDN
      MAX-ACCESS read-only
      STATUS current
      DESCRIPTION
        "The System Distinguished Name uniquely identifies the unit within the system
        controlled by the OMC."
      ::= { aimosAlarmListEntry 11 }

    
    aimosAlarmListTrapInfo OBJECT-TYPE
      SYNTAX Text
      MAX-ACCESS read-only
      STATUS current
      DESCRIPTION
        "This OID contains the Network Elements's TrapInfo"
      ::= { aimosAlarmListEntry 12 }

    
    aimosAlarmListComponentName OBJECT-TYPE
      SYNTAX Text
      MAX-ACCESS read-only
      STATUS current
      DESCRIPTION
        "This OID contains the Network Elements's Component Name"
      ::= { aimosAlarmListEntry 13 }

    
    aimosAlarmListLocation OBJECT-TYPE
      SYNTAX Text
      MAX-ACCESS read-only
      STATUS current
      DESCRIPTION
        "This OID contains the Network Elements's Location"
      ::= { aimosAlarmListEntry 14 }

    
    aimosAlarmListUniqueSystemID OBJECT-TYPE
      SYNTAX Text
      MAX-ACCESS read-only
      STATUS current
      DESCRIPTION
        "This OID contains the Network Elements's Unique System ID"
      ::= { aimosAlarmListEntry 15 }

    
    aimosAlarmListClearReason OBJECT-TYPE
      SYNTAX ClearReason
      MAX-ACCESS read-write
      STATUS current
      DESCRIPTION
        "This OID gives information weather the alarm was cleared or not. 
        If an alarm does not become automatically cleared (aimosAlarmClearMode 
        is set to manualClear), manualCleared is the only writeable value 
        (besides aimosAlarmListRecognitionState)."
      ::= { aimosAlarmListEntry 16 }

    
    aimosAlarmListClearTime OBJECT-TYPE
      SYNTAX VariableTime
      MAX-ACCESS read-only
      STATUS current
      DESCRIPTION
        "this object of type VariableTime states the time of the event specified in
        aimosAlarmListClearReason."
      ::= { aimosAlarmListEntry 17 }

    
    aimosAlarmListRaiseLatitude OBJECT-TYPE
      SYNTAX GPSPosition
      MAX-ACCESS read-only
      STATUS current
      DESCRIPTION
        "this object was introduced in V 2.6.0 and states the Network Elements Latitude 
        to the time the alarm was raised."
      ::= { aimosAlarmListEntry 18 }

    
    aimosAlarmListRaiseLongitude OBJECT-TYPE
      SYNTAX GPSPosition
      MAX-ACCESS read-only
      STATUS current
      DESCRIPTION
        "this object was introduced in V 2.6.0 and states the Network Elements Longitude
        to the time the alarm was raised."
      ::= { aimosAlarmListEntry 19 }

    
    aimosAlarmListClearLatitude OBJECT-TYPE
      SYNTAX GPSPosition
      MAX-ACCESS read-only
      STATUS current
      DESCRIPTION
        "this object was introduced in V 2.6.0 and states the Network Elements Latitude 
        to the time the alarm was cleared."
      ::= { aimosAlarmListEntry 20 }

    
    aimosAlarmListClearLongitude OBJECT-TYPE
      SYNTAX GPSPosition
      MAX-ACCESS read-only
      STATUS current
      DESCRIPTION
        "this object was introduced in V 2.6.0 and states the Network Elements Longitude
        to the time the alarm was cleared."
      ::= { aimosAlarmListEntry 21 }

    
    aimosAlarmListRecognitionState OBJECT-TYPE
      SYNTAX RecognitionState
      MAX-ACCESS read-write
      STATUS current
      DESCRIPTION
        "This object of type RecognitionState states whether or not the alarm 
        has been recognized. Together with aimosAlarmListClearReason these
        objects are the only writeable values of this table.
        
        Recognition is used to indicate an 'I have seen the alarm and will 
        take care about it'. It is available via SNMP as well as via the 
        AIMOS_Visu's Supervision page. 
        
        Recognition by means of SNMP will be done by setting this value 
        to recognized(2). Due to the fact that alarms are moved from 
        aimosAlarmListTable to aimosAlarmLogTable as soon as they are both 
        cleared and acknowledged aimosAlarmLogRecognitionState provides means 
        to recognize cleared alarms; it is the only writeable alarm log object.
        
        A SET request with unrecognized(1) (i.e. 'Unrecognition') is an 
        invalid operation and will be rejected by the SNMP Agent.
        
        For each alarm recognition the SNMP Agent sends a aimosAlarmRecognized 
        trap to SNMP Managers having aimosPhoneBookRecognitionTraps set to true.
        
        On the other hand the similar sounding term 'acknowledgement' is 
        pertaining to the SNMP protocol: it provides means for the SNMP 
        manager to acknowledge trap receipt. 
        Please note: in case both the acknowledgement feature and the 
        recognition-traps-feature are active, even the recognition traps 
        have to be acknowledged.
        
        "
      ::= { aimosAlarmListEntry 22 }

    
    aimosAlarmListRecognitionUser OBJECT-TYPE
      SYNTAX UserName
      MAX-ACCESS read-only
      STATUS current
      DESCRIPTION
        "This object indicates the user who has recognized the alarm.
        This object is empty if the alarm is not recognized at all."
      ::= { aimosAlarmListEntry 23 }

    
    aimosAlarmListRecognitionTime OBJECT-TYPE
      SYNTAX VariableTime
      MAX-ACCESS read-only
      STATUS current
      DESCRIPTION
        "This object of type VariableTime holds the time of recognition.
        This object is empty if the alarm is not recognized at all."
      ::= { aimosAlarmListEntry 24 }

    
    aimosAlarmLogTable OBJECT-TYPE
      SYNTAX SEQUENCE OF AimosAlarmLogEntry
      MAX-ACCESS not-accessible
      STATUS current
      DESCRIPTION
        "This table is indexed by aimosOrgID, aimosAlarmTrapID and aimosAlarmListID and
        contains the list of cleared and acknowledged alarms. The data is the content of
        the alarm list related to a specific SNMP Manager and the corresponding contents
        of the trap list.
        
        Insert rows: must only be done by system
        Delete rows: must only be done by system"
      ::= { aimosAlarmManagement 15 }

    
    aimosAlarmLogEntry OBJECT-TYPE
      SYNTAX AimosAlarmLogEntry
      MAX-ACCESS not-accessible
      STATUS current
      DESCRIPTION
        "see description for table entry..."
      REFERENCE
        "MIS=TMISAlarmLogTable
        MDS=TMDSAlarmLogTable"
      INDEX { aimosOrgID, aimosAlarmTrapID, aimosAlarmListID }
      ::= { aimosAlarmLogTable 1 }

    
    AimosAlarmLogEntry ::=
      SEQUENCE { 
        aimosAlarmLogPhoneBookID
          TableIndex,
        aimosAlarmLogNotificationID
          Unsigned32,
        aimosAlarmLogAlarmEventID
          Unsigned32,
        aimosAlarmLogAlarmID
          AlarmID,
        aimosAlarmLogEventType
          EventType,
        aimosAlarmLogEventTime
          VariableTime,
        aimosAlarmLogProbableCause
          ProbableCause,
        aimosAlarmLogSpecificProblem
          SpecificProblem,
        aimosAlarmLogSeverity
          Severity,
        aimosAlarmLogTrendIndication
          TrendIndication,
        aimosAlarmLogAdditionalText
          Text,
        aimosAlarmLogSDN
          SDN,
        aimosAlarmLogTrapInfo
          Text,
        aimosAlarmLogComponentName
          Text,
        aimosAlarmLogLocation
          Text,
        aimosAlarmLogUniqueSystemID
          Text,
        aimosAlarmLogAcknowledgementUser
          UserName,
        aimosAlarmLogAcknowledgementTime
          VariableTime,
        aimosAlarmLogClearReason
          ClearReason,
        aimosAlarmLogClearTime
          VariableTime,
        aimosAlarmLogClearTrapID
          Unsigned32,
        aimosAlarmLogClearNotificationID
          Unsigned32,
        aimosAlarmLogClearAcknowledgementUser
          UserName,
        aimosAlarmLogClearAcknowledgementTime
          VariableTime,
        aimosAlarmLogRaiseLatitude
          GPSPosition,
        aimosAlarmLogRaiseLongitude
          GPSPosition,
        aimosAlarmLogClearLatitude
          GPSPosition,
        aimosAlarmLogClearLongitude
          GPSPosition,
        aimosAlarmLogRecognitionState
          RecognitionState,
        aimosAlarmLogRecognitionUser
          UserName,
        aimosAlarmLogRecognitionTime
          VariableTime
       }

    aimosAlarmLogPhoneBookID OBJECT-TYPE
      SYNTAX TableIndex
      MAX-ACCESS read-only
      STATUS current
      DESCRIPTION
        "See corresponding description in aimosAlarmTrapTable."
      ::= { aimosAlarmLogEntry 1 }

    
    aimosAlarmLogNotificationID OBJECT-TYPE
      SYNTAX Unsigned32
      MAX-ACCESS read-only
      STATUS current
      DESCRIPTION
        "See corresponding description in aimosAlarmTrapTable."
      ::= { aimosAlarmLogEntry 2 }

    
    aimosAlarmLogAlarmEventID OBJECT-TYPE
      SYNTAX Unsigned32
      MAX-ACCESS read-only
      STATUS current
      DESCRIPTION
        "See corresponding description in aimosAlarmListTable."
      ::= { aimosAlarmLogEntry 3 }

    
    aimosAlarmLogAlarmID OBJECT-TYPE
      SYNTAX AlarmID
      MAX-ACCESS read-only
      STATUS current
      DESCRIPTION
        "See corresponding description in aimosAlarmListTable."
      ::= { aimosAlarmLogEntry 4 }

    
    aimosAlarmLogEventType OBJECT-TYPE
      SYNTAX EventType
      MAX-ACCESS read-only
      STATUS current
      DESCRIPTION
        "See corresponding description in aimosAlarmListTable."
      ::= { aimosAlarmLogEntry 5 }

    
    aimosAlarmLogEventTime OBJECT-TYPE
      SYNTAX VariableTime
      MAX-ACCESS read-only
      STATUS current
      DESCRIPTION
        "See corresponding description in aimosAlarmListTable."
      ::= { aimosAlarmLogEntry 6 }

    
    aimosAlarmLogProbableCause OBJECT-TYPE
      SYNTAX ProbableCause
      MAX-ACCESS read-only
      STATUS current
      DESCRIPTION
        "See corresponding description in aimosAlarmListTable."
      ::= { aimosAlarmLogEntry 7 }

    
    aimosAlarmLogSpecificProblem OBJECT-TYPE
      SYNTAX SpecificProblem
      MAX-ACCESS read-only
      STATUS current
      DESCRIPTION
        "See corresponding description in aimosAlarmListTable."
      ::= { aimosAlarmLogEntry 8 }

    
    aimosAlarmLogSeverity OBJECT-TYPE
      SYNTAX Severity
      MAX-ACCESS read-only
      STATUS current
      DESCRIPTION
        "See corresponding description in aimosAlarmListTable."
      ::= { aimosAlarmLogEntry 9 }

    
    aimosAlarmLogTrendIndication OBJECT-TYPE
      SYNTAX TrendIndication
      MAX-ACCESS read-only
      STATUS current
      DESCRIPTION
        "See corresponding description in aimosAlarmListTable."
      ::= { aimosAlarmLogEntry 10 }

    
    aimosAlarmLogAdditionalText OBJECT-TYPE
      SYNTAX Text
      MAX-ACCESS read-only
      STATUS current
      DESCRIPTION
        "See corresponding description in aimosAlarmListTable."
      ::= { aimosAlarmLogEntry 11 }

    
    aimosAlarmLogSDN OBJECT-TYPE
      SYNTAX SDN
      MAX-ACCESS read-only
      STATUS current
      DESCRIPTION
        "See corresponding description in aimosAlarmListTable."
      ::= { aimosAlarmLogEntry 12 }

    
    aimosAlarmLogTrapInfo OBJECT-TYPE
      SYNTAX Text
      MAX-ACCESS read-only
      STATUS current
      DESCRIPTION
        "See corresponding description in aimosAlarmListTable."
      ::= { aimosAlarmLogEntry 13 }

    
    aimosAlarmLogComponentName OBJECT-TYPE
      SYNTAX Text
      MAX-ACCESS read-only
      STATUS current
      DESCRIPTION
        "See corresponding description in aimosAlarmListTable."
      ::= { aimosAlarmLogEntry 14 }

    
    aimosAlarmLogLocation OBJECT-TYPE
      SYNTAX Text
      MAX-ACCESS read-only
      STATUS current
      DESCRIPTION
        "See corresponding description in aimosAlarmListTable."
      ::= { aimosAlarmLogEntry 15 }

    
    aimosAlarmLogUniqueSystemID OBJECT-TYPE
      SYNTAX Text
      MAX-ACCESS read-only
      STATUS current
      DESCRIPTION
        "See corresponding description in aimosAlarmListTable."
      ::= { aimosAlarmLogEntry 16 }

    
    aimosAlarmLogAcknowledgementUser OBJECT-TYPE
      SYNTAX UserName
      MAX-ACCESS read-only
      STATUS current
      DESCRIPTION
        "See corresponding description in aimosAlarmTrapTable."
      ::= { aimosAlarmLogEntry 17 }

    
    aimosAlarmLogAcknowledgementTime OBJECT-TYPE
      SYNTAX VariableTime
      MAX-ACCESS read-only
      STATUS current
      DESCRIPTION
        "See corresponding description in aimosAlarmTrapTable."
      ::= { aimosAlarmLogEntry 18 }

    
    aimosAlarmLogClearReason OBJECT-TYPE
      SYNTAX ClearReason
      MAX-ACCESS read-only
      STATUS current
      DESCRIPTION
        "See corresponding description in aimosAlarmListTable."
      ::= { aimosAlarmLogEntry 19 }

    
    aimosAlarmLogClearTime OBJECT-TYPE
      SYNTAX VariableTime
      MAX-ACCESS read-only
      STATUS current
      DESCRIPTION
        "See corresponding description in aimosAlarmListTable."
      ::= { aimosAlarmLogEntry 20 }

    
    aimosAlarmLogClearTrapID OBJECT-TYPE
      SYNTAX Unsigned32
      MAX-ACCESS read-only
      STATUS current
      DESCRIPTION
        "See corresponding description in aimosAlarmTrapTable."
      ::= { aimosAlarmLogEntry 21 }

    
    aimosAlarmLogClearNotificationID OBJECT-TYPE
      SYNTAX Unsigned32
      MAX-ACCESS read-only
      STATUS current
      DESCRIPTION
        "See corresponding description in aimosAlarmTrapTable."
      ::= { aimosAlarmLogEntry 22 }

    
    aimosAlarmLogClearAcknowledgementUser OBJECT-TYPE
      SYNTAX UserName
      MAX-ACCESS read-only
      STATUS current
      DESCRIPTION
        "See corresponding description in aimosAlarmTrapTable."
      ::= { aimosAlarmLogEntry 23 }

    
    aimosAlarmLogClearAcknowledgementTime OBJECT-TYPE
      SYNTAX VariableTime
      MAX-ACCESS read-only
      STATUS current
      DESCRIPTION
        "See corresponding description in aimosAlarmTrapTable."
      ::= { aimosAlarmLogEntry 24 }

    
    aimosAlarmLogRaiseLatitude OBJECT-TYPE
      SYNTAX GPSPosition
      MAX-ACCESS read-only
      STATUS current
      DESCRIPTION
        "See corresponding description in aimosAlarmListTable."
      ::= { aimosAlarmLogEntry 25 }

    
    aimosAlarmLogRaiseLongitude OBJECT-TYPE
      SYNTAX GPSPosition
      MAX-ACCESS read-only
      STATUS current
      DESCRIPTION
        "See corresponding description in aimosAlarmListTable."
      ::= { aimosAlarmLogEntry 26 }

    
    aimosAlarmLogClearLatitude OBJECT-TYPE
      SYNTAX GPSPosition
      MAX-ACCESS read-only
      STATUS current
      DESCRIPTION
        "See corresponding description in aimosAlarmListTable."
      ::= { aimosAlarmLogEntry 27 }

    
    aimosAlarmLogClearLongitude OBJECT-TYPE
      SYNTAX GPSPosition
      MAX-ACCESS read-only
      STATUS current
      DESCRIPTION
        "See corresponding description in aimosAlarmListTable."
      ::= { aimosAlarmLogEntry 28 }

    
    aimosAlarmLogRecognitionState OBJECT-TYPE
      SYNTAX RecognitionState
      MAX-ACCESS read-write
      STATUS current
      DESCRIPTION
        "See corresponding description in aimosAlarmListTable."
      ::= { aimosAlarmLogEntry 29 }

    
    aimosAlarmLogRecognitionUser OBJECT-TYPE
      SYNTAX UserName
      MAX-ACCESS read-only
      STATUS current
      DESCRIPTION
        "See corresponding description in aimosAlarmListTable."
      ::= { aimosAlarmLogEntry 30 }

    
    aimosAlarmLogRecognitionTime OBJECT-TYPE
      SYNTAX VariableTime
      MAX-ACCESS read-only
      STATUS current
      DESCRIPTION
        "See corresponding description in aimosAlarmListTable."
      ::= { aimosAlarmLogEntry 31 }

    
    aimosAlarmForwardingType OBJECT-TYPE
      SYNTAX AlarmForwardingType
      MAX-ACCESS read-write
      STATUS current
      DESCRIPTION
        "This object of type AlarmForwardingType specifies if and in what way, alarm
        forwarding is to be carried out:
        
        . If this object is set to disabled(0), there is no alarm forwarding even if the
          tables for the configuration of the alarm recipients have correct entries.
        
        . If TRAP-TYPE construct from SNMPv1 is to be used for alarm forwarding, the
          parameter snmpV1(1) has to be set.
        
        . The default setting of snmpV2c(2) specifies that NOTIFICATION-TYPE construct
          from SNMPv2, will be used for alarm forwarding.
        
        This setting refers to an organisation, not to an individual SNMP Manager.
        In order to exclude an individual SNMP Manager temporarily from SNMP alarm
        forwarding, set aimosPhoneBookActive to false.
        To exclude an SNMP Manager completely, delete the corresponding phone book entry
        from the according distribution lists (aimosAlarmRecipientListMemberTable)."
      REFERENCE
        "MDS=TMDSSystemParams
        Tag=3001"
      DEFVAL { snmpV2c }
      ::= { aimosAlarmManagement 16 }

    
    aimosAlarmAckExpectInterval OBJECT-TYPE
      SYNTAX Unsigned32 (10..600)
      UNITS "seconds"
      MAX-ACCESS read-write
      STATUS current
      DESCRIPTION
        "After having emitted an alarm notification, the SNMP Agent expects an
        acknowledgement within a certain interval. This period of time is adjustable
        by means of this object within the range from 10 to 600 second.
        
        If there is no such acknowledgement the SNMP Agent will continue to emit the
        alarm until the acknowledgement is received, except in the case, that the
        SNMP Manager has stated its inability for acknowledgement by setting
        aimosPhoneBookAckCapability to false.
        
        Changes, which are made here, affect all organizations.
        That's why TelCo's are not allowed to make any changes here."
      REFERENCE
        "MDS=TMDSSystemParams
        Tag=3002"
      DEFVAL { 15 }
      ::= { aimosAlarmManagement 17 }

    
    aimosAlarmListRebuild OBJECT-TYPE
      SYNTAX OperationMode
      MAX-ACCESS read-write
      STATUS current
      DESCRIPTION
        "ATTENTION: Setting this objects value to start(5) will initiate an Alarm List
        Rebuild process. During this process ALL ALARM INFORMATION WILL BE DELETED !
        
        The Alarm List Rebuild process
        ==============================
        
        When an employee discovers that the internal alarm table of the A.I.M.O.S. SNMP
        Agent is flawed, an alarm list rebuild can be triggered. Such a process may also
        be necessary if productive operation is to start after a test phase with an empty
        alarm list.
        
        The Alarm List Rebuild consists of the following steps:
        
        . A SNMP Manager sets aimosAlarmListRebuild to start(5). The logged in user
          must belong the Provider.
        
        . The A.I.M.O.S. SNMP Agent drops the contents of the internal alarm tables. The
          table is completely deleted; each alarm list entry for each organisation is
          removed !
        
        . The A.I.M.O.S. SNMP Agent resets each alarm notification related counter to
          zero. These counters are aimosAlarmListID, aimosAlarmListAlarmEventID,
          aimosAlarmTrapID and each managers aimosAlarmTrapNotificationID. The values of
          these counters are increased by one with each new alarm, i.e. with the first
          alarms the value is 1. A counter of 0 is only possible after the maximum value
          (2^32-1) has been reached; which is, however, highly unlikely.
        
        . The aimosAlarmListRebuildInitiated notification is forwarded to all SNMP
          Managers configured to receive this alarm. This will result in
          . one new alarm list entry per affected organisation
            (with aimosAlarmListID and aimosAlarmListAlarmEventID each set to 1) and
          . one trap list entry per affected manager
            (with aimosAlarmTrapNotificationID set to 1 and per SNMP Manager consecutive
            numbered values beginning with 1 in aimosAlarmTrapID)
        
        . The A.I.M.O.S. devices are informed about the rebuild in order to reset its
          internal alarm tables, too. The devices will report still existing alarms as new
          alarms immediately.
        
        . Suppress forwarding of further notifications to a specific manager until the
          manager acknowledges the aimosAlarmListRebuildInitiated notification. If the
          acknowledgement is missing for a specific period of time, the agent obviously
          emits the aimosAlarmListRebuildInitiated notification again
        
        On receipt of the aimosAlarmListRebuildInitiated notification, the SNMP Manager
        shall clean the internal alarm table prior to acknowledge this notification.
        
        There is no aimosAlarmCleared notification for this alarm. The alarm gets cleared
        on acknowledgement. Alarm notifications received after that acknowledgement needs
        to get acknowledged by the manager as usual; the manager is neither required nor
        able to distinguish if a notification is a result of the alarm list rebuild or a
        new (never received before) one.
        
        Changes, which are made here, affect all organizations.
        That's why TelCo's are not allowed to initiate an Alarm List Rebuild Process
        by setting this value to start(5)."
      REFERENCE
        "MDS=TMDSAlarmListRenew
        Tag=1"
      ::= { aimosAlarmManagement 18 }

    
    aimosAlarmListResync OBJECT-TYPE
      SYNTAX OperationMode
      MAX-ACCESS read-write
      STATUS current
      DESCRIPTION
        "This object of type OperationMode is provided to give each SNMP Manager the
        ability to synchronise its alarm table.
        
        Setting this value to start(5) will start the alarm list synchronisation process.
        If the current SNMP Manager has more than one IP address or if his phonebook
        entry is 127.0.0.1, the SNMP Agent cannot determine for which phonebook entry
        the Alarm List Resync is to be done. In such a case 
        - either aimosPhoneBookAlarmListResync must be used 
        - or the aimosLoginPhoneBookID should be set manually (recommended)
        in order to start the Alarm List Resync Process.
        
        The Alarm List Resync process
        =============================
        
        When an employee discovers that the internal alarm table of the SNMP Manager is
        flawed, a resynchronisation of the alarm list can be initiated, which is e.g. the
        case when the trap count (aimosAlarmTrapNotificationID), which is continuous for
        each SNMP Manager, is interrupted.
        
        Each SNMP Manager receiving alarms is allowed to start a synchronisation of the
        alarm list. In order to do that the SNMP Manager shall first clean the internal
        alarm table and then request for an alarm list rebuild by setting
        aimosAlarmListResync to start(5).
        
        This request does not cause the agent to send a notification like the alarm list
        rebuild process will do, but the A.I.M.O.S. SNMP Agent will perform the following
        steps:
        
        . Set the value of aimosAlarmListResync to running(3)
        
        . It resets the managers aimosAlarmTrapNotificationID to zero
        
        . All alarms in the alarm list related to the specific manager will be emit with
          unchanged aimosAlarmListID, aimosAlarmListAlarmEventID and aimosAlarmTrapID
          values. The aimosAlarmTrapNotificationID is a new generated consecutive
          numbered value. The agent doesn't wait for acknowledgement before emitting the
          next notification.
        
        . If the last notification is sent to the manager, aimosAlarmListResync is set to
          idle(0)
        
        The manager is required to acknowledge all notifications as usual.
        An alarm list synchronisation neither effect the contents from the A.I.M.O.S. SNMP
        Agent's nor from other SNMP Manager's alarm lists except of the affected SNMP
        Manager's notification ID.
        "
      REFERENCE
        "MDS=TMDSAlarmListRenew
        Tag=2"
      ::= { aimosAlarmManagement 19 }

    
    aimosUnitManagement OBJECT-IDENTITY
      STATUS current
      DESCRIPTION 
        "This area comprises all objects dealing with unit management. This introduction
        provides an explanation of its basic structures.
        
        For each unit type there is one general table and one table per hardware version.
        E.g. there is the aimosRemoteUnitTable with objects that are valid for each
        Remote Unit, and the aimosRemoteUnitV1Table with objects of the Remote Unit
        Version 1. The general table contains one OID referring to the unit-specific
        table.
        
        Unit Reference
        ==============
        
        The Index of the general tables is composed of the topological arrangement of
        the units, i.e. depending on the arrangement it might contain several objects.
        The Index of a general Remote Unit table entry (aimosRemoteUnitTable) is e.g.
        composed of the Index of the Master Unit (aimosMasterID of type MasterID), the
        Index of the SubRack Master Unit (aimosSubRackID of type SubRackID) and the
        Index of the Remote Unit itself (aimosRemoteID of type RemoteID), since they
        are arranged in this order, whereas the Master Unit itself only has one Index
        (aimosMasterID), because there are no higher level units.
        
        All unit-specific tables, however, are always identified by two objects, one of
        the UnitReference type and the other of type ValueSource. Here, it does not
        matter whether it is a Master Unit or a Remote Unit.
        
        Value Source
        ============
        
        The unit-specific tables have three entries per unit:
        . one entry specifies the desired values
        . one entry serves to read the current values and to buffer them for subsequent
          access
        . and the third entry contains the buffered values
        
        Which one of these three entries is to be accessed is specified with the second
        Index of the unit-specific tables of type ValueSource.
        
        To avoid that a GET BULK results in endless hardware accesses, the A.I.M.O.S. SNMP
        Agent normally provides only the buffered values. Also, in case of a GET NEXT
        only the table entry corresponding to ValueSource cachedValue(2) is returned.
        
        Read accesses with cachedValue(2), however, are treated like accesses with
        actualValue(1), if no buffered values are available or if the time stamp
        belonging to these values was deleted.
        
        ValueSource desiredValue(3) is to be used for write access. However, the
        A.I.M.O.S. SNMP Agent also accepts write access to table entries with ValueSource
        cachedValue(2). This is treated as if the write access was made with
        desiredValue(3).
        
        Values
        ======
        
        The unit specific tables comprise objects containing various types of status
        information. Due to performance reasons, values of the same 'topic' are put
        together on a logic basis. Such logical object groups can be recognised by the
        name. E.g. the aimosSubRackV1Table comprises the following objects regarding
        attenuation:
        . aimosSubRackV1AttenuationAge
        . aimosSubRackV1AttenuationAmp1DL
        . aimosSubRackV1AttenuationAmp1UL
        . aimosSubRackV1AttenuationAmp2DL
        . aimosSubRackV1AttenuationAmp2UL
        . aimosSubRackV1AttenuationAmp3DL
        . aimosSubRackV1AttenuationAmp3UL
        
        These values are always dealt with together, i.e. if one of these values is to
        be read directly by the Master Controller, all the other values will be read,
        too. The time of this access is recorded in the age-object belonging to each
        status group.
        
        Time objects can be set to 0. This serves to prompt the A.I.M.O.S. SNMP Agent
        to get the current values with the next access to a cachedValue(2)-instance."
      ::= { aimosObjects 5 }

    
    aimosNextMasterID OBJECT-TYPE
      SYNTAX MasterID
      MAX-ACCESS read-only
      STATUS current
      DESCRIPTION
        "This object of type MasterID is used in order to create new Master Unit table
        entries. Its value has to be used as the identifier (aimosMasterID) of the new
        Master Unit."
      REFERENCE
        "MDS=TMDSNextID
        Tag=3"
      ::= { aimosUnitManagement 1 }

    
    aimosMasterUnitTable OBJECT-TYPE
      SYNTAX SEQUENCE OF AimosMasterUnitEntry
      MAX-ACCESS not-accessible
      STATUS current
      DESCRIPTION
        "This table contains hardware revision independent information's about Master
        Units including its Master Controller. A Master Unit consists of up to 127
        Remote Units.
        
        Insert rows: set aimosMasterAddress.<value of aimosNextMasterID> to the master
                     units ip address and port
        Delete rows: set aimosMasterAddress.<aimosMasterID> to 'delete' (without
                     quotation marks)
        
        TelCo's are not allowed to insert or delete rows respective Master Units."
      ::= { aimosUnitManagement 2 }

    
    aimosMasterUnitEntry OBJECT-TYPE
      SYNTAX AimosMasterUnitEntry
      MAX-ACCESS not-accessible
      STATUS current
      DESCRIPTION
        "see description for table entry..."
      REFERENCE
        "MIS=TMISMasterUnit
        MDS=TMDSMasterUnit"
      INDEX { aimosMasterID }
      ::= { aimosMasterUnitTable 1 }

    
    AimosMasterUnitEntry ::=
      SEQUENCE { 
        aimosMasterID
          MasterID,
        aimosMasterRDN
          RDN,
        aimosMasterSDN
          SDN,
        aimosMasterIdentNo
          IdentNo,
        aimosMasterSerialNo
          SerialNo,
        aimosMasterTrapInfo
          Text,
        aimosMasterLocation
          Text,
        aimosMasterAnyText
          Text,
        aimosMasterMapXY
          Coordinates,
        aimosMasterOID
          RowPointer,
        aimosMasterAddress
          IPAddressAndPort,
        aimosMasterState
          MasterState,
        aimosMasterGUID
          GUID,
        aimosMasterLoginUserName
          OCTET STRING,
        aimosMasterLoginPassword
          ControllerPassword
       }

    aimosMasterID OBJECT-TYPE
      SYNTAX MasterID
      MAX-ACCESS read-only
      STATUS current
      DESCRIPTION
        "This object of type MasterID uniquely identifies the Master Controller within
        the OMC.
        
        aimosNextMasterID tells you the value to be used in row creation."
      ::= { aimosMasterUnitEntry 1 }

    
    aimosMasterRDN OBJECT-TYPE
      SYNTAX RDN
      MAX-ACCESS read-only
      STATUS current
      DESCRIPTION
        "This object of type RDN shows the Relative Distinguished Name which consists of
        the object type and an object instance divided by the Distinguished Name
        Separator defined in aimosOrgDNSeparator. (e.g. RDN: MC=11)"
      ::= { aimosMasterUnitEntry 2 }

    
    aimosMasterSDN OBJECT-TYPE
      SYNTAX SDN
      MAX-ACCESS read-only
      STATUS current
      DESCRIPTION
        "This object of type SDN shows the System Distinguished Name which consists of a
        chaining of all RDN's all the way down from the OMC point of view to the desired
        unit. The RDN's are divided by the Distinguished Name Concatenator defined in
        aimosOrgDNConcatenator. (e.g. SDN for MC=11: OMC=1,MC=11)"
      ::= { aimosMasterUnitEntry 3 }

    
    aimosMasterIdentNo OBJECT-TYPE
      SYNTAX IdentNo
      MAX-ACCESS read-only
      STATUS current
      DESCRIPTION
        "This object of type IdentNo carries the Mikom Identification Number of the
        Master Controller."
      ::= { aimosMasterUnitEntry 4 }

    
    aimosMasterSerialNo OBJECT-TYPE
      SYNTAX SerialNo
      MAX-ACCESS read-only
      STATUS current
      DESCRIPTION
        "This object of type SerialNo represents the Mikom Serial Number of the Master
        Controller."
      ::= { aimosMasterUnitEntry 5 }

    
    aimosMasterTrapInfo OBJECT-TYPE
      SYNTAX Text
      MAX-ACCESS read-write
      STATUS current
      DESCRIPTION
        "This object of type Text lays down additional information to be provided with
        each notification sent to any SNMP Manager.
        
        The SNMP Agent makes this information available in the object
        aimosAlarmListCustomerMasterInfo of messages, which concern these Master
        Controller or subordinated devices like Sub Rack Master Units and Remote Units."
      ::= { aimosMasterUnitEntry 6 }

    
    aimosMasterLocation OBJECT-TYPE
      SYNTAX Text
      MAX-ACCESS read-write
      STATUS current
      DESCRIPTION
        "This object of type Text is a textual description of the place, where the
        Master Unit is located."
      ::= { aimosMasterUnitEntry 7 }

    
    aimosMasterAnyText OBJECT-TYPE
      SYNTAX Text
      MAX-ACCESS read-write
      STATUS current
      DESCRIPTION
        "This object of type Text gives the ability to store any unit related text."
      ::= { aimosMasterUnitEntry 8 }

    
    aimosMasterMapXY OBJECT-TYPE
      SYNTAX Coordinates
      MAX-ACCESS read-write
      STATUS current
      DESCRIPTION
        "This object of type Coordinates carries co-ordinates of Master Unit location."
      ::= { aimosMasterUnitEntry 9 }

    
    aimosMasterOID OBJECT-TYPE
      SYNTAX RowPointer
      MAX-ACCESS read-only
      STATUS current
      DESCRIPTION
        "This object of type RowPointer provides the OID where to find hardware specific
        information. In the first release of A.I.M.O.S. this object will point to the
        appropriate instance of the columnar object aimosMasterV1UnitReference. That
        object contains the Master Unit's UnitReference."
      ::= { aimosMasterUnitEntry 10 }

    
    aimosMasterAddress OBJECT-TYPE
      SYNTAX IPAddressAndPort
      MAX-ACCESS read-write
      STATUS current
      DESCRIPTION
        "This object of type IPAddressAndPort provides the Master Controllers IP address
        and port number.
        
        When a new Master Controller was integrated into the network by the provider, it
        can be integrated into the MIB, in a way that the A.I.M.O.S. SNMP Agent can answer
        the corresponding requests and forward alarms. The only required information is
        the IP address of the Master Controller and the port number where the controller
        software waits for incoming connections. The default is 7420.
        
        Only users of the provider are entitled to integrate Master Controllers into the
        MIB. In order to create a new Master Controller in the table aimosMasterUnitTable
        the following steps are required:
        
        . aimosInitiallyMasterLoginUserName and aimosInitiallyMasterLoginPassword should
          correspond to the User name and password set at the Master Controller.
        
        . aimosOMCConnectorAddress should contain the IP address and the IP Port under
          which the OMC Connector can be reached.
        
        . aimosNextMasterID must be queried, in order to identify the Index to be used
          for creating the table entry.
        
        . The returned ID is used to set aimosMasterAddress to the IP address and Port
          of the Master Controller. IP address and Port have to be separated by colons.
          If the Standard-Port 7420 is used, the port number information (and the colon)
          is dispensable.
        
        aimosMasterState states the success of the Master Controller integration. The
        desired value is properlySet(7). If not please refer to the DESCRIPTION clause
        for the next object (aimosMasterState). It describes, how the success of the
        MIB integration can be examined.
        
        Set this value to 'delete' (without quotation marks) in order to delete a Master
        Controller's table entry.
        
        Changes, which are made here, affect all organizations.
        That's why TelCo's are not allowed to make any changes here."
      ::= { aimosMasterUnitEntry 11 }

    
    aimosMasterState OBJECT-TYPE
      SYNTAX MasterState
      MAX-ACCESS read-write
      STATUS current
      DESCRIPTION
        "This object of type MasterState indicates the state of the Master Controller's
        system integration and should always be properlySet(7).
        
        Immediately after the Master Controllers IP address has been assigned to the
        object aimosMasterAddress, the SNMP Agent tries to reach the Master Controller
        in order to query its GUID. Here, aimosMasterState has the value
        performGUIDRequest(2).
        
        Afterwards, the network structure as well as all current information is queried.
        During this process aimosMasterState has the value performNetInfoRequest(5).
        
        After the query the value changes to properlySet(7). Moreover, the tables
        aimosSubRackTable, aimosRemoteUnitTable, aimosGSMNSOTable and aimosUMTSNSOTable
        have one entry for each of the network elements found. Each of these tables
        (like the aimosMasterUnitTable) have one object referring to the hardware version
        specific tables (aimosMasterOID, aimosSubRackOID, aimosRemoteOID, etc.). These,
        too, have one entry for each of the network elements found after a successful
        query.
        
        It is possible that one of the queries mentioned before fails:
        
        . If the GUID query was not successful the value of aimosMasterState changes
          from performGUIDRequest(2) to missingGUID(3). For this, there may be various
          reasons:
          . One might be that the Master Controller cannot be reached under the IP
            address and Port Number given by aimosMasterAddress. In such a case, the
            A.I.M.O.S. SNMP Agent answers the allocation to aimosMasterAddress with SNMP
            ErrorStatus resourceUnavailable(13). The error will be corrected by
            correcting the IP address and/or Port in aimosMasterAddress.
        
          . Another reason may be that the User in aimosMasterLoginUserName or the
            password in aimosMasterLoginPassword are wrong. Then, the A.I.M.O.S. SNMP
            Agent returns SNMP ErrorStatus noAccess(6). The error is corrected by
            assigning the correct Username to aimosMasterLoginUserName and/or the correct
            password to aimosMasterLoginPassword. Such an error may be prevented in
            advance by adjusting the pre-settings of these two objects. This can be done
            via the two objects aimosInitiallyMasterLoginUserName and
            aimosInitiallyMasterLoginPassword. Afterwards, a new GUID query must be made
            by setting aimosMasterState to requestGUID(1).
        
          . It is also possible that the Master Controller is not ready. This error can
            be corrected by starting the Master Controller or by making it available in
            the network (Firewall ?). Afterwards, a new GUID query must be made by
            setting aimosMasterState to requestGUID(1).
        
        . When a query of the network structure and/or status information failed, the
          value of aimosMasterState changes from performNetInfoRequest(5) to
          missingNetInfo(6). After correcting the cause of the failure another try to
          query the network structure must be made by setting aimosMasterState to
          requestNetInfo(4).
        
        These steps must be repeated until aimosMasterState is set to properlySet(7).
        Sometimes it might help to delete Master Controller and create it anew.
        
        
        
        
        
        
        
        
        This Leaf indicates, if the master unit is properly configured.
        
        If the GUID is missing, this Leaf contains missingGUID(3).
        You can assign requestGUID(1) to aimosMasterState, in order to
        inquire the GUID at the CONTROLLER. During the inquiry
        aimosMasterState's value changes to performGUIDRequest(2).
        If the inquiry is done, the value changes to
        - missingGUID(3) if the request was not successful
          (that means, the GUID is still unknown)
        - missingNetInfo(6) if the master controllers network is unknown
        - missingCommParams(8) if aimosMasterCommunicationID is not set
        - properlySet(9) if the master controllers
          - GUID (aimosMasterGUID) is knownn
          - network is known
          - Communication ID (aimosMasterCommunicationID) is set
        
        If the master controllers network is unknown (missingNetInfo(6)),
        set aimosMasterState to requestNetInfo(4). Until this command
        is recognized by the master controller aimosMasterState is
        performNetInfoRequest(5).
        
        If the CommunicationID is unknown (missingCommParams(8)), set
        aimosMasterCommunicationID to an appropriate value. Until this
        command is recognized by the master controller aimosMasterState
        is performSetCommParams(7).
        
        Each master controller should have the value properlySet(9) here.
        
        Changes, which are made here, affect all organizations. That's why TelCo's are not
        allowed to make any changes here."
      ::= { aimosMasterUnitEntry 12 }

    
    aimosMasterGUID OBJECT-TYPE
      SYNTAX GUID
      MAX-ACCESS read-only
      STATUS current
      DESCRIPTION
        "This object of type GUID is a globally unambiguous name for the Master
        Controller.
        
        This is not redundant with regard to the aimosMasterID, for if a Master
        Controller is to be exchanged one day, the new one will certainly have
        another GUID while the aimosMasterID remains the same."
      ::= { aimosMasterUnitEntry 13 }

    
    aimosMasterLoginUserName OBJECT-TYPE
      SYNTAX OCTET STRING (SIZE (1..20))
      MAX-ACCESS read-write
      STATUS current
      DESCRIPTION
        "This object of type UserName is the user name (max. length is 20 characters)
        used by the OMC for establishing a login with the Master Controller.
        
        When a new table entry is made, the user name is determined by the contents of
        aimosInitiallyMasterLoginUserName."
      ::= { aimosMasterUnitEntry 14 }

    
    aimosMasterLoginPassword OBJECT-TYPE
      SYNTAX ControllerPassword
      MAX-ACCESS read-write
      STATUS current
      DESCRIPTION
        "This object of type ControllerPassword contains the password for establishing a
        login with the Master Controller. The password can be read but the A.I.M.O.S. SNMP
        Agent only displays stars ('*') instead of the actual password.
        
        When a new table entry is made, the password is determined by the contents of
        aimosInitiallyMasterLoginPassword."
      ::= { aimosMasterUnitEntry 15 }

    
    aimosSubRackTable OBJECT-TYPE
      SYNTAX SEQUENCE OF AimosSubRackEntry
      MAX-ACCESS not-accessible
      STATUS current
      DESCRIPTION
        "This table contains hardware revision independent information's about the
        SubRack Master Unit.
        
        Insert rows: must only be done by system
        Delete rows: must only be done by system"
      ::= { aimosUnitManagement 3 }

    
    aimosSubRackEntry OBJECT-TYPE
      SYNTAX AimosSubRackEntry
      MAX-ACCESS not-accessible
      STATUS current
      DESCRIPTION
        "see description for table entry..."
      REFERENCE
        "MIS=TMISSubRack
        MDS=TMDSSubRack"
      INDEX { aimosMasterID, aimosSubRackID }
      ::= { aimosSubRackTable 1 }

    
    AimosSubRackEntry ::=
      SEQUENCE { 
        aimosSubRackID
          SubRackID,
        aimosSubRackRDN
          RDN,
        aimosSubRackSDN
          SDN,
        aimosSubRackIdentNo
          IdentNo,
        aimosSubRackSerialNo
          SerialNo,
        aimosSubRackTrapInfo
          Text,
        aimosSubRackLocation
          Text,
        aimosSubRackAnyText
          Text,
        aimosSubRackMapXY
          Coordinates,
        aimosSubRackOID
          RowPointer
       }

    aimosSubRackID OBJECT-TYPE
      SYNTAX SubRackID
      MAX-ACCESS read-only
      STATUS current
      DESCRIPTION
        "This object of type SubRackID uniquely identifies the Sub Rack Master Unit
        within its parent, a Master Unit."
      ::= { aimosSubRackEntry 1 }

    
    aimosSubRackRDN OBJECT-TYPE
      SYNTAX RDN
      MAX-ACCESS read-only
      STATUS current
      DESCRIPTION
        "This object of type RDN shows the Relative Distinguished Name which consists of
        the object type and an object instance divided by the Distinguished Name
        Separator defined in aimosOrgDNSeparator. (e.g. RDN: SRMU=19)"
      ::= { aimosSubRackEntry 2 }

    
    aimosSubRackSDN OBJECT-TYPE
      SYNTAX SDN
      MAX-ACCESS read-only
      STATUS current
      DESCRIPTION
        "This object of type SDN shows the System Distinguished Name which consists of a
        chaining of all RDN's all the way down from the OMC point of view to the desired
        unit. The RDN's are divided by Distinguished Name Concatenator defined in
        aimosOrgDNConcatenator. (e.g. SDN for SRMU=19 of MC 11: OMC=1,MC=11,SRMU=19)"
      ::= { aimosSubRackEntry 3 }

    
    aimosSubRackIdentNo OBJECT-TYPE
      SYNTAX IdentNo
      MAX-ACCESS read-only
      STATUS current
      DESCRIPTION
        "This object of type IdentNo carries the Mikom Identification Number of the
        Sub Rack Master Unit."
      ::= { aimosSubRackEntry 4 }

    
    aimosSubRackSerialNo OBJECT-TYPE
      SYNTAX SerialNo
      MAX-ACCESS read-only
      STATUS current
      DESCRIPTION
        "This object of type SerialNo represents the Mikom Serial Number of the Sub Rack
        Mater Unit."
      ::= { aimosSubRackEntry 5 }

    
    aimosSubRackTrapInfo OBJECT-TYPE
      SYNTAX Text
      MAX-ACCESS read-write
      STATUS current
      DESCRIPTION
        "This object of type Text lays down additional information to be provided with
        each notification sent to any SNMP Manager.
        
        The SNMP Agent makes this information available in the object
        aimosAlarmListCustomerSubRackInfo of messages, which concern these Sub Rack
        Master Unit or subordinated devices like Remote Units."
      ::= { aimosSubRackEntry 6 }

    
    aimosSubRackLocation OBJECT-TYPE
      SYNTAX Text
      MAX-ACCESS read-write
      STATUS current
      DESCRIPTION
        "This object of type Text is a textual description of the place, where the
        Sub Rack Master Unit is located."
      ::= { aimosSubRackEntry 7 }

    
    aimosSubRackAnyText OBJECT-TYPE
      SYNTAX Text
      MAX-ACCESS read-write
      STATUS current
      DESCRIPTION
        "This object of type Text gives the ability to store any unit related text."
      ::= { aimosSubRackEntry 8 }

    
    aimosSubRackMapXY OBJECT-TYPE
      SYNTAX Coordinates
      MAX-ACCESS read-write
      STATUS current
      DESCRIPTION
        "This object of type Coordinates carries co-ordinates of Sub Rack Master Unit
        location."
      ::= { aimosSubRackEntry 9 }

    
    aimosSubRackOID OBJECT-TYPE
      SYNTAX RowPointer
      MAX-ACCESS read-only
      STATUS current
      DESCRIPTION
        "This object of type RowPointer provides the OID where to find hardware specific
        information. In the first release of A.I.M.O.S. this object will point to the
        appropriate instance of the columnar object aimosSubRackV1UnitReference. That
        object contains the Sub Rack Master Unit's UnitReference."
      ::= { aimosSubRackEntry 10 }

    
    aimosRemoteUnitTable OBJECT-TYPE
      SYNTAX SEQUENCE OF AimosRemoteUnitEntry
      MAX-ACCESS not-accessible
      STATUS current
      DESCRIPTION
        "This table contains hardware revision independent information's about
        Remote Units.
        
        Insert rows: must only be done by system
        Delete rows: must only be done by system"
      ::= { aimosUnitManagement 4 }

    
    aimosRemoteUnitEntry OBJECT-TYPE
      SYNTAX AimosRemoteUnitEntry
      MAX-ACCESS not-accessible
      STATUS current
      DESCRIPTION
        "see description for table entry..."
      REFERENCE
        "MIS=TMISRemoteUnit
        MDS=TMDSRemoteUnit"
      INDEX { aimosMasterID, aimosSubRackID, aimosRemoteID }
      ::= { aimosRemoteUnitTable 1 }

    
    AimosRemoteUnitEntry ::=
      SEQUENCE { 
        aimosRemoteID
          RemoteID,
        aimosRemoteRDN
          RDN,
        aimosRemoteSDN
          SDN,
        aimosRemoteIdentNo
          IdentNo,
        aimosRemoteSerialNo
          SerialNo,
        aimosRemoteTrapInfo
          Text,
        aimosRemoteLocation
          Text,
        aimosRemoteAnyText
          Text,
        aimosRemoteMapXY
          Coordinates,
        aimosRemoteOID
          RowPointer
       }

    aimosRemoteID OBJECT-TYPE
      SYNTAX RemoteID
      MAX-ACCESS read-only
      STATUS current
      DESCRIPTION
        "This object of type RemoteID uniquely identifies the Remote Unit within the
        connected Sub Rack Master Unit."
      ::= { aimosRemoteUnitEntry 1 }

    
    aimosRemoteRDN OBJECT-TYPE
      SYNTAX RDN
      MAX-ACCESS read-only
      STATUS current
      DESCRIPTION
        "This object of type RDN shows the Relative Distinguished Name which consists of
        the object type and an object instance divided by the Distinguished Name
        Separator defined in aimosOrgDNSeparator. (e.g. RDN: RU=1)"
      ::= { aimosRemoteUnitEntry 2 }

    
    aimosRemoteSDN OBJECT-TYPE
      SYNTAX SDN
      MAX-ACCESS read-only
      STATUS current
      DESCRIPTION
        "This object of type SDN shows the System Distinguished Name which consists of a
        chaining of all RDN's all the way down from the OMC point of view to the desired
        unit. The RDN's are divided by Distinguished Name Concatenator defined in
        aimosOrgDNConcatenator. (e.g. SDN for a single RU connected to SRMU 23 of MC 11:
        OMC=1,MC=11,SRMU=23,RU=1)"
      ::= { aimosRemoteUnitEntry 3 }

    
    aimosRemoteIdentNo OBJECT-TYPE
      SYNTAX IdentNo
      MAX-ACCESS read-only
      STATUS current
      DESCRIPTION
        "This object of type IdentNo carries the Mikom Identification Number of the
        Remote Unit."
      ::= { aimosRemoteUnitEntry 4 }

    
    aimosRemoteSerialNo OBJECT-TYPE
      SYNTAX SerialNo
      MAX-ACCESS read-only
      STATUS current
      DESCRIPTION
        "This object of type SerialNo represents the Mikom Serial Number of the
        Remote Unit."
      ::= { aimosRemoteUnitEntry 5 }

    
    aimosRemoteTrapInfo OBJECT-TYPE
      SYNTAX Text
      MAX-ACCESS read-write
      STATUS current
      DESCRIPTION
        "This object of type Text lays down additional information to be provided with
        each notification sent to any SNMP Manager.
        
        The SNMP Agent makes this information available in the object
        aimosAlarmListCustomerRemoteInfo of messages, which concern these Remote Unit
        or subordinated devices like GSM NSO's and UMTS NSO's."
      ::= { aimosRemoteUnitEntry 6 }

    
    aimosRemoteLocation OBJECT-TYPE
      SYNTAX Text
      MAX-ACCESS read-write
      STATUS current
      DESCRIPTION
        "This object of type Text is a textual description of the place, where the
        Remote Unit is located."
      ::= { aimosRemoteUnitEntry 7 }

    
    aimosRemoteAnyText OBJECT-TYPE
      SYNTAX Text
      MAX-ACCESS read-write
      STATUS current
      DESCRIPTION
        "This object of type Text gives the ability to store any unit related text."
      ::= { aimosRemoteUnitEntry 8 }

    
    aimosRemoteMapXY OBJECT-TYPE
      SYNTAX Coordinates
      MAX-ACCESS read-write
      STATUS current
      DESCRIPTION
        "This object of type Coordinates carries co-ordinates of Remote Unit location."
      ::= { aimosRemoteUnitEntry 9 }

    
    aimosRemoteOID OBJECT-TYPE
      SYNTAX RowPointer
      MAX-ACCESS read-only
      STATUS current
      DESCRIPTION
        "This object of type RowPointer provides the OID where to find hardware specific
        information. In the first release of A.I.M.O.S. this object will point to the
        appropriate instance of the columnar object aimosRemoteV1UnitReference. That
        object contains the Remote Unit's UnitReference."
      ::= { aimosRemoteUnitEntry 10 }

    
    aimosGSMNSOTable OBJECT-TYPE
      SYNTAX SEQUENCE OF AimosGSMNSOEntry
      MAX-ACCESS not-accessible
      STATUS current
      DESCRIPTION
        "This table contains hardware revision independent information's about GSM NSO's.
        
        Insert rows: must only be done by system
        Delete rows: must only be done by system"
      ::= { aimosUnitManagement 5 }

    
    aimosGSMNSOEntry OBJECT-TYPE
      SYNTAX AimosGSMNSOEntry
      MAX-ACCESS not-accessible
      STATUS current
      DESCRIPTION
        "see description for table entry..."
      REFERENCE
        "MIS=TMISGSMNSO
        MDS=TMDSGSMNSO"
      INDEX { aimosMasterID, aimosSubRackID, aimosRemoteID, aimosGSMNSOID }
      ::= { aimosGSMNSOTable 1 }

    
    AimosGSMNSOEntry ::=
      SEQUENCE { 
        aimosGSMNSOID
          NSOID,
        aimosGSMNSORDN
          RDN,
        aimosGSMNSOSDN
          SDN,
        aimosGSMNSOIdentNo
          IdentNo,
        aimosGSMNSOSerialNo
          SerialNo,
        aimosGSMNSOTrapInfo
          Text,
        aimosGSMNSOLocation
          Text,
        aimosGSMNSOAnyText
          Text,
        aimosGSMNSOMapXY
          Coordinates,
        aimosGSMNSOOID
          RowPointer,
        aimosGSMNSOOIDData
          RowPointer
       }

    aimosGSMNSOID OBJECT-TYPE
      SYNTAX NSOID
      MAX-ACCESS read-only
      STATUS current
      DESCRIPTION
        "This object of type NSOID uniquely identifies the GSM NSO within the connected
        Remote Unit."
      ::= { aimosGSMNSOEntry 1 }

    
    aimosGSMNSORDN OBJECT-TYPE
      SYNTAX RDN
      MAX-ACCESS read-only
      STATUS current
      DESCRIPTION
        "This object of type RDN shows the Relative Distinguished Name which consists of
        the object type and an object instance divided by the Distinguished Name
        Separator defined in aimosOrgDNSeparator. (e.g. RDN: NSOG=1)"
      ::= { aimosGSMNSOEntry 2 }

    
    aimosGSMNSOSDN OBJECT-TYPE
      SYNTAX SDN
      MAX-ACCESS read-only
      STATUS current
      DESCRIPTION
        "This object of type SDN shows the System Distinguished Name which consists of a
        chaining of all RDN's all the way down from the OMC point of view to the desired
        unit. The RDN's are divided by Distinguished Name Concatenator defined in
        aimosOrgDNConcatenator. (e.g. SDN for the GSM NSO at a single RU connected to
        SRMU 23 of MC 11: OMC=1,MC=11,SRMU=23,RU=1,NSOG=1)"
      ::= { aimosGSMNSOEntry 3 }

    
    aimosGSMNSOIdentNo OBJECT-TYPE
      SYNTAX IdentNo
      MAX-ACCESS read-only
      STATUS current
      DESCRIPTION
        "This object of type IdentNo carries the Mikom Identification Number of the
        GSM NSO."
      ::= { aimosGSMNSOEntry 4 }

    
    aimosGSMNSOSerialNo OBJECT-TYPE
      SYNTAX SerialNo
      MAX-ACCESS read-only
      STATUS current
      DESCRIPTION
        "This object of type SerialNo represents the Mikom Serial Number of the GSM NSO."
      ::= { aimosGSMNSOEntry 5 }

    
    aimosGSMNSOTrapInfo OBJECT-TYPE
      SYNTAX Text
      MAX-ACCESS read-write
      STATUS current
      DESCRIPTION
        "This object of type Text lays down additional information to be provided with
        each notification sent to any SNMP Manager.
        
        Since the GSM NSO is located in the Remote Unit, this objects value is
        identical to the aimosRemoteTrapInfo's value."
      ::= { aimosGSMNSOEntry 6 }

    
    aimosGSMNSOLocation OBJECT-TYPE
      SYNTAX Text
      MAX-ACCESS read-write
      STATUS current
      DESCRIPTION
        "This object of type Text is a textual description of the place, where the
        GSM NSO is located.
        
        Since the GSM NSO is located in the Remote Unit, this object's value is
        identical to aimosRemoteLocation's value."
      ::= { aimosGSMNSOEntry 7 }

    
    aimosGSMNSOAnyText OBJECT-TYPE
      SYNTAX Text
      MAX-ACCESS read-write
      STATUS current
      DESCRIPTION
        "This object of type Text gives the ability to store any unit related text."
      ::= { aimosGSMNSOEntry 8 }

    
    aimosGSMNSOMapXY OBJECT-TYPE
      SYNTAX Coordinates
      MAX-ACCESS read-write
      STATUS current
      DESCRIPTION
        "This object of type Coordinates carries co-ordinates of GSM NSO location."
      ::= { aimosGSMNSOEntry 9 }

    
    aimosGSMNSOOID OBJECT-TYPE
      SYNTAX RowPointer
      MAX-ACCESS read-only
      STATUS current
      DESCRIPTION
        "This object of type RowPointer provides the OID where to find hardware specific
        information. In the first release of A.I.M.O.S. this object will point to the
        appropriate instance of the columnar object aimosGSMNSOV1UnitReference. That
        object contains the GSM NSO's UnitReference."
      ::= { aimosGSMNSOEntry 10 }

    
    aimosGSMNSOOIDData OBJECT-TYPE
      SYNTAX RowPointer
      MAX-ACCESS read-only
      STATUS current
      DESCRIPTION
        "This object of type RowPointer shows the OID, which provides measurement
        data of GSM NSO. In the first release of A.I.M.O.S. this object will point to
        directly preceding the first appropriate instance of the columnar object
        aimosGSMNSODataV1ID."
      ::= { aimosGSMNSOEntry 11 }

    
    aimosUMTSNSOTable OBJECT-TYPE
      SYNTAX SEQUENCE OF AimosUMTSNSOEntry
      MAX-ACCESS not-accessible
      STATUS current
      DESCRIPTION
        "This table contains hardware revision independent information's about UMTS NSO's.
        
        Insert rows: must only be done by system
        Delete rows: must only be done by system"
      ::= { aimosUnitManagement 6 }

    
    aimosUMTSNSOEntry OBJECT-TYPE
      SYNTAX AimosUMTSNSOEntry
      MAX-ACCESS not-accessible
      STATUS current
      DESCRIPTION
        "see description for table entry..."
      REFERENCE
        "MIS=TMISUMTSNSO
        MDS=TMDSUMTSNSO"
      INDEX { aimosMasterID, aimosSubRackID, aimosRemoteID, aimosUMTSNSOID }
      ::= { aimosUMTSNSOTable 1 }

    
    AimosUMTSNSOEntry ::=
      SEQUENCE { 
        aimosUMTSNSOID
          NSOID,
        aimosUMTSNSORDN
          RDN,
        aimosUMTSNSOSDN
          SDN,
        aimosUMTSNSOIdentNo
          IdentNo,
        aimosUMTSNSOSerialNo
          SerialNo,
        aimosUMTSNSOTrapInfo
          Text,
        aimosUMTSNSOLocation
          Text,
        aimosUMTSNSOAnyText
          Text,
        aimosUMTSNSOMapXY
          Coordinates,
        aimosUMTSNSOOID
          RowPointer,
        aimosUMTSNSOOIDData
          RowPointer
       }

    aimosUMTSNSOID OBJECT-TYPE
      SYNTAX NSOID
      MAX-ACCESS read-only
      STATUS current
      DESCRIPTION
        "This object of type NSOID uniquely identifies the UMTS NSO within the connected
        Remote Unit."
      ::= { aimosUMTSNSOEntry 1 }

    
    aimosUMTSNSORDN OBJECT-TYPE
      SYNTAX RDN
      MAX-ACCESS read-only
      STATUS current
      DESCRIPTION
        "This object of type RDN shows the Relative Distinguished Name which consists of
        the object type and an object instance divided by the Distinguished Name
        Separator defined in aimosOrgDNSeparator. (e.g. RDN: NSOU=1)"
      ::= { aimosUMTSNSOEntry 2 }

    
    aimosUMTSNSOSDN OBJECT-TYPE
      SYNTAX SDN
      MAX-ACCESS read-only
      STATUS current
      DESCRIPTION
        "This object of type SDN shows the System Distinguished Name which consists of a
        chaining of all RDN's all the way down from the OMC point of view to the desired
        unit. The RDN's are divided by Distinguished Name Concatenator defined in
        aimosOrgDNConcatenator. (e.g. SDN for the UMTS NSO at a single RU connected to
        SRMU 23 of MC 11: OMC=1,MC=11,SRMU=23,RU=1,NSOU=1)"
      ::= { aimosUMTSNSOEntry 3 }

    
    aimosUMTSNSOIdentNo OBJECT-TYPE
      SYNTAX IdentNo
      MAX-ACCESS read-only
      STATUS current
      DESCRIPTION
        "This object of type IdentNo carries the Mikom Identification Number of the
        UMTS NSO."
      ::= { aimosUMTSNSOEntry 4 }

    
    aimosUMTSNSOSerialNo OBJECT-TYPE
      SYNTAX SerialNo
      MAX-ACCESS read-only
      STATUS current
      DESCRIPTION
        "This object of type SerialNo represents the Mikom Serial Number of the UMTS NSO."
      ::= { aimosUMTSNSOEntry 5 }

    
    aimosUMTSNSOTrapInfo OBJECT-TYPE
      SYNTAX Text
      MAX-ACCESS read-write
      STATUS current
      DESCRIPTION
        "This object of type Text lays down additional information to be provided with
        each notification sent to any SNMP Manager.
        
        Since the UMTS NSO is located in the Remote Unit, this objects value is
        identical to the aimosRemoteTrapInfo's value."
      ::= { aimosUMTSNSOEntry 6 }

    
    aimosUMTSNSOLocation OBJECT-TYPE
      SYNTAX Text
      MAX-ACCESS read-write
      STATUS current
      DESCRIPTION
        "This object of type Text is a textual description of the place, where the
        UMTS NSO is located.
        
        Since the UMTS NSO is located in the Remote Unit, this object's value is
        identical to aimosRemoteLocation's value."
      ::= { aimosUMTSNSOEntry 7 }

    
    aimosUMTSNSOAnyText OBJECT-TYPE
      SYNTAX Text
      MAX-ACCESS read-write
      STATUS current
      DESCRIPTION
        "This object of type Text gives the ability to store any unit related text."
      ::= { aimosUMTSNSOEntry 8 }

    
    aimosUMTSNSOMapXY OBJECT-TYPE
      SYNTAX Coordinates
      MAX-ACCESS read-write
      STATUS current
      DESCRIPTION
        "This object of type Coordinates carries co-ordinates of UMTS NSO location."
      ::= { aimosUMTSNSOEntry 9 }

    
    aimosUMTSNSOOID OBJECT-TYPE
      SYNTAX RowPointer
      MAX-ACCESS read-only
      STATUS current
      DESCRIPTION
        "This object of type RowPointer provides the OID where to find hardware specific
        information. In the first release of A.I.M.O.S. this object will point to the
        appropriate instance of the columnar object aimosUMTSNSOV1UnitReference. That
        object contains the UMTS NSO's UnitReference."
      ::= { aimosUMTSNSOEntry 10 }

    
    aimosUMTSNSOOIDData OBJECT-TYPE
      SYNTAX RowPointer
      MAX-ACCESS read-only
      STATUS current
      DESCRIPTION
        "This object of type RowPointer shows the OID, which provides measurement
        data of UMTS NSO. In the first release of A.I.M.O.S. this object will point to
        directly preceding the first appropriate instance of the columnar object
        aimosUMTSNSODataV1ID."
      ::= { aimosUMTSNSOEntry 11 }

    
    aimosNextCableID OBJECT-TYPE
      SYNTAX CableID
      MAX-ACCESS read-only
      STATUS current
      DESCRIPTION
        "This object of type CableID has to be used in order to create new entries in
        aimosCableTable. The value has to be used as the identifier for new entries."
      REFERENCE
        "MDS=TMDSNextID
        Tag=4"
      ::= { aimosUnitManagement 7 }

    
    aimosCableTable OBJECT-TYPE
      SYNTAX SEQUENCE OF AimosCableEntry
      MAX-ACCESS not-accessible
      STATUS current
      DESCRIPTION
        "This table contains information's about fibre-optic cables used in
        interconnection between Remote Units and SubRack Master Units.
        
        This information is transmitted as part of traps and, thus offers the
        possibility to recognise a cable damage in case several Remote Units that
        all use the same cable show a failure.
        
        If this information is not necessary this table may be left empty.
        
        Insert rows: set aimosCableCode.<value of aimosNextCableID> to the cable's code
        Delete rows: set aimosCableCode.<aimosCableID> to 'delete' (without quotation
                     marks)
        
        TelCo's are not allowed to insert or delete rows."
      ::= { aimosUnitManagement 8 }

    
    aimosCableEntry OBJECT-TYPE
      SYNTAX AimosCableEntry
      MAX-ACCESS not-accessible
      STATUS current
      DESCRIPTION
        "see description for table entry..."
      REFERENCE
        "MIS=TMISCable
        MDS=TMDSCable"
      INDEX { aimosCableID }
      ::= { aimosCableTable 1 }

    
    AimosCableEntry ::=
      SEQUENCE { 
        aimosCableID
          CableID,
        aimosCableCode
          CableCode,
        aimosCableTrapInfo
          Text,
        aimosCableLocation
          Text,
        aimosCableAnyText
          Text
       }

    aimosCableID OBJECT-TYPE
      SYNTAX CableID
      MAX-ACCESS read-only
      STATUS current
      DESCRIPTION
        "This object of type CableID is an unique identifier for cable table entries.
        
        aimosNextCableID tells you the value to be used in cable table entry creation."
      ::= { aimosCableEntry 1 }

    
    aimosCableCode OBJECT-TYPE
      SYNTAX CableCode
      MAX-ACCESS read-write
      STATUS current
      DESCRIPTION
        "This value of type CableCode holds the textual identification / representation
        of a specific cable.
        
        Set this value to 'delete' (without quotation marks) in order to delete this
        entry.
        
        Changes, which are made here, affect all organizations.
        That's why TelCo's are not allowed to make any changes here."
      ::= { aimosCableEntry 2 }

    
    aimosCableTrapInfo OBJECT-TYPE
      SYNTAX Text
      MAX-ACCESS read-write
      STATUS current
      DESCRIPTION
        "In aimosCableTrapInfo of type Text a freely definable identification can be
        entered, by which the cable can be identified. This identifier is transmitted
        with the alarm notifications referring to A.I.M.O.S. units (aimosAlarmNew,
        aimosAlarmChanged and aimosAlarmCleared) in the object
        aimosAlarmListCustomerCableInfo.
        
        In this text, the wildcard character %s can be used. It has the effect that at
        the according position in the traps the contents of the object
        aimosCableUsageFibreCode are inserted. In this way, the cable identification
        can be extended by the corresponding core identifier.
        
        Attention: If aimosCableUsageAlternativeTrapInfo contains text, that text will
        be used for the creation of the aimosAlarmListCustomerCableInfo, thus;
        aimosCableTrapInfo will then be without meaning."
      ::= { aimosCableEntry 3 }

    
    aimosCableLocation OBJECT-TYPE
      SYNTAX Text
      MAX-ACCESS read-write
      STATUS current
      DESCRIPTION
        "This object of type Text is a textual description of the place, where the cable
        is located.
        
        Changes, which are made here, affect all organizations.
        That's why TelCo's are not allowed to make any changes here."
      ::= { aimosCableEntry 4 }

    
    aimosCableAnyText OBJECT-TYPE
      SYNTAX Text
      MAX-ACCESS read-write
      STATUS current
      DESCRIPTION
        "This object of type Text gives the ability to store any unit related text.
        
        Changes, which are made here, affect all organizations.
        That's why TelCo's are not allowed to make any changes here."
      ::= { aimosCableEntry 5 }

    
    aimosCableUsageTable OBJECT-TYPE
      SYNTAX SEQUENCE OF AimosCableUsageEntry
      MAX-ACCESS not-accessible
      STATUS current
      DESCRIPTION
        "This table contains information as to which cable or even which cores of a cable
        were used to connect a certain Sub Rack Master Unit to a certain Remote Unit.
        This information is transmitted with the traps and is designed to indicate a
        cable damage in case several Remote Units that all use the same cable show a
        failure at the same time.
        
        If this information is not required, the table can be ignored.
        
        Insert rows: set aimosCableUsageCableID.<aimosCableUsageRemoteUnitReference>.
                     <aimosCableUsageID> to the aimosCableID of the used cable
        Delete rows: set aimosCableUsageCableID.<aimosCableUsageRemoteUnitReference>.
                     <aimosCableUsageID> to zero
        
        TelCo's are not allowed to insert or delete rows."
      ::= { aimosUnitManagement 9 }

    
    aimosCableUsageEntry OBJECT-TYPE
      SYNTAX AimosCableUsageEntry
      MAX-ACCESS not-accessible
      STATUS current
      DESCRIPTION
        "see description for table entry..."
      REFERENCE
        "MIS=TMISCableUsage
        MDS=TMDSCableUsage"
      INDEX { aimosCableUsageRemoteUnitReference, aimosCableUsageID }
      ::= { aimosCableUsageTable 1 }

    
    AimosCableUsageEntry ::=
      SEQUENCE { 
        aimosCableUsageRemoteUnitReference
          UnitReference,
        aimosCableUsageID
          TableIndex,
        aimosCableUsageCableID
          CableID,
        aimosCableUsageFibreCode
          CableCode,
        aimosCableUsageAlternativeTrapInfo
          Text
       }

    aimosCableUsageRemoteUnitReference OBJECT-TYPE
      SYNTAX UnitReference
      MAX-ACCESS read-only
      STATUS current
      DESCRIPTION
        "This object is of type UnitReference and identifies the Remote Unit to which the
        current table entry does refer."
      ::= { aimosCableUsageEntry 1 }

    
    aimosCableUsageID OBJECT-TYPE
      SYNTAX TableIndex
      MAX-ACCESS read-only
      STATUS current
      DESCRIPTION
        "This object determines the sequence of cables used in order to connect the
        Sub Rack Master Unit with a specific Remote Unit. The cable directly connected
        to the Sub Rack Master Unit get number one. The numbers increase by one with
        the distance from the Sub Rack Master Unit."
      ::= { aimosCableUsageEntry 2 }

    
    aimosCableUsageCableID OBJECT-TYPE
      SYNTAX CableID
      MAX-ACCESS read-write
      STATUS current
      DESCRIPTION
        "This object of type CableID shows which cable was used to connect the Remote Unit
        identified by aimosCableUsageRemoteUnitReference with the SubRack Master Unit.
        
        Setting this value to 0 deletes the table entry."
      ::= { aimosCableUsageEntry 3 }

    
    aimosCableUsageFibreCode OBJECT-TYPE
      SYNTAX CableCode
      MAX-ACCESS read-write
      STATUS current
      DESCRIPTION
        "This object of type CableCode can be used to identify the cores used
        in the cable. This identification can be taken over into the object
        aimosAlarmListCustomerCableInfo of several alarm traps by entering
        the wildcard character %s in aimosCableTrapInfo."
      ::= { aimosCableUsageEntry 4 }

    
    aimosCableUsageAlternativeTrapInfo OBJECT-TYPE
      SYNTAX Text
      MAX-ACCESS read-write
      STATUS current
      DESCRIPTION
        "In aimosCableUsageAlternativeTrapInfo of type Text a freely definable
        identification for identifying cable and used core can be entered.
        This identification is transmitted with the alarm notifications referring
        to A.I.M.O.S. units (aimosAlarmNew, aimosAlarmChanged and aimosAlarmCleared),
        in the object aimosAlarmListCustomerCableInfo.
        
        If this object is used, object aimosCableTrapInfo remains without meaning."
      ::= { aimosCableUsageEntry 5 }

    
    aimosMasterUnitV1Table OBJECT-TYPE
      SYNTAX SEQUENCE OF AimosMasterUnitV1Entry
      MAX-ACCESS not-accessible
      STATUS current
      DESCRIPTION
        "This table contains information's about Master Units with hardware revision 1.
        
        Insert rows: must only be done by system
        Delete rows: must only be done by system"
      ::= { aimosUnitManagement 13 }

    
    aimosMasterUnitV1Entry OBJECT-TYPE
      SYNTAX AimosMasterUnitV1Entry
      MAX-ACCESS not-accessible
      STATUS current
      DESCRIPTION
        "see description for table entry..."
      REFERENCE
        "MIS=TMISMasterUnitV1
        MDS=TMDSMasterUnitV1"
      INDEX { aimosMasterV1UnitReference, aimosMasterV1ValueSource }
      ::= { aimosMasterUnitV1Table 1 }

    
    AimosMasterUnitV1Entry ::=
      SEQUENCE { 
        aimosMasterV1UnitReference
          UnitReference,
        aimosMasterV1ValueSource
          ValueSource,
        aimosMasterV1HeartbeatInterval
          WeekMinutes,
        aimosMasterV1HeartbeatOvertime
          WeekMinutes,
        aimosMasterV1HeartbeatTime
          VariableTime
       }

    aimosMasterV1UnitReference OBJECT-TYPE
      SYNTAX UnitReference
      MAX-ACCESS read-only
      STATUS current
      DESCRIPTION
        "This object of type UnitReference is the first index of this table. It
        unambiguously identifies the unit, independent of its kind (Master Unit,
        Sub Rack Master Unit, Remote Unit,...)."
      ::= { aimosMasterUnitV1Entry 1 }

    
    aimosMasterV1ValueSource OBJECT-TYPE
      SYNTAX ValueSource
      MAX-ACCESS read-only
      STATUS current
      DESCRIPTION
        "This object of type ValueSource is the second index in this table.
        
        It indicates, which value is to be addressed (actual, cached or desired value):
        
        . actual : An access to the hardware takes place in order to query the current
                   values. These values are stored in the SNMP Agents local database.
                   Actual values are read only.
        
        . cached : The values stored with the last hardware access are indicated. This
                   is the default in order to shorten the period of reply.
                   If the associated age value is missing, then the access is treated in
                   such a way, as if actual one would have indicated.
                   Cached values are read only (see remark below).
        
        . desired: Has to be used, if values on the hardware are to be changed.
        
        Remark: Although write accesses on cached values do not make a sense, are they
        permitted in order to facilitate handling with the MIB. Write accesses on cached
        values are treated in such a way, as if desired one would have indicated."
      ::= { aimosMasterUnitV1Entry 2 }

    
    aimosMasterV1HeartbeatInterval OBJECT-TYPE
      SYNTAX WeekMinutes
      UNITS "minutes"
      MAX-ACCESS read-write
      STATUS current
      DESCRIPTION
        "Alternatively to a regular polling of the Master Controllers by an SNMP Manager,
        the Master Controller is capable of sending a regular 'I'm-alive-message' to the
        A.I.M.O.S. SNMP Agent. In this way, the A.I.M.O.S. SNMP Agent will recognise a
        failure of the Master Controller when the message is no longer sent and can
        consequently generate and send out a aimosAlarmNew notification with the objects
        aimosAlarmListAlarmID set to alarmHeartbeatMissing(63) and
        aimosAlarmListSpecificProblem set to 8888.
        
        aimosMasterV1HeartbeatInterval is an object of type WeekMinutes, by which the
        interval at which the Master Controller is to send this 'life sign' can be set.
        Values from 0 up to 10.080 are allowed.
        
        Setting 0 deactivates the Heartbeat feature, the highest setting 10.080 sets
        the interval to one week."
      DEFVAL { 0 }
      ::= { aimosMasterUnitV1Entry 3 }

    
    aimosMasterV1HeartbeatOvertime OBJECT-TYPE
      SYNTAX WeekMinutes
      UNITS "minutes"
      MAX-ACCESS read-write
      STATUS current
      DESCRIPTION
        "This object of type WeekMinutes offers the possibility to set a certain waiting
        time. This is required to compensate the differing latency periods of the Master
        Controller and the A.I.M.O.S. SNMP Agent. The default value of 1 minute should
        generally be sufficient. Only in case of a very slow connection establishment
        or if the Master Controller / A.I.M.O.S. SNMP Agent is very busy, this value
        should be increased to avoid false alarms."
      DEFVAL { 1 }
      ::= { aimosMasterUnitV1Entry 4 }

    
    aimosMasterV1HeartbeatTime OBJECT-TYPE
      SYNTAX VariableTime
      MAX-ACCESS read-only
      STATUS current
      DESCRIPTION
        "This object of type VariableTime provides the time when the Master Controller
        sent the last life sign.
        
        It does not make sense to read this value to an instance with
        aimosMasterV1ValueSource of actualValue(1); there is only one value for the
        instance cachedValue(2)."
      ::= { aimosMasterUnitV1Entry 5 }

    
    aimosSubRackV1Table OBJECT-TYPE
      SYNTAX SEQUENCE OF AimosSubRackV1Entry
      MAX-ACCESS not-accessible
      STATUS current
      DESCRIPTION
        "This table contains information's about SubRack Master Units with hardware
        revision 1.
        
        Insert rows: must only be done by system
        Delete rows: must only be done by system"
      ::= { aimosUnitManagement 14 }

    
    aimosSubRackV1Entry OBJECT-TYPE
      SYNTAX AimosSubRackV1Entry
      MAX-ACCESS not-accessible
      STATUS current
      DESCRIPTION
        "see description for table entry..."
      REFERENCE
        "MIS=TMISSubRackV1
        MDS=TMDSSubRackV1"
      INDEX { aimosSubRackV1UnitReference, aimosSubRackV1ValueSource }
      ::= { aimosSubRackV1Table 1 }

    
    AimosSubRackV1Entry ::=
      SEQUENCE { 
        aimosSubRackV1UnitReference
          UnitReference,
        aimosSubRackV1ValueSource
          ValueSource,
        aimosSubRackV1AttenuationAge
          VariableTime,
        aimosSubRackV1AttenuationAmp1DL
          Attenuation,
        aimosSubRackV1AttenuationAmp1UL
          Attenuation,
        aimosSubRackV1AttenuationAmp2DL
          Attenuation,
        aimosSubRackV1AttenuationAmp2UL
          Attenuation,
        aimosSubRackV1AttenuationAmp3DL
          Attenuation,
        aimosSubRackV1AttenuationAmp3UL
          Attenuation,
        aimosSubRackV1GainOffsetAge
          VariableTime,
        aimosSubRackV1GainOffsetAmp1DL
          GainOffset,
        aimosSubRackV1GainOffsetAmp1UL
          GainOffset,
        aimosSubRackV1GainOffsetAmp2DL
          GainOffset,
        aimosSubRackV1GainOffsetAmp2UL
          GainOffset,
        aimosSubRackV1GainOffsetAmp3DL
          GainOffset,
        aimosSubRackV1GainOffsetAmp3UL
          GainOffset,
        aimosSubRackV1TemperatureAge
          VariableTime,
        aimosSubRackV1TemperatureBoard
          TemperatureStatus,
        aimosSubRackV1AmplifierBandNamesAge
          VariableTime,
        aimosSubRackV1Amplifier1BandName
          OCTET STRING,
        aimosSubRackV1Amplifier2BandName
          OCTET STRING,
        aimosSubRackV1Amplifier3BandName
          OCTET STRING
       }

    aimosSubRackV1UnitReference OBJECT-TYPE
      SYNTAX UnitReference
      MAX-ACCESS read-only
      STATUS current
      DESCRIPTION
        "This object of type UnitReference is the first index of this table. It
        unambiguously identifies the unit, independent of its kind (Master Unit,
        Sub Rack Master Unit, Remote Unit,...)."
      ::= { aimosSubRackV1Entry 1 }

    
    aimosSubRackV1ValueSource OBJECT-TYPE
      SYNTAX ValueSource
      MAX-ACCESS read-only
      STATUS current
      DESCRIPTION
        "This object of type ValueSource is the second index in this table.
        
        It indicates, which value is to be addressed (actual, cached or desired value):
        
        . actual : An access to the hardware takes place in order to query the current
                   values. These values are stored in the SNMP Agents local database.
                   Actual values are read only.
        
        . cached : The values stored with the last hardware access are indicated. This
                   is the default in order to shorten the period of reply.
                   If the associated age value is missing, then the access is treated in
                   such a way, as if actual one would have indicated.
                   Cached values are read only (see remark below).
        
        . desired: Has to be used, if values on the hardware are to be changed.
        
        Remark: Although write accesses on cached values do not make a sense, are they
        permitted in order to facilitate handling with the MIB. Write accesses on cached
        values are treated in such a way, as if desired one would have indicated."
      ::= { aimosSubRackV1Entry 2 }

    
    aimosSubRackV1AttenuationAge OBJECT-TYPE
      SYNTAX VariableTime
      MAX-ACCESS read-write
      STATUS current
      DESCRIPTION
        "In both the uplink (UL) and the downlink (DL) path for each of the three bands
        supported by the three amplifiers (1 to 3), the attenuation of the corresponding
        attenuator (located in the optical device) responsible for Autolevelling can be
        read-off or (only in case of a provider) be changed. For this purpose, the MIB
        contains the following six objects:
        . aimosSubRackV1AttenuationAmp1DL
        . aimosSubRackV1AttenuationAmp1UL
        . aimosSubRackV1AttenuationAmp2DL
        . aimosSubRackV1AttenuationAmp2UL
        . aimosSubRackV1AttenuationAmp3DL
        . aimosSubRackV1AttenuationAmp3UL.
        
        These objects are of the Attenuation type and contain the attenuation value in
        dB.
        
        The time when the values were last read is recorded in the object
        aimosSubRackV1AttenuationAge of the VariableTime type. This value can be set to
        empty text in order to prompt the Controller to query the values anew with the
        next request to a cachedValue(2)-instance directly at the Master Controller."
      ::= { aimosSubRackV1Entry 3 }

    
    aimosSubRackV1AttenuationAmp1DL OBJECT-TYPE
      SYNTAX Attenuation
      UNITS "dB"
      MAX-ACCESS read-write
      STATUS current
      DESCRIPTION
        "Attenuation on amplifier 1 downlink.
        
        The object aimosSubRackV1AttenuationAge indicates the age of this information.
        
        Changes, which are made here, affect the hardware.
        That's why TelCo's are not allowed to make any changes here."
      ::= { aimosSubRackV1Entry 4 }

    
    aimosSubRackV1AttenuationAmp1UL OBJECT-TYPE
      SYNTAX Attenuation
      UNITS "dB"
      MAX-ACCESS read-write
      STATUS current
      DESCRIPTION
        "Attenuation on amplifier 1 uplink.
        
        The object aimosSubRackV1AttenuationAge indicates the age of this information.
        
        Changes, which are made here, affect the hardware.
        That's why TelCo's are not allowed to make any changes here."
      ::= { aimosSubRackV1Entry 5 }

    
    aimosSubRackV1AttenuationAmp2DL OBJECT-TYPE
      SYNTAX Attenuation
      UNITS "dB"
      MAX-ACCESS read-write
      STATUS current
      DESCRIPTION
        "Attenuation on amplifier 2 downlink.
        
        The object aimosSubRackV1AttenuationAge indicates the age of this information.
        
        Changes, which are made here, affect the hardware.
        That's why TelCo's are not allowed to make any changes here."
      ::= { aimosSubRackV1Entry 6 }

    
    aimosSubRackV1AttenuationAmp2UL OBJECT-TYPE
      SYNTAX Attenuation
      UNITS "dB"
      MAX-ACCESS read-write
      STATUS current
      DESCRIPTION
        "Attenuation on amplifier 2 uplink.
        
        The object aimosSubRackV1AttenuationAge indicates the age of this information.
        
        Changes, which are made here, affect the hardware.
        That's why TelCo's are not allowed to make any changes here."
      ::= { aimosSubRackV1Entry 7 }

    
    aimosSubRackV1AttenuationAmp3DL OBJECT-TYPE
      SYNTAX Attenuation
      UNITS "dB"
      MAX-ACCESS read-write
      STATUS current
      DESCRIPTION
        "Attenuation on amplifier 3 downlink.
        
        The object aimosSubRackV1AttenuationAge indicates the age of this information.
        
        Changes, which are made here, affect the hardware.
        That's why TelCo's are not allowed to make any changes here."
      ::= { aimosSubRackV1Entry 8 }

    
    aimosSubRackV1AttenuationAmp3UL OBJECT-TYPE
      SYNTAX Attenuation
      UNITS "dB"
      MAX-ACCESS read-write
      STATUS current
      DESCRIPTION
        "Attenuation on amplifier 3 uplink.
        
        The object aimosSubRackV1AttenuationAge indicates the age of this information.
        
        Changes, which are made here, affect the hardware.
        That's why TelCo's are not allowed to make any changes here."
      ::= { aimosSubRackV1Entry 9 }

    
    aimosSubRackV1GainOffsetAge OBJECT-TYPE
      SYNTAX VariableTime
      MAX-ACCESS read-write
      STATUS current
      DESCRIPTION
        "In both the uplink (UL) and the downlink (DL) path for each of the three bands
        provided by the three amplifiers (1 to 3), the gain offset can be read-off and
        is adjustable by the provider. For this the MIB contains the following six
        objects:
        . aimosSubRackV1GainOffsetAmp1DL
        . aimosSubRackV1GainOffsetAmp1UL
        . aimosSubRackV1GainOffsetAmp2DL
        . aimosSubRackV1GainOffsetAmp2UL
        . aimosSubRackV1GainOffsetAmp3DL
        . aimosSubRackV1GainOffsetAmp3UL.
        
        These objects are of the GainOffset type and contain the gain offset values.
        
        The time when the values were last read is recorded in the object
        aimosSubRackV1GainOffsetAge of the VariableTime type. This value can be set to
        empty text in order to prompt the Controller to query the values anew with the
        next request to a cachedValue(2)-instance directly at the Master Controller."
      ::= { aimosSubRackV1Entry 10 }

    
    aimosSubRackV1GainOffsetAmp1DL OBJECT-TYPE
      SYNTAX GainOffset
      UNITS "dB"
      MAX-ACCESS read-write
      STATUS current
      DESCRIPTION
        "Gain offset on amplifier 1 downlink.
        
        The object aimosSubRackV1GainOffsetAge indicates the age of this information.
        
        Changes, which are made here, affect the hardware.
        That's why TelCo's are not allowed to make any changes here."
      ::= { aimosSubRackV1Entry 11 }

    
    aimosSubRackV1GainOffsetAmp1UL OBJECT-TYPE
      SYNTAX GainOffset
      UNITS "dB"
      MAX-ACCESS read-write
      STATUS current
      DESCRIPTION
        "Gain offset on amplifier 1 uplink.
        
        The object aimosSubRackV1GainOffsetAge indicates the age of this information.
        
        Changes, which are made here, affect the hardware.
        That's why TelCo's are not allowed to make any changes here."
      ::= { aimosSubRackV1Entry 12 }

    
    aimosSubRackV1GainOffsetAmp2DL OBJECT-TYPE
      SYNTAX GainOffset
      UNITS "dB"
      MAX-ACCESS read-write
      STATUS current
      DESCRIPTION
        "Gain offset on amplifier 2 downlink.
        
        The object aimosSubRackV1GainOffsetAge indicates the age of this information.
        
        Changes, which are made here, affect the hardware.
        That's why TelCo's are not allowed to make any changes here."
      ::= { aimosSubRackV1Entry 13 }

    
    aimosSubRackV1GainOffsetAmp2UL OBJECT-TYPE
      SYNTAX GainOffset
      UNITS "dB"
      MAX-ACCESS read-write
      STATUS current
      DESCRIPTION
        "Gain offset on amplifier 2 uplink.
        
        The object aimosSubRackV1GainOffsetAge indicates the age of this information.
        
        Changes, which are made here, affect the hardware.
        That's why TelCo's are not allowed to make any changes here."
      ::= { aimosSubRackV1Entry 14 }

    
    aimosSubRackV1GainOffsetAmp3DL OBJECT-TYPE
      SYNTAX GainOffset
      UNITS "dB"
      MAX-ACCESS read-write
      STATUS current
      DESCRIPTION
        "Gain offset on amplifier 3 downlink.
        
        The object aimosSubRackV1GainOffsetAge indicates the age of this information.
        
        Changes, which are made here, affect the hardware.
        That's why TelCo's are not allowed to make any changes here."
      ::= { aimosSubRackV1Entry 15 }

    
    aimosSubRackV1GainOffsetAmp3UL OBJECT-TYPE
      SYNTAX GainOffset
      UNITS "dB"
      MAX-ACCESS read-write
      STATUS current
      DESCRIPTION
        "Gain offset on amplifier 3 uplink.
        
        The object aimosSubRackV1GainOffsetAge indicates the age of this information.
        
        Changes, which are made here, affect the hardware.
        That's why TelCo's are not allowed to make any changes here."
      ::= { aimosSubRackV1Entry 16 }

    
    aimosSubRackV1TemperatureAge OBJECT-TYPE
      SYNTAX VariableTime
      MAX-ACCESS read-write
      STATUS current
      DESCRIPTION
        "aimosSubRackV1TemperatureBoard is an object of the TemperatureStatus type and
        contains the temperature measured at the SubRack Master Unit, in degrees Celsius.
        
        The time when the value was last read is recorded in the object
        aimosSubRackV1TemperatureAge of the VariableTime type. This value can be set to
        empty text in order to prompt the Controller to query the temperature anew with
        the next request to a cachedValue(2)-instance directly at the Master Controller."
      ::= { aimosSubRackV1Entry 17 }

    
    aimosSubRackV1TemperatureBoard OBJECT-TYPE
      SYNTAX TemperatureStatus
      UNITS "degrees centigrade"
      MAX-ACCESS read-only
      STATUS current
      DESCRIPTION
        "Temperature in degrees centigrade measured at the Sub Rack Master Unit.
        
        The object aimosSubRackV1TemperatureAge indicates the age of this information."
      ::= { aimosSubRackV1Entry 18 }

    
    aimosSubRackV1AmplifierBandNamesAge OBJECT-TYPE
      SYNTAX VariableTime
      MAX-ACCESS read-write
      STATUS current
      DESCRIPTION
        "Both Sub Rack Master Unit and each of its connected Remote Units have up to
        three amplifiers. The objects
        . aimosSubRackV1Amplifier1BandName
        . aimosSubRackV1Amplifier2BandName
        . aimosSubRackV1Amplifier3BandName
        contain the frequency band names, which are strengthened by the Sub Rack Master
        Units and its connected Remote Units amplifiers. Each of the object is of type
        Text with up to 10 characters.
        
        The time when the values were last read is recorded in the object
        aimosSubRackV1AmplifierBandNamesAge of the VariableTime type. This value can be
        set to empty text in order to prompt the Controller to query the names anew with
        the next request to a cachedValue(2)-instance directly at the Master Controller.
        "
      ::= { aimosSubRackV1Entry 19 }

    
    aimosSubRackV1Amplifier1BandName OBJECT-TYPE
      SYNTAX OCTET STRING (SIZE (0..10))
      MAX-ACCESS read-only
      STATUS current
      DESCRIPTION
        "States which frequency band (UMTS, GSM1800, GSM900, or any else)
        is assigned to amplifier 1.
        
        The object aimosSubRackV1AmplifierBandNamesAge indicates the age of this
        information."
      ::= { aimosSubRackV1Entry 20 }

    
    aimosSubRackV1Amplifier2BandName OBJECT-TYPE
      SYNTAX OCTET STRING (SIZE (0..10))
      MAX-ACCESS read-only
      STATUS current
      DESCRIPTION
        "States which frequency band (UMTS, GSM1800, GSM900, or any else)
        is assigned to amplifier 2.
        
        The object aimosSubRackV1AmplifierBandNamesAge indicates the age of this
        information."
      ::= { aimosSubRackV1Entry 21 }

    
    aimosSubRackV1Amplifier3BandName OBJECT-TYPE
      SYNTAX OCTET STRING (SIZE (0..10))
      MAX-ACCESS read-only
      STATUS current
      DESCRIPTION
        "States which frequency band (UMTS, GSM1800, GSM900, or any else)
        is assigned to amplifier 3.
        
        The object aimosSubRackV1AmplifierBandNamesAge indicates the age of this
        information."
      ::= { aimosSubRackV1Entry 22 }

    
    aimosRemoteUnitV1Table OBJECT-TYPE
      SYNTAX SEQUENCE OF AimosRemoteUnitV1Entry
      MAX-ACCESS not-accessible
      STATUS current
      DESCRIPTION
        "This table contains information's about Remote Units with hardware revision 1.
        
        Insert rows: must only be done by system
        Delete rows: must only be done by system"
      ::= { aimosUnitManagement 15 }

    
    aimosRemoteUnitV1Entry OBJECT-TYPE
      SYNTAX AimosRemoteUnitV1Entry
      MAX-ACCESS not-accessible
      STATUS current
      DESCRIPTION
        "see description for table entry..."
      REFERENCE
        "MIS=TMISRemoteUnitV1
        MDS=TMDSRemoteUnitV1"
      INDEX { aimosRemoteV1UnitReference, aimosRemoteV1ValueSource }
      ::= { aimosRemoteUnitV1Table 1 }

    
    AimosRemoteUnitV1Entry ::=
      SEQUENCE { 
        aimosRemoteV1UnitReference
          UnitReference,
        aimosRemoteV1ValueSource
          ValueSource,
        aimosRemoteV1NominalTemperatureAge
          VariableTime,
        aimosRemoteV1NominalTemperature
          NominalTemperature,
        aimosRemoteV1TemperatureAge
          VariableTime,
        aimosRemoteV1TemperatureAmp1
          TemperatureStatus,
        aimosRemoteV1TemperatureAmp2
          TemperatureStatus,
        aimosRemoteV1TemperatureAmp3
          TemperatureStatus,
        aimosRemoteV1TemperatureBoard
          TemperatureStatus,
        aimosRemoteV1TemperaturePowerSupply
          TemperatureStatus,
        aimosRemoteV1AmplifierStateAge
          VariableTime,
        aimosRemoteV1Amplifier1State
          Boolean,
        aimosRemoteV1Amplifier2State
          Boolean,
        aimosRemoteV1Amplifier3State
          Boolean,
        aimosRemoteV1AmplifierPowerAge
          VariableTime,
        aimosRemoteV1Amplifier1Power
          AmplifierPower,
        aimosRemoteV1Amplifier2Power
          AmplifierPower,
        aimosRemoteV1Amplifier3Power
          AmplifierPower,
        aimosRemoteV1AttenuationAge
          VariableTime,
        aimosRemoteV1AttenuationAmp1DL
          Attenuation,
        aimosRemoteV1AttenuationAmp1UL
          Attenuation,
        aimosRemoteV1AttenuationAmp2DL
          Attenuation,
        aimosRemoteV1AttenuationAmp2UL
          Attenuation,
        aimosRemoteV1AttenuationAmp3DL
          Attenuation,
        aimosRemoteV1AttenuationAmp3UL
          Attenuation,
        aimosRemoteV1GainOffsetAge
          VariableTime,
        aimosRemoteV1GainOffsetAmp1DL
          GainOffset,
        aimosRemoteV1GainOffsetAmp1UL
          GainOffset,
        aimosRemoteV1GainOffsetAmp2DL
          GainOffset,
        aimosRemoteV1GainOffsetAmp2UL
          GainOffset,
        aimosRemoteV1GainOffsetAmp3DL
          GainOffset,
        aimosRemoteV1GainOffsetAmp3UL
          GainOffset,
        aimosRemoteV1ALCThresholdAge
          VariableTime,
        aimosRemoteV1ALCThresholdAmp1DL
          ALCThreshold,
        aimosRemoteV1ALCThresholdAmp1UL
          ALCThreshold,
        aimosRemoteV1ALCThresholdAmp2DL
          ALCThreshold,
        aimosRemoteV1ALCThresholdAmp2UL
          ALCThreshold,
        aimosRemoteV1ALCThresholdAmp3DL
          ALCThreshold,
        aimosRemoteV1ALCThresholdAmp3UL
          ALCThreshold,
        aimosRemoteV1OpticalLossAge
          VariableTime,
        aimosRemoteV1OpticalLossDL
          OpticalLoss,
        aimosRemoteV1OpticalLossUL
          OpticalLoss,
        aimosRemoteV1Output1Name
          OCTET STRING,
        aimosRemoteV1Output2Name
          OCTET STRING,
        aimosRemoteV1Output3Name
          OCTET STRING,
        aimosRemoteV1Output4Name
          OCTET STRING,
        aimosRemoteV1OutputAge
          VariableTime,
        aimosRemoteV1Output1Value
          Boolean,
        aimosRemoteV1Output2Value
          Boolean,
        aimosRemoteV1Output3Value
          Boolean,
        aimosRemoteV1Output4Value
          Boolean,
        aimosRemoteV1Input1Name
          OCTET STRING,
        aimosRemoteV1Input2Name
          OCTET STRING,
        aimosRemoteV1Input3Name
          OCTET STRING,
        aimosRemoteV1Input4Name
          OCTET STRING
       }

    aimosRemoteV1UnitReference OBJECT-TYPE
      SYNTAX UnitReference
      MAX-ACCESS read-only
      STATUS current
      DESCRIPTION
        "This object of type UnitReference is the first index of this table. It
        unambiguously identifies the unit, independent of its kind (Master Unit,
        Sub Rack Master Unit, Remote Unit,...)."
      ::= { aimosRemoteUnitV1Entry 1 }

    
    aimosRemoteV1ValueSource OBJECT-TYPE
      SYNTAX ValueSource
      MAX-ACCESS read-only
      STATUS current
      DESCRIPTION
        "This object of type ValueSource is the second index in this table.
        
        It indicates, which value is to be addressed (actual, cached or desired value):
        
        . actual : An access to the hardware takes place in order to query the current
                   values. These values are stored in the SNMP Agents local database.
                   Actual values are read only.
        
        . cached : The values stored with the last hardware access are indicated. This
                   is the default in order to shorten the period of reply.
                   If the associated age value is missing, then the access is treated in
                   such a way, as if actual one would have indicated.
                   Cached values are read only (see remark below).
        
        . desired: Has to be used, if values on the hardware are to be changed.
        
        Remark: Although write accesses on cached values do not make a sense, are they
        permitted in order to facilitate handling with the MIB. Write accesses on cached
        values are treated in such a way, as if desired one would have indicated."
      ::= { aimosRemoteUnitV1Entry 2 }

    
    aimosRemoteV1NominalTemperatureAge OBJECT-TYPE
      SYNTAX VariableTime
      MAX-ACCESS read-write
      STATUS current
      DESCRIPTION
        "aimosRemoteUnitV1NominalTemperature is an object of type NominalTemperature,
        where the temperature to be obtained by fan control is entered in degrees
        centigrade.
        
        The time when the value was last read is recorded in the object
        aimosRemoteUnitV1NominalTemperatureAge of the VariableTime type. This value
        can be set to empty text in order to prompt the Controller to query the nominal
        temperature anew with the next request to a cachedValue(2)-instance directly
        at the Master Controller."
      ::= { aimosRemoteUnitV1Entry 3 }

    
    aimosRemoteV1NominalTemperature OBJECT-TYPE
      SYNTAX NominalTemperature
      UNITS "degrees centigrade"
      MAX-ACCESS read-write
      STATUS current
      DESCRIPTION
        "Temperature to be obtained by fan control in degrees centigrade.
        
        The object aimosRemoteV1NominalTemperatureAge indicates the age of this
        information.
        
        Changes, which are made here, affect the hardware.
        That's why TelCo's are not allowed to make any changes here."
      ::= { aimosRemoteUnitV1Entry 4 }

    
    aimosRemoteV1TemperatureAge OBJECT-TYPE
      SYNTAX VariableTime
      MAX-ACCESS read-write
      STATUS current
      DESCRIPTION
        "The Remote Unit has five temperature probes. For this, the MIB contains the
        following objects:
        . aimosRemoteV1TemperatureAmp1
        . aimosRemoteV1TemperatureAmp2
        . aimosRemoteV1TemperatureAmp3
        . aimosRemoteV1TemperatureBoard
        . aimosRemoteV1TemperaturePowerSupply
        
        These objects are of type TemperatureStatus and contain the temperatures
        measured at the according probe in degrees centigrade.
        
        The time when the values were last read is recorded in the object
        aimosRemoteV1TemperatureAge of type VariableTime. This value can be set to empty
        text in order to prompt the Controller to query the temperatures anew with the
        next request to a cachedValue(2)-instance directly at the Master Controller."
      ::= { aimosRemoteUnitV1Entry 5 }

    
    aimosRemoteV1TemperatureAmp1 OBJECT-TYPE
      SYNTAX TemperatureStatus
      UNITS "degrees centigrade"
      MAX-ACCESS read-only
      STATUS current
      DESCRIPTION
        "Amplifier 1 temperature in degrees centigrade.
        
        The object aimosRemoteV1TemperatureAge indicates the age of this information."
      ::= { aimosRemoteUnitV1Entry 6 }

    
    aimosRemoteV1TemperatureAmp2 OBJECT-TYPE
      SYNTAX TemperatureStatus
      UNITS "degrees centigrade"
      MAX-ACCESS read-only
      STATUS current
      DESCRIPTION
        "Amplifier 2 temperature in degrees centigrade.
        
        The object aimosRemoteV1TemperatureAge indicates the age of this information."
      ::= { aimosRemoteUnitV1Entry 7 }

    
    aimosRemoteV1TemperatureAmp3 OBJECT-TYPE
      SYNTAX TemperatureStatus
      UNITS "degrees centigrade"
      MAX-ACCESS read-only
      STATUS current
      DESCRIPTION
        "Amplifier 3 temperature in degrees centigrade.
        
        The object aimosRemoteV1TemperatureAge indicates the age of this information."
      ::= { aimosRemoteUnitV1Entry 8 }

    
    aimosRemoteV1TemperatureBoard OBJECT-TYPE
      SYNTAX TemperatureStatus
      UNITS "degrees centigrade"
      MAX-ACCESS read-only
      STATUS current
      DESCRIPTION
        "Board temperature in degrees centigrade.
        
        The object aimosRemoteV1TemperatureAge indicates the age of this information."
      ::= { aimosRemoteUnitV1Entry 9 }

    
    aimosRemoteV1TemperaturePowerSupply OBJECT-TYPE
      SYNTAX TemperatureStatus
      UNITS "degrees centigrade"
      MAX-ACCESS read-only
      STATUS current
      DESCRIPTION
        "Power supply temperature in degrees centigrade.
        
        The object aimosRemoteV1TemperatureAge indicates the age of this information."
      ::= { aimosRemoteUnitV1Entry 10 }

    
    aimosRemoteV1AmplifierStateAge OBJECT-TYPE
      SYNTAX VariableTime
      MAX-ACCESS read-write
      STATUS current
      DESCRIPTION
        "The downlink amplifiers for each one of the three frequency bands supported by
        the Remote Unit can be switched individually. For this, the MIB contains the
        following three objects:
        . aimosRemoteV1Amplifier1State
        . aimosRemoteV1Amplifier2State
        . aimosRemoteV1Amplifier3State
        
        These objects are of the Boolean type and show whether the corresponding
        amplifier is active or not.
        
        The time when the value was last read is recorded in the object
        aimosRemoteV1AmplifierStateAge of the type VariableTime. This value can be set
        to empty text in order to prompt the Controller to query the values anew with
        the next request to a cachedValue(2)-instance directly at the Master Controller."
      ::= { aimosRemoteUnitV1Entry 11 }

    
    aimosRemoteV1Amplifier1State OBJECT-TYPE
      SYNTAX Boolean
      MAX-ACCESS read-write
      STATUS current
      DESCRIPTION
        "Denotes if the amplifier 1 is active or not.
        
        The object aimosRemoteV1AmplifierStateAge indicates the age of this information.
        
        Changes, which are made here, affect the hardware.
        That's why TelCo's are not allowed to make any changes here."
      ::= { aimosRemoteUnitV1Entry 12 }

    
    aimosRemoteV1Amplifier2State OBJECT-TYPE
      SYNTAX Boolean
      MAX-ACCESS read-write
      STATUS current
      DESCRIPTION
        "Denotes if the amplifier 2 is active or not.
        
        The object aimosRemoteV1AmplifierStateAge indicates the age of this information.
        
        Changes, which are made here, affect the hardware.
        That's why TelCo's are not allowed to make any changes here."
      ::= { aimosRemoteUnitV1Entry 13 }

    
    aimosRemoteV1Amplifier3State OBJECT-TYPE
      SYNTAX Boolean
      MAX-ACCESS read-write
      STATUS current
      DESCRIPTION
        "Denotes if the amplifier 3 is active or not.
        
        The object aimosRemoteV1AmplifierStateAge indicates the age of this information.
        
        Changes, which are made here, affect the hardware.
        That's why TelCo's are not allowed to make any changes here."
      ::= { aimosRemoteUnitV1Entry 14 }

    
    aimosRemoteV1AmplifierPowerAge OBJECT-TYPE
      SYNTAX VariableTime
      MAX-ACCESS read-write
      STATUS current
      DESCRIPTION
        "The output power at the downlink amplifiers for each one of the three frequency
        bands supported by the Remote Unit can be read off individually. For this, the
        MIB contains the following three objects:
        . aimosRemoteV1Amplifier1Power
        . aimosRemoteV1Amplifier2Power
        . aimosRemoteV1Amplifier3Power
        
        These objects are of the AmplifierPower type and show the output power of the
        corresponding amplifier in one tenth of dB.
        
        The time when the value was last read is recorded in the object
        aimosRemoteV1AmplifierPowerAge of type VariableTime. This value can be set to
        empty text in order to prompt the Controller to query the values anew with the
        next request to a cachedValue(2)-instance directly at the Master Controller."
      ::= { aimosRemoteUnitV1Entry 15 }

    
    aimosRemoteV1Amplifier1Power OBJECT-TYPE
      SYNTAX AmplifierPower
      UNITS "dB/10"
      MAX-ACCESS read-only
      STATUS current
      DESCRIPTION
        "Power of amplifier 1 in dB.
        
        The object aimosRemoteV1AmplifierPowerAge indicates the age of this information."
      ::= { aimosRemoteUnitV1Entry 16 }

    
    aimosRemoteV1Amplifier2Power OBJECT-TYPE
      SYNTAX AmplifierPower
      UNITS "dB/10"
      MAX-ACCESS read-only
      STATUS current
      DESCRIPTION
        "Power of amplifier 2 in dB.
        
        The object aimosRemoteV1AmplifierPowerAge indicates the age of this information."
      ::= { aimosRemoteUnitV1Entry 17 }

    
    aimosRemoteV1Amplifier3Power OBJECT-TYPE
      SYNTAX AmplifierPower
      UNITS "dB/10"
      MAX-ACCESS read-only
      STATUS current
      DESCRIPTION
        "Power of amplifier 3 in dB.
        
        The object aimosRemoteV1AmplifierPowerAge indicates the age of this information."
      ::= { aimosRemoteUnitV1Entry 18 }

    
    aimosRemoteV1AttenuationAge OBJECT-TYPE
      SYNTAX VariableTime
      MAX-ACCESS read-write
      STATUS current
      DESCRIPTION
        "For both the uplink (UL) and downlink (DL) paths the attenuation of the
        corresponding attenuator (located at the optical unit) required for
        Autolevelling for each one of the three frequency bands can be read off
        individually or may be changed (only by the provider). For this, the MIB
        contains the following six objects:
        . aimosRemoteV1AttenuationAmp1DL
        . aimosRemoteV1AttenuationAmp1UL
        . aimosRemoteV1AttenuationAmp2DL
        . aimosRemoteV1AttenuationAmp2UL
        . aimosRemoteV1AttenuationAmp3DL
        . aimosRemoteV1AttenuationAmp3UL.
        
        These objects are of the Attenuation type and contain the attenuation value
        in dB.
        
        The time when the value was last read is recorded in the object
        aimosRemoteV1AttenuationAge of type VariableTime. This value can be set to empty
        text in order to prompt the Controller to query the values anew with the next
        request to a cachedValue(2)-instance directly at the Master Controller."
      ::= { aimosRemoteUnitV1Entry 19 }

    
    aimosRemoteV1AttenuationAmp1DL OBJECT-TYPE
      SYNTAX Attenuation
      UNITS "dB"
      MAX-ACCESS read-write
      STATUS current
      DESCRIPTION
        "Attenuation on amplifier 1 downlink.
        
        The object aimosRemoteV1AttenuationAge indicates the age of this information.
        
        Changes, which are made here, affect the hardware.
        That's why TelCo's are not allowed to make any changes here."
      ::= { aimosRemoteUnitV1Entry 20 }

    
    aimosRemoteV1AttenuationAmp1UL OBJECT-TYPE
      SYNTAX Attenuation
      UNITS "dB"
      MAX-ACCESS read-write
      STATUS current
      DESCRIPTION
        "Attenuation on amplifier 1 uplink.
        
        The object aimosRemoteV1AttenuationAge indicates the age of this information.
        
        Changes, which are made here, affect the hardware.
        That's why TelCo's are not allowed to make any changes here."
      ::= { aimosRemoteUnitV1Entry 21 }

    
    aimosRemoteV1AttenuationAmp2DL OBJECT-TYPE
      SYNTAX Attenuation
      UNITS "dB"
      MAX-ACCESS read-write
      STATUS current
      DESCRIPTION
        "Attenuation on amplifier 2 downlink.
        
        The object aimosRemoteV1AttenuationAge indicates the age of this information.
        
        Changes, which are made here, affect the hardware.
        That's why TelCo's are not allowed to make any changes here."
      ::= { aimosRemoteUnitV1Entry 22 }

    
    aimosRemoteV1AttenuationAmp2UL OBJECT-TYPE
      SYNTAX Attenuation
      UNITS "dB"
      MAX-ACCESS read-write
      STATUS current
      DESCRIPTION
        "Attenuation on amplifier 2 uplink.
        
        The object aimosRemoteV1AttenuationAge indicates the age of this information.
        
        Changes, which are made here, affect the hardware.
        That's why TelCo's are not allowed to make any changes here."
      ::= { aimosRemoteUnitV1Entry 23 }

    
    aimosRemoteV1AttenuationAmp3DL OBJECT-TYPE
      SYNTAX Attenuation
      UNITS "dB"
      MAX-ACCESS read-write
      STATUS current
      DESCRIPTION
        "Attenuation on amplifier 3 downlink.
        
        The object aimosRemoteV1AttenuationAge indicates the age of this information.
        
        Changes, which are made here, affect the hardware.
        That's why TelCo's are not allowed to make any changes here."
      ::= { aimosRemoteUnitV1Entry 24 }

    
    aimosRemoteV1AttenuationAmp3UL OBJECT-TYPE
      SYNTAX Attenuation
      UNITS "dB"
      MAX-ACCESS read-write
      STATUS current
      DESCRIPTION
        "Attenuation on amplifier 3 uplink.
        
        The object aimosRemoteV1AttenuationAge indicates the age of this information.
        
        Changes, which are made here, affect the hardware.
        That's why TelCo's are not allowed to make any changes here."
      ::= { aimosRemoteUnitV1Entry 25 }

    
    aimosRemoteV1GainOffsetAge OBJECT-TYPE
      SYNTAX VariableTime
      MAX-ACCESS read-write
      STATUS current
      DESCRIPTION
        "For both the uplink (UL) and downlink (DL) paths the gain offset for each one of
        the three frequency bands can be read off individually or may be changed (only
        by the provider). For this, the MIB contains the following six objects:
        . aimosRemoteV1GainOffsetAmp1DL
        . aimosRemoteV1GainOffsetAmp1UL
        . aimosRemoteV1GainOffsetAmp2DL
        . aimosRemoteV1GainOffsetAmp2UL
        . aimosRemoteV1GainOffsetAmp3DL
        . aimosRemoteV1GainOffsetAmp3UL.
        
        These objects are of the GainOffset type and show the gain offset values.
        
        The time when the value was last read is recorded in the object
        aimosRemoteV1GainOffsetAge of type VariableTime This value can be set to empty
        text in order to prompt the Controller to query the values anew with the next
        request to a cachedValue(2)-instance directly at the Master Controller."
      ::= { aimosRemoteUnitV1Entry 26 }

    
    aimosRemoteV1GainOffsetAmp1DL OBJECT-TYPE
      SYNTAX GainOffset
      UNITS "dB"
      MAX-ACCESS read-write
      STATUS current
      DESCRIPTION
        "Gain offset on amplifier 1 downlink.
        
        The object aimosRemoteV1GainOffsetAge indicates the age of this information.
        
        Changes, which are made here, affect the hardware.
        That's why it's not allowed to make any changes here."
      ::= { aimosRemoteUnitV1Entry 27 }

    
    aimosRemoteV1GainOffsetAmp1UL OBJECT-TYPE
      SYNTAX GainOffset
      UNITS "dB"
      MAX-ACCESS read-write
      STATUS current
      DESCRIPTION
        "Gain offset on amplifier 1 uplink.
        
        The object aimosRemoteV1GainOffsetAge indicates the age of this information.
        
        Changes, which are made here, affect the hardware.
        That's why it's not allowed to make any changes here."
      ::= { aimosRemoteUnitV1Entry 28 }

    
    aimosRemoteV1GainOffsetAmp2DL OBJECT-TYPE
      SYNTAX GainOffset
      UNITS "dB"
      MAX-ACCESS read-write
      STATUS current
      DESCRIPTION
        "Gain offset on amplifier 2 downlink.
        
        The object aimosRemoteV1GainOffsetAge indicates the age of this information.
        
        Changes, which are made here, affect the hardware.
        That's why it's not allowed to make any changes here."
      ::= { aimosRemoteUnitV1Entry 29 }

    
    aimosRemoteV1GainOffsetAmp2UL OBJECT-TYPE
      SYNTAX GainOffset
      UNITS "dB"
      MAX-ACCESS read-write
      STATUS current
      DESCRIPTION
        "Gain offset on amplifier 2 uplink.
        
        The object aimosRemoteV1GainOffsetAge indicates the age of this information.
        
        Changes, which are made here, affect the hardware.
        That's why it's not allowed to make any changes here."
      ::= { aimosRemoteUnitV1Entry 30 }

    
    aimosRemoteV1GainOffsetAmp3DL OBJECT-TYPE
      SYNTAX GainOffset
      UNITS "dB"
      MAX-ACCESS read-write
      STATUS current
      DESCRIPTION
        "Gain offset on amplifier 3 downlink.
        
        The object aimosRemoteV1GainOffsetAge indicates the age of this information.
        
        Changes, which are made here, affect the hardware.
        That's why it's not allowed to make any changes here."
      ::= { aimosRemoteUnitV1Entry 31 }

    
    aimosRemoteV1GainOffsetAmp3UL OBJECT-TYPE
      SYNTAX GainOffset
      UNITS "dB"
      MAX-ACCESS read-write
      STATUS current
      DESCRIPTION
        "Gain offset on amplifier 3 uplink.
        
        The object aimosRemoteV1GainOffsetAge indicates the age of this information.
        
        Changes, which are made here, affect the hardware.
        That's why it's not allowed to make any changes here."
      ::= { aimosRemoteUnitV1Entry 32 }

    
    aimosRemoteV1ALCThresholdAge OBJECT-TYPE
      SYNTAX VariableTime
      MAX-ACCESS read-write
      STATUS current
      DESCRIPTION
        "For each one of the three frequency bands supported by the Remote Unit
        . the output power at the downlink amplifier can be limited (DL) and
        . the input power at the optical interface can be limited (UL).
        
        For this, the MIB contains the following six objects:
        . aimosRemoteV1ALCThresholdAmp1DL
        . aimosRemoteV1ALCThresholdAmp1UL
        . aimosRemoteV1ALCThresholdAmp2DL
        . aimosRemoteV1ALCThresholdAmp2UL
        . aimosRemoteV1ALCThresholdAmp3DL
        . aimosRemoteV1ALCThresholdAmp3UL
        
        These objects area of type ALCThreshold and show the threshold values.
        
        The time when the value was last read is recorded in the object
        aimosRemoteV1ALCThresholdAge of type VariableTime. This value can be set to
        empty text in order to prompt the Controller to query the values anew with the
        next request to a cachedValue(2)-instance directly at the Master Controller."
      ::= { aimosRemoteUnitV1Entry 33 }

    
    aimosRemoteV1ALCThresholdAmp1DL OBJECT-TYPE
      SYNTAX ALCThreshold
      MAX-ACCESS read-write
      STATUS current
      DESCRIPTION
        "ALC threshold on amplifier 1 downlink.
        
        The object aimosRemoteV1ALCThresholdAge indicates the age of this information.
        
        Changes, which are made here, affect the hardware.
        That's why it's not allowed to make any changes here."
      ::= { aimosRemoteUnitV1Entry 34 }

    
    aimosRemoteV1ALCThresholdAmp1UL OBJECT-TYPE
      SYNTAX ALCThreshold
      MAX-ACCESS read-write
      STATUS current
      DESCRIPTION
        "ALC threshold on amplifier 1 uplink.
        
        The object aimosRemoteV1ALCThresholdAge indicates the age of this information.
        
        Changes, which are made here, affect the hardware.
        That's why it's not allowed to make any changes here."
      ::= { aimosRemoteUnitV1Entry 35 }

    
    aimosRemoteV1ALCThresholdAmp2DL OBJECT-TYPE
      SYNTAX ALCThreshold
      MAX-ACCESS read-write
      STATUS current
      DESCRIPTION
        "ALC threshold on amplifier 2 downlink.
        
        The object aimosRemoteV1ALCThresholdAge indicates the age of this information.
        
        Changes, which are made here, affect the hardware.
        That's why it's not allowed to make any changes here."
      ::= { aimosRemoteUnitV1Entry 36 }

    
    aimosRemoteV1ALCThresholdAmp2UL OBJECT-TYPE
      SYNTAX ALCThreshold
      MAX-ACCESS read-write
      STATUS current
      DESCRIPTION
        "ALC threshold on amplifier 2 uplink.
        
        The object aimosRemoteV1ALCThresholdAge indicates the age of this information.
        
        Changes, which are made here, affect the hardware.
        That's why it's not allowed to make any changes here."
      ::= { aimosRemoteUnitV1Entry 37 }

    
    aimosRemoteV1ALCThresholdAmp3DL OBJECT-TYPE
      SYNTAX ALCThreshold
      MAX-ACCESS read-write
      STATUS current
      DESCRIPTION
        "ALC threshold on amplifier 3 downlink.
        
        The object aimosRemoteV1ALCThresholdAge indicates the age of this information.
        
        Changes, which are made here, affect the hardware.
        That's why it's not allowed to make any changes here."
      ::= { aimosRemoteUnitV1Entry 38 }

    
    aimosRemoteV1ALCThresholdAmp3UL OBJECT-TYPE
      SYNTAX ALCThreshold
      MAX-ACCESS read-write
      STATUS current
      DESCRIPTION
        "ALC threshold on amplifier 3 uplink.
        
        The object aimosRemoteV1ALCThresholdAge indicates the age of this information.
        
        Changes, which are made here, affect the hardware.
        That's why it's not allowed to make any changes here."
      ::= { aimosRemoteUnitV1Entry 39 }

    
    aimosRemoteV1OpticalLossAge OBJECT-TYPE
      SYNTAX VariableTime
      MAX-ACCESS read-write
      STATUS current
      DESCRIPTION
        "For both the uplink and downlink paths the optical loss can be read-off via the
        following two objects in the MIB:
        . aimosRemoteV1OpticalLossDL and
        . aimosRemoteV1OpticalLossUL.
        
        These objects are of type OpticalLoss and show the optical loss value.
        
        The time when the value was last read is recorded in the object
        aimosRemoteV1OpticalLossAge of type VariableTime. This value can be set to
        empty text in order to prompt the Controller to query the values anew with the
        next request to a cachedValue(2)-instance directly at the Master Controller."
      ::= { aimosRemoteUnitV1Entry 40 }

    
    aimosRemoteV1OpticalLossDL OBJECT-TYPE
      SYNTAX OpticalLoss
      UNITS "dB/10"
      MAX-ACCESS read-only
      STATUS current
      DESCRIPTION
        "Optical loss on downlink fibre.
        
        The object aimosRemoteV1OpticalLossAge indicates the age of this information."
      ::= { aimosRemoteUnitV1Entry 41 }

    
    aimosRemoteV1OpticalLossUL OBJECT-TYPE
      SYNTAX OpticalLoss
      UNITS "dB/10"
      MAX-ACCESS read-only
      STATUS current
      DESCRIPTION
        "Optical loss on uplink fibre.
        
        The object aimosRemoteV1OpticalLossAge indicates the age of this information."
      ::= { aimosRemoteUnitV1Entry 42 }

    
    aimosRemoteV1Output1Name OBJECT-TYPE
      SYNTAX OCTET STRING (SIZE (0..40))
      MAX-ACCESS read-write
      STATUS current
      DESCRIPTION
        "Names the output pin 1 for recognition what is connected.
        
        Changes, which are made here, affect the hardware.
        That's why TelCo's are not allowed to make any changes here."
      ::= { aimosRemoteUnitV1Entry 43 }

    
    aimosRemoteV1Output2Name OBJECT-TYPE
      SYNTAX OCTET STRING (SIZE (0..40))
      MAX-ACCESS read-write
      STATUS current
      DESCRIPTION
        "Names the output pin 2 for recognition what is connected.
        
        Changes, which are made here, affect the hardware.
        That's why TelCo's are not allowed to make any changes here."
      ::= { aimosRemoteUnitV1Entry 44 }

    
    aimosRemoteV1Output3Name OBJECT-TYPE
      SYNTAX OCTET STRING (SIZE (0..40))
      MAX-ACCESS read-write
      STATUS current
      DESCRIPTION
        "Names the output pin 3 for recognition what is connected.
        
        Changes, which are made here, affect the hardware.
        That's why TelCo's are not allowed to make any changes here."
      ::= { aimosRemoteUnitV1Entry 45 }

    
    aimosRemoteV1Output4Name OBJECT-TYPE
      SYNTAX OCTET STRING (SIZE (0..40))
      MAX-ACCESS read-write
      STATUS current
      DESCRIPTION
        "Names the output pin 4 for recognition what is connected.
        
        Changes, which are made here, affect the hardware.
        That's why TelCo's are not allowed to make any changes here."
      ::= { aimosRemoteUnitV1Entry 46 }

    
    aimosRemoteV1OutputAge OBJECT-TYPE
      SYNTAX VariableTime
      MAX-ACCESS read-write
      STATUS current
      DESCRIPTION
        "Each of the four digital outputs available at the Remote Unit can be accessed
        individually via one of the following four objects:
        . aimosRemoteV1Output1Value,
        . aimosRemoteV1Output2Value,
        . aimosRemoteV1Output3Value,
        . aimosRemoteV1Output4Value.
        
        These objects are of the Boolean type and determine the status of the
        corresponding output.
        
        The time when the value was last read is recorded in the object
        aimosRemoteV1OutputAge of type VariableTime. This value can be set to empty text
        in order to prompt the Controller to query the values anew with the next
        request to a cachedValue(2)-instance directly at the Master Controller."
      ::= { aimosRemoteUnitV1Entry 47 }

    
    aimosRemoteV1Output1Value OBJECT-TYPE
      SYNTAX Boolean
      MAX-ACCESS read-write
      STATUS current
      DESCRIPTION
        "State on external out pin 1.
        
        The object aimosRemoteV1OutputAge indicates the age of this information.
        
        Changes, which are made here, affect the hardware.
        That's why TelCo's are not allowed to make any changes here."
      ::= { aimosRemoteUnitV1Entry 48 }

    
    aimosRemoteV1Output2Value OBJECT-TYPE
      SYNTAX Boolean
      MAX-ACCESS read-write
      STATUS current
      DESCRIPTION
        "State on external out pin 2.
        
        The object aimosRemoteV1OutputAge indicates the age of this information.
        
        Changes, which are made here, affect the hardware.
        That's why TelCo's are not allowed to make any changes here."
      ::= { aimosRemoteUnitV1Entry 49 }

    
    aimosRemoteV1Output3Value OBJECT-TYPE
      SYNTAX Boolean
      MAX-ACCESS read-write
      STATUS current
      DESCRIPTION
        "State on external out pin 3.
        
        The object aimosRemoteV1OutputAge indicates the age of this information.
        
        Changes, which are made here, affect the hardware.
        That's why TelCo's are not allowed to make any changes here."
      ::= { aimosRemoteUnitV1Entry 50 }

    
    aimosRemoteV1Output4Value OBJECT-TYPE
      SYNTAX Boolean
      MAX-ACCESS read-write
      STATUS current
      DESCRIPTION
        "State on external out pin 4.
        
        The object aimosRemoteV1OutputAge indicates the age of this information.
        
        Changes, which are made here, affect the hardware.
        That's why TelCo's are not allowed to make any changes here."
      ::= { aimosRemoteUnitV1Entry 51 }

    
    aimosRemoteV1Input1Name OBJECT-TYPE
      SYNTAX OCTET STRING (SIZE (0..40))
      MAX-ACCESS read-write
      STATUS current
      DESCRIPTION
        "Names the input pin 1 for recognition what is connected.
        
        Changes, which are made here, affect the hardware.
        That's why TelCo's are not allowed to make any changes here."
      ::= { aimosRemoteUnitV1Entry 52 }

    
    aimosRemoteV1Input2Name OBJECT-TYPE
      SYNTAX OCTET STRING (SIZE (0..40))
      MAX-ACCESS read-write
      STATUS current
      DESCRIPTION
        "Names the input pin 2 for recognition what is connected.
        
        Changes, which are made here, affect the hardware.
        That's why TelCo's are not allowed to make any changes here."
      ::= { aimosRemoteUnitV1Entry 53 }

    
    aimosRemoteV1Input3Name OBJECT-TYPE
      SYNTAX OCTET STRING (SIZE (0..40))
      MAX-ACCESS read-write
      STATUS current
      DESCRIPTION
        "Names the input pin 3 for recognition what is connected.
        
        Changes, which are made here, affect the hardware.
        That's why TelCo's are not allowed to make any changes here."
      ::= { aimosRemoteUnitV1Entry 54 }

    
    aimosRemoteV1Input4Name OBJECT-TYPE
      SYNTAX OCTET STRING (SIZE (0..40))
      MAX-ACCESS read-write
      STATUS current
      DESCRIPTION
        "Names the input pin 4 for recognition what is connected.
        
        Changes, which are made here, affect the hardware.
        That's why TelCo's are not allowed to make any changes here."
      ::= { aimosRemoteUnitV1Entry 55 }

    
    aimosGSMNSOV1Table OBJECT-TYPE
      SYNTAX SEQUENCE OF AimosGSMNSOV1Entry
      MAX-ACCESS not-accessible
      STATUS current
      DESCRIPTION
        "Hardware version related informations about the GSM NSO's.
        
        Insert rows: must only be done by system
        Delete rows: must only be done by system"
      ::= { aimosUnitManagement 16 }

    
    aimosGSMNSOV1Entry OBJECT-TYPE
      SYNTAX AimosGSMNSOV1Entry
      MAX-ACCESS not-accessible
      STATUS current
      DESCRIPTION
        "see description for table entry..."
      INDEX { aimosGSMNSOV1UnitReference, aimosGSMNSOV1ValueSource }
      ::= { aimosGSMNSOV1Table 1 }

    
    AimosGSMNSOV1Entry ::=
      SEQUENCE { 
        aimosGSMNSOV1UnitReference
          UnitReference,
        aimosGSMNSOV1ValueSource
          ValueSource,
        aimosGSMNSOV1Name
          OCTET STRING,
        aimosGSMNSOV1ScanInterval
          Unsigned32,
        aimosGSMNSOV1ScanBCCH
          Boolean,
        aimosGSMNSOV1CellStatus
          Unsigned32,
        aimosGSMNSOV1MinScanSignalStrength
          Integer32,
        aimosGSMNSOV1SignalStrengthHysteresis
          Integer32,
        aimosGSMNSOV1MinAllowedSignalStrength
          Integer32,
        aimosGSMNSOV1MaxAllowedSignalStrength
          Integer32,
        aimosGSMNSOV1MaxAllowedBER
          BER
       }

    aimosGSMNSOV1UnitReference OBJECT-TYPE
      SYNTAX UnitReference
      MAX-ACCESS read-only
      STATUS current
      DESCRIPTION
        "This object of type UnitReference is the first index of this table. It
        unambiguously identifies the unit, independent of its kind (Master Unit,
        Sub Rack Master Unit, Remote Unit,...)."
      ::= { aimosGSMNSOV1Entry 1 }

    
    aimosGSMNSOV1ValueSource OBJECT-TYPE
      SYNTAX ValueSource
      MAX-ACCESS read-only
      STATUS current
      DESCRIPTION
        "This object of type ValueSource is the second index in this table.
        
        It indicates, which value is to be addressed (actual, cached or desired value):
        
        . actual : An access to the hardware takes place in order to query the current
                   values. These values are stored in the SNMP Agents local database.
                   Actual values are read only.
        
        . cached : The values stored with the last hardware access are indicated. This
                   is the default in order to shorten the period of reply.
                   If the associated age value is missing, then the access is treated in
                   such a way, as if actual one would have indicated.
                   Cached values are read only (see remark below).
        
        . desired: Has to be used, if values on the hardware are to be changed.
        
        Remark: Although write accesses on cached values do not make a sense, are they
        permitted in order to facilitate handling with the MIB. Write accesses on cached
        values are treated in such a way, as if desired one would have indicated."
      ::= { aimosGSMNSOV1Entry 2 }

    
    aimosGSMNSOV1Name OBJECT-TYPE
      SYNTAX OCTET STRING (SIZE (0..8))
      MAX-ACCESS read-only
      STATUS current
      DESCRIPTION
        "Presents the unique 8 character name of the NSO."
      ::= { aimosGSMNSOV1Entry 3 }

    
    aimosGSMNSOV1ScanInterval OBJECT-TYPE
      SYNTAX Unsigned32 (0 | 180..3600)
      MAX-ACCESS read-write
      STATUS current
      DESCRIPTION
        "Denotes the intervall time the NSO will restart its measurement. Note, the NSO needs
        approximately 60 seconds for measurement and some seconds for transmitting data to the
        master. So you should not determine a value smaller than 180."
      DEFVAL { 300 }
      ::= { aimosGSMNSOV1Entry 4 }

    
    aimosGSMNSOV1ScanBCCH OBJECT-TYPE
      SYNTAX Boolean
      MAX-ACCESS read-write
      STATUS current
      DESCRIPTION
        "Denotes if the BCCH channel will be scanned."
      ::= { aimosGSMNSOV1Entry 5 }

    
    aimosGSMNSOV1CellStatus OBJECT-TYPE
      SYNTAX Unsigned32 (0..255)
      MAX-ACCESS read-write
      STATUS current
      DESCRIPTION
        "Cell State
        
        Bit Remark
         0  CELL_SUITABLE
         1  CELL_LOW_PRIORITY
         2  CELL_BARRED
         3  CELL_LOW_LEVEL
         4  CELL_FORBIDDEN
         5  CELL_OTHER
        
        Other cell states indicating an alarm state."
      ::= { aimosGSMNSOV1Entry 6 }

    
    aimosGSMNSOV1MinScanSignalStrength OBJECT-TYPE
      SYNTAX Integer32 (-110..0)
      MAX-ACCESS read-write
      STATUS current
      DESCRIPTION
        "Channels with a lower RX level are not scanned."
      ::= { aimosGSMNSOV1Entry 7 }

    
    aimosGSMNSOV1SignalStrengthHysteresis OBJECT-TYPE
      SYNTAX Integer32 (0..50)
      MAX-ACCESS read-write
      STATUS current
      DESCRIPTION
        "Signal strength modifications within the hysteresis do not cause the NSO to send data
        with new signal strength values. E.g., a hysteresis of +/- 1 dB ignores signal strength
        modifications within a range of 2 dB. If actually the signal strength is 20, you will
        recognize signal strength modification if the value gets lower than 19 or higher than 21."
      ::= { aimosGSMNSOV1Entry 8 }

    
    aimosGSMNSOV1MinAllowedSignalStrength OBJECT-TYPE
      SYNTAX Integer32 (-100..0)
      MAX-ACCESS read-write
      STATUS current
      DESCRIPTION
        "RX levels with a lower level indicating an alarm state."
      ::= { aimosGSMNSOV1Entry 9 }

    
    aimosGSMNSOV1MaxAllowedSignalStrength OBJECT-TYPE
      SYNTAX Integer32 (-100..0)
      MAX-ACCESS read-write
      STATUS current
      DESCRIPTION
        "RX levels with a higher level indicating an alarm state."
      ::= { aimosGSMNSOV1Entry 10 }

    
    aimosGSMNSOV1MaxAllowedBER OBJECT-TYPE
      SYNTAX BER
      MAX-ACCESS read-write
      STATUS current
      DESCRIPTION
        "Bit Error Rates with a higher level indicating an alarm state."
      ::= { aimosGSMNSOV1Entry 11 }

    
    aimosGSMNSODataV1Table OBJECT-TYPE
      SYNTAX SEQUENCE OF AimosGSMNSODataV1Entry
      MAX-ACCESS not-accessible
      STATUS current
      DESCRIPTION
        "GSM NSO measurement data.
        
        Insert rows: must only be done by system
        Delete rows: must only be done by system"
      ::= { aimosUnitManagement 17 }

    
    aimosGSMNSODataV1Entry OBJECT-TYPE
      SYNTAX AimosGSMNSODataV1Entry
      MAX-ACCESS not-accessible
      STATUS current
      DESCRIPTION
        "see description for table entry..."
      INDEX { aimosGSMNSOV1UnitReference, aimosGSMNSODataV1ID }
      ::= { aimosGSMNSODataV1Table 1 }

    
    AimosGSMNSODataV1Entry ::=
      SEQUENCE { 
        aimosGSMNSODataV1ID
          TableIndex,
        aimosGSMNSODataV1LAC
          LAC,
        aimosGSMNSODataV1CI
          CI,
        aimosGSMNSODataV1DateTime
          VariableTime,
        aimosGSMNSODataV1ARFCN
          ARFCN,
        aimosGSMNSODataV1BSIC
          Integer32,
        aimosGSMNSODataV1CS
          CellStatus,
        aimosGSMNSODataV1SignalStrength
          Integer32,
        aimosGSMNSODataV1BER
          BER
       }

    aimosGSMNSODataV1ID OBJECT-TYPE
      SYNTAX TableIndex
      MAX-ACCESS read-only
      STATUS current
      DESCRIPTION
        "Identifies the table entry. This value ist determined by the system."
      ::= { aimosGSMNSODataV1Entry 1 }

    
    aimosGSMNSODataV1LAC OBJECT-TYPE
      SYNTAX LAC
      MAX-ACCESS read-only
      STATUS current
      DESCRIPTION
        "Local Area Code."
      ::= { aimosGSMNSODataV1Entry 2 }

    
    aimosGSMNSODataV1CI OBJECT-TYPE
      SYNTAX CI
      MAX-ACCESS read-only
      STATUS current
      DESCRIPTION
        "Cell Identifier"
      ::= { aimosGSMNSODataV1Entry 3 }

    
    aimosGSMNSODataV1DateTime OBJECT-TYPE
      SYNTAX VariableTime
      MAX-ACCESS read-only
      STATUS current
      DESCRIPTION
        "Time of measurement."
      ::= { aimosGSMNSODataV1Entry 4 }

    
    aimosGSMNSODataV1ARFCN OBJECT-TYPE
      SYNTAX ARFCN
      MAX-ACCESS read-only
      STATUS current
      DESCRIPTION
        "Channel"
      ::= { aimosGSMNSODataV1Entry 5 }

    
    aimosGSMNSODataV1BSIC OBJECT-TYPE
      SYNTAX Integer32
      MAX-ACCESS read-only
      STATUS current
      DESCRIPTION
        "Base Station Identity Code."
      ::= { aimosGSMNSODataV1Entry 6 }

    
    aimosGSMNSODataV1CS OBJECT-TYPE
      SYNTAX CellStatus
      MAX-ACCESS read-only
      STATUS current
      DESCRIPTION
        "Cell Status"
      ::= { aimosGSMNSODataV1Entry 7 }

    
    aimosGSMNSODataV1SignalStrength OBJECT-TYPE
      SYNTAX Integer32 (-150..100)
      MAX-ACCESS read-only
      STATUS current
      DESCRIPTION
        "Current RX level. "
      ::= { aimosGSMNSODataV1Entry 8 }

    
    aimosGSMNSODataV1BER OBJECT-TYPE
      SYNTAX BER
      MAX-ACCESS read-only
      STATUS current
      DESCRIPTION
        "Current Bit Error Rate."
      ::= { aimosGSMNSODataV1Entry 9 }

    
    aimosUMTSNSOV1Table OBJECT-TYPE
      SYNTAX SEQUENCE OF AimosUMTSNSOV1Entry
      MAX-ACCESS not-accessible
      STATUS current
      DESCRIPTION
        "Hardware version related informations about the UMTS NSO's.
        
        Insert rows: must only be done by system
        Delete rows: must only be done by system"
      ::= { aimosUnitManagement 18 }

    
    aimosUMTSNSOV1Entry OBJECT-TYPE
      SYNTAX AimosUMTSNSOV1Entry
      MAX-ACCESS not-accessible
      STATUS current
      DESCRIPTION
        "see description for table entry..."
      INDEX { aimosUMTSNSOV1UnitReference, aimosUMTSNSOV1ValueSource }
      ::= { aimosUMTSNSOV1Table 1 }

    
    AimosUMTSNSOV1Entry ::=
      SEQUENCE { 
        aimosUMTSNSOV1UnitReference
          UnitReference,
        aimosUMTSNSOV1ValueSource
          ValueSource
       }

    aimosUMTSNSOV1UnitReference OBJECT-TYPE
      SYNTAX UnitReference
      MAX-ACCESS read-only
      STATUS current
      DESCRIPTION
        "This object of type UnitReference is the first index of this table. It
        unambiguously identifies the unit, independent of its kind (Master Unit,
        Sub Rack Master Unit, Remote Unit,...)."
      ::= { aimosUMTSNSOV1Entry 1 }

    
    aimosUMTSNSOV1ValueSource OBJECT-TYPE
      SYNTAX ValueSource
      MAX-ACCESS read-only
      STATUS current
      DESCRIPTION
        "This object of type ValueSource is the second index in this table.
        
        It indicates, which value is to be addressed (actual, cached or desired value):
        
        . actual : An access to the hardware takes place in order to query the current
                   values. These values are stored in the SNMP Agents local database.
                   Actual values are read only.
        
        . cached : The values stored with the last hardware access are indicated. This
                   is the default in order to shorten the period of reply.
                   If the associated age value is missing, then the access is treated in
                   such a way, as if actual one would have indicated.
                   Cached values are read only (see remark below).
        
        . desired: Has to be used, if values on the hardware are to be changed.
        
        Remark: Although write accesses on cached values do not make a sense, are they
        permitted in order to facilitate handling with the MIB. Write accesses on cached
        values are treated in such a way, as if desired one would have indicated."
      ::= { aimosUMTSNSOV1Entry 2 }

    
    aimosUMTSNSODataV1Table OBJECT-TYPE
      SYNTAX SEQUENCE OF AimosUMTSNSODataV1Entry
      MAX-ACCESS not-accessible
      STATUS current
      DESCRIPTION
        "UMTS NSO measurement data.
        
        Insert rows: must only be done by system
        Delete rows: must only be done by system"
      ::= { aimosUnitManagement 19 }

    
    aimosUMTSNSODataV1Entry OBJECT-TYPE
      SYNTAX AimosUMTSNSODataV1Entry
      MAX-ACCESS not-accessible
      STATUS current
      DESCRIPTION
        "see description for table entry..."
      INDEX { aimosUMTSNSOV1UnitReference, aimosUMTSNSODataV1ID }
      ::= { aimosUMTSNSODataV1Table 1 }

    
    AimosUMTSNSODataV1Entry ::=
      SEQUENCE { 
        aimosUMTSNSODataV1ID
          TableIndex
       }

    aimosUMTSNSODataV1ID OBJECT-TYPE
      SYNTAX TableIndex
      MAX-ACCESS read-only
      STATUS current
      DESCRIPTION
        "Identifies the table entry. This value ist determined by the system."
      ::= { aimosUMTSNSODataV1Entry 1 }

    
    aimosNEOperations OBJECT-IDENTITY
      STATUS current
      DESCRIPTION 
        "This object identity provides means to execute Network Element Operations.
        For example it is possible to request for a reboot of a NE."
      ::= { aimosObjects 6 }

    
    aimosNEOperationsTable OBJECT-TYPE
      SYNTAX SEQUENCE OF AimosNEOperationsEntry
      MAX-ACCESS not-accessible
      STATUS current
      DESCRIPTION
        "This table contains the Network Elements capable of operation execution.
        
        The following Network Elements are supported (V 2.8.0):
        - Node M
        - Node C
        - Node G
        - Node A 
        - Node AM
        - MRx18
        - ION-M RU
        - ION-M EU"
      ::= { aimosNEOperations 1 }

    
    aimosNEOperationsEntry OBJECT-TYPE
      SYNTAX AimosNEOperationsEntry
      MAX-ACCESS not-accessible
      STATUS current
      DESCRIPTION
        "see description for table entry..."
      REFERENCE
        "MIS=TMISNEOperations
        MDS=TMDSNEOperations"
      INDEX { aimosNEOperationsID }
      ::= { aimosNEOperationsTable 1 }

    
    AimosNEOperationsEntry ::=
      SEQUENCE { 
        aimosNEOperationsID
          UnitReference,
        aimosNEOperationsSDN
          SDN,
        aimosNEOperationsTrapInfo
          Text,
        aimosNEOperationsComponentName
          Text,
        aimosNEOperationsLocation
          Text,
        aimosNEOperationsUniqueSystemID
          Text,
        aimosNEOperationsNEActive
          Boolean,
        aimosNEOperationsDeactivateNE
          NEOperationStatus,
        aimosNEOperationsDeactivateNEInfo
          Text,
        aimosNEOperationsActivateNE
          NEOperationStatus,
        aimosNEOperationsActivateNEInfo
          Text,
        aimosNEOperationsReboot
          NEOperationStatus,
        aimosNEOperationsRebootInfo
          Text,
        aimosNEOperationsQueryAlarms
          NEOperationStatus,
        aimosNEOperationsQueryAlarmsInfo
          Text
       }

    aimosNEOperationsID OBJECT-TYPE
      SYNTAX UnitReference
      MAX-ACCESS read-only
      STATUS current
      DESCRIPTION
        "This object of type UnitReference uniquely identifies the Network Element.
        
        This value is related to the column 'NE No.' of the 'Network Element List'
        (A.I.M.O.S. Visu)."
      ::= { aimosNEOperationsEntry 1 }

    
    aimosNEOperationsSDN OBJECT-TYPE
      SYNTAX SDN
      MAX-ACCESS read-only
      STATUS current
      DESCRIPTION
        "This object of type SDN shows the System Distinguished Name which consists of a
        chaining of all RDN's all the way down from the OMC point of view to the desired
        unit. The RDN's are divided by the Distinguished Name Concatenator defined in
        aimosOrgDNConcatenator. (e.g. SDN for MC=11: OMC=1,MC=11)"
      ::= { aimosNEOperationsEntry 2 }

    
    aimosNEOperationsTrapInfo OBJECT-TYPE
      SYNTAX Text
      MAX-ACCESS read-only
      STATUS current
      DESCRIPTION
        "This object of type Text contains the Network Elements TrapInfo."
      ::= { aimosNEOperationsEntry 3 }

    
    aimosNEOperationsComponentName OBJECT-TYPE
      SYNTAX Text
      MAX-ACCESS read-only
      STATUS current
      DESCRIPTION
        "This object of type Text contains the Network Elements Component Name."
      ::= { aimosNEOperationsEntry 4 }

    
    aimosNEOperationsLocation OBJECT-TYPE
      SYNTAX Text
      MAX-ACCESS read-only
      STATUS current
      DESCRIPTION
        "This object of type Text contains the Network Elements Location."
      ::= { aimosNEOperationsEntry 5 }

    
    aimosNEOperationsUniqueSystemID OBJECT-TYPE
      SYNTAX Text
      MAX-ACCESS read-only
      STATUS current
      DESCRIPTION
        "This object of type Text contains the Network Elements Unique System ID."
      ::= { aimosNEOperationsEntry 6 }

    
    aimosNEOperationsNEActive OBJECT-TYPE
      SYNTAX Boolean
      MAX-ACCESS read-only
      STATUS current
      DESCRIPTION
        "This object of type Boolean indicates whether or not a Network Element (or 
        at least one component capable of de-/activation if applicable) is active.
        
        This object will report true for a
        - Node M   if 'Complete Network Element Active' is true
        - Node C   if 'Complete Network Element Active' is true
        - Node G   if 'Complete Network Element Active' is true
        - Node A   if 'Disable Repeater' is false 
        - Node AM  if 'Disable Repeater' is false 
        - MRx18    if at least one Segment is powered on
        - ION-M RU if at least one Amplifier is active
        - ION-M EU if at least one Amplifier is active
        
        Otherwise it will report false."
      ::= { aimosNEOperationsEntry 50 }

    
    aimosNEOperationsDeactivateNE OBJECT-TYPE
      SYNTAX NEOperationStatus
      MAX-ACCESS read-write
      STATUS current
      DESCRIPTION
        "This object of type NEOperationStatus provides means to 
        deactivate a Network Element by applying a value of neoSubmit(2).
        
        Deactivation is performed in the following way:
        - Node M  : 'Complete Network Element Active' is set to false
        - Node C  : 'Complete Network Element Active' is set to false
        - Node G  : 'Complete Network Element Active' is set to false
        - Node A  : 'Disable Repeater' is set to true
        - Node AM : 'Disable Repeater' is set to true
        - MRx18   : all Segments are powered off
        - ION-M RU: all Amplifiers are deactivated
        - ION-M EU: all Amplifiers are deactivated
        
        Furthermore its values indicates the progress of the Deactivation 
        Command Transmission to the Network Element. If no Deactivation 
        was initiated since Agent Startup this object's value is neoIdle(1).
        
        "
      ::= { aimosNEOperationsEntry 51 }

    
    aimosNEOperationsDeactivateNEInfo OBJECT-TYPE
      SYNTAX Text
      MAX-ACCESS read-only
      STATUS current
      DESCRIPTION
        "This object of type Text is the textual representation of the value 
        retunred by aimosNEOperationsDeactivateNE.
        In case it is neoFailed(10) a more precise description is returned."
      ::= { aimosNEOperationsEntry 52 }

    
    aimosNEOperationsActivateNE OBJECT-TYPE
      SYNTAX NEOperationStatus
      MAX-ACCESS read-write
      STATUS current
      DESCRIPTION
        "This object of type NEOperationStatus provides means to 
        activate a Network Element by applying a value of neoSubmit(2).
        
        Activation is performed in the following way:
        - Node M  : 'Complete Network Element Active' is set to true
        - Node C  : 'Complete Network Element Active' is set to true
        - Node G  : 'Complete Network Element Active' is set to true
        - Node A  : 'Disable Repeater' is set to false
        - Node AM : 'Disable Repeater' is set to false
        - MRx18   : all Segments are powered on
        - ION-M RU: all Amplifiers are activated
        - ION-M EU: all Amplifiers are activated
        
        Furthermore its values indicates the progress of the Activation 
        Command Transmission to the Network Element. If no Activation was 
        initiated since Agent Startup this object's value is neoIdle(1).
        
        "
      ::= { aimosNEOperationsEntry 53 }

    
    aimosNEOperationsActivateNEInfo OBJECT-TYPE
      SYNTAX Text
      MAX-ACCESS read-only
      STATUS current
      DESCRIPTION
        "This object of type Text is the textual representation of the value 
        retunred by aimosNEOperationsActivateNE.
        In case it is neoFailed(10) a more precise description is returned."
      ::= { aimosNEOperationsEntry 54 }

    
    aimosNEOperationsReboot OBJECT-TYPE
      SYNTAX NEOperationStatus
      MAX-ACCESS read-write
      STATUS current
      DESCRIPTION
        "This object of type NEOperationStatus provides means to initiate a reboot
        of a Network Element by applying a value of neoSubmit(2).
        
        Furthermore its values indicates the progress of the Reboot Command 
        Transmission to the Network Element. If no Reboot was initiated since
        Agent Startup this object's value is neoIdle(1)."
      ::= { aimosNEOperationsEntry 60 }

    
    aimosNEOperationsRebootInfo OBJECT-TYPE
      SYNTAX Text
      MAX-ACCESS read-only
      STATUS current
      DESCRIPTION
        "This object of type Text is the textual representation of the value 
        retunred by aimosNEOperationsReboot.
        In case it is neoFailed(10) a more precise description is returned."
      ::= { aimosNEOperationsEntry 61 }

    
    aimosNEOperationsQueryAlarms OBJECT-TYPE
      SYNTAX NEOperationStatus
      MAX-ACCESS read-write
      STATUS current
      DESCRIPTION
        "This object of type NEOperationStatus provides means to forward a Query 
        Alarms Command to a Network Element by applying a value of neoSubmit(2).
        
        Furthermore its values indicates the progress of the Query Alarms Command 
        Transmission to the Network Element. If no Query Alarms has been requested
        since Agent Startup this object's value is neoIdle(1)."
      ::= { aimosNEOperationsEntry 70 }

    
    aimosNEOperationsQueryAlarmsInfo OBJECT-TYPE
      SYNTAX Text
      MAX-ACCESS read-only
      STATUS current
      DESCRIPTION
        "This object of type Text is the textual representation of the value 
        retunred by aimosNEOperationsQueryAlarms.
        In case it is neoFailed(10) a more precise description is returned."
      ::= { aimosNEOperationsEntry 71 }

    
    aimosNotifications OBJECT-IDENTITY
      STATUS current
      DESCRIPTION 
        "The A.I.M.O.S. SNMP Agent sends alarm notifications to as many alarm recipients
        as desired.
        
        All notifications contains the following objects:
        . sysUpTime                    duration of time the SNMP Agent is running
        . snmpTrapOID                  notification OID
                                       (note: if aimosPhoneBookInterfaceType is set to
                                       ifAimosObsolete(4) aimosTrapOID is used instead)
        . aimosOMCSDN                  name of the OMC / SNMP Agent
        . aimosOrgID                   the SNMP Managers organisation ID
        . aimosAlarmTrapID             trap number (unambiguous from SNMP Agents view)
        . aimosAlarmTrapNotificationID trap number (contiguous enumerated from SNMP
                                                    Managers view)
        . aimosAlarmListID             identifies an alarm list entry
        . aimosAlarmListAlarmEventID   contiguously enumerates alarm events, change and
                                       clear alarms has the same event ID as the raise
        
        aimosAgentAnnouncement notifications have afterwards the following object:
        . aimosAgentState              indicates of what the A.I.M.O.S. SNMP Agent is
                                       about to do
        
        aimosAlarmNew, aimosAlarmChanged and aimosAlarmCleared notifications have
        afterwards the following objects:
        . aimosAlarmListAlarmID             kind of alarm
        . aimosAlarmListEventType
        . aimosAlarmListEventTime
        . aimosAlarmListProbableCause       compliant to X.733 with additions
        . aimosAlarmListSpecificProblem
        . aimosAlarmListSeverity            compliant to X.733 with one addition
        . aimosAlarmListTrendIndication
        . aimosAlarmListAdditionalText
        . aimosAlarmListSDN                 unique name of the affected device
        . aimosAlarmListCustomerMasterInfo  custom name for the affected Master Unit
        . aimosAlarmListCustomerSubRackInfo custom name for the affected Sub Rack Master
                                            Unit
        . aimosAlarmListCustomerCableInfo   custom names of the cables used in the
                                            interconnection between Master & Remote Unit
        . aimosAlarmListCustomerRemoteInfo  custom name for the affected Remote Unit
        
        aimosAlarmCleared notifications have afterwards the following object:
        . aimosAlarmListClearReason         the reason why alarm has gone
        
        All alarms end with the following objects:
        . aimosAcknowledgementOID acknowledgement OID value
        . snmpTrapEnterprise      enterprise OID value
                                  (note: if aimosPhoneBookInterfaceType is set to
                                  ifAimosObsolete(4) aimosTrapEnterprise is used instead)
        
        If aimosPhoneBookInterfaceType is on its default value ifMIBDefault(0), then each
        of the object mentioned before has an appropriate instance identifier. That is,
        aimosOrgID has the OrgID itself as instance identifier and, for example,
        aimosAlarmListID has aimosOrgID and aimosAlarmListID as instance identifier,
        since these objects are defined in that manner.
        
        If aimosPhoneBookInterfaceType is set to ifAimosObsolete(4), then each object in
        the alarm notification has an instance identifier of zero. The only exception
        from this rule is aimosTrapOID. This object has no instance identifier.
        
        After having emitted an alarm notification with the objects mentioned before
        included, the A.I.M.O.S. SNMP Agent expects an acknowledgement within a certain
        period of time. This interval can be specified in aimosAlarmAckExpectInterval.
        
        Each SNMP Manager must confirm the receipt of the notification unless its
        inability of acknowledgements is indicated by appropriate settings made to
        aimosPhoneBookAckCapability.
        The acknowledgement will be done by setting aimosAlarmTrapAcknowledgementState
        to acknowledged(2). This OID is indexed by aimosOrgID, aimosAlarmTrapID and
        aimosAlarmListID. The notification makes the OID required for acknowledgement
        (object including instance identifiers) available in the aimosAcknowledgementOID.
        
        If a set request is made to aimosAlarmTrapAcknowledgementState, additionally
        aimosAlarmTrapAcknowledgementUser is set to the current user and
        aimosAlarmTrapAcknowledgementTime is set to the time of the acknowledgement.
        
        If an expected acknowledgement is missed by the A.I.M.O.S. SNMP Agent it will send
        the alarm repeatedly again until the alarm is acknowledged by the affected SNMP
        Manager. The objects contents of a re-sending alarm notification are identical
        to the preceding ones, especially the counter values (aimosAlarmTrapID,
        aimosAlarmTrapNotificationID, aimosAlarmListID, aimosAlarmListAlarmEventID).
        
        Each SNMP Manager may examine the incoming alarms notification ID. If it is not
        incremented by one since the last notification, it is an indication for missing
        notifications. The SNMP manager should wait a while until the SnMP Agent has
        resend the missing notification(s) unless acknowledgement is deactivated
        (aimosPhoneBookAckCapability is false(0)). In the latter case the SNMP Manager
        should synchronize its alarm table with the SNMP Agent ones by setting
        aimosPhoneBookAlarmListResync to start(5)."
      ::= { aimos 4 }

    
    aimosAgentState OBJECT-TYPE
      SYNTAX AgentState
      MAX-ACCESS accessible-for-notify
      STATUS current
      DESCRIPTION
        "This value indicates what the agent is about to do.
        
        Please refer also to the DESCRIPTION clause for aimosAgentAnnouncement."
      ::= { aimosNotifications 1 }

    
    aimosAcknowledgementOID OBJECT-TYPE
      SYNTAX OBJECT IDENTIFIER
      MAX-ACCESS accessible-for-notify
      STATUS current
      DESCRIPTION
        "This object comprises the OID, the value of which must be set to acknowledged(2)
        in order to confirm the alarm reception (i.e. perform the acknowledgement).
        
        If a SNMP Manager is not able to perform an acknowledgement, it should set
        aimosPhoneBookAckCapability to false."
      ::= { aimosNotifications 2 }

    
    aimosTrapEnterprise OBJECT-TYPE
      SYNTAX OBJECT IDENTIFIER
      MAX-ACCESS accessible-for-notify
      STATUS current
      DESCRIPTION
        "This object was intended to carry the entrerprise OID value in notifications,
        although the existing object snmpTrapEnterprise had already exactly this task.
        
        This object is used in notifications instead of snmpTrapEnterprise if
        aimosPhoneBookInterfaceType is set to ifAimosObsolete(4) for compatibility
        reasons to the first version of this MIB.
        
        It is recommended to leave aimosPhoneBookInterfaceType on its default value
        ifMIBDefault(0). In that case snmpTrapEnterprise is used."
      ::= { aimosNotifications 3 }

    
    aimosAgentAnnouncement NOTIFICATION-TYPE
      OBJECTS { aimosOMCSDN, aimosOrgID, aimosAlarmTrapID, aimosAlarmTrapNotificationID, aimosAlarmListID, 
        aimosAlarmListAlarmEventID, aimosAgentState, aimosAcknowledgementOID }
      STATUS current
      DESCRIPTION 
        "A aimosAgentAnnouncement notification is emitted by the agent if it is put in or
        out of operation. aimosAgentState of type AgentState indicates what actually
        happens. aimosAgentAnnouncement notification has no aimosAlarmCleared
        notification.
        
        Cold Start
        ==========
        A aimosAgentState of snmpColdStart(1) indicates, that the agent has been started.
        Already existing Sessions are invalid; requests will be responded by
        authorisation errors.
        
        The relevant alarm list entry contains aimosAlarmListAlarmID set to alarmOMC(62)
        and aimosAlarmListSpecificProblem set to 8880.
        
        Pause
        =====
        A aimosAgentState of snmpPause(2) signifies that the A.I.M.O.S. SNMP Agent is
        proceed to pause its activity. Even though the A.I.M.O.S. SNMP Agent's process
        will remain active, requests will result in time outs until aimosAgentAnnouncement
        with aimosAgentState set to snmpResume(3) is forwarded.
        
        The relevant alarm list entry contains aimosAlarmListAlarmID set to alarmOMC(62)
        and aimosAlarmListSpecificProblem set to 8887.
        
        The agent is waiting a certain period of time for acknowledgements before going
        in pause mode. If the agent comes back in operation, it will recognise missing
        acknowledgements and continue sending out aimosAgentAnnouncement notifications
        regarding the AgentState of snmpPause(2) additional to the aimosAgentAnnouncement
        notifications regarding the AgentState of snmpResume(3). This may prevent the
        manager from requesting a synchronisation of the alarm list due to the gap in the
        sequence of notification ID's.
        
        Resume
        ======
        A aimosAgentState of snmpResume(3) signifies that the A.I.M.O.S. SNMP Agent is
        resuming its activity. Already existing Sessions remain valid, except they were
        not used for a period longer than the one specified in aimosSessionTimeout.
        
        The relevant alarm list entry contains aimosAlarmListAlarmID set to alarmOMC(62)
        and aimosAlarmListSpecificProblem set to 8881.
        
        Shut Down
        =========
        A aimosAgentState of snmpShutDown(4) signifies that the A.I.M.O.S. SNMP Agent is
        about to shut down. The A.I.M.O.S. SNMP Agent waits a certain time for the SNMP
        Managers to be able to acknowledge this notification before actually shutting down.
        
        If the process terminates, all Sessions are invalidated. The agent doesn't
        respond to requests until aimosAgentAnnouncement with aimosAgentState set to
        snmpColdStart(1) is forwarded.
        
        The relevant alarm list entry contains aimosAlarmListAlarmID set to alarmOMC(62)
        and aimosAlarmListSpecificProblem set to 8889.
        
        If the A.I.M.O.S. SNMP Agent comes back in operation, it will recognise missing
        acknowledgements and continue sending out aimosAgentAnnouncement notifications
        regarding the AgentState of snmpShutDown(4) additional to the
        aimosAgentAnnouncement notifications regarding the AgentState of
        snmpColdStart(1). This may prevent the manager from requesting a synchronisation
        of the alarm list due to the gapin the sequence of notification ID's."
      ::= { aimosNotifications 4 }

    
    aimosAlarmNew NOTIFICATION-TYPE
      OBJECTS { aimosOMCSDN, aimosOrgID, aimosAlarmTrapID, aimosAlarmTrapNotificationID, aimosAlarmListID, 
        aimosAlarmListAlarmEventID, aimosAlarmListAlarmID, aimosAlarmListEventType, aimosAlarmListEventTime, aimosAlarmListProbableCause, 
        aimosAlarmListSpecificProblem, aimosAlarmListSeverity, aimosAlarmListTrendIndication, aimosAlarmListAdditionalText, aimosAlarmListSDN, 
        aimosAlarmListTrapInfo, aimosAlarmListComponentName, aimosAlarmListLocation, aimosAlarmListUniqueSystemID, aimosAcknowledgementOID, 
        aimosAlarmListRaiseLatitude, aimosAlarmListRaiseLongitude }
      STATUS current
      DESCRIPTION 
        "The aimosAlarmNew notification is used when a new alarm appears. It contains
        a new aimosAlarmListAlarmEventID.
        
        The aimosAlarmNew notification causes the A.I.M.O.S. SNMP Agent to create
        . one alarm list entry per affected organisation and
        . one alarm trap list entry per affected SNMP Manager
        containing the values of the notification objects."
      ::= { aimosNotifications 5 }

    
    aimosAlarmChanged NOTIFICATION-TYPE
      OBJECTS { aimosOMCSDN, aimosOrgID, aimosAlarmTrapID, aimosAlarmTrapNotificationID, aimosAlarmListID, 
        aimosAlarmListAlarmEventID, aimosAlarmListAlarmID, aimosAlarmListEventType, aimosAlarmListEventTime, aimosAlarmListProbableCause, 
        aimosAlarmListSpecificProblem, aimosAlarmListSeverity, aimosAlarmListTrendIndication, aimosAlarmListAdditionalText, aimosAlarmListSDN, 
        aimosAlarmListTrapInfo, aimosAlarmListComponentName, aimosAlarmListLocation, aimosAlarmListUniqueSystemID, aimosAcknowledgementOID
         }
      STATUS current
      DESCRIPTION 
        "The aimosAlarmChanged notification is used when the severity of an uncleared
        alarm has changed. The alarm is correlated with the aimosAlarmNew notification
        by identical values in aimosAlarmListAlarmEventID.
        
        The aimosAlarmChanged notification causes the A.I.M.O.S. SNMP Agent to create
        . one alarm list entry per affected organisation and
        . one alarm trap list entry per affected SNMP Manager
        containing the values of the notifications objects."
      ::= { aimosNotifications 6 }

    
    aimosAlarmCleared NOTIFICATION-TYPE
      OBJECTS { aimosOMCSDN, aimosOrgID, aimosAlarmTrapID, aimosAlarmTrapNotificationID, aimosAlarmListID, 
        aimosAlarmListAlarmEventID, aimosAlarmListAlarmID, aimosAlarmListEventType, aimosAlarmListEventTime, aimosAlarmListProbableCause, 
        aimosAlarmListSpecificProblem, aimosAlarmListSeverity, aimosAlarmListTrendIndication, aimosAlarmListAdditionalText, aimosAlarmListSDN, 
        aimosAlarmLogTrapInfo, aimosAlarmLogComponentName, aimosAlarmLogLocation, aimosAlarmLogUniqueSystemID, aimosAlarmListClearReason, 
        aimosAcknowledgementOID, aimosAlarmLogRaiseLatitude, aimosAlarmLogRaiseLongitude, aimosAlarmLogClearLatitude, aimosAlarmLogClearLongitude
         }
      STATUS current
      DESCRIPTION 
        "The aimosAlarmCleared notification is used when an alarm gets cleared. The alarm
        is correlated with the aimosAlarmNew and aimosAlarmCleared notification by
        identical values in aimosAlarmListAlarmEventID.
        
        It has an additional object aimosAlarmListClearReason. In contrast to
        aimosAlarmNew and aimosAlarmCleared the alarm notification object
        aimosAlarmListEventTime contains the time when the alarm condition is cleared.
        
        The aimosAlarmCleared notification causes the A.I.M.O.S. SNMP Agent to
        . create a new alarm trap list entry containing the values of the notification
          objects,
        . but not to create a new alarm list entry.
        
        Instead, the agent makes some amendments to the alarm list. Its entries created
        for the aimosAlarmNew and if applicable aimosAlarmChanged notifications
        (correlated with the aimosAlarmCleared notification by identical values in
        aimosAlarmListAlarmEventID) are modified in the following manner:
        . the notifications value of aimosAlarmListClearReason is assigned to the alarm
          lists value of aimosAlarmListClearReason
        . the notifications value of aimosAlarmListEventTime is assigned to the alarm
          lists value of aimosAlarmListClearTime
        
        After a aimosAlarmCleared notification was acknowledged all information of the
        alarm trap table entries and the alarm list entries are combined and filed in a
        new alarm log table entry. In this process, the entry from the alarm trap table
        is always deleted. The alarm list entry is also deleted, if no acknowledgement
        of another SNMP Manager of the according organisation is missing."
      ::= { aimosNotifications 7 }

    
    aimosAlarmListRebuildInitiated NOTIFICATION-TYPE
      OBJECTS { aimosOMCSDN, aimosOrgID, aimosAlarmTrapID, aimosAlarmTrapNotificationID, aimosAlarmListID, 
        aimosAlarmListAlarmEventID, aimosAcknowledgementOID }
      STATUS current
      DESCRIPTION 
        "The aimosAlarmListRebuildInitiated notification is sent, when an alarm list
        rebuild process was triggered. The notification will be emitted prior to the
        rebuild, immediately after dropping the content of the alarm table.
        
        On reception of this notification, the SNMP Manager shall clean the internal
        alarm table to be synchronised with the agent prior to acknowledge this
        notification. Before acknowledgement the agent will not send any notification
        (expect of re-send this notification by the A.I.M.O.S. SNMP Agent until
        acknowledgement is received by the A.I.M.O.S. SNMP Agent).
        
        The alarm list contains one entry with
        . aimosAlarmListID and aimosAlarmListAlarmEventID set to 1
        . aimosAlarmListAlarmID set to alarmOMC(62)
        . aimosAlarmListSpecificProblem set to 8885.
        
        The alarm trap list contains one entry per affected SNMP Manager (alarm
        recipient) with
        . aimosAlarmTrapNotificationID set to 1 for each SNMP Manager
        . aimosAlarmTrapID set to 1 for the first SNMP Manager, 2 for the second, ...
        
        There is no aimosAlarmCleared-notification for this alarm. It is cleared by
        acknowledgement."
      ::= { aimosNotifications 8 }

    
    aimosHeartbeat NOTIFICATION-TYPE
      OBJECTS { aimosOMCSDN, aimosCurrentTime }
      STATUS current
      DESCRIPTION 
        "The aimosHeartbeat notification is sent out each [aimosWorkShiftHeartbeatInterval]
        minutes to the members of the Alarm Recipient List specified by the object
        [aimosWorkShiftHeartbeatRecipientList]. This notification must not be acknowledged,
        even if the SNMP Manager performs acknowledgement to all other notifications.
        Additionally, this notifications are neither inserted to the Alarm Table nor to
        the Alarm Log. Therefore this notification contains no continuous numbering."
      ::= { aimosNotifications 9 }

    
    aimosAlarmRecognized NOTIFICATION-TYPE
      OBJECTS { aimosOMCSDN, aimosOrgID, aimosAlarmTrapID, aimosAlarmTrapNotificationID, aimosAlarmListID, 
        aimosAlarmListAlarmEventID, aimosAlarmListAlarmID, aimosAlarmListSpecificProblem, aimosAlarmListAdditionalText, aimosAlarmListSDN, 
        aimosAlarmListTrapInfo, aimosAlarmListComponentName, aimosAlarmListLocation, aimosAlarmListUniqueSystemID, aimosAlarmListRecognitionUser, 
        aimosAlarmListRecognitionTime, aimosAcknowledgementOID }
      STATUS current
      DESCRIPTION 
        "The aimosAlarmRecognized alarm is raised in case an alarm is recognized 
        . either via aimosAlarmListRecognitionState
        . by means of the AIMOS_VIsu program
        
        The description for aimosAlarmListRecognitionState provides more 
        information about this notification.
        "
      ::= { aimosNotifications 10 }

    
    aimosGroups OBJECT-IDENTITY
      STATUS current
      DESCRIPTION 
        "Group objects"
      ::= { aimos 5 }

    
    aimosMIB2Group OBJECT-GROUP
      OBJECTS { sysDescr, sysObjectID, sysUpTime, sysContact, sysName, 
        sysLocation }
      STATUS current
      DESCRIPTION 
        "Description."
      ::= { aimosGroups 1 }

    
    aimosLoginGroup OBJECT-GROUP
      OBJECTS { aimosSystemAvailability, aimosCommunity, aimosCommunityLength, aimosMinPasswordLength, aimosLoginUserName, 
        aimosLoginPassword, aimosLoginState, aimosLoginOrgID, aimosLoginPhoneBookID }
      STATUS current
      DESCRIPTION 
        "Description."
      ::= { aimosGroups 2 }

    
    aimosSystemInfoGroup OBJECT-GROUP
      OBJECTS { aimosMIBVersion, aimosAgentVersion, aimosOMCConnectorVersion, aimosCurrentTime }
      STATUS current
      DESCRIPTION 
        "Description."
      ::= { aimosGroups 4 }

    
    aimosSystemConfigGroup OBJECT-GROUP
      OBJECTS { aimosOMCSDN, aimosOMCName, aimosTimeFormat, aimosPasswordExpirationPeriod, aimosPasswordReuseCounter, 
        aimosPasswordStandard, aimosSessionTimeout, aimosOMCConnectorAddress }
      STATUS current
      DESCRIPTION 
        "Description."
      ::= { aimosGroups 5 }

    
    aimosBandConfigGroup OBJECT-GROUP
      OBJECTS { aimosBandID, aimosBandDLmin, aimosBandDLmax, aimosBandULFrequencyGap, aimosBandULChannelGap, 
        aimosBandCalculationID, aimosBandCalculationMin, aimosBandCalculationMax, aimosBandCalculationFormulaStart, aimosBandCalculationFormulaBandWidth, 
        aimosBandCalculationFormulaOffset, aimosLicenseeFirstARFCN, aimosLicenseeARFCNCount }
      STATUS current
      DESCRIPTION 
        "Description."
      ::= { aimosGroups 6 }

    
    aimosBandInfoGroup OBJECT-GROUP
      OBJECTS { aimosFrequencyARFCN, aimosFrequencyValue, aimosFrequencyOwner, aimosARFCNFrequency, aimosARFCNValue, 
        aimosARFCNOwner }
      STATUS current
      DESCRIPTION 
        "Description."
      ::= { aimosGroups 7 }

    
    aimosUserGroup OBJECT-GROUP
      OBJECTS { aimosOrgID, aimosOrgName, aimosOrgText, aimosOrgLevel, aimosOrgMCC, 
        aimosOrgMNC, aimosOrgActive, aimosOrgDNSeparator, aimosOrgDNConcatenator, aimosOrgCCConcatenator, 
        aimosOrgActiveWorkShiftID, aimosOrgNextUserID, aimosOrgNextWorkShiftID, aimosOrgNextAlarmRecipientListID, aimosOrgNextPhoneBookID, 
        aimosUserID, aimosUserName, aimosUserPassword, aimosUserText, aimosUserRoleID, 
        aimosUserActive, aimosUserPasswordAge, aimosInitiallyMasterLoginUserName, aimosInitiallyMasterLoginPassword }
      STATUS current
      DESCRIPTION 
        "Description."
      ::= { aimosGroups 8 }

    
    aimosRoleGroup OBJECT-GROUP
      OBJECTS { aimosNextRoleID, aimosRoleID, aimosRoleName, aimosRoleRightArea, aimosRoleRightAccess
         }
      STATUS current
      DESCRIPTION 
        "Description."
      ::= { aimosGroups 9 }

    
    aimosPhoneBookGroup OBJECT-GROUP
      OBJECTS { aimosPhoneBookID, aimosPhoneBookName, aimosPhoneBookAddress, aimosPhoneBookActive, aimosPhoneBookLastNotificationID, 
        aimosPhoneBookAlarmListResync, aimosPhoneBookTimeDisplayFormat, aimosPhoneBookRecognitionTraps, aimosPhoneBookAckCapability, aimosPhoneBookInterfaceType, 
        aimosPhoneBookGeographicPositionFormat }
      STATUS current
      DESCRIPTION 
        "Description."
      ::= { aimosGroups 10 }

    
    aimosAlarmConfigGroup OBJECT-GROUP
      OBJECTS { aimosAlarmID, aimosAlarmDescription, aimosAlarmEventType, aimosAlarmDefaultSeverity, aimosAlarmSeverityMin, 
        aimosAlarmAlarmGroupID, aimosAlarmClearMode, aimosWorkShiftID, aimosWorkShiftName, aimosAlarmDistributionPlanRecipientListID, 
        aimosAlarmRecipientListID, aimosAlarmRecipientListName, aimosPhoneBookAlarmListResync, aimosAlarmRecipientListMemberActive, aimosAlarmAckExpectInterval, 
        aimosAlarmListRebuild, aimosWorkShiftHeartbeatRecipientList, aimosWorkShiftHeartbeatInterval, aimosAlarmListResync, aimosAlarmForwardingType
         }
      STATUS current
      DESCRIPTION 
        "Description."
      ::= { aimosGroups 11 }

    
    aimosAlarmConfigGroupDeprecated OBJECT-GROUP
      OBJECTS { aimosAlarmSeverityRangeMinValue, aimosAlarmSeverityRangeMaxValue, aimosAlarmSeverityRangeSeverity }
      STATUS deprecated
      DESCRIPTION 
        "Description."
      ::= { aimosGroups 12 }

    
    aimosAlarmInfoGroup OBJECT-GROUP
      OBJECTS { aimosAlarmTrapID, aimosAlarmTrapNotificationID, aimosAlarmTrapPhonebookID, aimosAlarmTrapAcknowledgementState, aimosAlarmTrapAcknowledgementUser, 
        aimosAlarmTrapAcknowledgementTime, aimosAlarmListID, aimosAlarmListAlarmEventID, aimosAlarmListAlarmID, aimosAlarmListEventType, 
        aimosAlarmListEventTime, aimosAlarmListProbableCause, aimosAlarmListSpecificProblem, aimosAlarmListSeverity, aimosAlarmListTrendIndication, 
        aimosAlarmListAdditionalText, aimosAlarmListSDN, aimosAlarmListTrapInfo, aimosAlarmListComponentName, aimosAlarmListLocation, 
        aimosAlarmListUniqueSystemID, aimosAlarmListClearReason, aimosAlarmListClearTime, aimosAlarmListRaiseLatitude, aimosAlarmListRaiseLongitude, 
        aimosAlarmListClearLatitude, aimosAlarmListClearLongitude, aimosAlarmLogPhoneBookID, aimosAlarmLogNotificationID, aimosAlarmLogAlarmEventID, 
        aimosAlarmLogAlarmID, aimosAlarmLogEventType, aimosAlarmLogEventTime, aimosAlarmLogProbableCause, aimosAlarmLogSpecificProblem, 
        aimosAlarmLogSeverity, aimosAlarmLogTrendIndication, aimosAlarmLogAdditionalText, aimosAlarmLogSDN, aimosAlarmLogTrapInfo, 
        aimosAlarmLogComponentName, aimosAlarmLogLocation, aimosAlarmLogUniqueSystemID, aimosAlarmLogAcknowledgementUser, aimosAlarmLogAcknowledgementTime, 
        aimosAlarmLogClearReason, aimosAlarmLogClearTime, aimosAlarmLogClearTrapID, aimosAlarmLogClearNotificationID, aimosAlarmLogClearAcknowledgementUser, 
        aimosAlarmLogClearAcknowledgementTime, aimosAlarmLogRaiseLatitude, aimosAlarmLogRaiseLongitude, aimosAlarmLogClearLatitude, aimosAlarmLogRecognitionState, 
        aimosAlarmLogRecognitionUser, aimosAlarmLogRecognitionTime, aimosAlarmLogClearLongitude, aimosAlarmListRecognitionState, aimosAlarmListRecognitionUser, 
        aimosAlarmListRecognitionTime }
      STATUS current
      DESCRIPTION 
        "Description."
      ::= { aimosGroups 13 }

    
    aimosAlarmGroupConfigGroup OBJECT-GROUP
      OBJECTS { aimosAlarmGroupID, aimosAlarmGroupName, aimosAlarmGroupAllowedOrgActive, aimosNextAlarmGroupID }
      STATUS current
      DESCRIPTION 
        "Description."
      ::= { aimosGroups 14 }

    
    aimosMasterGroup OBJECT-GROUP
      OBJECTS { aimosNextMasterID, aimosMasterID, aimosMasterRDN, aimosMasterSDN, aimosMasterIdentNo, 
        aimosMasterSerialNo, aimosMasterTrapInfo, aimosMasterLocation, aimosMasterAnyText, aimosMasterMapXY, 
        aimosMasterOID, aimosMasterAddress, aimosMasterState, aimosMasterGUID, aimosMasterLoginPassword, 
        aimosMasterLoginUserName }
      STATUS current
      DESCRIPTION 
        "Description."
      ::= { aimosGroups 15 }

    
    aimosMasterV1Group OBJECT-GROUP
      OBJECTS { aimosMasterV1UnitReference, aimosMasterV1ValueSource, aimosMasterV1HeartbeatInterval, aimosMasterV1HeartbeatOvertime, aimosMasterV1HeartbeatTime
         }
      STATUS current
      DESCRIPTION 
        "Description."
      ::= { aimosGroups 16 }

    
    aimosSubRackGroup OBJECT-GROUP
      OBJECTS { aimosSubRackID, aimosSubRackRDN, aimosSubRackSDN, aimosSubRackIdentNo, aimosSubRackSerialNo, 
        aimosSubRackTrapInfo, aimosSubRackLocation, aimosSubRackAnyText, aimosSubRackMapXY, aimosSubRackOID
         }
      STATUS current
      DESCRIPTION 
        "Description."
      ::= { aimosGroups 17 }

    
    aimosSubRackV1Group OBJECT-GROUP
      OBJECTS { aimosSubRackV1UnitReference, aimosSubRackV1ValueSource, aimosSubRackV1AttenuationAge, aimosSubRackV1AttenuationAmp1DL, aimosSubRackV1AttenuationAmp1UL, 
        aimosSubRackV1AttenuationAmp2DL, aimosSubRackV1AttenuationAmp2UL, aimosSubRackV1AttenuationAmp3DL, aimosSubRackV1AttenuationAmp3UL, aimosSubRackV1GainOffsetAge, 
        aimosSubRackV1GainOffsetAmp1DL, aimosSubRackV1GainOffsetAmp1UL, aimosSubRackV1GainOffsetAmp2DL, aimosSubRackV1GainOffsetAmp2UL, aimosSubRackV1GainOffsetAmp3DL, 
        aimosSubRackV1GainOffsetAmp3UL, aimosSubRackV1TemperatureAge, aimosSubRackV1TemperatureBoard, aimosSubRackV1AmplifierBandNamesAge, aimosSubRackV1Amplifier1BandName, 
        aimosSubRackV1Amplifier2BandName, aimosSubRackV1Amplifier3BandName }
      STATUS current
      DESCRIPTION 
        "Description."
      ::= { aimosGroups 18 }

    
    aimosRemoteGroup OBJECT-GROUP
      OBJECTS { aimosRemoteID, aimosRemoteRDN, aimosRemoteSDN, aimosRemoteIdentNo, aimosRemoteSerialNo, 
        aimosRemoteTrapInfo, aimosRemoteLocation, aimosRemoteAnyText, aimosRemoteMapXY, aimosRemoteOID
         }
      STATUS current
      DESCRIPTION 
        "Description."
      ::= { aimosGroups 19 }

    
    aimosRemoteV1Group OBJECT-GROUP
      OBJECTS { aimosRemoteV1UnitReference, aimosRemoteV1ValueSource, aimosRemoteV1NominalTemperatureAge, aimosRemoteV1NominalTemperature, aimosRemoteV1TemperatureAge, 
        aimosRemoteV1TemperatureAmp1, aimosRemoteV1TemperatureAmp2, aimosRemoteV1TemperatureAmp3, aimosRemoteV1TemperatureBoard, aimosRemoteV1TemperaturePowerSupply, 
        aimosRemoteV1AmplifierStateAge, aimosRemoteV1Amplifier1State, aimosRemoteV1Amplifier2State, aimosRemoteV1Amplifier3State, aimosRemoteV1AmplifierPowerAge, 
        aimosRemoteV1Amplifier1Power, aimosRemoteV1Amplifier2Power, aimosRemoteV1Amplifier3Power, aimosRemoteV1AttenuationAge, aimosRemoteV1AttenuationAmp1DL, 
        aimosRemoteV1AttenuationAmp1UL, aimosRemoteV1AttenuationAmp2DL, aimosRemoteV1AttenuationAmp2UL, aimosRemoteV1AttenuationAmp3DL, aimosRemoteV1AttenuationAmp3UL, 
        aimosRemoteV1GainOffsetAge, aimosRemoteV1GainOffsetAmp1DL, aimosRemoteV1GainOffsetAmp1UL, aimosRemoteV1GainOffsetAmp2DL, aimosRemoteV1GainOffsetAmp2UL, 
        aimosRemoteV1GainOffsetAmp3DL, aimosRemoteV1GainOffsetAmp3UL, aimosRemoteV1ALCThresholdAge, aimosRemoteV1ALCThresholdAmp1DL, aimosRemoteV1ALCThresholdAmp1UL, 
        aimosRemoteV1ALCThresholdAmp2DL, aimosRemoteV1ALCThresholdAmp2UL, aimosRemoteV1ALCThresholdAmp3DL, aimosRemoteV1ALCThresholdAmp3UL, aimosRemoteV1OpticalLossAge, 
        aimosRemoteV1OpticalLossDL, aimosRemoteV1OpticalLossUL, aimosRemoteV1Output1Name, aimosRemoteV1Output2Name, aimosRemoteV1Output3Name, 
        aimosRemoteV1Output4Name, aimosRemoteV1Output1Value, aimosRemoteV1Output2Value, aimosRemoteV1Output3Value, aimosRemoteV1Output4Value, 
        aimosRemoteV1Input1Name, aimosRemoteV1Input2Name, aimosRemoteV1Input3Name, aimosRemoteV1Input4Name, aimosRemoteV1OutputAge
         }
      STATUS current
      DESCRIPTION 
        "Description."
      ::= { aimosGroups 20 }

    
    aimosGSMNSOGroup OBJECT-GROUP
      OBJECTS { aimosGSMNSOID, aimosGSMNSORDN, aimosGSMNSOSDN, aimosGSMNSOIdentNo, aimosGSMNSOSerialNo, 
        aimosGSMNSOTrapInfo, aimosGSMNSOLocation, aimosGSMNSOAnyText, aimosGSMNSOMapXY, aimosGSMNSOOID, 
        aimosGSMNSOOIDData }
      STATUS current
      DESCRIPTION 
        "Description."
      ::= { aimosGroups 21 }

    
    aimosGSMNSOV1Group OBJECT-GROUP
      OBJECTS { aimosGSMNSOV1UnitReference, aimosGSMNSOV1ValueSource, aimosGSMNSOV1Name, aimosGSMNSOV1ScanInterval, aimosGSMNSOV1ScanBCCH, 
        aimosGSMNSOV1CellStatus, aimosGSMNSOV1MinScanSignalStrength, aimosGSMNSOV1SignalStrengthHysteresis, aimosGSMNSOV1MinAllowedSignalStrength, aimosGSMNSOV1MaxAllowedSignalStrength, 
        aimosGSMNSOV1MaxAllowedBER, aimosGSMNSODataV1ID, aimosGSMNSODataV1LAC, aimosGSMNSODataV1CI, aimosGSMNSODataV1DateTime, 
        aimosGSMNSODataV1ARFCN, aimosGSMNSODataV1BSIC, aimosGSMNSODataV1CS, aimosGSMNSODataV1SignalStrength, aimosGSMNSODataV1BER
         }
      STATUS current
      DESCRIPTION 
        "Description."
      ::= { aimosGroups 22 }

    
    aimosUMTSNSOGroup OBJECT-GROUP
      OBJECTS { aimosUMTSNSOID, aimosUMTSNSORDN, aimosUMTSNSOSDN, aimosUMTSNSOIdentNo, aimosUMTSNSOSerialNo, 
        aimosUMTSNSOTrapInfo, aimosUMTSNSOLocation, aimosUMTSNSOAnyText, aimosUMTSNSOMapXY, aimosUMTSNSOOID, 
        aimosUMTSNSOOIDData }
      STATUS current
      DESCRIPTION 
        "Description."
      ::= { aimosGroups 23 }

    
    aimosUMTSNSOV1Group OBJECT-GROUP
      OBJECTS { aimosUMTSNSOV1UnitReference, aimosUMTSNSOV1ValueSource, aimosUMTSNSODataV1ID }
      STATUS current
      DESCRIPTION 
        "Description."
      ::= { aimosGroups 24 }

    
    aimosCableConfigGroup OBJECT-GROUP
      OBJECTS { aimosNextCableID, aimosCableID, aimosCableCode, aimosCableTrapInfo, aimosCableLocation, 
        aimosCableAnyText, aimosCableUsageID, aimosCableUsageRemoteUnitReference, aimosCableUsageCableID, aimosCableUsageFibreCode, 
        aimosCableUsageAlternativeTrapInfo }
      STATUS current
      DESCRIPTION 
        "Description."
      ::= { aimosGroups 27 }

    
    aimosNotificationGroup OBJECT-GROUP
      OBJECTS { aimosTrapOID, aimosAgentState, aimosAcknowledgementOID, aimosTrapEnterprise }
      STATUS current
      DESCRIPTION 
        "Description."
      ::= { aimosGroups 29 }

    
    midsNotificationsGroup NOTIFICATION-GROUP
      NOTIFICATIONS { aimosAgentAnnouncement, aimosAlarmNew, aimosAlarmChanged, aimosAlarmCleared, aimosAlarmListRebuildInitiated, 
        aimosHeartbeat, aimosAlarmRecognized }
      STATUS current
      DESCRIPTION 
        "Description."
      ::= { aimosGroups 30 }

    
    aimosNetworkElementOperationsGroup OBJECT-GROUP
      OBJECTS { aimosNEOperationsQueryAlarmsInfo, aimosNEOperationsReboot, aimosNEOperationsRebootInfo, aimosNEOperationsQueryAlarms, aimosNEOperationsID, 
        aimosNEOperationsSDN, aimosNEOperationsTrapInfo, aimosNEOperationsComponentName, aimosNEOperationsLocation, aimosNEOperationsUniqueSystemID, 
        aimosNEOperationsDeactivateNEInfo, aimosNEOperationsNEActive, aimosNEOperationsDeactivateNE, aimosNEOperationsActivateNE, aimosNEOperationsActivateNEInfo
         }
      STATUS current
      DESCRIPTION 
        "Description."
      ::= { aimosGroups 31 }

    
    aimosCompliances OBJECT-IDENTITY
      STATUS current
      DESCRIPTION 
        "Compliance objects"
      ::= { aimos 6 }

    
    aimosCompliance MODULE-COMPLIANCE
      STATUS current
      DESCRIPTION 
        "Description."
      MODULE -- this module
        MANDATORY-GROUPS { aimosLoginGroup, aimosSystemInfoGroup, aimosSystemConfigGroup, aimosBandConfigGroup, aimosBandInfoGroup, 
          aimosUserGroup, aimosRoleGroup, aimosPhoneBookGroup, aimosAlarmConfigGroup, aimosAlarmInfoGroup, 
          aimosAlarmGroupConfigGroup, aimosCableConfigGroup, aimosNotificationGroup, aimosNetworkElementOperationsGroup, midsNotificationsGroup, 
          aimosMIB2Group, aimosAlarmConfigGroupDeprecated, aimosMasterGroup, aimosMasterV1Group, aimosSubRackGroup, 
          aimosSubRackV1Group, aimosRemoteGroup, aimosRemoteV1Group, aimosGSMNSOGroup, aimosGSMNSOV1Group, 
          aimosUMTSNSOGroup, aimosUMTSNSOV1Group }
      ::= { aimosCompliances 1 }

    
  
  END

--
-- AIMOS.my
--
