--Refer to Compas ID 86507 for an explanation of the use of this MIB. 
--Contact the Services R&D Alarm Team under Margaret VanAndel for help 
--in implementation and compatibility testing of this MIB with Avaya's alarm 
--receivers, specifically the Alarm Fault Manager (AFM).
---------------------------------------------------------------------------------------

INADS-MIB DEFINITIONS ::= BEGIN

    IMPORTS
      MODULE-IDENTITY, OBJECT-TYPE, NOTIFICATION-TYPE
          FROM SNMPv2-SMI
      MODULE-COMPLIANCE, OBJECT-GROUP, NOTIFICATION-GROUP
          FROM SNMPv2-CONF
      DisplayString
          FROM SNMPv2-TC
      mibs
          FROM AVAYAGEN-MIB;

inadssnmp MODULE-IDENTITY
    LAST-UPDATED "200402230000Z"
    ORGANIZATION "Avaya, Inc."
    CONTACT-INFO "Postal:  Avaya, Inc.
                           211 Mt Airy Rd.
			   Basking Ridge, NJ 07920
                           USA

                  Tel:     +1 908 953 6000
                  E-mail:  executiveoffic@avaya.com
                  WWW:     http://www.avaya.com"
    DESCRIPTION  " "


    REVISION 	"200402230000Z" -- 23 February 2004
    DESCRIPTION
        "Rev 1.0.4 - Chris Gentle
        Updates from CTO SNMP Review CID 101101 - Jan 2004"

    REVISION 	"200312160000Z" -- 16 December 2003
    DESCRIPTION
        "Rev 1.0.3 - Chris Gentle
        Minor rework of description text"

    REVISION 	"200312100000Z" -- 10 December 2003
    DESCRIPTION
        "Rev 1.0.2 - Ian Partridge
        Further SMIv2 compliance revisions"

    REVISION 	"200312050000Z" -- 5 December 2003
    DESCRIPTION
        "Rev 1.0.1 - Ian Partridge
        Revised to be more SMIv2 compliant."

    REVISION 	"200312050000Z" -- 1 May 2001
    DESCRIPTION
        "Rev 1.0.0 - Lisa Y. Kawahara
        Original version."

    ::= { services 1 }

services        OBJECT IDENTIFIER ::= { mibs 70 }


inadssnmpObjects         OBJECT IDENTIFIER ::= { inadssnmp 1 }
inadssnmpNotifications   OBJECT IDENTIFIER ::= { inadssnmp 2 }
inadssnmpConformance     OBJECT IDENTIFIER ::= { inadssnmp 3 }

-- The inadssnmpObjects Group

inadssnmpAlarmMessage OBJECT-TYPE
    SYNTAX     OCTET STRING (SIZE(1..300))
    MAX-ACCESS accessible-for-notify
    STATUS     current
    DESCRIPTION "The INADS-formated alarm string that contains information about an event.
    		 The string is a variable length record, which is always terminated with a
		 space character.
		 0-9	Prefix and product ID
		 10	Space character
		 11-12	Day of the month
		 13	/ character
		 14-15	Hour of day (00-23)
		 16	: character
	 	 17-18	Minute of alarm (00-59)
		 19	, character
		 20-22	Alarm type
		 23	| character
		 24-240 Up to 217 bytes of alarm information
		 (last)	Space character termination"
    ::= { inadssnmpObjects 1 }

inadssnmpAlarmAck  OBJECT-TYPE
    SYNTAX     DisplayString (SIZE(1..5))
    MAX-ACCESS read-write
    STATUS     current
    DESCRIPTION "A response from Avaya's management application 
		 inadssnmpAlarmMessage sender describing whether 
		 the manager received the alarm and recognises it 
		 as valid. 
		 This string will contain:
		   so 2
		        if the inadssnmpAlarmMessage is valid, or 
                   so 3 
		        if the inadssnmpAlarmMessage is invalid"
    ::= { inadssnmpObjects 2 }

inadssnmpAlarmTime OBJECT-TYPE
    SYNTAX  DisplayString (SIZE(1..32))
    MAX-ACCESS  accessible-for-notify
    STATUS  current
    DESCRIPTION
            "A time tag or sequence number used to uniquely qualify 
            inadssnmpAlarmMessage objects"
    ::= { inadssnmpObjects 3 }


-- The inadssnmpNotifications Group

inadssnmpAlarm NOTIFICATION-TYPE
    OBJECTS    { inadssnmpAlarmMessage, inadssnmpAlarmTime }
    STATUS     current
    DESCRIPTION "The full structure used for product alarming"
    ::= { inadssnmpNotifications 1 }

inadssnmpAck NOTIFICATION-TYPE
    OBJECTS    { inadssnmpAlarmAck, inadssnmpAlarmTime}
    STATUS     current
    DESCRIPTION "The full acknowledgment structure returned to the poduct
		 in response to an alarm"
    ::= { inadssnmpNotifications 2 }

inadssnmpAlarmSet NOTIFICATION-TYPE
    OBJECTS    { inadssnmpAlarmMessage, inadssnmpAlarmTime }
    STATUS     current
    DESCRIPTION "The full structure used for product alarming with a 
		 set used for the acknowledgment."
    ::= { inadssnmpNotifications 3 }

inadssnmpCompliances OBJECT IDENTIFIER ::= { inadssnmpConformance 1 }
inadssnmpGroups      OBJECT IDENTIFIER ::= { inadssnmpConformance 2 }

--
-- compliance statements
--

inadssnmpCompliance MODULE-COMPLIANCE
    STATUS current
    DESCRIPTION
	"The compliance statement for IP Office agents"
    MODULE -- this module
    MANDATORY-GROUPS {
        inadssnmpNotificationObjectsGroup,
        inadssnmpNotificationsGroup
    }
    ::= { inadssnmpCompliances 1 }

--
-- MIB groupings
--

inadssnmpNotificationObjectsGroup OBJECT-GROUP
    OBJECTS {
	inadssnmpAlarmMessage,
        inadssnmpAlarmAck,
        inadssnmpAlarmTime
    }
    STATUS current
    DESCRIPTION
	"Objects that are contained in the INADS notifications."
    ::= { inadssnmpGroups 1 }

inadssnmpNotificationsGroup NOTIFICATION-GROUP
    NOTIFICATIONS {
        inadssnmpAlarm,
        inadssnmpAck,
        inadssnmpAlarmSet
    }
    STATUS current
    DESCRIPTION
	"The notifications which indicate specific changes in the
	state of the IP Office system."
    ::= { inadssnmpGroups 2 }

END
