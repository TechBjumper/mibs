-- Avaya Load MIB
-- Copyright(c) 2004-2005  by Avaya Inc. All rights reserved.
-- ========================================================
-- $Revision: 10 $
-- Check In: $Date: 19/04/09 5:57p $
-- $Author: Sbiton $
-- $Archive: /MIBs/Version 1.0/Source/Avaya/AVAYA-LOAD-MIB.MY $
-- =========================================================
-- 
-- Overview:
-- 
-- The Avaya Load MIB defines upload, download and copy of application software
-- and configuration information.
-- 
-- The avGenOperations group
-- 
--   Each row in the avGenOpTable represents an operation that this system 
--   can perform. A walk of this table should provide a list of available 
--   operations that can be performed by the system. 
--   The avGenOpTable contains all configuration information necessary to 
--   perform upload, download, and copy operations within the system.  
--   Source, Destination, operational 
--   trigger, opertional status and error logging information are contained 
--   on a per row basis (each row again representing an operation that 
--   this table can perform).
-- 
-- The avGenApplication Group
-- 
--   Table of Application (FILE) entries.  Each row uniquely defines an
--   application in the system.  Applications can be defined as any entity 
--   that can be read or written from or to the system.  This includes 
--   software images, boot code, configuration files, prom code, etc. 
--   Each row contains information used to catalog the application (FILE)
--   entries present in the system. A walk of the avGenAppFileTable should
--   provide a directory-like listing of all application software, 
--   bootcode, configuration files and misc. accessable embedded software
--   in the system.  Each entry contains information about the application 
--   such as type, size, version number and date stamp.
-- 
-- =========================================================
   AVAYA-LOAD-MIB DEFINITIONS ::= BEGIN
 
        IMPORTS
             IpAddress, Integer32, OBJECT-TYPE, MODULE-IDENTITY, NOTIFICATION-TYPE            
                FROM SNMPv2-SMI     
		avGatewayMibs				
		FROM AVAYAGEN-MIB       
            DisplayString, RowStatus, TEXTUAL-CONVENTION            
                FROM SNMPv2-TC;
                                
    avLoad MODULE-IDENTITY 
			LAST-UPDATED "200901181307Z"		
			ORGANIZATION 
				"Avaya, Inc."
			CONTACT-INFO 
				"    Avaya Customer Services
					Postal: Avaya, Inc.
				        211 Mt Airy Rd.
				        Basking Ridge, NJ 07920
				        USA

				Tel:    +1 908 953 6000
				E-mail: executiveoffic@avaya.com
				WWW:    http://www.avaya.com
				"
			DESCRIPTION 
				"The avLoad MIB defines upload, download and 
				copy of application software  and configuration
				information.
				Copyright(c) 2004-2005  by Avaya Inc. All rights reserved."
			::= { avGatewayMibs 5 }
  
  
  
-- Version 200901181307Z - Shlomi Biton.
-- 1.  Add new enumeration reset(48) to avGenOpIndex. 
  
-- Version 200808071105Z - Shlomi Biton.
-- 1.  Add new enumeration not-administered(3) to avGenAppFileDuplStatus.

-- Version 200714061143Z - Shlomi Biton.
-- 1.  Add new enumeration flash(7) to avGenAppFileLocation.

-- Version 200718021531Z - Shlomi Biton.
-- 1. Adding new enumeration to avGenOpProtocolType - ftpResume(10). 
-- 2. Add new enumeration to avGenOpLastFailureIndex: In case of download a file using 
--    ftp_resume, and there is a partial/full file with different name in the same location, 
--    then avGenOpLastFailureIndex - ftpResumeBadFilename(220).
-- 3. Add new enumeration to avGenOpLastFailureIndex: In case of download a file using 
--    ftp_resume, and there is NO file at all to resume, then 
--    avGenOpLastFailureIndex - ftpResumeEmptyFile(221)
-- 4. Add new enumeration to avGenOpLastFailureIndex: In case of download a file using 
--    ftp_resume, and the FTP server does not support FTP resume, then: 
--    avGenOpLastFailureIndex - ftpResumeNotSupported(222).
-- 5. Add new enumeration to avGenOpIndex - localVoiceMailFileMove(47). 

-- Version 200612041652Z - Shlomi Biton.
-- 1. Adding new enumeration to avGenOpIndex - downloadVoiceMailFile(40) and
--    uploadVoiceMailFile(41).
-- 2. Adding new enumeration to avGenAppFileType - staticLanguagePack(30). 
-- 3. Adding new enumerations to avGenAppFileType - phoneAvayaUnicodeMessageFile(31)
--    and phoneCustomUnicodeMessageFile(32). 
--    Adding new enumerations to avGenOpIndex - downloadPhoneMessageFile(42)
--    and uploadPhoneMessageFile(43).
-- 4. Adding new enumerations to avGenAppFileType - startupConfigurationWizardTaskFile(33)
--    and genConfigurationWizardTaskFile(34). 
--    Adding new enumerations to avGenOpIndex - downloadConfigurationWizardTaskFile(44)
--    and uploadConfigurationWizardTaskFile(45).
-- 5. Add new enumeration to avGenOpIndex - localSWFileMove(46).  
-- 6. Add avGenAppFileCompatibleVersionNumber to avGenAppFileEntry. 
-- 7. New error code was defined for genOpLastFailureIndex - 
--    configFileSecretIntegrityFault(210) error  related to validation of 
--    encryption key.
 
-- Version 200607241652Z - Shlomi Biton.
-- 1. Adding new enumeration to avGenOpIndex - uploadPhoneImageFile(39).
-- 2. Enlarge the avGenOpLastFailureDisplay to 0..255 instead of  0..64 to allow
--    longer failure strings.  
-- 3. Add avGenRestoreOperationState to present restore operation status even after reset is done. 
--
-- Version 200604101457Z - Shlomi Biton.
-- 1. Adding new enumeration to avGenOpIndex - commit(30), uploadServicePack(31),
--    downloadServicePack(32), localServicePackFileCopy(33), backup(34), generateFile(35), 
--    downloadCertificate(36), uploadCertificate(37), switchPartitions(38).
-- 2. Adding new enumeration to avGenOpProtocolType - http(8) and https(9).  
-- 3. Adding new enumerations to avGenAppFileLocation - compactFlash(6).
-- 4. Adding new enumerations to avGenAppFileType - swRuntimeServicePack(24),
--    swComponentServicePack(25), trustedCertificate(26), certificateRequest(27), 
--    serverCertificate(28), privateKey(29).
-- 
-- Version 200602141745Z - Shlomi Biton.
-- 1. Adding new enumerations to avGenOpIndex - backupConfig(28), restore(29), 
--    uploadAuthFile(22), uploadLicFile(23), uploadSyslogFile(24) and uploadCDRFile(25).
-- 2. Adding new enumeration to avGenOpProtocolType - usb(7).
-- 3. Adding note to avGenOpFileName regarding usb mass storage devices. 
-- 4. Add new enumeration to avGenAppFileType - backupDatabase(21), syslogFile(22) and 
--    cdrFile(23).
-- 5. Add avLoadAppDynamicFileTable for displaying files/directories (used by external USB 
--    mass storage devices. 
-- 6. Changing the length of avGenOpLastWarningDisplay to 0..255 instead of 0..64 to allow
--    reporting of missing files during restore operation.
--
-- Version 200507031611Z - Shlomi Biton.
-- 1. Remove the fileAlreadyExistsInDirectory(18) error code in AvGenOpLastFailureIndex.
-- 2. Add the avLoadApplMemTable for presenting for each file type the amount of memory 
--    is used, how many bytes are free and used. 
-- 
-- Version 200505100945Z - Shlomi Biton.
-- 1. Updating the MIB to include annoucements file transfer support using SCP protocol.
-- 	a. Announcements file will be presented in Module ID == 9.
--  b. Adding the Values uploadAnnouncements(18), downloadAnnouncements(19), and
--     renameFile(20) to avGenOpIndex.
--  c. New Errors use for with announcement files:
--    	readOnlyFile(15) - For cases where management system tries to erase/delete file
-- 			which is read-only.   
-- 		emptyFile(16) - When trying to erase/upload file that does not exists or size with size 0.
--      noEnoughFreeMemoryLeft(17) - When trying to download a file to the device and there is 
--			no place left to it. 
-- 		fileAlreadyExistsInDirectory(18) - when trying to download file which already exists
--			in the directory (in one of the other AvGenAppFileTable rows, if we want to update 
-- 			it we need to use the same row in the table).
--	d. Adding new type of announcementFile(20) to avGenAppFileType.
--  e. The field avGenAppFileSize is used as R/O instead of read-create.
--  f. Adding note to AvGenAppFileRowStatus - destroy(6) value that Used to delete Applications
--	 	in the system. Used only for destroying rows will file size 0. 
--		i.e. erase shall be done in operation mib and then destroy the row.
-- 2. Adding avGenLoadConnectionState for the SAT Connection status under new branch 
--    avLoadGeneralInformation. I.e. for cases where the agent
--    must log into the CM server via SAT connection to collect the data. The agent retrieves the 
--    data via the SAT and converts it into SNMP MIB data which is accessible via standard SNMP get 
--    commands. 
-- 3. Using renameAnnouncement(20) and eraseAnnouncement(21) enumerations in avGenOpIndex 
--    instead of renameFile(20) and eraseFile(9).
--    
--
-- Version 200501261842Z - Shlomi Biton.
-- 1. Adding avGenOpLastFailureIndex and avGenOpLastFailureDisplay as part of the varbind
-- to avDownloadFault and avUploadFault.
--
-- Version 200501170822Z - Shlomi Biton.
-- 1. The avGenAppFileVersionNumber was changed to be DisplayString instead of OCTET STRING. In
--    order to solve the presentation problem of this firmware version in the Lucent Load MIB. 
-- 2. Add the notification section for download/upload events.
--    a. Use a new list of varbind of: avLoadSysDescription, avGenOpModuleId , avGenAppFileId, 
--    avGenAppFileName, avGenAppFileDescription, avGenAppFileVersionNumber
-- 	  b. Add the varbind avLoadSeverity for the trap severity.
--    c. Use general traps for upload/download instead of specific trap for each type of software. 
-- 3. Add the following new mib items:
--    a. The avGenOpDownloadProxy is the location of a CLAN board that will serve as the proxy for 
--    the firmware download of a TDM-based board, since these boards are unable to perform the 
--    download operation themselves. The CLAN will be responsible for obtaining the image.
--    b. The avGenAppFilePortNetwork is the Port Network that a downloadable TN board is location 
--    in. This is useful to the customer in determining the Download Proxy, since location is a 
--    factor in determining whether a download is possible. This will represent the possible Port 
--    Networks of 1 through 64.
--    c. The avGenAppFileDuplStatus is the duplication state of the various TN boards that can be 
--    duplicated. These include the IPSI and Crossfire boards. This is also useful to the customer 
--    in order for them to determine whether a board is active or not. Typical operation is to 
--    update the firmware on the standbys first, then have the standbys become active, followed by 
--    updating the firmware on the standbys that were orginially active. This will help the customer 
--    see if they are selecting an active board for upgrading.
-- 4. Adding two new states to avGenOpRunningState:
--    a. blocked(8) - to be used when the Load MIB agent is unable to perform a requested operation,
--    this could happen in CM if a firmware download job was submitted directly from the SAT. Since 
--    CM only accepts one job at a time, the Load MIB agent will be blocked until that job completes.
--    b. reset(9) - to be used to request a reset only of a TN board, this capability is a existing 
--    capability in Software Update Manager that we want to support directly in the Load MIB.

		AvLoadItuPerceivedSeverity ::= TEXTUAL-CONVENTION
       		STATUS current
       		DESCRIPTION
            		"ITU perceived severity values"
       		REFERENCE
            "ITU Recommendation M.3100, 'Generic Network Information
               Model', 1995
               ITU Recommendation X.733, 'Information Technology - Open
               Systems Interconnection - System Management: Alarm
               Reporting Function', 1992"
       		SYNTAX         INTEGER
              	{
              	cleared (1),
              	indeterminate (2),
              	critical (3),
              	major (4),
              	minor (5),
              	warning (6)
              	}   


		avLoadNotification OBJECT IDENTIFIER ::= { avLoad 0 }

        avDownloadBegun	NOTIFICATION-TYPE
			OBJECTS   {avLoadSysDescription, avGenOpModuleId , avGenAppFileId, avGenAppFileName, 
			avGenAppFileDescription, avGenAppFileVersionNumber, avLoadSeverity } 
			STATUS      current
			DESCRIPTION
			"The device has begun download operation."
		::= { avLoadNotification 1 }

		avDownloadSuccess	NOTIFICATION-TYPE
			OBJECTS   { avLoadSysDescription, avGenOpModuleId , avGenAppFileId, avGenAppFileName, 
			avGenAppFileDescription, avGenAppFileVersionNumber, avLoadSeverity } 
			STATUS      current
			DESCRIPTION
			"The device has completed successful download operation."
		::= { avLoadNotification 2 }

		avDownloadFault	NOTIFICATION-TYPE
			OBJECTS   { avLoadSysDescription, avGenOpModuleId , avGenAppFileId, avGenAppFileName, 
			avGenAppFileDescription, avGenAppFileVersionNumber, avGenOpLastFailureIndex ,
			avGenOpLastFailureDisplay, avLoadSeverity }
			STATUS      current
			DESCRIPTION
			"The download operation was failed."
		::= { avLoadNotification 3 }                                          

        avUploadBegun	NOTIFICATION-TYPE
			OBJECTS   {avLoadSysDescription, avGenOpModuleId , avGenAppFileId, avGenAppFileName, 
			avGenAppFileDescription, avGenAppFileVersionNumber, avLoadSeverity } 
			STATUS      current
			DESCRIPTION
			"The device has begun download operation."
		::= { avLoadNotification 4 }

		avUploadSuccess	NOTIFICATION-TYPE
			OBJECTS   { avLoadSysDescription, avGenOpModuleId , avGenAppFileId, avGenAppFileName, 
			avGenAppFileDescription, avGenAppFileVersionNumber, avLoadSeverity } 
			STATUS      current
			DESCRIPTION
			"The device has completed successful download operation."
		::= { avLoadNotification 5 }

		avUploadFault	NOTIFICATION-TYPE
			OBJECTS   { avLoadSysDescription, avGenOpModuleId , avGenAppFileId, avGenAppFileName, 
			avGenAppFileDescription, avGenAppFileVersionNumber, avGenOpLastFailureIndex ,
			avGenOpLastFailureDisplay, avLoadSeverity }
			STATUS      current
			DESCRIPTION
			"The download operation was failed."
		::= { avLoadNotification 6 }
	
--     Groups in the Load mib
        avGenOperations OBJECT IDENTIFIER ::= { avLoad 1 }
        
--     The avGenOperations group
-- 
        avGenLoadNumberOfSession OBJECT-TYPE
            SYNTAX Integer32
            MAX-ACCESS read-only
            STATUS current
            DESCRIPTION
                "The number of operational sessions in progress in this system"
            ::= { avGenOperations 1 }

        avGenOpTable OBJECT-TYPE
            SYNTAX SEQUENCE OF AvGenOpEntry
            MAX-ACCESS not-accessible
            STATUS current
            DESCRIPTION
                "Table of configuration attributes which define the operational 
                functions and the results on a per module basis.  This group provides
                the mechanism by which available operations are initiated, monitored 
                and reported."
            ::= { avGenOperations 2 }
        
        avGenOpEntry OBJECT-TYPE
            SYNTAX AvGenOpEntry
            MAX-ACCESS not-accessible
            STATUS current
            DESCRIPTION
                "An entry in the table, containing data about a single modules 
                operations."
            INDEX { avGenOpModuleId, avGenOpIndex }
            ::= { avGenOpTable 1 }
        
        AvGenOpEntry ::=
            SEQUENCE { 
                avGenOpModuleId
                    INTEGER,
                avGenOpIndex
                    INTEGER,
                avGenOpRunningState
                    INTEGER,
                avGenOpSourceIndex
                    Integer32,
                avGenOpDestIndex
                    Integer32,
                avGenOpServerIP
                    IpAddress,
                avGenOpUserName
                    DisplayString,
                avGenOpPassword
                    OCTET STRING,
                avGenOpProtocolType
                    INTEGER,
                avGenOpFileName
                    DisplayString,
                avGenOpRunningStateDisplay
                    DisplayString,
                avGenOpLastFailureIndex
                    INTEGER,
                avGenOpLastFailureDisplay
                    DisplayString,
                avGenOpLastWarningDisplay
                    DisplayString,
                avGenOpErrorLogIndex
                    Integer32,
                avGenOpResetSupported
                    INTEGER,
                avGenOpEnableReset
                    INTEGER,
                avGenOpNextBootImageIndex
                    Integer32,
                avGenOpLastBootImageIndex
                    Integer32,
                avGenOpFileSystemType
                    INTEGER,
                avGenOpReportSpecificFlags
                    INTEGER,
                avGenOpOctetsReceived
                    Integer32,
                avGenOpDownloadProxy
                	Integer32
                   }

        avGenOpModuleId OBJECT-TYPE
            SYNTAX INTEGER (1..255)
            MAX-ACCESS read-only
            STATUS current
            DESCRIPTION
                "Index which identifies the module inside the chassis for which this
                entry contains information. Equals the number of the slot by which
                the group is accessed or the stackable index.
                Announcements file will be presented in Module ID == 9.
                "
            ::= { avGenOpEntry 1 }
        
        avGenOpIndex OBJECT-TYPE
            SYNTAX INTEGER
                {
                uploadConfig(1),
                downloadConfig(2),
                report(3),
                uploadSoftware(4),
                downloadSoftware(5),
                localConfigFileCopy(6),
                localSWFileCopy(7),
                uploadLogfile(8),
                eraseFile(9),
                show(10),
                syncStandbyAgent(11),
                downloadAuthFile(12),
                downloadLicFile(13),
                downloadPhoneScriptFile(14),
                uploadPhoneScriptFile(15),
                downloadPhoneImageFile(16),
                uploadDhcpBindingFile(17),
                uploadAnnouncements(18),
                downloadAnnouncements(19),
                renameAnnouncement(20),
                eraseAnnouncement(21),
                uploadAuthFile(22),  	-- Reserved for LOAD-MIB
                uploadLicFile(23),      -- Reserved for LOAD-MIB
                uploadSyslogFile(24),	-- Reserved for LOAD-MIB
                uploadCDRFile(25),		-- Reserved for LOAD-MIB
                backupConfig(28),
                restore(29),
                commit(30), 
                uploadServicePack(31),
                downloadServicePack(32),
                localServicePackFileCopy(33),
                backup(34),
                generateFile(35),
                downloadCertificate(36),
                uploadCertificate(37),
                switchPartitions(38),
				uploadPhoneImageFile(39),
				downloadVoiceMailFile(40),
				uploadVoiceMailFile(41),
				downloadPhoneMessageFile(42),
				uploadPhoneMessageFile(43),
				downloadConfigurationWizardTaskFile(44),
				uploadConfigurationWizardTaskFile(45),
				localSWFileMove(46),
				localVoiceMailFileMove(47),
				reset(48)
                }
            MAX-ACCESS read-only
            STATUS current
            DESCRIPTION
                "Index to identify the operation supported by this row entry. 
                Each operation type that is supported by this module should be 
                represented by a unique row in this MIB Table.  A walk of this 
                MIB table should reveal all the operations that are supported by 
                the device.
                
                The operations supported are:
                
                uploadConfig -- 
                    The 'avGenOpDestIndex' should be set to 0 (to indicate destination
                        of server).
                    The 'avGenOpServerIP' should be set to the server to which the
                        config will be saved.
                    The 'avGenOpProtocolType' should be set to the IP protocol used
                        to transport the file.
                    The 'avGenOpSourceIndex' should be set to the 'avGenAppFileId'
                        of the config file you are uploading.
                    The 'avGenOpFileName' should be set to the name and path of the
                               config file on the TFTP server.
                
                downloadConfig --
                    The 'avGenOpDestIndex' should be set to the 'avGenAppFileId' of
                        the config file you are downloading to (if one does not
                        exist, you'll need to RowCreate it in the 'avGenAppFileTable').
                    The 'avGenOpServerIP' should be set to the server from which the
                        config will be copied.
                    The 'avGenOpProtocolType' should be set to the IP protocol used
                        to transport the file.
                    The 'avGenOpSourceIndex' should be set to 0 (to indicate source
                        of server).
                    The 'avGenOpFileName' should be set to the name and path of the
                               config file on the TFTP server.
                
                report --
                
                uploadSoftware -- 
                    The 'avGenOpDestIndex' should be set to 0 (to indicate destination
                         of server).
                    The 'avGenOpServerIP' should be set to the server to which the
                        config file will be saved.
                    The 'avGenOpProtocolType' should be set to the IP protocol used
                         to transport the file.
                    The 'avGenOpSourceIndex' should be set to the 'avGenAppFileId' of
                               the software file you are uploading.
                    The 'avGenOpFileName' should be set to the name and path of the
                               image file on the TFTP server.
                
                downloadSoftware --
                    The 'avGenOpDestIndex' should be set to the 'avGenAppFileId' of
                               the software file you are downloading to (if one does not
                               exist, you'll need to RowCreate it in the 'avGenAppFileTable').
                    The 'avGenOpServerIP' should be set to the server from which the
                               config file will be copied.
                    The 'avGenOpProtocolType' should be set to the IP protocol used
                               to transport the file.
                    The 'avGenOpSourceIndex' should be set to 0 (to indicate source
                               of server).
                    The 'avGenOpFileName' should be set to the name and path of the
                               image file on the TFTP server.
                
                localConfigFileCopy -- (using a 'avGenOpType' of 'localPeerTransport')
                    The 'avGenOpDestIndex' should be set to the 'avGenAppFileId' of the
                        config file you are copying to (if one does not exist
                        you'll need to RowCreate it in the 'avGenAppFileTable').
                    The 'avGenOpSourceIndex' should be set to the 'avGenAppFileId'
                               of the config file you are copying from.
                    The 'avGenOpServerIP' should be set to NULL.
                    The 'avGenOpProtocolType' should be set to 'localPeerTransport'.
                    The 'avGenOpFileName' should be set to NULL.
                
                localSWFileCopy -- (using a 'avGenOpType' of 'localPeerTransport')
                    The 'avGenOpDestIndex' should be set to the 'avGenAppFileId' of
                               the software file you are copying to (if one does not
                        exist you'll need to RowCreate it in the 'avGenAppFileTable').
                    The 'avGenOpSourceIndex' should be set to the 'avGenAppFileId' of
                               the software file you are copying from.
                    The 'avGenOpServerIP' should be set to NULL.
                    The 'avGenOpProtocolType' should be set to 'localPeerTransport'.
                    The 'avGenOpFileName' should be set to NULL.
                
                localConfigFileCopy -- (using a 'avGenOpType' of 'localServerTransport')
                    The 'avGenOpDestIndex' should be set to the 'avGenAppFileId' of the
                        config file you are copying to (if one does not exist you'll
                        need to RowCreate it in the 'avGenAppFileTable') or ZERO (0)
                        if copying to a localServer.
                    The 'avGenOpSourceIndex' should be set to the 'avGenAppFileId' of
                        the config file you are copying from or ZERO (0) if
                        copying from a localServer.
                    The 'avGenOpServerIP' should be set to the address of the local
                         server.
                    The 'avGenOpProtocolType' should be set to 'localServerTransport'.
                
                localSWFileCopy -- (using a 'avGenOpType' of 'localServerTransport')
                    The 'avGenOpDestIndex' should be set to the 'avGenAppFileId' of the
                               software file you are copying to (if one does not exist
                        you'll need to RowCreate it in the 'avGenAppFileTable').
                    The 'avGenOpSourceIndex' should be set to the 'avGenAppFileId'
                        of the software file you are copying from.
                    The 'avGenOpServerIP' should be set to the address of the local
                        server.
                    The 'avGenOpProtocolType' should be set to 'localServerTransport'.
                
                uploadLogfile --
                    The 'avGenOpDestIndex' should be set to 0 (to indicate destination
                               of server).
                    The 'avGenOpSourceIndex' should be set to the 'avGenAppFileId' of
                        the log file you are copying from.
                    The 'avGenOpServerIP' should be set to the server to which the
                        config will be saved.
                    The 'avGenOpProtocolType' should be set to the IP protocol used
                        to transport the file.
                    The 'avGenOpFileName' should be set to the name and path of the
                               log file on the TFTP server.
                
                eraseFile --
                    The 'avGenOpDestIndex' Is not applicable for this command.
                    The 'avGenOpSourceIndex' should be set to the 'avGenAppFileId'
                        of the file you wish to erase.
                    The 'avGenOpServerIP' should be set to 0.
                    The 'avGenOpProtocolType' should be set to 0.	
                    The 'avGenOpFileName' should be set to NULL.
                
                show -- 
                    Reporting information to the CLI.
                syncStandbyAgent(11) -- copy configuration AND software image files
                           to the (non-active) standby agent in a P550/P880.
                    The 'avGenOpDestIndex' should be set to 1
                    The 'avGenOpSourceIndex' should be set to 1
                    The 'avGenOpServerIP' should be set to NULL.
                    The 'avGenOpProtocolType' should be set to 'localPeerTransport'.
                    The 'avGenOpFileName' should be set to NULL.                     
                    
                downloadAuthFile (12) --  copy Services Logins authentication file to the
                                          device. 
                    The 'avGenOpDestIndex' should be set to the 'avGenAppFileId' of
                        the auth file you are downloading to (if one does not
                        exist, you'll need to RowCreate it in the 'avGenAppFileTable').
                    The 'avGenOpServerIP' should be set to the server from which the
                        config will be copied.
                    The 'avGenOpProtocolType' should be set to the IP protocol used
                        to transport the file.
                    The 'avGenOpSourceIndex' should be set to 0 (to indicate source
                        of server).
                    The 'avGenOpFileName' should be set to the name and path of the
                               config file on the TFTP/ftp/scp server.
                
                downloadLicFile (13) - --  copy SLicense file to the device. 
                
                    The 'avGenOpDestIndex' should be set to the 'avGenAppFileId' of
                        the auth file you are downloading to (if one does not
                        exist, you'll need to RowCreate it in the 'avGenAppFileTable').
                    The 'avGenOpServerIP' should be set to the server from which the
                        config will be copied.
                    The 'avGenOpProtocolType' should be set to the IP protocol used
                        to transport the file.
                    The 'avGenOpSourceIndex' should be set to 0 (to indicate source
                        of server).
                    The 'avGenOpFileName' should be set to the name and path of the
                               config file on the TFTP/ftp/scp server. 
                               
                downloadPhoneScriptFile (14) - copy IP phone configuration file 
                (or other endpoints configuration files) to the 
                device TFTP Server directory. IP Phone configuration file includes 
                Setting File and Upgrade Script. Non Volatile Storage.
                
                    The 'avGenOpDestIndex' should be set to the 'avGenAppFileId' of
                        the phone configuration file you are downloading to (if one does not
                        exist, you'll need to RowCreate it in the 'avGenAppFileTable').
                    The 'avGenOpServerIP' should be set to the server from which the
                        config will be copied.
                    The 'avGenOpProtocolType' should be set to the IP protocol used
                        to transport the file.
                    The 'avGenOpSourceIndex' should be set to 0 (to indicate source
                        of server).
                    The 'avGenOpFileName' should be set to the name and path of the
                               config file on the TFTP/ftp/scp server. 
                               
                uploadPhoneScriptFile(15) - copy IP phone configuration file 
                	(or other endpoints configuration files) from the device 
                	TFTP Server directory to remote server.
                IP Phone configuration file	includes Setting File and Upgrade Script.
                    The 'avGenOpDestIndex' should be set to 0 (to indicate destination
                        of server).
                    The 'avGenOpServerIP' should be set to the server to which the
                        config will be saved.
                    The 'avGenOpProtocolType' should be set to the IP protocol used
                        to transport the file.
                    The 'avGenOpSourceIndex' should be set to the 'avGenAppFileId'
                        of the config file you are uploading.
                    The 'avGenOpFileName' should be set to the name and path of the
                               config file on the TFTP/ftp/scp server.
                
                downloadPhoneImageFile(16) - copy IP phone images file (or other endpoints images files)
                	to the device TFTP Server Directory. Volatile Storage. 
                    The 'avGenOpDestIndex' should be set to the 'avGenAppFileId' of
                               the software file you are downloading to (if one does not
                               exist, you'll need to RowCreate it in the 'avGenAppFileTable').
                    The 'avGenOpServerIP' should be set to the server from which the
                               config file will be copied.
                    The 'avGenOpProtocolType' should be set to the IP protocol used
                               to transport the file.
                    The 'avGenOpSourceIndex' should be set to 0 (to indicate source
                               of server).
                    The 'avGenOpFileName' should be set to the name and path of the
                               image file on the TFTP/ftp server.
                
                uploadDhcpBindingFile(17) - copy DHCP Binding File from the device to remote server.  
                The binding file includes information of IP , MAC couples and leased time. 
                Non Volatile Storage.
                The 'avGenOpDestIndex' should be set to 0 (to indicate destination
                        of server).
                    The 'avGenOpServerIP' should be set to the server to which the
                        config will be saved.
                    The 'avGenOpProtocolType' should be set to the IP protocol used
                        to transport the file.
                    The 'avGenOpSourceIndex' should be set to the 'avGenAppFileId'
                        of the config file you are uploading.
                    The 'avGenOpFileName' should be set to the name and path of the
                               config file on the TFTP/ftp/scp server.
                
                uploadAnnouncements(18) - copy announcements files from the device to remote server.  
                The announcements files are stored in Non Volatile Storage.
                The 'avGenOpDestIndex' should be set to 0 (to indicate destination 
                        of server).
                The 'avGenOpServerIP' should be set to the server to which the 
                		announcement file will be saved.
                The 'avGenOpProtocolType' should be set to the IP protocol used 
                		to transport the file. 
                The 'avGenOpSourceIndex' should be set to the 'avGenAppFileId' of the announcement 
                		file you are uploading.
                The 'avGenOpFileName' should be set to the name and path of the 
                		announcement file on the remote server.
                
                downloadAnnouncements(19)- copy announcement file to the device from remote server.
                The 'avGenOpDestIndex' should be set to the 'avGenAppFileId' of 
                	the software file you are downloading to (if one does not exist, 
                	you'll need to RowCreate it in the 'avGenAppFileTable').
                The 'avGenOpServerIP' should be set to the server from which the 
                	announcement file will be copied.
                The 'avGenOpProtocolType' should be set to the IP protocol used to 
                	transport the file. 
                The 'avGenOpSourceIndex' should be set to 0 (to indicate source of server).
                The 'avGenOpFileName' should be set to the name and path of the 
                	announcement file on the remote server.
                
                renameFile(20) - Rename announcement file name on the local device.  
                The 'avGenOpDestIndex' is not applicable for this command. 
                The 'avGenOpSourceIndex' should be set to the 'avGenAppFileId' of the 
                	software file you are renaming.
                The 'avGenOpServerIP' should be set to 0.
                The 'avGenOpProtocolType' should be set to 'localPeerTransport'.
                The 'avGenOpFileName' should be set to the new name.
                
                
                Commit --
                   The 'avGenOpDestIndex' Is not applicable for this command.
                    The 'avGenOpSourceIndex' should be set to the 'avGenAppFileId'
                        of the file you wish to commit.
                    The 'avGenOpServerIP' should be set to 0.
                    The 'avGenOpProtocolType' should be set to 0.	
                    The 'avGenOpFileName' should be set to NULL. 
                    
                reset(48) --
                   The 'avGenOpDestIndex' Is not applicable for this command.
                    The 'avGenOpSourceIndex' Is not applicable for this command.
                    The 'avGenOpServerIP' should be set to 0.
                    The 'avGenOpProtocolType' should be set to 0.	
                    The 'avGenOpFileName' should be set to NULL.
                "
            ::= { avGenOpEntry 2 }
        
        avGenOpRunningState OBJECT-TYPE
            SYNTAX INTEGER
                {
                idle(1),
                beginOperation(2),
                waitingIp(3),
                runningIp(4),
                copyingLocal(5),
                readingConfiguration(6),
                executing(7),
                blocked(8),
                reset(9)
                }
            MAX-ACCESS read-write
            STATUS current
            DESCRIPTION
                "Identifies the operation to perform and the state of that operation.
                This field acts as both the trigger to initiate the operation (via
                the beginOperation) and the status field of the operation itself 
                (i.e. waiting-ip, running-ip, etc.).  It is expected that all 
                dependent MIB objects will be set before the trigger is set to
                beginOperation. The operations completion is triggered by the 
                return to the idle state.
                
                idle(1), - Operation not in progress
                beginOperation(2), - Trigger by NMS to start the operation
                waitingIp(3), - Communication phase; waiting for response
                runningIp(4), - Communication phase; transferring data
                copyingLocal(5), - Local operation
                readingConfiguration(6), - Parsing / Executing configuration file
                executing(7) - Executing Command (such as erasing a file or reporting)
                blocked(8) - to be used when the Load MIB agent is unable to perform a requested operation, 
                this could happen in CM if a firmware download job was submitted directly from the 
                SAT. Since CM only accepts one job at a time, the Load MIB agent will be blocked 
                until that job completes.
                reset(9) - to be used to request a reset only of a TN board, this capability is a 
                existing capability in Software Update Manager that we want to support directly in 
                the Load MIB.
                "
            DEFVAL { idle }
            ::= { avGenOpEntry 3 }
        
        avGenOpSourceIndex OBJECT-TYPE
            SYNTAX Integer32
            MAX-ACCESS read-write
            STATUS current
            DESCRIPTION
                "The index value (taken from the avGenAppFileTable) of the source of
                the operation.	NOTE: A value of zero (0) here indicates that the
                Server (specified below) is the	source."
            ::= { avGenOpEntry 4 }
        
        avGenOpDestIndex OBJECT-TYPE
            SYNTAX Integer32
            MAX-ACCESS read-write
            STATUS current
            DESCRIPTION
                "The index value (taken from the avGenAppFileTable) of the destination
                of the operation.  NOTE: A value of zero (0) here indicates that 
                the Server (specified below) is the Destination."
            ::= { avGenOpEntry 5 }
        
        avGenOpServerIP OBJECT-TYPE
            SYNTAX IpAddress
            MAX-ACCESS read-write
            STATUS current
            DESCRIPTION
                "The IP Address of the server from/to which the file has to be
                Download/Upload.  NOTE: In the case of localPeerTransport this
                value should be NULL."
            ::= { avGenOpEntry 6 }
        
        avGenOpUserName OBJECT-TYPE
            SYNTAX DisplayString (SIZE (0..128))
            MAX-ACCESS read-write
            STATUS current
            DESCRIPTION
                "Contains the username to be used if the protocol specified in
                avGenOpProtocolType requires one. The default value will be the
                empty string"
            DEFVAL { '00'h }
            ::= { avGenOpEntry 7 }
        
        avGenOpPassword OBJECT-TYPE
            SYNTAX OCTET STRING (SIZE (0..128))
            MAX-ACCESS read-write
            STATUS current
            DESCRIPTION
                "Contains the password to be used if the protocol specified in
                avGenOpProtocolType requires one. The default value will be the
                empty string"
            DEFVAL { '00'h }
            ::= { avGenOpEntry 8 }
        
        avGenOpProtocolType OBJECT-TYPE
            SYNTAX INTEGER
                {
                tftp(1),
                ftp(2),
                localPeerTransport(3),
                localServerTransport(4),
                scp(5),
                sftp(6),
                usb(7),
                http(8),
                https(9),
                ftpResume(10)
                }
            MAX-ACCESS read-write
            STATUS current
            DESCRIPTION
                "Identifies the protocol between the management station and the
                device for Download/Upload of the file."
            ::= { avGenOpEntry 9 }
        
        avGenOpFileName OBJECT-TYPE
            SYNTAX DisplayString
            MAX-ACCESS read-write
            STATUS current
            DESCRIPTION
                "The location (including the FULL path) of the file in the server.
                NOTE: In the case of localPeerTransport this value should be NULL.
                
                In case of genOpProtocolType==usb(7) the file name shall include 
                the prefix of the usbdevice/file system as follows: 
                /usbdevice0-127/backupdirectory/backupsubdirectory/filename. 
                An example can be: 
                /usbdevice0/backupg350/IPPHONE/46xx_settings.txt.
                
                If there is only one usb mass storage device connected to the gateway then
                use /usbdevice0/ to copy from/to this device files. 
                "
            ::= { avGenOpEntry 10 }
        
        avGenOpRunningStateDisplay OBJECT-TYPE
            SYNTAX DisplayString (SIZE (0..64))
            MAX-ACCESS read-only
            STATUS current
            DESCRIPTION
                "The state of the operation for Display on the terminal during
                operation process."
            ::= { avGenOpEntry 11 }
        
        avGenOpLastFailureIndex OBJECT-TYPE
            SYNTAX INTEGER
                {
                noError(1),
                genError(2),
                configError(3),
                busy(4),
                timeout(5),
                cancelled(6),
                incompatibleFile(7),
                fileTooBig(8),
                protocolError(9),
                flashWriteError(10),
                nvramWriteError(11),
                confFileGenErr(12),
                confFileParseError(13),
                confFileExecError(14),
                readOnlyFile(15),
                emptyFile(16),
                noEnoughFreeMemoryLeft(17),
                undefinedError(100),
                fileNotFound(101),
                accessViolation(102),
                outOfMemory(103),
                illegalOperation(104),
                unknownTransferId(105),
                fileAlreadyExists(106),
                noSuchUser(107),
                sshServerAuth(108),
                sshDeviceAuth(109),
                badChainOfTrust(201),
                badChainOfTrustFormat (202),
                notCodeSigningAuthority (203),
                illegalDSA (204),
                badPublicKeyFormat(205),
                illegalDSKeySize(206),
                badDSFormat(207),
                authDSFailure(208),
                configFileSecretIntegrityFault(210),
                ftpResumeBadFilename(220), -- In case of download a file using 
										   -- ftp_resume, and there is a partial/full 
										   -- file with different name in the same location. 
				ftpResumeEmptyFile(221),   -- In case of download a file using 
										   -- ftp_resume, and there is NO file at all to 
										   -- resume.
                ftpResumeNotSupported(222) -- In case of download a file using 
											-- ftp_resume, and the FTP server does not 
											-- support FTP resume.
              }
            MAX-ACCESS read-only
            STATUS current
            DESCRIPTION
                "While a download is in progress this will 
                always be 'no-error'.  After a download is complete 
                this indicates the success or failure of the download.
                If it is anything other than 'no-error' then 
                'avGenOpLastFailureDisplay' will contain a textual 
                description of the error.  Error codes from 100 
                upwards are errors returned from a TFTP server.  
                errors below this are locally generated.
                
                Configuration files may return errors after download
                as a result of reading a config file into the system.
                
                confFileGenErr     - General (unknown error)
                confFileParseError - Reading of config file resulted in 
                		     parsing errors.
                confFileExecError  - Reading of config file resulted in
                		     execution errors.
                sshServerAuth      - SCP server failed to authenticated himself 
                                            to a device.
                sshDeviceAuth(109)- device failed to authenticate to the SCP server 
                                            (unknown user/bad password)
                badChainOfTrust(201) - Failed to authenticate the download with Trusted 
                                       Certificate Root Authority
                badChainOfTrustFormat (202) - Not supported chain of trust format	
                notCodeSigningAuthority (203) Software image was signed by non-authorized 
                                              Certificate Authority
                illegalDSA (204) - Software image is signed with non FIPS 140-2 
                                   certified algorithm	 
                badPublicKeyFormat(205) - Not supported public key format.	
                illegalDSKeySize(206) - Software image is signed with non FIPS 140-2 
                                        certified key size
                badDSFormat(207) - Not supported digital signature format	
                authDSFailure(208) - Failed to authenticate digital image signature
                
                New Errors use for with announcement files:
                readOnlyFile(15) - For cases where management system tries to erase/delete file
                which is read-only.   
                emptyFile(16) - When trying to erase/upload file that does not exists or size with size 0.
                noEnoughFreeMemoryLeft(17) - When trying to download a file to the device and there is no place 
                left to it. 
                fileAlreadyExistsInDirectory(18) - when trying to download file which already exists
                in the directory (in one of the other AvGenAppFileTable rows, if we want to update 
                it we need to use the same row in the table).
                "
            ::= { avGenOpEntry 12 }
        
        avGenOpLastFailureDisplay OBJECT-TYPE
            SYNTAX DisplayString (SIZE (0..255))
            MAX-ACCESS read-only
            STATUS current
            DESCRIPTION
                "Contains the last error, Null if there is no error."
            ::= { avGenOpEntry 13 }
        
        avGenOpLastWarningDisplay OBJECT-TYPE
            SYNTAX DisplayString (SIZE (0..255))
            MAX-ACCESS read-only
            STATUS current
            DESCRIPTION
                "Last warning which didn't stop the operation (not fatal error)."
            ::= { avGenOpEntry 14 }
        
        avGenOpErrorLogIndex OBJECT-TYPE
            SYNTAX Integer32
            MAX-ACCESS read-write
            STATUS current
            DESCRIPTION
                "The Index in the 'avGenAppFileTable' under which an error log has
                been created.  In the case of file that produce errors this file
                should contain a log of errors that occurred. (This item should
                be zero if it does not exist)"
            ::= { avGenOpEntry 15 }
        
        avGenOpResetSupported OBJECT-TYPE
            SYNTAX INTEGER
                {
                supported(1),
                notSupported(2)
                }
            MAX-ACCESS read-only
            STATUS current
            DESCRIPTION
                "Indicates if a reset (after operation completion) is supported by
                this Module."
            ::= { avGenOpEntry 16 }
        
        avGenOpEnableReset OBJECT-TYPE
            SYNTAX INTEGER
                {
                enable(1),
                disable(2)
                }
            MAX-ACCESS read-write
            STATUS current
            DESCRIPTION
                "Whether to do a reset after the operation completed successfully."
            ::= { avGenOpEntry 17 }
        
        avGenOpNextBootImageIndex OBJECT-TYPE
            SYNTAX Integer32
            MAX-ACCESS read-write
            STATUS current
            DESCRIPTION
                "The row in the 'avGenAppFileTable' of the default Application that
                the device will boot from when a standard reboot is performed."
            ::= { avGenOpEntry 18 }
        
        avGenOpLastBootImageIndex OBJECT-TYPE
            SYNTAX Integer32
            MAX-ACCESS read-only
            STATUS current
            DESCRIPTION
                "The Index in the 'avGenAppFileTable' of the default Application
                that the device	was last booted from."
            ::= { avGenOpEntry 19 }
        
        avGenOpFileSystemType OBJECT-TYPE
            SYNTAX INTEGER
                {
                static(1),
                dynamic(2)
                }
            MAX-ACCESS read-only
            STATUS current
            DESCRIPTION
                "Indicates what type of file system is supported by this module.
                A value of 'static' indicates that rows in the 'avGenAppFileTable'
                are not removable nor can new entries be created.  
                
                A value of 'dynamic' indicates that entries in the 'avGenAppFileTable'
                are both removable and can be created."
            ::= { avGenOpEntry 20 }
        
--     without OSPF database
        avGenOpReportSpecificFlags OBJECT-TYPE
            SYNTAX INTEGER
                {
                fullReport(1),
                partialReport(2),
                notSupported(255)
                }
            MAX-ACCESS read-write
            STATUS current
            DESCRIPTION
                "Contain modifiers to the Report operation.
                
                fullReport - Full configuration report
                partialReport - A report without the information stored
                                       in the OSPF database
                notSupported - For operations other than report, this MIB
                                      has no meaning and can return not Supported or
                                      not be supported."
            ::= { avGenOpEntry 21 }
        
        avGenOpOctetsReceived OBJECT-TYPE
            SYNTAX Integer32
            MAX-ACCESS read-only
            STATUS current
            DESCRIPTION
                "While a download is in progress this indicates the number
                of bytes transferred so far. "
            ::= { avGenOpEntry 22 }
        
        avGenOpDownloadProxy OBJECT-TYPE
            SYNTAX Integer32
            MAX-ACCESS read-write
            STATUS current
            DESCRIPTION
                "The avGenOpDownloadProxy is the location of a CLAN board that will serve as 
                the proxy for the firmware download of a TDM-based board, since these boards 
                are unable to perform the download operation themselves. The CLAN will be 
                responsible for obtaining the image.
                1 - any
                2 - self
                6657-413216 - Board location.
                Default value is 1."
            ::= { avGenOpEntry 23 }
        
        avGenApplications OBJECT IDENTIFIER ::= { avLoad 2 }
        
--     The avGenApplication Group
-- 
        avGenAppFileTable OBJECT-TYPE
            SYNTAX SEQUENCE OF AvGenAppFileEntry
            MAX-ACCESS not-accessible
            STATUS current
            DESCRIPTION
                "Table of Application (FILE) entries.  Each row uniquely defines
                an application in the system.  Applications can be defined as
                any entity that can be read or written from or to the system.
                This includes software images, boot code, configuration files,
                prom code, etc."
            ::= { avGenApplications 1 }
        
        avGenAppFileEntry OBJECT-TYPE
            SYNTAX AvGenAppFileEntry
            MAX-ACCESS not-accessible
            STATUS current
            DESCRIPTION
                "An entry in the table, containing data about a single application
                / config file."
            INDEX { avGenOpModuleId, avGenAppFileId }
            ::= { avGenAppFileTable 1 }
        
        AvGenAppFileEntry ::=
            SEQUENCE { 
                avGenAppFileId
                    INTEGER,
                avGenAppFileName
                    DisplayString,
                avGenAppFileType
                    INTEGER,
                avGenAppFileDescription
                    DisplayString,
                avGenAppFileSize
                    Integer32,
                avGenAppFileVersionNumber
                    DisplayString,
                avGenAppFileLocation
                    INTEGER,
                avGenAppFileDateStamp
                    DisplayString,
                avGenAppFileRowStatus
                    RowStatus,
                avGenAppFilePortNetwork
                	Integer32,
                avGenAppFileDuplStatus
                	INTEGER,
                avGenAppFileCompatibleVersionNumber    
                	DisplayString
             }      

        avGenAppFileId OBJECT-TYPE
            SYNTAX INTEGER (1..65535)
            MAX-ACCESS read-only
            STATUS current
            DESCRIPTION
                "Index which uniquely identifies the application. 
                NOTE: This index CANNOT BE ZERO (0) since the index of zero is
                reserved as an indication of network server location in the
                avGenOpSourceIndex and avGenOpDestIndex above.
                "
            ::= { avGenAppFileEntry 1 }
        
        avGenAppFileName OBJECT-TYPE
            SYNTAX DisplayString (SIZE (0..64))
            MAX-ACCESS read-create
            STATUS current
            DESCRIPTION
                "The name of the application."
            ::= { avGenAppFileEntry 2 }
        
        avGenAppFileType OBJECT-TYPE
            SYNTAX INTEGER
                {
                runningConfiguration(1),
                startupConfiguration(2),
                defaultConfiguration(3),
                report(4),
                genConfigFile(5),
                logFile(6),
                nvramFile(7),
                swRuntimeImage(8),
                swBootImage(9),
                swComponent(10),
                other(11),
                swWebImage(12),
                swAPImage(13),
                swNonDownLoadRunTimeImage(14),
                asgAuthFile(15),
                licenseFile(16),
                phoneScriptFile(17),
                phoneImageFile(18),
                dhcpBindingFile(19),
                announcementFile(20),
                backupDatabase(21),
                syslogFile(22),		-- Reserved for LOAD-MIB
				cdrFile(23),         -- Reserved for LOAD-MIB
				swRuntimeServicePack(24),
				swComponentServicePack(25),
				trustedCertificate(26),
				certificateRequest(27),
				serverCertificate(28),
				privateKey(29),
				staticLanguagePack(30),
				phoneAvayaUnicodeMessageFile(31),
				phoneCustomUnicodeMessageFile(32),
				startupConfigurationWizardTaskFile(33),
				genConfigurationWizardTaskFile(34)
              }
            MAX-ACCESS read-create
            STATUS current
            DESCRIPTION
                "The type (class) of the application. This class serves to catagorize
                the many application files in the system into some fixed types:
                
                runningConfiguration -- This entry represents a virtual file in
                        the system.  Use of this entry in the avGenOpTable should
                               serve to cause the system to generate it's configuration 
                        or to force the system to read a new config into it's
                               configuration.
                
                startupConfiguration -- This entry represents a real file that
                               is used at start-up to configure the device.
                
                defaultConfiguration -- This entry represents a file which contains
                        the default configuration of the device.
                
                report -- ??
                
                genConfigFile -- This entry represents a file which contains
                        configuration information (similar to the 
                               'startupConfiguration' above but is not automatically
                               read by the device.  This entry is used to represent
                               'alternate', 'backup' or 'experimental' configurations
                               that the user may which to store on the device.
                
                nvramFile -- This entry represents a file that is contain in the
                        nvram files system that does not fit any of the other
                               pre-defined types.
                
                swRuntimeImage -- This entry represents a software images that
                        contains operational code that is currently being used
                        to run the device.
                
                swBootImage -- This entry represents a software image that
                               contain operational code that is used to initally boot
                        the device.
                
                swComponent -- This entry represents a file that is stored as an
                        'alternate', 'backup' or 'experimental' version of 
                        operational code.
                
                other -- other 
                
                swWebImage -- The Image file of the embedded Web application
                               (java application, etc).
                
                swAPImage  -- the firmware of the Light AP. Device stores the image to 
                              support Light AP firmwareless operation. 
                              image boot service
                swNonDownLoadRunTimeImage - image of a non-downloadable code e.g.
                                                       a bootstrap code
                
                asgAuthFile   - encrypted Services Logins file  
                
                licenseFile   - file controlling licensed features activation
                
                phoneScriptFile(17) - Avaya IP Phone Configuration files 
                				(or other endpoints configuration files) as Setting file 
                				and Upgrade Script, Stored in device TFTP Server directory, 
                				Non Volatile Storage.
                
                phoneImageFile(18) - Avaya IP Phone Images files (or other endpoints images files),
                stored in device TFTP Server directory, Volatile Storage.
                
                dhcpBindingFile(19) - Device DHCP server IP binding file. Includes information about 
                bindings of IP to MAC and leased time.
                                                       
				announcementFile(20) - Announcement files.                                             
                "
            ::= { avGenAppFileEntry 3 }
        
        avGenAppFileDescription OBJECT-TYPE
            SYNTAX DisplayString (SIZE (0..64))
            MAX-ACCESS read-create
            STATUS current
            DESCRIPTION
                "A description of the application."
            ::= { avGenAppFileEntry 4 }
        
        avGenAppFileSize OBJECT-TYPE
            SYNTAX Integer32
            MAX-ACCESS read-only
            STATUS current
            DESCRIPTION
                "The size (expressed as the number of bytes) of the application."
            ::= { avGenAppFileEntry 5 }
        
        avGenAppFileVersionNumber OBJECT-TYPE
            SYNTAX DisplayString
            MAX-ACCESS read-only
            STATUS current
            DESCRIPTION
                "The current version of the application. If this file does not
                carry a version this field should be NULL.
                An example is a string of '24.6.0' for G350 software version."
            ::= { avGenAppFileEntry 6 }
        
        avGenAppFileLocation OBJECT-TYPE
            SYNTAX INTEGER
                {
                ram(1),
                flashBankA(2),
                flashBankB(3),
                nvram(4),
                bootProm(5),
                compactFlash(6),
                flash(7)
                }
            MAX-ACCESS read-create
            STATUS current
            DESCRIPTION
                "The physical location of the application."
            ::= { avGenAppFileEntry 7 }
        
        avGenAppFileDateStamp OBJECT-TYPE
            SYNTAX DisplayString (SIZE (0..64))
            MAX-ACCESS read-only
            STATUS current
            DESCRIPTION
                "The time stamp is the Real Time if supported otherwise sysUpTime.
                The convention for this field is as follows:
                
                Real Time: Entry is prefixed with an 'R' character and time is
                   formatted using the convention for date-and-time (rfc1903)
                
                   DISPLAY-HINT 'R-2d-1d-1d,1d:1d:1d.1d,1a1d:1d'
                
                           field  octets  contents                  range 
                           -----  ------  --------                  ----- 
                             1      1-2   year                      0..65536 
                             2       3    month                     1..12 
                             3       4    day                       1..31 
                             4       5    hour                      0..23 
                             5       6    minutes                   0..59 
                             6       7    seconds                   0..60 
                                          (use 60 for leap-second) 
                             7       8    deci-seconds              0..9 
                             8       9    direction from UTC        '+' / '-' 
                             9      10    hours from UTC            0..11 
                            10      11    minutes from UTC          0..59 
                
                           For example, Tuesday May 26, 1992 at 1:30:15 PM EDT would be 
                           displayed as: 
                
                                       R-1992-5-26,13:30:15.0,-4:0 
                
                           Note that if only local time is known, then timezone 
                           information (fields 8-10) is not present.
                
                SysUpTime: Entry is prefixed with an 'S' character and time is
                   formatted using a portion of that date-and-time convention
                
                   DISPLAY-HINT 'S-1d-1d,1d:1d:1d.1d'
                
                           field  octets  contents                  range 
                           -----  ------  --------                  ----- 
                             1       3    month                     1..12 
                             2       4    day                       1..31 
                             3       5    hour                      0..23 
                             4       6    minutes                   0..59 
                             5       7    seconds                   0..60 
                             6       8    deci-seconds              0..9 
                
                           For example,
                                            S-5-26,13:30:15.0
                
                    Represents a file that has existed in the system for 5 months, 
                    26 days, 13 hours, 30 minutes, 15 seconds exactly.  This value
                    will be reset after a reboot of the system."
            ::= { avGenAppFileEntry 8 }
        
        avGenAppFileRowStatus OBJECT-TYPE
            SYNTAX RowStatus
            MAX-ACCESS read-create
            STATUS current
            DESCRIPTION
                "The status of this entry in the table.  Note the available states:
                active(1), -- Fully configured and active.
                notInService(2) -- NOT SUPPORTED.
                notReady(3), -- Entry NOT FULLY configured.
                createAndGo(4), -- Used to add new Applications in the system. 
                createAndWait(5) -- Used to add new Applications in the system.   
                destroy(6) -- Used to delete Applications in the system. 
                	Used only for destroying rows will file size 0. i.e. 
                	erase shall be done in operation mib and then destroy the row.
                "
        ::= { avGenAppFileEntry 9 }

		
        avGenAppFilePortNetwork OBJECT-TYPE
            SYNTAX Integer32
            MAX-ACCESS read-only
            STATUS current
            DESCRIPTION
                "The avGenAppFilePortNetwork is the Port Network that a downloadable TN board is
                 location in. This is useful to the customer in determining the Download Proxy, 
                 since location is a factor in determining whether a download is possible. This 
                 will represent the possible Port Networks of 1 through 64.
                 Default is 1."
            ::= { avGenAppFileEntry 10 }

        avGenAppFileDuplStatus OBJECT-TYPE
            SYNTAX INTEGER
                {
                active(1),
                standby(2),
                not-administered(3)
                }
            MAX-ACCESS read-only
            STATUS current
            DESCRIPTION
                "The avGenAppFileDuplStatus is the duplication state of the various TN boards that
                 can be duplicated. These include the IPSI and Crossfire boards. This is also useful
                 to the customer in order for them to determine whether a board is active or not. 
                 Typical operation is to update the firmware on the standbys first, then have the 
                 standbys become active, followed by updating the firmware on the standbys that 
                 were originally active. This will help the customer see if they are selecting an 
                 active board for upgrading.
                 Default is standby(2)."
            DEFVAL { standby }
            ::= { avGenAppFileEntry 11 }
        
        avGenAppFileCompatibleVersionNumber OBJECT-TYPE
            SYNTAX DisplayString
            MAX-ACCESS read-only
            STATUS current
            DESCRIPTION
                "The compatability version relevant to other files on the system. 
                If the value is not needed then this field should be NULL.
                An example is a string of '18.1'. "
            ::= { avGenAppFileEntry 12 }
       
		avLoadNotificationDefinitions OBJECT IDENTIFIER ::= { avLoad 3 }
        
        avLoadSysDescription OBJECT-TYPE
            SYNTAX DisplayString
            MAX-ACCESS accessible-for-notify
            STATUS current
            DESCRIPTION
                "The system description."
            ::= { avLoadNotificationDefinitions 1 }
        
  		avLoadSeverity OBJECT-TYPE            
        	SYNTAX   AvLoadItuPerceivedSeverity
        	MAX-ACCESS accessible-for-notify
        	STATUS current            
        	DESCRIPTION
         	"The severity of the notification."
        	::= { avLoadNotificationDefinitions 2} 

		avLoadGeneralInformation OBJECT IDENTIFIER ::= { avLoad 4 }
    
      		avGenLoadConnectionState OBJECT-TYPE
        SYNTAX    INTEGER
  			{
			other(1), -- none of the following
			off(2), -- connection is disabled
			down(3), -- connection is down
			init(4), -- connection is initializing
			up(5), -- connection is up
			idle(6) -- connection is idle
  			}
        MAX-ACCESS    read-write
        STATUS    current
        DESCRIPTION
            "The SAT Connection status. For cases where the agent must log into the CM server via 
            a SAT connection to collect the data. The agent retrieves the data via the SAT and 
            converts it into SNMP MIB data which is accessible via standard SNMP get commands. 
            The current state of the switch connection; this object
            can be set to 'off' to disable the connection and can be
            set to 'init' to re-initialize the connection. It can also
    		be set to 'idle'.
            "
        ::= { avLoadGeneralInformation 1 }
        
        avGenRestoreOperationState OBJECT-TYPE
        SYNTAX    INTEGER
  			{
			idle(1), 
			executing(2)			
  			}
        MAX-ACCESS    read-only
        STATUS    current
        DESCRIPTION
            "The state of the restore operation. The state will be: idle(1) when no restore operation
            is activated. executing(2) when restore operation is activated, after restore reset
            until restore operation is finished and then the status changed to idle(1)."
        ::= { avLoadGeneralInformation 2 }

		avLoadApplMemTable OBJECT-TYPE
			SYNTAX SEQUENCE OF AvLoadApplMemEntry
			MAX-ACCESS not-accessible
			STATUS current
			DESCRIPTION
				"Table of different application types and their memory allocation in the RAM and NvRAM."
			::= { avLoad 5 }
	
		avLoadApplMemEntry OBJECT-TYPE
			SYNTAX AvLoadApplMemEntry
			MAX-ACCESS not-accessible
			STATUS current
			DESCRIPTION
				"An entry in the table, containing data about application and its memory type."
			INDEX { avLoadApplMemModuleId, avLoadApplMemLocation, avLoadApplMemType }
			::= { avLoadApplMemTable 1 }
		
		AvLoadApplMemEntry ::=
			SEQUENCE { 
				avLoadApplMemModuleId
					INTEGER,
				avLoadApplMemLocation
					INTEGER,            
				avLoadApplMemType
					INTEGER,
				avLoadApplMemSize
					INTEGER,	
				avLoadApplMemTotalBytesUsed
					INTEGER,
				avLoadApplMemTotalBytesFree
					INTEGER
				 }

		avLoadApplMemModuleId OBJECT-TYPE
			SYNTAX INTEGER 
			MAX-ACCESS read-only
			STATUS current
			DESCRIPTION
				"The module ID."
			::= { avLoadApplMemEntry 1 }
		
        avLoadApplMemLocation OBJECT-TYPE
			SYNTAX INTEGER   {
                ram(1),
                flashBankA(2),
                flashBankB(3),
                nvram(4),
                bootProm(5)
                }
			MAX-ACCESS read-only
			STATUS current
			DESCRIPTION
				"The Type of the memory that the the file is stored."
			::= { avLoadApplMemEntry 2 }
        
		avLoadApplMemType OBJECT-TYPE
			SYNTAX INTEGER {
				announcementFile(20)
                }
            MAX-ACCESS read-only
			STATUS current
			DESCRIPTION
				"The type of the application file."
			::= { avLoadApplMemEntry 3 }

         avLoadApplMemSize OBJECT-TYPE
			SYNTAX INTEGER 
			MAX-ACCESS read-write
			STATUS current
			DESCRIPTION
				"The size of the Memory in Bytes  for specific application and memory type."
			::= { avLoadApplMemEntry 4 }
			
			
			avLoadApplMemTotalBytesUsed OBJECT-TYPE
			SYNTAX INTEGER 
			MAX-ACCESS read-only
			STATUS current
			DESCRIPTION
				"Total Bytes used for the specific module/memory type and file type."
			::= { avLoadApplMemEntry 5 }
			
			
		 avLoadApplMemTotalBytesFree OBJECT-TYPE
			SYNTAX INTEGER 
			MAX-ACCESS read-only
			STATUS current
			DESCRIPTION
				"Total Bytes free for the specific module/memory type and file type."
			::= { avLoadApplMemEntry 6 }    


		avLoadAppDynamicFileTable OBJECT-TYPE
			SYNTAX SEQUENCE OF AvLoadAppDynamicFileEntry
			MAX-ACCESS not-accessible
			STATUS current
			DESCRIPTION
				"Table of dynamic applications.
				This MIB table can be used to show files on external USB mass storage device."
			::= { avLoad 6 }
	
		avLoadAppDynamicFileEntry OBJECT-TYPE
			SYNTAX AvLoadAppDynamicFileEntry
			MAX-ACCESS not-accessible
			STATUS current
			DESCRIPTION
				"An entry in the table, containing data about the application."
			INDEX { avLoadAppDynamicFileName }
			::= { avLoadAppDynamicFileTable 1 }
		
		AvLoadAppDynamicFileEntry ::=
			SEQUENCE { 
				avLoadAppDynamicFileName
					DisplayString,
				avLoadAppDynamicFileType
					INTEGER,            
				avLoadAppDynamicFileSize
					Integer32,
				avLoadAppDynamicFileDateStamp
					DisplayString,	
				avLoadAppDynamicFileRowStatus
					RowStatus
					}

		avLoadAppDynamicFileName OBJECT-TYPE
			SYNTAX DisplayString  (SIZE (0..255))
			MAX-ACCESS read-only
			STATUS current
			DESCRIPTION
				"The filename including file system, path and filename.
				An example: /usbdevice0/backup1/imageA.bin where 
				/usbdevice0/ is the file system of external usb mass storage device. 
				/backup1/ is directory and imageA.bin is the file. "
			::= { avLoadAppDynamicFileEntry 1 }
    
    
         avLoadAppDynamicFileType OBJECT-TYPE
			SYNTAX INTEGER   {
                file(1),
                directory(2)
                }			
            MAX-ACCESS read-only
			STATUS current
			DESCRIPTION
				"Type of the entry (file or directory)."
			::= { avLoadAppDynamicFileEntry 2 }


        avLoadAppDynamicFileSize OBJECT-TYPE
            SYNTAX Integer32
            MAX-ACCESS read-only
            STATUS current
            DESCRIPTION
                "The size (expressed as the number of bytes) of the file."
            ::= { avLoadAppDynamicFileEntry 3 }
    

		avLoadAppDynamicFileDateStamp OBJECT-TYPE
            SYNTAX DisplayString (SIZE (0..64))
            MAX-ACCESS read-only
            STATUS current
            DESCRIPTION
                "Time stamp of the file. Refer to avGenAppFileDateStamp syntax description."
            ::= { avLoadAppDynamicFileEntry 4 }

        avLoadAppDynamicFileRowStatus OBJECT-TYPE
            SYNTAX RowStatus
            MAX-ACCESS read-create
            STATUS current
            DESCRIPTION
                "The status of this entry in the table.  Note the available states:
                active(1), -- Fully configured and active.
                notInService(2) -- NOT SUPPORTED.
                notReady(3), -- Entry NOT FULLY configured. NOT SUPPORTED.
                createAndGo(4), -- Used to add new Applications in the system. NOT SUPPORTED.
                createAndWait(5) -- Used to add new Applications in the system. NOT SUPPORTED.   
                destroy(6) -- Used to delete Applications in the system.      
                
                If destroy(6) is used on directory then all the files/directories inside this
                directory are also deleted.
                "
        ::= { avLoadAppDynamicFileEntry 5 }

    
    END
