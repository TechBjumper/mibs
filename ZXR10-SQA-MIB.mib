--  ************************************************
--  $Id: rosng.mib 8 2010-04-06 16:13:00Z DingG $
--
--  rosngsqa.mib: ZXR10 SQA MIB file
--
--  Apr. 2010, DingG181824
--
--  Copyright(c) 2008 by ZTE Corporaton
--  All rights reservered
--
--  ************************************************ 
ZXR10-SQA-MIB DEFINITIONS ::= BEGIN

IMPORTS
   OBJECT-TYPE                    FROM SNMPv2-SMI  
   
   MODULE-IDENTITY                FROM SNMPv2-SMI
   
   enterprises                    FROM SNMPv2-SMI

   IpAddress                      FROM SNMPv2-SMI      

   Unsigned32                     FROM SNMPv2-SMI
   
   Integer32                      FROM SNMPv2-SMI

   TEXTUAL-CONVENTION             FROM SNMPv2-TC
   
   DisplayString                  FROM SNMPv2-TC
   
   MacAddress                     FROM SNMPv2-TC
   
   Counter64                      FROM SNMPv2-TC 
   
   RowStatus                     FROM SNMPv2-TC
   
   NOTIFICATION-TYPE             FROM SNMPv2-TC ;
 
sqaMib  MODULE-IDENTITY
    LAST-UPDATED "201611140000Z" --2016-11-14 00:00
    ORGANIZATION "ZTE Corp."
    CONTACT-INFO
        "ZTE Corporation 
         Nanjing Institute of ZTE Corporation
         
         No.68 Zijinghua Rd. Yuhuatai District, Nanjing, China
         
         Tel: +86-25-52870000"
    DESCRIPTION
        "ZXROS SMI MIB" 

    REVISION "201611280000Z" --2016-11-28 00:00
    DESCRIPTION
       "modif       sqaOperationTestNum
        modif       sqaTestOperation
        modif       sqaUdpTestTable
        modif       sqaUdpTestEntry
        modif       sqaUdpTestNum
        modif       sqaUdpTestRepeat
        modif       sqaUdpTestSize       
        modif       sqaUdpTestTos
        modif       sqaUdpTestInterval
        modif       sqaUdpJitterTestTable
        modif       sqaUdpJitterTestEntry
        modif       sqaUdpJitterTestNum
        modif       sqaUdpJitterTestRepeat
        modif       sqaUdpJitterTestSize        
        modif       sqaUdpJitterTestTos
        modif       sqaUdpJitterTestInterval
        modif       sqaIcmpTestTable
        modif       sqaIcmpTestEntry
        modif       sqaIcmpTestNum
        modif       sqaIcmpTestRepeat
        modif       sqaIcmpTestSize       
        modif       sqaIcmpTestTos
        modif       sqaIcmpTestTtl
        modif       sqaIcmpTestInterval
        modif       sqaIcmpTestDscp
        modif       sqaIcmpJitterTestTable
        modif       sqaIcmpJitterTestEntry
        modif       sqaIcmpJitterTestNum        
        modif       sqaIcmpJitterTestRepeat
        modif       sqaIcmpJitterTestSize
        modif       sqaIcmpJitterTestTos
        modif       sqaIcmpJitterTestTtl
        modif       sqaIcmpJitterTestInterval
        modif       sqaIcmpJitterTestDscp"

    REVISION "201611140000Z" --2016-11-14 00:00
    DESCRIPTION
       "add       TestOperation ::TEXTUAL-CONVENTION
        add       sqaTestOperationTable
        add       sqaUdpTestTable
        add       sqaUdpJitterTestTable
        add       sqaIcmpTestTable
        add       sqaIcmpJitterTestTable
        modif     sqaUdpServerGrp"
        
     REVISION "201509140000Z" --2015-09-14 00:00
    DESCRIPTION
        "modif     TpResultStatus
         modif     TestOnlineState
         modif     TestClientMode
         modif     sqaTestSenderClientMode
         modif     sqaTestSenderTestMode
         modif     sqaTestSenderDisNonTest8021p
         modif     sqaTestSenderDisNonTestDscp
         modif     sqaTestSenderReflectorMode
         modif     sqaTestSenderInVlanId
         modif     sqaTestSenderExVlanId
         modif     sqaTestSenderPriority8021p
         modif     sqaTestSenderDscp
         modif     sqaTestSenderTpEnable
         modif     sqaTestSenderTpRateType
         modif     sqaTestSenderTpHighRate
         modif     sqaTestSenderTpLowRate
         modif     sqaTestSenderTpTimeOut
         modif     sqaTestSenderTpOneRateDuration
         modif     sqaTestSenderTpDuration
         modif     sqaTestSenderTpPrecision
         modif     sqaTestSenderTpLossThreshold
         modif     sqaTestSenderLossRateType
         modif     sqaTestSenderLossRate
         modif     sqaTestSenderLossTimeOut
         modif     sqaTestSenderLossDuration
         modif     sqaTestSenderLossRatioThreshold
         modif     sqaTestSenderDelayRateType
         modif     sqaTestSenderDelayRate
         modif     sqaTestSenderDelayInterval
         modif     sqaTestSenderDelayDuration
         modif     sqaTestSenderDelayThreshold
         modif     sqaTestSenderPacketSize1
         modif     sqaTestSenderPacketSize2
         modif     sqaTestSenderPacketSize3
         modif     sqaTestSenderPacketSize4
         modif     sqaTestSenderPacketSize5
         modif     sqaTestSenderPacketSize6
         modif     sqaTestSenderPacketSize7
         modif     sqaTestSenderOnlineOfflineFlag
         modif     sqaTestSenderFreeArpInterval
         modif     sqaTestReflectorRefMode
         modif     sqaTestReflectorTestMode
         modif     sqaTestReflectorDisNonTest8021p
         modif     sqaTestReflectorDisNonTestDscp
         modif     sqaTestReflectorAgeingTime
         modif     sqaTestReflectorSourcePort
         modif     sqaTestReflectorDestinationPort
         modif     sqaTestReflectorPriority8021p
         modif     sqaTestReflectorDscp
         modif     sqaTestReflectorOnOfflineFlag
         modif     sqaTestReflectorFreeArpInterval
         modif     sqaTestTpResultPacketSize
         modif     sqaTestTpResultPrecision
         modif     sqaTestTpResultTp
         modif     sqaTestTpResultInfoRate
         modif     sqaTestTpResultLossRatio
         modif     sqaTestTpResultTestDuration
         modif     sqaTestLossResultPacketSize
         modif     sqaTestLossResultTestRate
         modif     sqaTestLossResultLossPktRatio
         modif     sqaTestLossResultTestDuration
         modif     sqaTestDelayResultPacketSize
         modif     sqaTestDelayResultTestRate
         modif     sqaTestDelayResultMinDelay
         modif     sqaTestDelayResultMaxDelay
         modif     sqaTestDelayResultAvgDelay
         modif     sqaTestDelayResultMinJitter
         modif     sqaTestDelayResultMaxJitter
         modif     sqaTestDelayResultAvgJitter
         modif     sqaTestDelayResultTestDuration"
          
     REVISION "201505080000Z" --2015-05-08 00:00
    DESCRIPTION
        "modif     sqaTestNum
         modif     sqaTestIcmpResultTestNum
         modif     sqaTestUdpResultTestNum
         modif     sqaTestTcpResultTestNum
         modif     sqaTestFtpResultTestNum
         modif     sqaTestDnsResultTestNum
         modif     sqaTestUdpJitterResultTestNum
         modif     sqaTestSnmpResultTestNum
         modif     sqaTestHttpResultTestNum
         modif     sqaTestIcmpJitterResultTestNum
         add       sqaTestSenderTable
         add       sqaTestReflectorTable
         add       sqaTestTpResultTable
         add       sqaTestLossResultTable
         add       sqaTestDelayResultTable
         add       zxr10SqaNotifications"

    REVISION "201503200000Z" --2015-03-20 00:00
    DESCRIPTION
        "add       sqaTestDnsResultDesurl"

    REVISION "201308080000Z" --2013-08-08 00:00
    DESCRIPTION
        "modif     TEXTUAL-CONVENTION
         modif     sqaTestTrapenable
         modif     sqaTestTos
         modif     sqaTestFtpPassword
         delete    TestBeginOrStop
         delete    NOTIFICATION-TYPE
         add       sqaTestDscp
         add       sqaTestSnmpCommunity"

    REVISION "201306140000Z" --2013-06-14 00:00
    DESCRIPTION
        "modif     TestType
         modif     TestTrapOnOff
         modif     TestStatus
         modif     TestBeginOrStop
         modif:    sqaTestFtpResultTable
         modif:    sqaTestFtpResultEntry
         modif:    sqaTestSnmpResultTable
         modif:    sqaTestSnmpResultEntry"
   
    REVISION "200905200000Z"
    DESCRIPTION
                "sqamib"
        ::= { zxr10RosngMIB 132 }
-- sqa table
       zte OBJECT IDENTIFIER ::= { enterprises 3902 }
       zxr10 OBJECT IDENTIFIER ::= { zte 3}
       zxr10RosngMIB OBJECT IDENTIFIER ::= { zxr10 6000}       
       
 --type def
    TestType ::= TEXTUAL-CONVENTION
            STATUS       current
            DESCRIPTION  "sqa test type"               
            SYNTAX   INTEGER
               {    
                icmp(1),
                tcp(2),
                udp(3),
                ftp(4), 
                dns(5),
                udpjitter(6),
                http(7),
                snmp(8),
                icmpjitter(9)
                --more
                }   
    TestTrapOnOff ::= TEXTUAL-CONVENTION
            STATUS       current
            DESCRIPTION  "sqa test trap enable or disable"               
            SYNTAX   INTEGER
               {
                on(1),
                off(2)
                }  
    TestStatus   ::= TEXTUAL-CONVENTION
            STATUS       current
            DESCRIPTION  "sqa test status"               
            SYNTAX   INTEGER
               {
                sqaIdle(1),
                sqaWaitingFirst(2),
                sqaWaitingNext(3),
                sqaWaitingResult(4),
                sqaSuccessEnd(5), 
                sqaErrorEnd(6),
                sqaIpstackErrorEnd(7),
                sqaPauseEnd(8),
                sqaEntityBusy(9),
                sqaWaitingTimerange(10),
                sqaWaitingIpstackUpcall(11),
                sqaWaitingConfig(12),
                sqaFinished(13),
                sqaRunning(14)
                } 
     TestResultStatus   ::= TEXTUAL-CONVENTION
            STATUS       current
            DESCRIPTION  "sqa test result status"               
            SYNTAX   INTEGER
               {
                sqaSuccessEnd(1),
                sqaErrorEnd(2)
                } 
               
     TestEnableStatus   ::= TEXTUAL-CONVENTION
            STATUS       current
            DESCRIPTION  "sqa test enable status"               
            SYNTAX   INTEGER
               {
                   enable(1),
                   disable(2)
               }                
                
     TestRateType   ::= TEXTUAL-CONVENTION
            STATUS       current
            DESCRIPTION  "sqa test rate type"               
            SYNTAX   INTEGER
               {
                   ir(1),
                   ulr(2)
               }  
               
     TestClientMode   ::= TEXTUAL-CONVENTION
            STATUS       current
            DESCRIPTION  "sqa test client mode"               
            SYNTAX   INTEGER
               {
                   uni-12(1),
                   uni-13(2),
                   bridge-uni-12(3),
                   undefined(255)
               }
               
     TestTestMode   ::= TEXTUAL-CONVENTION
            STATUS       current
            DESCRIPTION  "sqa test test mode"               
            SYNTAX   INTEGER
               {
                   share-mode(1),
                   exclusive-mode(2)
               }
               
     TestReflectorMode   ::= TEXTUAL-CONVENTION
            STATUS       current
            DESCRIPTION  "sqa test reflector mode"               
            SYNTAX   INTEGER
               {
                   l1(1),
                   l2(2),
                   l3(3),
                   l4(4),
                   default(5)
               }              
                
     TestOnlineState   ::= TEXTUAL-CONVENTION
            STATUS       current
            DESCRIPTION  "sqa test online state"               
            SYNTAX   INTEGER
               {
                   online(1),
                   offline(2)
               }                
     
     TpResultStatus   ::= TEXTUAL-CONVENTION
            STATUS       current
            DESCRIPTION  "sqa throughputtest test result status,durationTimeout: Could not find throughtput in the specified time,lowRateConfigError: Configuration of the lowest rate can not meet the requirements of packet loss rate"               
            SYNTAX   INTEGER
               {
                   pass(1),
                   durationTimeout(2),
                   lowRateConfigError(3)
                }
                
     ReflectorMode   ::= TEXTUAL-CONVENTION
            STATUS       current
            DESCRIPTION  "sqa reflector mode"               
            SYNTAX   INTEGER
               {
                   l2(1),
                   l3(2)
               } 
     TestOperation   ::= TEXTUAL-CONVENTION
            STATUS       current
            DESCRIPTION  "sqa test operation"               
            SYNTAX   INTEGER
               {
                   begin(1),
                   stop(2)
               }      
        --  This data type is used to model textual information taken
        --  from the NVT ASCII character set.  By convention, objects
        --  with this syntax are declared as having
        --  SIZE (0..255)
             
 --test config info       
    sqaTestTable  OBJECT-TYPE
        SYNTAX SEQUENCE OF SqaTestEntry
        MAX-ACCESS not-accessible
        STATUS current  
        DESCRIPTION "sqa test entity configuration"                 
        ::={sqaMib 1}  
         
    sqaTestEntry  OBJECT-TYPE
        SYNTAX SqaTestEntry
        MAX-ACCESS not-accessible
        STATUS current
        DESCRIPTION "sqa test entity configuration table"
        INDEX { sqaTestNum } 
        ::={sqaTestTable 1}
          
    SqaTestEntry ::=
        SEQUENCE {     
            sqaTestNum
                Unsigned32,
            sqaTestType
                TestType,  
            sqaTestVrf
                DisplayString,
            sqaTestDesIP
                IpAddress,  
            sqaTestDesPort
                Unsigned32,
            sqaTestSourceIP
                IpAddress,
            sqaTestRepeat
                Unsigned32,
            sqaTestSize
                Unsigned32,
            sqaTestTos
                Unsigned32,
            sqaTestTtl
                Unsigned32,
            sqaTestTimeout
                Unsigned32,
            sqaTestInterval
                Unsigned32,
            sqaTestFtpName
                DisplayString,
            sqaTestFtpPassword
                DisplayString,
            sqaTestFtpFileName
                DisplayString,
            sqaTestFtpRoot
                DisplayString,
         -- sqaTestFtpRemoteFileName
         --     DisplayString,
            sqaTestTrapenable
                TestTrapOnOff,
            sqaTestTrapPercent
                Unsigned32, 
        --  sqaTestBeginOrStop
        --      TestBeginOrStop,
            sqaTestStatus
                TestStatus,
            sqaTestTimeRange
                DisplayString,
            sqaTestDestinationUrl
                DisplayString,
            sqaTestDscp
                Unsigned32,                    
            sqaTestSnmpCommunity
                DisplayString                                      
        } 
        --num                      
    sqaTestNum  OBJECT-TYPE 
        SYNTAX Unsigned32 ( 1..65535 )   
        MAX-ACCESS read-only
        STATUS current
        DESCRIPTION "sqa test num. The range of this parameter depend on the device."
        ::= {sqaTestEntry 1}  
        --type        
    sqaTestType  OBJECT-TYPE
        SYNTAX  TestType
        MAX-ACCESS read-only
        STATUS current
        DESCRIPTION "sqa test type"
        ::= {sqaTestEntry 2}    
        --vrf            
    sqaTestVrf  OBJECT-TYPE
        SYNTAX DisplayString (SIZE(0..32))
        MAX-ACCESS read-only
        STATUS current
        DESCRIPTION "sqa test vrf"
        ::= {sqaTestEntry 3}  
         --des ip 
    sqaTestDesIP      OBJECT-TYPE
        SYNTAX IpAddress
        MAX-ACCESS read-only
        STATUS current
        DESCRIPTION "sqa des ip"
        ::= {sqaTestEntry 4}
         --des port 
    sqaTestDesPort    OBJECT-TYPE
        SYNTAX Unsigned32 ( 0..65535 )
        MAX-ACCESS read-only
        STATUS current
        DESCRIPTION "sqa des port"
        ::= {sqaTestEntry 5}
         --source ip 
    sqaTestSourceIP   OBJECT-TYPE
        SYNTAX IpAddress
        MAX-ACCESS read-only
        STATUS current
        DESCRIPTION "sqa test source ip"
        ::= {sqaTestEntry 6}
         --repeat 
    sqaTestRepeat      OBJECT-TYPE
        SYNTAX Unsigned32 ( 0..65535 )
        MAX-ACCESS read-only
        STATUS current
        DESCRIPTION "sqa test repeat"
        ::={sqaTestEntry 7}
         --size 
    sqaTestSize         OBJECT-TYPE
        SYNTAX Unsigned32 ( 0..8192 )
        MAX-ACCESS read-only
        STATUS current
        DESCRIPTION "sqa test size"
        ::={sqaTestEntry 8}
                             
         --tos 
    sqaTestTos          OBJECT-TYPE
        SYNTAX Unsigned32 ( 0..256 )
        MAX-ACCESS read-only
        STATUS current
        DESCRIPTION "sqa test tos,256 is the invalid value"
        ::={sqaTestEntry 9}
         --ttl 
    sqaTestTtl          OBJECT-TYPE
        SYNTAX Unsigned32 ( 0..255 )
        MAX-ACCESS read-only
        STATUS current
        DESCRIPTION "sqa test ttl"
        ::={sqaTestEntry 10}
         --timeout  
    sqaTestTimeout      OBJECT-TYPE
        SYNTAX Unsigned32
        MAX-ACCESS read-only
        STATUS obsolete
        DESCRIPTION "sqa test timeout"
        ::={sqaTestEntry 11}
         --interval 
    sqaTestInterval     OBJECT-TYPE
        SYNTAX Unsigned32 ( 0..65535 )
        MAX-ACCESS read-only
        STATUS current
        DESCRIPTION "sqa test interval"
        ::={sqaTestEntry 12}
         --ftpname  
    sqaTestFtpName      OBJECT-TYPE
        SYNTAX DisplayString (SIZE(0..31))
        MAX-ACCESS read-only
        STATUS current
        DESCRIPTION "sqa test ftp name"
        ::= {sqaTestEntry 13}
         --ftppassword 
    sqaTestFtpPassword  OBJECT-TYPE
        SYNTAX DisplayString (SIZE(64))
        MAX-ACCESS read-only
        STATUS current
        DESCRIPTION "sqa test ftp encrypted password,
                     the length of this password is 64"
        ::= {sqaTestEntry 14}
         --filename  
    sqaTestFtpFileName  OBJECT-TYPE
        SYNTAX DisplayString (SIZE(0..79))
        MAX-ACCESS read-only
        STATUS current
        DESCRIPTION "sqa test ftp file name"
        ::= {sqaTestEntry 15}
         --localpath  
    sqaTestFtpRoot      OBJECT-TYPE
        SYNTAX DisplayString (SIZE(0..151))
        MAX-ACCESS read-only
        STATUS current
        DESCRIPTION "sqa test ftp root"
        ::= {sqaTestEntry 16}  
                             
         --remotefielname
         --sqaTestFtpRemoteFileName OBJECT-TYPE
         --                    SYNTAX DisplayString
         --                    MAX-ACCESS read-only
         --                    STATUS current
         --                    DESCRIPTION "sqa test ftp remote file name"
         --                    ::={sqaTestEntry 17}   
         
         --enable 
    sqaTestTrapenable   OBJECT-TYPE
        SYNTAX  TestTrapOnOff 
        MAX-ACCESS read-only
        STATUS current
        DESCRIPTION "sqa test trap enable"    
        ::= {sqaTestEntry 18}  
              
         --percent  
    sqaTestTrapPercent  OBJECT-TYPE
        SYNTAX  Unsigned32 ( 1..100 )
        MAX-ACCESS read-only
        STATUS current
        DESCRIPTION "sqa test trap percent"
        ::= {sqaTestEntry 19}  
         
          --begin,stop 
          --sqaTestBeginOrStop OBJECT-TYPE
          --                   SYNTAX TestBeginOrStop
          --                   MAX-ACCESS read-only
          --                   STATUS current
          --                   DESCRIPTION "sqa test begin or stop"
          --                   ::={sqaTestEntry 20}   
          
          --status
    sqaTestStatus     OBJECT-TYPE
        SYNTAX TestStatus
        MAX-ACCESS read-only
        STATUS current
        DESCRIPTION "sqa test status"
        ::={sqaTestEntry 21} 
           
          --timerange
    sqaTestTimeRange  OBJECT-TYPE
        SYNTAX  DisplayString (SIZE(0..31))
        MAX-ACCESS read-only
        STATUS current
        DESCRIPTION "sqa test time range"
        ::={sqaTestEntry 22}    
 
        --destinationurl
    sqaTestDestinationUrl OBJECT-TYPE
        SYNTAX  DisplayString (SIZE(0..128))
        MAX-ACCESS read-only
        STATUS current
        DESCRIPTION "sqa test destination url"
        ::={sqaTestEntry 23}
        
        --dscp 
    sqaTestDscp          OBJECT-TYPE
        SYNTAX Unsigned32 (0..63 | 255)
        MAX-ACCESS read-only
        STATUS current
        DESCRIPTION "sqa test dscp,255 is the invalid value"
        ::={sqaTestEntry 24}
        
        --community
    sqaTestSnmpCommunity OBJECT-TYPE
        SYNTAX  DisplayString (SIZE(64))
        MAX-ACCESS read-only
        STATUS current
        DESCRIPTION "sqa test encrypted community, 
                     the length of this community is 64"
        ::={sqaTestEntry 25}    

 --sqa tcp server                           
    sqaTcpServerGrp   OBJECT IDENTIFIER ::={sqaMib 2}                   
   
                            
    sqaTcpServerVrf OBJECT-TYPE
        SYNTAX DisplayString
        MAX-ACCESS read-only                    
        STATUS obsolete
        DESCRIPTION "sqa tcp server vrf"
        ::={sqaTcpServerGrp 1}    
                          
    sqaTcpServerIP  OBJECT-TYPE
        SYNTAX IpAddress
        MAX-ACCESS read-only 
        STATUS current
        DESCRIPTION "sqa tcp server ip"
        ::={sqaTcpServerGrp 2}
                          
    sqaTcpServerPort OBJECT-TYPE
        SYNTAX Unsigned32 ( 0..65535 ) 
        MAX-ACCESS read-only 
        STATUS current
        DESCRIPTION "sqa tcp server port"
        ::={sqaTcpServerGrp 3}
        
        
 --sqa udp server                           
    sqaUdpServerGrp     OBJECT IDENTIFIER ::={sqaMib 3}   
 
                            
    sqaUdpServerVrf OBJECT-TYPE
        SYNTAX DisplayString
        MAX-ACCESS read-only                     
        STATUS obsolete
        DESCRIPTION "sqa udp server vrf"
        ::={sqaUdpServerGrp 1}    
        
    sqaUdpServerIP  OBJECT-TYPE
        SYNTAX IpAddress
        MAX-ACCESS read-create 
        STATUS current
        DESCRIPTION "sqa udp server ip"
        ::={sqaUdpServerGrp 2}
                          
    sqaUdpServerPort OBJECT-TYPE
        SYNTAX Unsigned32 ( 0..65535 ) 
        MAX-ACCESS read-create 
        STATUS current
        DESCRIPTION "sqa udp server port"
        ::={sqaUdpServerGrp 3}      

 -- icmp result        
    sqaTestIcmpResultTable         OBJECT-TYPE  
        SYNTAX SEQUENCE OF  SqaTestIcmpResultEntry    
        MAX-ACCESS not-accessible
        STATUS current
        DESCRIPTION "sqa icmp result table"  
        ::={sqaMib 10} 
                                   
    sqaTestIcmpResultEntry        OBJECT-TYPE   
        SYNTAX SqaTestIcmpResultEntry
        MAX-ACCESS not-accessible
        STATUS current
        DESCRIPTION "sqa icmp result entry"   
        INDEX {sqaTestIcmpResultTestNum}
        ::={sqaTestIcmpResultTable 1}   
                                      
    SqaTestIcmpResultEntry::= 
        SEQUENCE
            { 
            sqaTestIcmpResultTestNum
                INTEGER,
            sqaTestIcmpResultRepeat
                Unsigned32,
            sqaTestIcmpResultResponse
                Unsigned32, 
            sqaTestIcmpResultStatus
                TestResultStatus,
            sqaTestIcmpResultDesIP
                IpAddress,
            sqaTestIcmpResultMinRTT
                Unsigned32,
            sqaTestIcmpResultMaxRTT
                Unsigned32,
            sqaTestIcmpResultAvgRTT
                Unsigned32,
            sqaTestIcmpResultSumRTT
                Unsigned32,
            sqaTestIcmpResultProbeTime
                DisplayString,   
            sqaTestIcmpResultPacketLossRate
                DisplayString,
            sqaTestIcmpResultMinPosJitter
                Unsigned32,
            sqaTestIcmpResultMaxPosJitter
                Unsigned32,
            sqaTestIcmpResultAvgPosJitter
                Unsigned32,
            sqaTestIcmpResultSumPosJitter
                Unsigned32,
            sqaTestIcmpResultMinNegJitter
                Unsigned32,
            sqaTestIcmpResultMaxNegJitter
                Unsigned32,
            sqaTestIcmpResultAvgNegJitter
                Unsigned32,
            sqaTestIcmpResultSumNegJitter
                Unsigned32,
            sqaTestIcmpResultMinJitter
                Unsigned32,
            sqaTestIcmpResultMaxJitter
                Unsigned32,
            sqaTestIcmpResultAvgJitter
                Unsigned32,
            sqaTestIcmpResultSumJitter
                Unsigned32   
            
            } 
          --test num
    sqaTestIcmpResultTestNum  OBJECT-TYPE
        SYNTAX INTEGER ( 1..65535 )
        MAX-ACCESS read-only
        STATUS current
        DESCRIPTION "sqa icmp test num"
        ::= {sqaTestIcmpResultEntry 1}     
         --repeat                                                   
    sqaTestIcmpResultRepeat  OBJECT-TYPE
        SYNTAX Unsigned32 ( 1..65535 )
        MAX-ACCESS read-only
        STATUS current
        DESCRIPTION "sqa icmp result repeat"
        ::= {sqaTestIcmpResultEntry 2}    
         --response                          
    sqaTestIcmpResultResponse OBJECT-TYPE
        SYNTAX Unsigned32 ( 0..65535 )
        MAX-ACCESS read-only
        STATUS current
        DESCRIPTION "sqa icmp result response"
        ::= {sqaTestIcmpResultEntry 3}  
         --status                          
    sqaTestIcmpResultStatus   OBJECT-TYPE
        SYNTAX TestResultStatus
        MAX-ACCESS read-only
        STATUS current
        DESCRIPTION "sqa icmp result status"
        ::= {sqaTestIcmpResultEntry 4} 
         --des ip                          
    sqaTestIcmpResultDesIP    OBJECT-TYPE
        SYNTAX IpAddress
        MAX-ACCESS read-only
        STATUS current
        DESCRIPTION "sqa icmp result des ip"
        ::= {sqaTestIcmpResultEntry 5} 
         --min rtt                          
    sqaTestIcmpResultMinRTT   OBJECT-TYPE
        SYNTAX Unsigned32
        MAX-ACCESS read-only
        STATUS current
        DESCRIPTION "sqa icmp result min rtt"
        ::= {sqaTestIcmpResultEntry 6}  
         --max rtt                          
    sqaTestIcmpResultMaxRTT   OBJECT-TYPE
        SYNTAX Unsigned32
        MAX-ACCESS read-only
        STATUS current
        DESCRIPTION "sqa icmp result max rtt"
        ::= {sqaTestIcmpResultEntry 7} 
         --avg rtt                          
    sqaTestIcmpResultAvgRTT   OBJECT-TYPE
        SYNTAX Unsigned32
        MAX-ACCESS read-only
        STATUS current
        DESCRIPTION "sqa icmp result avg rtt"
        ::= {sqaTestIcmpResultEntry 8}
         --sum rtt
    sqaTestIcmpResultSumRTT   OBJECT-TYPE
        SYNTAX Unsigned32
        MAX-ACCESS read-only
        STATUS current
        DESCRIPTION "sqa icmp result sum rtt"
        ::= {sqaTestIcmpResultEntry 9}
         --probe time
    sqaTestIcmpResultProbeTime OBJECT-TYPE
        SYNTAX DisplayString
        MAX-ACCESS read-only
        STATUS current
        DESCRIPTION "sqa icmp result probe time"
        ::= {sqaTestIcmpResultEntry 10}
         --packet loss rate
    sqaTestIcmpResultPacketLossRate  OBJECT-TYPE
        SYNTAX DisplayString
        MAX-ACCESS read-only
        STATUS current
        DESCRIPTION "sqa icmp result packet loss rate"
        ::= {sqaTestIcmpResultEntry 11}
         --min pos jitter                             
    sqaTestIcmpResultMinPosJitter   OBJECT-TYPE
        SYNTAX Unsigned32
        MAX-ACCESS read-only
        STATUS current
        DESCRIPTION "sqa icmp result min pos jitter"
        ::= {sqaTestIcmpResultEntry 12} 
         --max pos jitter                             
    sqaTestIcmpResultMaxPosJitter   OBJECT-TYPE
        SYNTAX Unsigned32
        MAX-ACCESS read-only
        STATUS current
        DESCRIPTION "sqa icmp result max pos jitter"
        ::= {sqaTestIcmpResultEntry 13} 
         --avg pos jitter                           
    sqaTestIcmpResultAvgPosJitter   OBJECT-TYPE
        SYNTAX Unsigned32
        MAX-ACCESS read-only
        STATUS current
        DESCRIPTION "sqa icmp result avg pos jitter"
        ::= {sqaTestIcmpResultEntry 14}
         --sum pos jitter                           
    sqaTestIcmpResultSumPosJitter   OBJECT-TYPE
        SYNTAX Unsigned32
        MAX-ACCESS read-only
        STATUS current
        DESCRIPTION "sqa icmp result sum pos jitter"
        ::= {sqaTestIcmpResultEntry 15}  
         --min neg jitter                             
    sqaTestIcmpResultMinNegJitter   OBJECT-TYPE
        SYNTAX Unsigned32
        MAX-ACCESS read-only
        STATUS current
        DESCRIPTION "sqa icmp result min neg jitter"
        ::= {sqaTestIcmpResultEntry 16} 
         --max neg jitter                             
    sqaTestIcmpResultMaxNegJitter   OBJECT-TYPE
        SYNTAX Unsigned32
        MAX-ACCESS read-only
        STATUS current
        DESCRIPTION "sqa icmp result max neg jitter"
        ::= {sqaTestIcmpResultEntry 17}  
         --avg neg jitter                           
    sqaTestIcmpResultAvgNegJitter   OBJECT-TYPE
        SYNTAX Unsigned32
        MAX-ACCESS read-only
        STATUS current
        DESCRIPTION "sqa icmp result avg neg jitter"
        ::= {sqaTestIcmpResultEntry 18}  
         --sum neg jitter                           
    sqaTestIcmpResultSumNegJitter   OBJECT-TYPE
        SYNTAX Unsigned32
        MAX-ACCESS read-only
        STATUS current
        DESCRIPTION "sqa icmp result sum neg jitter"
        ::= {sqaTestIcmpResultEntry 19}
         --min jitter                             
    sqaTestIcmpResultMinJitter   OBJECT-TYPE
        SYNTAX Unsigned32
        MAX-ACCESS read-only
        STATUS current
        DESCRIPTION "sqa icmp result min jitter"
        ::= {sqaTestIcmpResultEntry 20} 
         --max jitter                             
    sqaTestIcmpResultMaxJitter   OBJECT-TYPE
        SYNTAX Unsigned32
        MAX-ACCESS read-only
        STATUS current
        DESCRIPTION "sqa icmp result max jitter"
        ::= {sqaTestIcmpResultEntry 21}  
         --avg jitter                           
    sqaTestIcmpResultAvgJitter   OBJECT-TYPE
        SYNTAX Unsigned32
        MAX-ACCESS read-only
        STATUS current
        DESCRIPTION "sqa icmp result avg jitter"
        ::= {sqaTestIcmpResultEntry 22}  
         --sum jitter                           
    sqaTestIcmpResultSumJitter   OBJECT-TYPE
        SYNTAX Unsigned32
        MAX-ACCESS read-only
        STATUS current
        DESCRIPTION "sqa icmp result sum jitter"
        ::= {sqaTestIcmpResultEntry 23} 
                                      
 --udp result         
    sqaTestUdpResultTable  OBJECT-TYPE
        SYNTAX SEQUENCE OF SqaTestUdpResultEntry
        MAX-ACCESS not-accessible
        STATUS current
        DESCRIPTION "sqa udp result table"
        ::={sqaMib 11} 
    sqaTestUdpResultEntry      OBJECT-TYPE
        SYNTAX SqaTestUdpResultEntry
        MAX-ACCESS not-accessible
        STATUS current
        DESCRIPTION "sqa udp result entry"
        INDEX {sqaTestUdpResultTestNum} 
        ::={sqaTestUdpResultTable 1}  
    SqaTestUdpResultEntry::= 
        SEQUENCE
        {  
            sqaTestUdpResultTestNum
                INTEGER,
            sqaTestUdpResultRepeat
                Unsigned32,
            sqaTestUdpResultResponse
                Unsigned32, 
            sqaTestUdpResultStatus
                TestResultStatus,
            sqaTestUdpResultDesIP
                IpAddress,
            sqaTestUdpResultMinRTT
                Unsigned32,
            sqaTestUdpResultMaxRTT
                Unsigned32,
            sqaTestUdpResultAvgRTT
                Unsigned32,
            sqaTestUdpResultSumRTT
                Unsigned32,
            sqaTestUdpResultMinPosJitter
                Unsigned32,
            sqaTestUdpResultMaxPosJitter
                Unsigned32,
            sqaTestUdpResultAvgPosJitter
                Unsigned32,
            sqaTestUdpResultSumPosJitter
                Unsigned32,
            sqaTestUdpResultMinNegJitter
                Unsigned32,
            sqaTestUdpResultMaxNegJitter
                Unsigned32,
            sqaTestUdpResultAvgNegJitter
                Unsigned32,
            sqaTestUdpResultSumNegJitter
                Unsigned32,
            sqaTestUdpResultProbeTime
                DisplayString,  
            sqaTestUdpResultPacketLossRate
                DisplayString,
            sqaTestUdpResultMinJitter
                Unsigned32,
            sqaTestUdpResultMaxJitter
                Unsigned32,
            sqaTestUdpResultAvgJitter
                Unsigned32,
            sqaTestUdpResultSumJitter
                Unsigned32                                                  
        } 
         --test num
    sqaTestUdpResultTestNum   OBJECT-TYPE
        SYNTAX INTEGER ( 1..65535 )
        MAX-ACCESS read-only
        STATUS current
        DESCRIPTION "sqa udp result test num"
        ::= {sqaTestUdpResultEntry 1}  
         --repeat                               
    sqaTestUdpResultRepeat   OBJECT-TYPE
        SYNTAX Unsigned32 ( 1..1000 )
        MAX-ACCESS read-only
        STATUS current
        DESCRIPTION "sqa udp result repeat"
        ::= {sqaTestUdpResultEntry 2}    
         --response                          
    sqaTestUdpResultResponse  OBJECT-TYPE
        SYNTAX Unsigned32 ( 0..1000 )
        MAX-ACCESS read-only
        STATUS current
        DESCRIPTION "sqa udp result response"
        ::= {sqaTestUdpResultEntry 3}  
         --ststus                          
    sqaTestUdpResultStatus    OBJECT-TYPE
        SYNTAX TestResultStatus
        MAX-ACCESS read-only
        STATUS current
        DESCRIPTION "sqa udp result status"
        ::= {sqaTestUdpResultEntry 4} 
         --des ip                          
    sqaTestUdpResultDesIP     OBJECT-TYPE
        SYNTAX IpAddress
        MAX-ACCESS read-only
        STATUS current
        DESCRIPTION "sqa udp result des ip"
        ::= {sqaTestUdpResultEntry 5} 
         --min rtt                          
    sqaTestUdpResultMinRTT    OBJECT-TYPE
        SYNTAX Unsigned32
        MAX-ACCESS read-only
        STATUS current
        DESCRIPTION "sqa udp result min rtt"
        ::= {sqaTestUdpResultEntry 6}  
         --max rtt                          
    sqaTestUdpResultMaxRTT    OBJECT-TYPE
        SYNTAX Unsigned32
        MAX-ACCESS read-only
        STATUS current
        DESCRIPTION "sqa udp result max rtt"
        ::= {sqaTestUdpResultEntry 7} 
         --avg rtt                          
    sqaTestUdpResultAvgRTT    OBJECT-TYPE
        SYNTAX Unsigned32
        MAX-ACCESS read-only
        STATUS current
        DESCRIPTION "sqa udp result avg rtt"
        ::= {sqaTestUdpResultEntry 8}
         --sum rtt
    sqaTestUdpResultSumRTT     OBJECT-TYPE
        SYNTAX Unsigned32
        MAX-ACCESS read-only
        STATUS current
        DESCRIPTION "sqa udp result sum rtt"
        ::= {sqaTestUdpResultEntry 9} 
         --min pos jitter                             
    sqaTestUdpResultMinPosJitter   OBJECT-TYPE
        SYNTAX Unsigned32
        MAX-ACCESS read-only
        STATUS current
        DESCRIPTION "sqa udp result min pos jitter"
        ::= {sqaTestUdpResultEntry 10} 
         --max pos jitter                             
    sqaTestUdpResultMaxPosJitter   OBJECT-TYPE
        SYNTAX Unsigned32
        MAX-ACCESS read-only
        STATUS current
        DESCRIPTION "sqa udp result max pos jitter"
        ::= {sqaTestUdpResultEntry 11} 
         --avg pos jitter                           
    sqaTestUdpResultAvgPosJitter   OBJECT-TYPE
        SYNTAX Unsigned32
        MAX-ACCESS read-only
        STATUS current
        DESCRIPTION "sqa udp result avg pos jitter"
        ::= {sqaTestUdpResultEntry 12}
         --sum pos jitter                           
    sqaTestUdpResultSumPosJitter   OBJECT-TYPE
        SYNTAX Unsigned32
        MAX-ACCESS read-only
        STATUS current
        DESCRIPTION "sqa udp result sum pos jitter"
        ::= {sqaTestUdpResultEntry 13}  
         --min neg jitter                             
    sqaTestUdpResultMinNegJitter   OBJECT-TYPE
        SYNTAX Unsigned32
        MAX-ACCESS read-only
        STATUS current
        DESCRIPTION "sqa udp result min neg jitter"
        ::= {sqaTestUdpResultEntry 14} 
         --max neg jitter                             
    sqaTestUdpResultMaxNegJitter   OBJECT-TYPE
        SYNTAX Unsigned32
        MAX-ACCESS read-only
        STATUS current
        DESCRIPTION "sqa udp result max neg jitter"
        ::= {sqaTestUdpResultEntry 15}  
         --avg neg jitter                           
    sqaTestUdpResultAvgNegJitter   OBJECT-TYPE
        SYNTAX Unsigned32
        MAX-ACCESS read-only
        STATUS current
        DESCRIPTION "sqa udp result avg neg jitter"
        ::= {sqaTestUdpResultEntry 16}  
         --sum net jitter                           
    sqaTestUdpResultSumNegJitter   OBJECT-TYPE
        SYNTAX Unsigned32
        MAX-ACCESS read-only
        STATUS current
        DESCRIPTION "sqa udp result sum neg jitter"
        ::= {sqaTestUdpResultEntry 17}

                           
         --probe time
    sqaTestUdpResultProbeTime OBJECT-TYPE
        SYNTAX DisplayString
        MAX-ACCESS read-only
        STATUS current
        DESCRIPTION "sqa udp result probe time"
        ::= {sqaTestUdpResultEntry 18} 
         --packet loss rate
    sqaTestUdpResultPacketLossRate  OBJECT-TYPE
        SYNTAX DisplayString
        MAX-ACCESS read-only
        STATUS current
        DESCRIPTION "sqa udp result packet loss rate"
        ::= {sqaTestUdpResultEntry 19}
         --min jitter                             
    sqaTestUdpResultMinJitter  OBJECT-TYPE
        SYNTAX Unsigned32
        MAX-ACCESS read-only
        STATUS current
        DESCRIPTION "sqa udp result min jitter"
        ::= {sqaTestUdpResultEntry 20} 
         --max jitter                             
    sqaTestUdpResultMaxJitter  OBJECT-TYPE
        SYNTAX Unsigned32
        MAX-ACCESS read-only
        STATUS current
        DESCRIPTION "sqa udp result max jitter"
        ::= {sqaTestUdpResultEntry 21}  
         --avg jitter                           
    sqaTestUdpResultAvgJitter  OBJECT-TYPE
        SYNTAX Unsigned32
        MAX-ACCESS read-only
        STATUS current
        DESCRIPTION "sqa udp result avg jitter"
        ::= {sqaTestUdpResultEntry 22}  
         --sum jitter                           
    sqaTestUdpResultSumJitter  OBJECT-TYPE
        SYNTAX Unsigned32
        MAX-ACCESS read-only
        STATUS current
        DESCRIPTION "sqa udp result sum jitter"
        ::= {sqaTestUdpResultEntry 23}

                                    
                                    
 --tcp result         
    sqaTestTcpResultTable  OBJECT-TYPE
        SYNTAX SEQUENCE OF SqaTestTcpResultEntry
        MAX-ACCESS not-accessible
        STATUS current
        DESCRIPTION "sqa tcp result table"
        ::={sqaMib 12}  
                              
    sqaTestTcpResultEntry OBJECT-TYPE
        SYNTAX  SqaTestTcpResultEntry
        MAX-ACCESS not-accessible
        STATUS current
        DESCRIPTION "sqa tcp result entry"
        INDEX {sqaTestTcpResultTestNum} 
        ::={sqaTestTcpResultTable 1}    
    SqaTestTcpResultEntry::= 
        SEQUENCE
        { 
            sqaTestTcpResultTestNum
                INTEGER,
            sqaTestTcpResultRepeat
                Unsigned32,
            sqaTestTcpResultResponse
                Unsigned32, 
            sqaTestTcpResultStatus
                TestResultStatus,
            sqaTestTcpResultDesIP
                IpAddress,
            sqaTestTcpResultMinRTT
                Unsigned32,
            sqaTestTcpResultMaxRTT
                Unsigned32,
            sqaTestTcpResultAvgRTT
                Unsigned32,
            sqaTestTcpResultSumRTT
                Unsigned32,
            sqaTestTcpResultProbeTime
                DisplayString   
                                            
                                             
        }   
         --test num
    sqaTestTcpResultTestNum   OBJECT-TYPE
        SYNTAX INTEGER ( 1..65535 )
        MAX-ACCESS read-only
        STATUS current
        DESCRIPTION "sqa tcp result test num"
        ::= {sqaTestTcpResultEntry 1}  
         --repeat                               
    sqaTestTcpResultRepeat  OBJECT-TYPE
        SYNTAX Unsigned32 ( 1..200 )
        MAX-ACCESS read-only
        STATUS current
        DESCRIPTION "sqa tcp result repeat"
        ::= {sqaTestTcpResultEntry 2}    
         --response                          
    sqaTestTcpResultResponse OBJECT-TYPE
        SYNTAX Unsigned32 ( 0..200 )
        MAX-ACCESS read-only
        STATUS current
        DESCRIPTION "sqa tcp result response"
        ::= {sqaTestTcpResultEntry 3}  
         --ststus                          
    sqaTestTcpResultStatus   OBJECT-TYPE
        SYNTAX TestResultStatus
        MAX-ACCESS read-only
        STATUS current
        DESCRIPTION "sqa tcp result status"
        ::= {sqaTestTcpResultEntry 4} 
         --des ip                          
    sqaTestTcpResultDesIP    OBJECT-TYPE
        SYNTAX IpAddress
        MAX-ACCESS read-only
        STATUS current
        DESCRIPTION "sqa tcp result des ip"
        ::= {sqaTestTcpResultEntry 5} 
         --min rtt                          
    sqaTestTcpResultMinRTT   OBJECT-TYPE
        SYNTAX Unsigned32
        MAX-ACCESS read-only
        STATUS current
        DESCRIPTION "sqa tcp result min rtt"
        ::= {sqaTestTcpResultEntry 6}  
         --max rtt                          
    sqaTestTcpResultMaxRTT   OBJECT-TYPE
        SYNTAX Unsigned32
        MAX-ACCESS read-only
        STATUS current
        DESCRIPTION "sqa tcp result max rtt"
        ::= {sqaTestTcpResultEntry 7} 
         --avg rtt                          
    sqaTestTcpResultAvgRTT   OBJECT-TYPE
        SYNTAX Unsigned32
        MAX-ACCESS read-only
        STATUS current
        DESCRIPTION "sqa tcp result avg rtt"
        ::= {sqaTestTcpResultEntry 8}
         --last rtt
    sqaTestTcpResultSumRTT    OBJECT-TYPE
        SYNTAX Unsigned32
        MAX-ACCESS read-only
        STATUS current
        DESCRIPTION "sqa tcp result sum rtt"
        ::= {sqaTestTcpResultEntry 9}
         --probe time
    sqaTestTcpResultProbeTime OBJECT-TYPE
        SYNTAX DisplayString
        MAX-ACCESS read-only
        STATUS current
        DESCRIPTION "sqa tcp result probe time"
        ::= {sqaTestTcpResultEntry 10}
                                         
 --ftp result
    sqaTestFtpResultTable  OBJECT-TYPE
        SYNTAX SEQUENCE OF SqaTestFtpResultEntry
        MAX-ACCESS not-accessible
        STATUS current
        DESCRIPTION "sqa ftp result table" 
        ::={sqaMib 13} 
                              
    sqaTestFtpResultEntry      OBJECT-TYPE
        SYNTAX SqaTestFtpResultEntry
        MAX-ACCESS not-accessible   
        STATUS current
        DESCRIPTION "sqa ftp result entry"
        INDEX {sqaTestFtpResultTestNum}
        ::={sqaTestFtpResultTable 1}    
                                        
    SqaTestFtpResultEntry ::=
        SEQUENCE
        { 
            sqaTestFtpResultTestNum
                INTEGER, 
            sqaTestFtpResultStatus
                TestResultStatus,
            sqaTestFtpResultLastRTT
                Unsigned32,
            sqaTestFtpResultReadBytes
                Unsigned32,
            sqaTestFtpResultProbeTime
                DisplayString
        }
          --test num 
    sqaTestFtpResultTestNum   OBJECT-TYPE
        SYNTAX INTEGER ( 1..65535 )
        MAX-ACCESS read-only
        STATUS current
        DESCRIPTION "sqa ftp result test num"
        ::={sqaTestFtpResultEntry 1}  
          --status
    sqaTestFtpResultStatus   OBJECT-TYPE
        SYNTAX TestResultStatus
        MAX-ACCESS read-only
        STATUS current
        DESCRIPTION "sqa ftp result test status"
        ::={sqaTestFtpResultEntry 2}
          --last rtt                          
    sqaTestFtpResultLastRTT   OBJECT-TYPE
        SYNTAX Unsigned32
        MAX-ACCESS read-only
        STATUS current
        DESCRIPTION "sqa ftp result last rtt"
        ::= {sqaTestFtpResultEntry 3}   
           --read bytes                          
    sqaTestFtpResultReadBytes   OBJECT-TYPE
        SYNTAX Unsigned32
        MAX-ACCESS read-only
        STATUS current
        DESCRIPTION "sqa ftp result read bytes"
        ::= {sqaTestFtpResultEntry 4}

         --probe time
    sqaTestFtpResultProbeTime  OBJECT-TYPE
        SYNTAX DisplayString
        MAX-ACCESS read-only
        STATUS current
        DESCRIPTION "sqa ftp result probe time"
        ::= {sqaTestFtpResultEntry 5}

                   
       --dns result         
    sqaTestDnsResultTable  OBJECT-TYPE
        SYNTAX SEQUENCE OF SqaTestDnsResultEntry
        MAX-ACCESS not-accessible
        STATUS current
        DESCRIPTION "sqa dns result table"
        ::={sqaMib 14}  
                              
    sqaTestDnsResultEntry      OBJECT-TYPE
        SYNTAX  SqaTestDnsResultEntry
        MAX-ACCESS not-accessible
        STATUS current
        DESCRIPTION "sqa dns result entry"
        INDEX {sqaTestDnsResultTestNum} 
        ::={sqaTestDnsResultTable 1}    
    SqaTestDnsResultEntry::= 
        SEQUENCE
        { 
            sqaTestDnsResultTestNum
                INTEGER,
            sqaTestDnsResultRepeat
                Unsigned32,
            sqaTestDnsResultResponse
                Unsigned32, 
            sqaTestDnsResultStatus
                TestResultStatus,
            sqaTestDnsResultResolvedIP
                IpAddress,
            sqaTestDnsResultMinRTT
                Unsigned32,
            sqaTestDnsResultMaxRTT
                Unsigned32,
            sqaTestDnsResultAvgRTT
                Unsigned32,
            sqaTestDnsResultSumRTT
                Unsigned32,
            sqaTestDnsResultProbeTime
                DisplayString,
            sqaTestDnsResultDesurl
                DisplayString   
        }   
         --test num
    sqaTestDnsResultTestNum   OBJECT-TYPE
        SYNTAX INTEGER ( 1..65535 )
        MAX-ACCESS read-only
        STATUS current
        DESCRIPTION "sqa dns result test num"
        ::= {sqaTestDnsResultEntry 1}  
         --repeat                               
    sqaTestDnsResultRepeat    OBJECT-TYPE
        SYNTAX Unsigned32 ( 1..10 )
        MAX-ACCESS read-only
        STATUS current
        DESCRIPTION "sqa dns result repeat"
        ::= {sqaTestDnsResultEntry 2}    
         --response                          
    sqaTestDnsResultResponse OBJECT-TYPE
        SYNTAX Unsigned32 ( 0..10 )
        MAX-ACCESS read-only
        STATUS current
        DESCRIPTION "sqa dns result response"
        ::= {sqaTestDnsResultEntry 3}  
         --status                          
    sqaTestDnsResultStatus   OBJECT-TYPE
        SYNTAX TestResultStatus
        MAX-ACCESS read-only
        STATUS current
        DESCRIPTION "sqa dns result status"
        ::= {sqaTestDnsResultEntry 4} 
         --resolved ip                          
    sqaTestDnsResultResolvedIP    OBJECT-TYPE
        SYNTAX IpAddress
        MAX-ACCESS read-only
        STATUS current
        DESCRIPTION "sqa dns result resolved ip"
        ::= {sqaTestDnsResultEntry 5} 
         --min rtt                          
    sqaTestDnsResultMinRTT   OBJECT-TYPE
        SYNTAX Unsigned32
        MAX-ACCESS read-only
        STATUS current
        DESCRIPTION "sqa dns result min rtt"
        ::= {sqaTestDnsResultEntry 6}  
         --max rtt                          
    sqaTestDnsResultMaxRTT   OBJECT-TYPE
        SYNTAX Unsigned32
        MAX-ACCESS read-only
        STATUS current
        DESCRIPTION "sqa dns result max rtt"
        ::= {sqaTestDnsResultEntry 7} 
         --avg rtt                          
    sqaTestDnsResultAvgRTT   OBJECT-TYPE
        SYNTAX Unsigned32
        MAX-ACCESS read-only
        STATUS current
        DESCRIPTION "sqa dns result avg rtt"
        ::= {sqaTestDnsResultEntry 8}
         --last rtt
    sqaTestDnsResultSumRTT    OBJECT-TYPE
        SYNTAX Unsigned32
        MAX-ACCESS read-only
        STATUS current
        DESCRIPTION "sqa dns result sum rtt"
        ::= {sqaTestDnsResultEntry 9}
         --probe time
    sqaTestDnsResultProbeTime OBJECT-TYPE
        SYNTAX DisplayString
        MAX-ACCESS read-only
        STATUS current
        DESCRIPTION "sqa dns result probe time"
        ::= {sqaTestDnsResultEntry 10}
           --destination url
    sqaTestDnsResultDesurl    OBJECT-TYPE
        SYNTAX DisplayString
        MAX-ACCESS read-only
        STATUS current
        DESCRIPTION "sqa dns result destination url"
        ::= {sqaTestDnsResultEntry 11}  


       --udpjitter result         
    sqaTestUdpJitterResultTable  OBJECT-TYPE
        SYNTAX SEQUENCE OF SqaTestUdpJitterResultEntry
        MAX-ACCESS not-accessible
        STATUS current
        DESCRIPTION "sqa udp jitter result table"
        ::={sqaMib 15} 
    sqaTestUdpJitterResultEntry      OBJECT-TYPE
        SYNTAX SqaTestUdpJitterResultEntry
        MAX-ACCESS not-accessible
        STATUS current
        DESCRIPTION "sqa udp jitter result entry"
        INDEX {sqaTestUdpJitterResultTestNum} 
        ::={sqaTestUdpJitterResultTable 1}  
    SqaTestUdpJitterResultEntry::= 
        SEQUENCE
        {  
            sqaTestUdpJitterResultTestNum
                INTEGER,
            sqaTestUdpJitterResultRepeat
                Unsigned32,
            sqaTestUdpJitterResultResponse
                Unsigned32, 
            sqaTestUdpJitterResultStatus
                TestResultStatus,
            sqaTestUdpJitterResultDesIP
                IpAddress, 
            
            sqaTestUdpJitterResultMinRTTSD
                Integer32,
            sqaTestUdpJitterResultMaxRTTSD
                Integer32,
            sqaTestUdpJitterResultAvgRTTSD
                Integer32,
            sqaTestUdpJitterResultSumRTTSD
                Integer32, 
            
            sqaTestUdpJitterResultMinRTTDS
                Integer32,
            sqaTestUdpJitterResultMaxRTTDS
                Integer32,
            sqaTestUdpJitterResultAvgRTTDS
                Integer32,
            sqaTestUdpJitterResultSumRTTDS
                Integer32,

            sqaTestUdpJitterResultMinPosSD
                Unsigned32,
            sqaTestUdpJitterResultMaxPosSD
                Unsigned32,
            sqaTestUdpJitterResultAvgPosSD
                Unsigned32,
            sqaTestUdpJitterResultSumPosSD
                Unsigned32,
            sqaTestUdpJitterResultNumPosSD
                Unsigned32,

            sqaTestUdpJitterResultMinNegSD
                Unsigned32,
            sqaTestUdpJitterResultMaxNegSD
                Unsigned32,
            sqaTestUdpJitterResultAvgNegSD
                Unsigned32,
            sqaTestUdpJitterResultSumNegSD
                Unsigned32,
            sqaTestUdpJitterResultNumNegSD
                Unsigned32,   
            
            sqaTestUdpJitterResultMinPosDS
                Unsigned32,
            sqaTestUdpJitterResultMaxPosDS
                Unsigned32,
            sqaTestUdpJitterResultAvgPosDS
                Unsigned32,
            sqaTestUdpJitterResultSumPosDS
                Unsigned32, 
            sqaTestUdpJitterResultNumPosDS
                Unsigned32,

            sqaTestUdpJitterResultMinNegDS
                Unsigned32,
            sqaTestUdpJitterResultMaxNegDS
                Unsigned32,
            sqaTestUdpJitterResultAvgNegDS
                Unsigned32,
            sqaTestUdpJitterResultSumNegDS
                Unsigned32,
            sqaTestUdpJitterResultNumNegDS
                Unsigned32,
                                         
            sqaTestUdpJitterResultDisposeNumSD
                Unsigned32,
            sqaTestUdpJitterResultDisposeNumDS
                Unsigned32,
            sqaTestUdpJitterResultProbeTime
                DisplayString                                                    
        } 
         --test num
    sqaTestUdpJitterResultTestNum   OBJECT-TYPE
        SYNTAX INTEGER ( 1..65535 )
        MAX-ACCESS read-only
        STATUS current
        DESCRIPTION "sqa udp jitter result test num"
        ::= {sqaTestUdpJitterResultEntry 1}  
         --repeat                               
    sqaTestUdpJitterResultRepeat    OBJECT-TYPE
        SYNTAX Unsigned32 ( 1..1000 )
        MAX-ACCESS read-only
        STATUS current
        DESCRIPTION "sqa udp jitter result repeat"
        ::= {sqaTestUdpJitterResultEntry 2}    
         --response                          
    sqaTestUdpJitterResultResponse  OBJECT-TYPE
        SYNTAX Unsigned32 ( 0..1000 )
        MAX-ACCESS read-only
        STATUS current
        DESCRIPTION "sqa udp jitter result response"
        ::= {sqaTestUdpJitterResultEntry 3}  
         --status                          
    sqaTestUdpJitterResultStatus    OBJECT-TYPE
        SYNTAX TestResultStatus
        MAX-ACCESS read-only
        STATUS current
        DESCRIPTION "sqa udp jitter result status"
        ::= {sqaTestUdpJitterResultEntry 4} 
         --des ip                          
    sqaTestUdpJitterResultDesIP     OBJECT-TYPE
        SYNTAX IpAddress
        MAX-ACCESS read-only
        STATUS current
        DESCRIPTION "sqa udp jitter result des ip"
        ::= {sqaTestUdpJitterResultEntry 5} 
         --min rtt sd                         
    sqaTestUdpJitterResultMinRTTSD    OBJECT-TYPE
        SYNTAX Integer32
        MAX-ACCESS read-only
        STATUS current
        DESCRIPTION "sqa udp jitter result min rtt sd"
        ::= {sqaTestUdpJitterResultEntry 6}  
         --max rtt sd                         
    sqaTestUdpJitterResultMaxRTTSD    OBJECT-TYPE
        SYNTAX Integer32
        MAX-ACCESS read-only
        STATUS current
        DESCRIPTION "sqa udp jitter result max rtt sd"
        ::= {sqaTestUdpJitterResultEntry 7} 
         --avg rtt sd                          
    sqaTestUdpJitterResultAvgRTTSD    OBJECT-TYPE
        SYNTAX Integer32
        MAX-ACCESS read-only
        STATUS current
        DESCRIPTION "sqa udp jitter result avg rtt sd"
        ::= {sqaTestUdpJitterResultEntry 8}
         --sum rtt sd
    sqaTestUdpJitterResultSumRTTSD    OBJECT-TYPE
        SYNTAX Integer32
        MAX-ACCESS read-only
        STATUS current
        DESCRIPTION "sqa udp jitter result sum rtt sd"
        ::= {sqaTestUdpJitterResultEntry 9} 
         --min rtt ds                         
    sqaTestUdpJitterResultMinRTTDS    OBJECT-TYPE
        SYNTAX Integer32
        MAX-ACCESS read-only
        STATUS current
        DESCRIPTION "sqa udp jitter result min rtt ds"
        ::= {sqaTestUdpJitterResultEntry 10}  
         --max rtt ds                         
    sqaTestUdpJitterResultMaxRTTDS    OBJECT-TYPE
        SYNTAX Integer32
        MAX-ACCESS read-only
        STATUS current
        DESCRIPTION "sqa udp jitter result max rtt ds"
        ::= {sqaTestUdpJitterResultEntry 11} 
         --avg rtt ds                          
    sqaTestUdpJitterResultAvgRTTDS    OBJECT-TYPE
        SYNTAX Integer32
        MAX-ACCESS read-only
        STATUS current
        DESCRIPTION "sqa udp jitter result avg rtt ds"
        ::= {sqaTestUdpJitterResultEntry 12}
         --sum rtt ds
    sqaTestUdpJitterResultSumRTTDS    OBJECT-TYPE
        SYNTAX Integer32
        MAX-ACCESS read-only
        STATUS current
        DESCRIPTION "sqa udp jitter result sum rtt ds"
        ::= {sqaTestUdpJitterResultEntry 13}     
         --min pos sd                             
    sqaTestUdpJitterResultMinPosSD   OBJECT-TYPE
        SYNTAX Unsigned32
        MAX-ACCESS read-only
        STATUS current
        DESCRIPTION "sqa udp jitter result min pos sd"
        ::= {sqaTestUdpJitterResultEntry 14} 
         --max pos sd                             
    sqaTestUdpJitterResultMaxPosSD   OBJECT-TYPE
        SYNTAX Unsigned32
        MAX-ACCESS read-only
        STATUS current
        DESCRIPTION "sqa udp jitter result max pos sd"
        ::= {sqaTestUdpJitterResultEntry 15} 
         --avg pos sd                           
    sqaTestUdpJitterResultAvgPosSD   OBJECT-TYPE
        SYNTAX Unsigned32
        MAX-ACCESS read-only
        STATUS current
        DESCRIPTION "sqa udp jitter result avg pos sd"
        ::= {sqaTestUdpJitterResultEntry 16}
         --sum pos sd                           
    sqaTestUdpJitterResultSumPosSD   OBJECT-TYPE
        SYNTAX Unsigned32
        MAX-ACCESS read-only
        STATUS current
        DESCRIPTION "sqa udp jitter result sum pos sd"
        ::= {sqaTestUdpJitterResultEntry 17}
         --num pos sd                           
    sqaTestUdpJitterResultNumPosSD   OBJECT-TYPE
        SYNTAX Unsigned32
        MAX-ACCESS read-only
        STATUS obsolete
        DESCRIPTION "sqa udp jitter result num pos sd"
        ::= {sqaTestUdpJitterResultEntry 18}  
         --min neg sd                             
    sqaTestUdpJitterResultMinNegSD   OBJECT-TYPE
        SYNTAX Unsigned32
        MAX-ACCESS read-only
        STATUS current
        DESCRIPTION "sqa udp jitter result min neg sd"
        ::= {sqaTestUdpJitterResultEntry 19} 
         --max neg sd                             
    sqaTestUdpJitterResultMaxNegSD   OBJECT-TYPE
        SYNTAX Unsigned32
        MAX-ACCESS read-only
        STATUS current
        DESCRIPTION "sqa udp jitter result max neg sd"
        ::= {sqaTestUdpJitterResultEntry 20}  
         --avg neg sd                           
    sqaTestUdpJitterResultAvgNegSD   OBJECT-TYPE
        SYNTAX Unsigned32
        MAX-ACCESS read-only
        STATUS current
        DESCRIPTION "sqa udp jitter result avg neg sd"
        ::= {sqaTestUdpJitterResultEntry 21}  
         --sum neg sd                           
    sqaTestUdpJitterResultSumNegSD   OBJECT-TYPE
        SYNTAX Unsigned32
        MAX-ACCESS read-only
        STATUS current
        DESCRIPTION "sqa udp jitter result sum neg sd"
        ::= {sqaTestUdpJitterResultEntry 22}
        --num neg sd                           
    sqaTestUdpJitterResultNumNegSD   OBJECT-TYPE
        SYNTAX Unsigned32
        MAX-ACCESS read-only
        STATUS obsolete
        DESCRIPTION "sqa udp jitter result num neg sd"
        ::= {sqaTestUdpJitterResultEntry 23}

        --min pos ds                             
    sqaTestUdpJitterResultMinPosDS   OBJECT-TYPE
        SYNTAX Unsigned32
        MAX-ACCESS read-only
        STATUS current
        DESCRIPTION "sqa udp jitter result min pos ds"
        ::= {sqaTestUdpJitterResultEntry 24} 
         --max pos ds                             
    sqaTestUdpJitterResultMaxPosDS   OBJECT-TYPE
        SYNTAX Unsigned32
        MAX-ACCESS read-only
        STATUS current
        DESCRIPTION "sqa udp jitter result max pos ds"
        ::= {sqaTestUdpJitterResultEntry 25} 
         --avg pos ds                           
    sqaTestUdpJitterResultAvgPosDS   OBJECT-TYPE
        SYNTAX Unsigned32
        MAX-ACCESS read-only
        STATUS current
        DESCRIPTION "sqa udp jitter result avg pos ds"
        ::= {sqaTestUdpJitterResultEntry 26}
         --sum pos ds                           
    sqaTestUdpJitterResultSumPosDS   OBJECT-TYPE
        SYNTAX Unsigned32
        MAX-ACCESS read-only
        STATUS current
        DESCRIPTION "sqa udp jitter result sum pos ds"
        ::= {sqaTestUdpJitterResultEntry 27}
         --num pos ds                           
    sqaTestUdpJitterResultNumPosDS   OBJECT-TYPE
        SYNTAX Unsigned32
        MAX-ACCESS read-only
        STATUS obsolete
        DESCRIPTION "sqa udp jitter result num pos ds"
        ::= {sqaTestUdpJitterResultEntry 28}   
         --min neg ds                             
    sqaTestUdpJitterResultMinNegDS   OBJECT-TYPE
        SYNTAX Unsigned32
        MAX-ACCESS read-only
        STATUS current
        DESCRIPTION "sqa udp jitter result min neg ds"
        ::= {sqaTestUdpJitterResultEntry 29} 
         --max neg ds                             
    sqaTestUdpJitterResultMaxNegDS   OBJECT-TYPE
        SYNTAX Unsigned32
        MAX-ACCESS read-only
        STATUS current
        DESCRIPTION "sqa udp jitter result max neg ds"
        ::= {sqaTestUdpJitterResultEntry 30}  
         --avg neg ds                           
    sqaTestUdpJitterResultAvgNegDS   OBJECT-TYPE
        SYNTAX Unsigned32
        MAX-ACCESS read-only
        STATUS current
        DESCRIPTION "sqa udp jitter result avg neg ds"
        ::= {sqaTestUdpJitterResultEntry 31}  
         --sum neg ds                           
    sqaTestUdpJitterResultSumNegDS   OBJECT-TYPE
        SYNTAX Unsigned32
        MAX-ACCESS read-only
        STATUS current
        DESCRIPTION "sqa udp jitter result sum neg ds"
        ::= {sqaTestUdpJitterResultEntry 32}
         --num neg ds                           
    sqaTestUdpJitterResultNumNegDS   OBJECT-TYPE
        SYNTAX Unsigned32
        MAX-ACCESS read-only
        STATUS obsolete
        DESCRIPTION "sqa udp jitter result num neg ds"
        ::= {sqaTestUdpJitterResultEntry 33}
         --num dispose sd                           
    sqaTestUdpJitterResultDisposeNumSD   OBJECT-TYPE
        SYNTAX Unsigned32
        MAX-ACCESS read-only
        STATUS current
        DESCRIPTION "sqa udp jitter result dispose num sd"
        ::= {sqaTestUdpJitterResultEntry 34}
         --num dispose ds                           
    sqaTestUdpJitterResultDisposeNumDS   OBJECT-TYPE
        SYNTAX Unsigned32
        MAX-ACCESS read-only
        STATUS current
        DESCRIPTION "sqa udp jitter result dispose num ds"
        ::= {sqaTestUdpJitterResultEntry 35}
                  
         --probe time
    sqaTestUdpJitterResultProbeTime OBJECT-TYPE
        SYNTAX DisplayString
        MAX-ACCESS read-only
        STATUS current
        DESCRIPTION "sqa udp jitterresult probe time"
        ::= {sqaTestUdpJitterResultEntry 36}
        
 
--snmp result
    sqaTestSnmpResultTable  OBJECT-TYPE
        SYNTAX SEQUENCE OF SqaTestSnmpResultEntry
        MAX-ACCESS not-accessible
        STATUS current
        DESCRIPTION "sqa snmp result table" 
        ::={sqaMib 16} 
                              
    sqaTestSnmpResultEntry      OBJECT-TYPE
        SYNTAX SqaTestSnmpResultEntry
        MAX-ACCESS not-accessible   
        STATUS current
        DESCRIPTION "sqa snmp result entry"
        INDEX {sqaTestSnmpResultTestNum}
        ::={sqaTestSnmpResultTable 1}    
                                        
    SqaTestSnmpResultEntry ::=
        SEQUENCE
        { 
            sqaTestSnmpResultTestNum
                INTEGER, 
            sqaTestSnmpResultStatus
                TestResultStatus,
            sqaTestSnmpResultRTT
                Unsigned32,
            sqaTestSnmpResultProbeTime
                DisplayString
        } 
         --test number
    sqaTestSnmpResultTestNum   OBJECT-TYPE
        SYNTAX INTEGER ( 1..65535 )
        MAX-ACCESS read-only
        STATUS current
        DESCRIPTION "sqa snmp result test num"
        ::={sqaTestSnmpResultEntry 1}  
         --status
    sqaTestSnmpResultStatus   OBJECT-TYPE
        SYNTAX TestResultStatus
        MAX-ACCESS read-only
        STATUS current
        DESCRIPTION "sqa snmp result test status"
        ::={sqaTestSnmpResultEntry 2}
         --rtt                           
    sqaTestSnmpResultRTT   OBJECT-TYPE
        SYNTAX Unsigned32
        MAX-ACCESS read-only
        STATUS current
        DESCRIPTION "sqa snmp result last rtt"
        ::= {sqaTestSnmpResultEntry 3}   
        
        --probe time
    sqaTestSnmpResultProbeTime  OBJECT-TYPE
        SYNTAX DisplayString
        MAX-ACCESS read-only
        STATUS current
        DESCRIPTION "sqa snmp result probe time"
        ::= {sqaTestSnmpResultEntry 4}
  
  
--http result         
    sqaTestHttpResultTable     OBJECT-TYPE
        SYNTAX SEQUENCE OF SqaTestHttpResultEntry
        MAX-ACCESS not-accessible
        STATUS current
        DESCRIPTION "sqa http result table"
        ::={sqaMib 17} 
    sqaTestHttpResultEntry     OBJECT-TYPE
        SYNTAX SqaTestHttpResultEntry
        MAX-ACCESS not-accessible
        STATUS current
        DESCRIPTION "sqa http result entry"
        INDEX {sqaTestHttpResultTestNum} 
        ::={sqaTestHttpResultTable 1}  
    SqaTestHttpResultEntry::= 
        SEQUENCE
        {  
            sqaTestHttpResultTestNum
                INTEGER,
            sqaTestHttpResultRepeat
                Unsigned32,
            sqaTestHttpResultResponse
                Unsigned32, 
            sqaTestHttpResultStatus
                TestResultStatus,
            sqaTestHttpResultDesIP
                IpAddress,
            sqaTestHttpResultDesurl
                DisplayString, 
            sqaTestHttpResultDNSMinRTT
                Unsigned32,
            sqaTestHttpResultDNSMaxRTT
                Unsigned32,
            sqaTestHttpResultDNSAvgRTT
                Unsigned32,
            sqaTestHttpResultDNSSumRTT
                Unsigned32,
            sqaTestHttpResultDNSNum
                Unsigned32,
            sqaTestHttpResultTCPMinRTT
                Unsigned32,
            sqaTestHttpResultTCPMaxRTT
                Unsigned32,
            sqaTestHttpResultTCPAvgRTT
                Unsigned32,
            sqaTestHttpResultTCPSumRTT
                Unsigned32,
            sqaTestHttpResultTCPNum
                Unsigned32,
            sqaTestHttpResultHTTPMinRTT
                Unsigned32,
            sqaTestHttpResultHTTPMaxRTT
                Unsigned32,
            sqaTestHttpResultHTTPAvgRTT
                Unsigned32,
            sqaTestHttpResultHTTPSumRTT
                Unsigned32,
            sqaTestHttpResultHTTPNum
                Unsigned32, 
            sqaTestHttpResultMinRTT
                Unsigned32,
            sqaTestHttpResultMaxRTT
                Unsigned32,
            sqaTestHttpResultAvgRTT
                Unsigned32,
            sqaTestHttpResultSumRTT
                Unsigned32,
            sqaTestHttpResultProbeTime
                DisplayString                                                    
        } 
        --test num
    sqaTestHttpResultTestNum   OBJECT-TYPE
        SYNTAX INTEGER ( 1..65535 )
        MAX-ACCESS read-only
        STATUS current
        DESCRIPTION "sqa http result test num"
        ::= {sqaTestHttpResultEntry 1}  
        --repeat                              
    sqaTestHttpResultRepeat    OBJECT-TYPE
        SYNTAX Unsigned32 ( 1..10 )
        MAX-ACCESS read-only
        STATUS current
        DESCRIPTION "sqa http result repeat"
        ::= {sqaTestHttpResultEntry 2}    
        --response                          
    sqaTestHttpResultResponse  OBJECT-TYPE
        SYNTAX Unsigned32 ( 0..10 )
        MAX-ACCESS read-only
        STATUS current
        DESCRIPTION "sqa http result response"
        ::= {sqaTestHttpResultEntry 3}  
        --status                          
    sqaTestHttpResultStatus    OBJECT-TYPE
        SYNTAX TestResultStatus
        MAX-ACCESS read-only
        STATUS current
        DESCRIPTION "sqa http result status"
        ::= {sqaTestHttpResultEntry 4} 
        --des ip                          
    sqaTestHttpResultDesIP     OBJECT-TYPE
        SYNTAX IpAddress
        MAX-ACCESS read-only
        STATUS current
        DESCRIPTION "sqa http result des ip"
        ::= {sqaTestHttpResultEntry 5} 
         --destination url
    sqaTestHttpResultDesurl    OBJECT-TYPE
        SYNTAX DisplayString
        MAX-ACCESS read-only
        STATUS current
        DESCRIPTION "sqa http result destination url"
        ::= {sqaTestHttpResultEntry 6}
        --dns min rtt                          
    sqaTestHttpResultDNSMinRTT    OBJECT-TYPE
        SYNTAX Unsigned32
        MAX-ACCESS read-only
        STATUS current
        DESCRIPTION "sqa http result dns min rtt"
        ::= {sqaTestHttpResultEntry 7}  
        --dns max rtt                          
    sqaTestHttpResultDNSMaxRTT    OBJECT-TYPE
        SYNTAX Unsigned32
        MAX-ACCESS read-only
        STATUS current
        DESCRIPTION "sqa http result dns max rtt"
        ::= {sqaTestHttpResultEntry 8} 
        --dns avg rtt                          
    sqaTestHttpResultDNSAvgRTT    OBJECT-TYPE
        SYNTAX Unsigned32
        MAX-ACCESS read-only
        STATUS current
        DESCRIPTION "sqa http result dns avg rtt"
        ::= {sqaTestHttpResultEntry 9}
        --dns sum rtt
    sqaTestHttpResultDNSSumRTT     OBJECT-TYPE
        SYNTAX Unsigned32
        MAX-ACCESS read-only
        STATUS current
        DESCRIPTION "sqa http result dns sum rtt"
        ::= {sqaTestHttpResultEntry 10}
        --dns num 
    sqaTestHttpResultDNSNum        OBJECT-TYPE
        SYNTAX Unsigned32
        MAX-ACCESS read-only
        STATUS obsolete
        DESCRIPTION "sqa http result dns num"
        ::= {sqaTestHttpResultEntry 11}  
        --tcp min rtt                          
    sqaTestHttpResultTCPMinRTT    OBJECT-TYPE
        SYNTAX Unsigned32
        MAX-ACCESS read-only
        STATUS current
        DESCRIPTION "sqa http result tcp min rtt"
        ::= {sqaTestHttpResultEntry 12}  
        --tcp max rtt                          
    sqaTestHttpResultTCPMaxRTT    OBJECT-TYPE
        SYNTAX Unsigned32
        MAX-ACCESS read-only
        STATUS current
        DESCRIPTION "sqa http result tcp max rtt"
        ::= {sqaTestHttpResultEntry 13} 
        --tcp avg rtt                          
    sqaTestHttpResultTCPAvgRTT    OBJECT-TYPE
        SYNTAX Unsigned32
        MAX-ACCESS read-only
        STATUS current
        DESCRIPTION "sqa http result tcp avg rtt"
        ::= {sqaTestHttpResultEntry 14}
        --tcp sum rtt
    sqaTestHttpResultTCPSumRTT     OBJECT-TYPE
        SYNTAX Unsigned32
        MAX-ACCESS read-only
        STATUS current
        DESCRIPTION "sqa http result tcp sum rtt"
        ::= {sqaTestHttpResultEntry 15}
        --tcp num 
    sqaTestHttpResultTCPNum     OBJECT-TYPE
        SYNTAX Unsigned32
        MAX-ACCESS read-only
        STATUS obsolete
        DESCRIPTION "sqa http result tcp num "
        ::= {sqaTestHttpResultEntry 16}         
        --http min rtt                          
    sqaTestHttpResultHTTPMinRTT    OBJECT-TYPE
        SYNTAX Unsigned32
        MAX-ACCESS read-only
        STATUS current
        DESCRIPTION "sqa http result http min rtt"
        ::= {sqaTestHttpResultEntry 17}  
        --http max rtt                          
    sqaTestHttpResultHTTPMaxRTT    OBJECT-TYPE
        SYNTAX Unsigned32
        MAX-ACCESS read-only
        STATUS current
        DESCRIPTION "sqa http result http max rtt"
        ::= {sqaTestHttpResultEntry 18} 
        --http avg rtt                          
    sqaTestHttpResultHTTPAvgRTT    OBJECT-TYPE
        SYNTAX Unsigned32
        MAX-ACCESS read-only
        STATUS current
        DESCRIPTION "sqa http result http avg rtt"
        ::= {sqaTestHttpResultEntry 19}
        --http sum rtt
    sqaTestHttpResultHTTPSumRTT     OBJECT-TYPE
        SYNTAX Unsigned32
        MAX-ACCESS read-only
        STATUS current
        DESCRIPTION "sqa http result http sum rtt"
        ::= {sqaTestHttpResultEntry 20} 
        --http num rtt
    sqaTestHttpResultHTTPNum     OBJECT-TYPE
        SYNTAX Unsigned32
        MAX-ACCESS read-only
        STATUS obsolete
        DESCRIPTION "sqa http result http num"
        ::= {sqaTestHttpResultEntry 21}
        --min rtt                          
    sqaTestHttpResultMinRTT    OBJECT-TYPE
        SYNTAX Unsigned32
        MAX-ACCESS read-only
        STATUS current
        DESCRIPTION "sqa http result min rtt"
        ::= {sqaTestHttpResultEntry 22}  
        --max rtt                          
    sqaTestHttpResultMaxRTT    OBJECT-TYPE
        SYNTAX Unsigned32
        MAX-ACCESS read-only
        STATUS current
        DESCRIPTION "sqa http result max rtt"
        ::= {sqaTestHttpResultEntry 23} 
        --avg rtt                          
    sqaTestHttpResultAvgRTT    OBJECT-TYPE
        SYNTAX Unsigned32
        MAX-ACCESS read-only
        STATUS current
        DESCRIPTION "sqa http result avg rtt"
        ::= {sqaTestHttpResultEntry 24}
        --sum rtt
    sqaTestHttpResultSumRTT     OBJECT-TYPE
        SYNTAX Unsigned32
        MAX-ACCESS read-only
        STATUS current
        DESCRIPTION "sqa http result sum rtt"
        ::= {sqaTestHttpResultEntry 25}                    
         --probe time
    sqaTestHttpResultProbeTime OBJECT-TYPE
        SYNTAX DisplayString
        MAX-ACCESS read-only
        STATUS current
        DESCRIPTION "sqa http result probe time"
        ::= {sqaTestHttpResultEntry 26}
                 
    --icmpjitter result         
    sqaTestIcmpJitterResultTable  OBJECT-TYPE
        SYNTAX SEQUENCE OF SqaTestIcmpJitterResultEntry
        MAX-ACCESS not-accessible
        STATUS current
        DESCRIPTION "sqa icmp jitter result table"
        ::={sqaMib 18} 
    sqaTestIcmpJitterResultEntry      OBJECT-TYPE
        SYNTAX SqaTestIcmpJitterResultEntry
        MAX-ACCESS not-accessible
        STATUS current
        DESCRIPTION "sqa icmp jitter result entry"
        INDEX {sqaTestIcmpJitterResultTestNum} 
        ::={sqaTestIcmpJitterResultTable 1}  
    SqaTestIcmpJitterResultEntry::= 
        SEQUENCE
        {  
            sqaTestIcmpJitterResultTestNum
                INTEGER,
            sqaTestIcmpJitterResultRepeat
                Unsigned32,
            sqaTestIcmpJitterResultResponse
                Unsigned32, 
            sqaTestIcmpJitterResultStatus
                TestResultStatus,
            sqaTestIcmpJitterResultDesIP
                IpAddress, 
            
            sqaTestIcmpJitterResultMinRTTSD
                Unsigned32,
            sqaTestIcmpJitterResultMaxRTTSD
                Unsigned32,
            sqaTestIcmpJitterResultAvgRTTSD
                Unsigned32,
            sqaTestIcmpJitterResultSumRTTSD
                Unsigned32, 
            
            sqaTestIcmpJitterResultMinRTTDS
                Unsigned32,
            sqaTestIcmpJitterResultMaxRTTDS
                Unsigned32,
            sqaTestIcmpJitterResultAvgRTTDS
                Unsigned32,
            sqaTestIcmpJitterResultSumRTTDS
                Unsigned32,

            sqaTestIcmpJitterResultMinPosSD
                Unsigned32,
            sqaTestIcmpJitterResultMaxPosSD
                Unsigned32,
            sqaTestIcmpJitterResultAvgPosSD
                Unsigned32,
            sqaTestIcmpJitterResultSumPosSD
                Unsigned32,

            sqaTestIcmpJitterResultMinNegSD
                Unsigned32,
            sqaTestIcmpJitterResultMaxNegSD
                Unsigned32,
            sqaTestIcmpJitterResultAvgNegSD
                Unsigned32,
            sqaTestIcmpJitterResultSumNegSD
                Unsigned32,
            
            sqaTestIcmpJitterResultMinPosDS
                Unsigned32,
            sqaTestIcmpJitterResultMaxPosDS
                Unsigned32,
            sqaTestIcmpJitterResultAvgPosDS
                Unsigned32,
            sqaTestIcmpJitterResultSumPosDS
                Unsigned32, 

            sqaTestIcmpJitterResultMinNegDS
                Unsigned32,
            sqaTestIcmpJitterResultMaxNegDS
                Unsigned32,
            sqaTestIcmpJitterResultAvgNegDS
                Unsigned32,
            sqaTestIcmpJitterResultSumNegDS
                Unsigned32,
            
            sqaTestIcmpJitterResultProbeTime
                DisplayString                                                    
        } 
         --test num
    sqaTestIcmpJitterResultTestNum  OBJECT-TYPE
        SYNTAX INTEGER ( 1..65535 )
        MAX-ACCESS read-only
        STATUS current
        DESCRIPTION "sqa icmp jitter result test num"
        ::= {sqaTestIcmpJitterResultEntry 1}  
         --repeat                               
    sqaTestIcmpJitterResultRepeat   OBJECT-TYPE
        SYNTAX Unsigned32 ( 1..65535 )
        MAX-ACCESS read-only
        STATUS current
        DESCRIPTION "sqa icmp jitter result repeat"
        ::= {sqaTestIcmpJitterResultEntry 2}    
         --response                          
    sqaTestIcmpJitterResultResponse OBJECT-TYPE
        SYNTAX Unsigned32 ( 0..65535 )
        MAX-ACCESS read-only
        STATUS current
        DESCRIPTION "sqa icmp jitter result response"
        ::= {sqaTestIcmpJitterResultEntry 3}  
         --status                          
    sqaTestIcmpJitterResultStatus   OBJECT-TYPE
        SYNTAX TestResultStatus
        MAX-ACCESS read-only
        STATUS current
        DESCRIPTION "sqa icmp jitter result status"
        ::= {sqaTestIcmpJitterResultEntry 4} 
         --des ip                          
    sqaTestIcmpJitterResultDesIP    OBJECT-TYPE
        SYNTAX IpAddress
        MAX-ACCESS read-only
        STATUS current
        DESCRIPTION "sqa icmp jitter result des ip"
        ::= {sqaTestIcmpJitterResultEntry 5} 
         --min rtt sd                         
    sqaTestIcmpJitterResultMinRTTSD   OBJECT-TYPE
        SYNTAX Unsigned32
        MAX-ACCESS read-only
        STATUS current
        DESCRIPTION "sqa icmp jitter result min rtt sd"
        ::= {sqaTestIcmpJitterResultEntry 6}  
         --max rtt sd                         
    sqaTestIcmpJitterResultMaxRTTSD   OBJECT-TYPE
        SYNTAX Unsigned32
        MAX-ACCESS read-only
        STATUS current
        DESCRIPTION "sqa icmp jitter result max rtt sd"
        ::= {sqaTestIcmpJitterResultEntry 7} 
         --avg rtt sd                          
    sqaTestIcmpJitterResultAvgRTTSD   OBJECT-TYPE
        SYNTAX Unsigned32
        MAX-ACCESS read-only
        STATUS current
        DESCRIPTION "sqa icmp jitter result avg rtt sd"
        ::= {sqaTestIcmpJitterResultEntry 8}
         --sum rtt sd
    sqaTestIcmpJitterResultSumRTTSD   OBJECT-TYPE
        SYNTAX Unsigned32
        MAX-ACCESS read-only
        STATUS current
        DESCRIPTION "sqa icmp jitter result sum rtt sd"
        ::= {sqaTestIcmpJitterResultEntry 9} 
         --min rtt ds                         
    sqaTestIcmpJitterResultMinRTTDS   OBJECT-TYPE
        SYNTAX Unsigned32
        MAX-ACCESS read-only
        STATUS current
        DESCRIPTION "sqa icmp jitter result min rtt ds"
        ::= {sqaTestIcmpJitterResultEntry 10}  
         --max rtt ds                         
    sqaTestIcmpJitterResultMaxRTTDS   OBJECT-TYPE
        SYNTAX Unsigned32
        MAX-ACCESS read-only
        STATUS current
        DESCRIPTION "sqa udp jitter result max rtt ds"
        ::= {sqaTestIcmpJitterResultEntry 11} 
         --avg rtt ds                          
    sqaTestIcmpJitterResultAvgRTTDS   OBJECT-TYPE
        SYNTAX Unsigned32
        MAX-ACCESS read-only
        STATUS current
        DESCRIPTION "sqa icmp jitter result avg rtt ds"
        ::= {sqaTestIcmpJitterResultEntry 12}
         --sum rtt ds
    sqaTestIcmpJitterResultSumRTTDS   OBJECT-TYPE
        SYNTAX Unsigned32
        MAX-ACCESS read-only
        STATUS current
        DESCRIPTION "sqa icmp jitter result sum rtt ds"
        ::= {sqaTestIcmpJitterResultEntry 13}     
         --min pos sd                             
    sqaTestIcmpJitterResultMinPosSD  OBJECT-TYPE
        SYNTAX Unsigned32
        MAX-ACCESS read-only
        STATUS current
        DESCRIPTION "sqa icmp jitter result min pos sd"
        ::= {sqaTestIcmpJitterResultEntry 14} 
         --max pos sd                             
    sqaTestIcmpJitterResultMaxPosSD  OBJECT-TYPE
        SYNTAX Unsigned32
        MAX-ACCESS read-only
        STATUS current
        DESCRIPTION "sqa icmp jitter result max pos sd"
        ::= {sqaTestIcmpJitterResultEntry 15} 
         --avg pos sd                           
    sqaTestIcmpJitterResultAvgPosSD  OBJECT-TYPE
        SYNTAX Unsigned32
        MAX-ACCESS read-only
        STATUS current
        DESCRIPTION "sqa icmp jitter result avg pos sd"
        ::= {sqaTestIcmpJitterResultEntry 16}
         --sum pos sd                           
    sqaTestIcmpJitterResultSumPosSD  OBJECT-TYPE
        SYNTAX Unsigned32
        MAX-ACCESS read-only
        STATUS current
        DESCRIPTION "sqa icmp jitter result sum pos sd"
        ::= {sqaTestIcmpJitterResultEntry 17}
         --min neg sd                             
    sqaTestIcmpJitterResultMinNegSD  OBJECT-TYPE
        SYNTAX Unsigned32
        MAX-ACCESS read-only
        STATUS current
        DESCRIPTION "sqa icmp jitter result min neg sd"
        ::= {sqaTestIcmpJitterResultEntry 18} 
         --max neg sd                             
    sqaTestIcmpJitterResultMaxNegSD  OBJECT-TYPE
        SYNTAX Unsigned32
        MAX-ACCESS read-only
        STATUS current
        DESCRIPTION "sqa icmp jitter result max neg sd"
        ::= {sqaTestIcmpJitterResultEntry 19}  
         --avg neg sd                           
    sqaTestIcmpJitterResultAvgNegSD  OBJECT-TYPE
        SYNTAX Unsigned32
        MAX-ACCESS read-only
        STATUS current
        DESCRIPTION "sqa icmp jitter result avg neg sd"
        ::= {sqaTestIcmpJitterResultEntry 20}  
         --sum neg sd                           
    sqaTestIcmpJitterResultSumNegSD  OBJECT-TYPE
        SYNTAX Unsigned32
        MAX-ACCESS read-only
        STATUS current
        DESCRIPTION "sqa icmp jitter result sum neg sd"
        ::= {sqaTestIcmpJitterResultEntry 21}
         --min pos ds                             
    sqaTestIcmpJitterResultMinPosDS  OBJECT-TYPE
        SYNTAX Unsigned32
        MAX-ACCESS read-only
        STATUS current
        DESCRIPTION "sqa icmp jitter result min pos ds"
        ::= {sqaTestIcmpJitterResultEntry 22} 
         --max pos ds                             
    sqaTestIcmpJitterResultMaxPosDS  OBJECT-TYPE
        SYNTAX Unsigned32
        MAX-ACCESS read-only
        STATUS current
        DESCRIPTION "sqa icmp jitter result max pos ds"
        ::= {sqaTestIcmpJitterResultEntry 23} 
         --avg pos ds                           
    sqaTestIcmpJitterResultAvgPosDS  OBJECT-TYPE
        SYNTAX Unsigned32
        MAX-ACCESS read-only
        STATUS current
        DESCRIPTION "sqa icmp jitter result avg pos ds"
        ::= {sqaTestIcmpJitterResultEntry 24}
         --sum pos ds                           
    sqaTestIcmpJitterResultSumPosDS  OBJECT-TYPE
        SYNTAX Unsigned32
        MAX-ACCESS read-only
        STATUS current
        DESCRIPTION "sqa icmp jitter result sum pos ds"
        ::= {sqaTestIcmpJitterResultEntry 25}  
         --min neg ds                             
    sqaTestIcmpJitterResultMinNegDS  OBJECT-TYPE
        SYNTAX Unsigned32
        MAX-ACCESS read-only
        STATUS current
        DESCRIPTION "sqa icmp jitter result min neg ds"
        ::= {sqaTestIcmpJitterResultEntry 26} 
         --max neg ds                             
    sqaTestIcmpJitterResultMaxNegDS  OBJECT-TYPE
        SYNTAX Unsigned32
        MAX-ACCESS read-only
        STATUS current
        DESCRIPTION "sqa icmp jitter result max neg ds"
        ::= {sqaTestIcmpJitterResultEntry 27}  
         --avg neg ds                           
    sqaTestIcmpJitterResultAvgNegDS  OBJECT-TYPE
        SYNTAX Unsigned32
        MAX-ACCESS read-only
        STATUS current
        DESCRIPTION "sqa icmp jitter result avg neg ds"
        ::= {sqaTestIcmpJitterResultEntry 28}  
         --sum neg ds                           
    sqaTestIcmpJitterResultSumNegDS  OBJECT-TYPE
        SYNTAX Unsigned32
        MAX-ACCESS read-only
        STATUS current
        DESCRIPTION "sqa icmp jitter result sum neg ds"
        ::= {sqaTestIcmpJitterResultEntry 29}
         --probe time
    sqaTestIcmpJitterResultProbeTime OBJECT-TYPE
        SYNTAX DisplayString
        MAX-ACCESS read-only
        STATUS current
        DESCRIPTION "sqa icmp jitterresult probe time"
        ::= {sqaTestIcmpJitterResultEntry 30}
       
    sqaTestSenderTable  OBJECT-TYPE
        SYNTAX SEQUENCE OF SqaTestSenderEntry
        MAX-ACCESS not-accessible
        STATUS current
        DESCRIPTION "sqa generalflow sender table"
        ::={sqaMib 19} 
    sqaTestSenderEntry      OBJECT-TYPE
        SYNTAX SqaTestSenderEntry
        MAX-ACCESS not-accessible
        STATUS current
        DESCRIPTION "sqa generalflow sender entry"
        INDEX {sqaTestSenderTestNum} 
        ::={sqaTestSenderTable 1}  
    
    SqaTestSenderEntry::= 
        SEQUENCE
        {  
            sqaTestSenderTestNum
                Unsigned32,
            sqaTestSenderClientMode
                TestClientMode,
            sqaTestSenderInboundInterface
                DisplayString, 
            sqaTestSenderTestMode
                TestTestMode,
            sqaTestSenderDisNonTest8021p
                Unsigned32,             
            sqaTestSenderDisNonTestDscp
                Unsigned32,
            sqaTestSenderReflectorMode
                TestReflectorMode,
            sqaTestSenderSourceMac
                MacAddress,
            sqaTestSenderDestinationMac
                MacAddress,             
            sqaTestSenderSourceIp
                IpAddress,
            sqaTestSenderDestinationIp
                IpAddress,
            sqaTestSenderVlanId
                Unsigned32,
            sqaTestSenderInVlanId
                Unsigned32,
            sqaTestSenderExVlanId
                Unsigned32,
            sqaTestSenderPriority8021p
                Unsigned32,
            sqaTestSenderDscp
                Unsigned32,

            sqaTestSenderTpEnable
                TestEnableStatus,
            sqaTestSenderTpRateType
                TestRateType,
            sqaTestSenderTpHighRate
                Unsigned32,
            sqaTestSenderTpLowRate
                Unsigned32,
            sqaTestSenderTpTimeOut
                Unsigned32,           
            sqaTestSenderTpOneRateDuration
                Unsigned32,
            sqaTestSenderTpDuration
                Unsigned32,
            sqaTestSenderTpPrecision
                Unsigned32,
            sqaTestSenderTpLossThreshold
                Unsigned32,
 
            sqaTestSenderLossEnable
                TestEnableStatus,
            sqaTestSenderLossRateType
                TestRateType,
            sqaTestSenderLossRate
                Unsigned32,
            sqaTestSenderLossTimeOut
                Unsigned32,            
            sqaTestSenderLossDuration
                Unsigned32,                
            sqaTestSenderLossRatioThreshold
                Unsigned32, 

            sqaTestSenderDelayEnable
                TestEnableStatus,
            sqaTestSenderDelayRateType
                TestRateType,
            sqaTestSenderDelayRate
                Unsigned32,
            sqaTestSenderDelayInterval
                Unsigned32,
            sqaTestSenderDelayDuration
                Unsigned32,
            sqaTestSenderDelayThreshold
                Unsigned32,
            sqaTestSenderJitterThreshold
                Unsigned32,

            sqaTestSenderPacketSize1
                Unsigned32,
            sqaTestSenderPacketSize2
                Unsigned32,
            sqaTestSenderPacketSize3
                Unsigned32,           
            sqaTestSenderPacketSize4
                Unsigned32,
            sqaTestSenderPacketSize5
                Unsigned32,
            sqaTestSenderPacketSize6
                Unsigned32,
            sqaTestSenderPacketSize7
                Unsigned32,
 
            sqaTestSenderOnlineOfflineFlag
                TestOnlineState,
            sqaTestSenderFreeArpEnable
                TestEnableStatus,
            sqaTestSenderFreeArpInterval
                Unsigned32,
            sqaTestSenderTimeRange
                DisplayString                                                  
        }
         --test num
    sqaTestSenderTestNum  OBJECT-TYPE
        SYNTAX Unsigned32 ( 1..65535 )
        MAX-ACCESS not-accessible
        STATUS current
        DESCRIPTION "sqa sender test num. The range of this parameter depend on the device."
        ::= {sqaTestSenderEntry 1}  
         --ClientMode                               
    sqaTestSenderClientMode   OBJECT-TYPE
        SYNTAX TestClientMode
        MAX-ACCESS read-only
        STATUS current
        DESCRIPTION "sqa sender client mode, 1: l2-uni, 2: l3-uni, 3: l2-bridge-uni, 255: undefined(invalid)"
        ::= {sqaTestSenderEntry 2}    
         --InboundInterface                          
    sqaTestSenderInboundInterface OBJECT-TYPE
        SYNTAX DisplayString    (SIZE(0..31))
        MAX-ACCESS read-only
        STATUS current
        DESCRIPTION "sqa sender inbound interface"
        ::= {sqaTestSenderEntry 3}  
         --TestMode                          
    sqaTestSenderTestMode   OBJECT-TYPE
        SYNTAX TestTestMode
        MAX-ACCESS read-only
        STATUS current
        DESCRIPTION "sqa sender test mode, 1: share-mode(default), 2: exclusive-mode"
        ::= {sqaTestSenderEntry 4} 
         --DisNonTest8021p                          
    sqaTestSenderDisNonTest8021p    OBJECT-TYPE
        SYNTAX Unsigned32    ( 0..7 | 255)
        MAX-ACCESS read-only
        STATUS current
        DESCRIPTION "sqa sender disNonTest8021p, 255: undefined(invalid)"
        ::= {sqaTestSenderEntry 5} 
         --DisNonTestDscp                         
    sqaTestSenderDisNonTestDscp   OBJECT-TYPE
        SYNTAX Unsigned32    ( 0..63 | 255)
        MAX-ACCESS read-only
        STATUS current
        DESCRIPTION "sqa sender disNonTestDscp, 255: undefined(invalid)"
        ::= {sqaTestSenderEntry 6}  
         --RefectorMode                         
    sqaTestSenderReflectorMode   OBJECT-TYPE
        SYNTAX TestReflectorMode
        MAX-ACCESS read-only
        STATUS current
        DESCRIPTION "sqa sender reflector mode, 1:l1, 2:l2, 3:l3, 4:l4, 5:default"
        ::= {sqaTestSenderEntry 7} 
         --SourceMac                          
    sqaTestSenderSourceMac   OBJECT-TYPE
        SYNTAX MacAddress
        MAX-ACCESS read-only
        STATUS current
        DESCRIPTION "sqa sender source mac"
        ::= {sqaTestSenderEntry 8}
         --DestinationMac
    sqaTestSenderDestinationMac   OBJECT-TYPE
        SYNTAX MacAddress
        MAX-ACCESS read-only
        STATUS current
        DESCRIPTION "sqa sender destination mac"
        ::= {sqaTestSenderEntry 9} 
         --SourceIp                         
    sqaTestSenderSourceIp   OBJECT-TYPE
        SYNTAX IpAddress
        MAX-ACCESS read-only
        STATUS current
        DESCRIPTION "sqa sender source ip"
        ::= {sqaTestSenderEntry 10}  

         --DestinationIp                         
    sqaTestSenderDestinationIp   OBJECT-TYPE
        SYNTAX IpAddress
        MAX-ACCESS read-only
        STATUS current
        DESCRIPTION "sqa sender destination ip"
        ::= {sqaTestSenderEntry 11} 
         --VlanId                          
    sqaTestSenderVlanId   OBJECT-TYPE
        SYNTAX Unsigned32   ( 0..4094 )
        MAX-ACCESS read-only
        STATUS current
        DESCRIPTION "sqa sender vlan id"
        ::= {sqaTestSenderEntry 12}
         --InVlanId
    sqaTestSenderInVlanId   OBJECT-TYPE
        SYNTAX Unsigned32    ( 0..4094 )
        MAX-ACCESS read-only
        STATUS current
        DESCRIPTION "sqa sender internal vlan id"
        ::= {sqaTestSenderEntry 13}     
         --ExVlanId                             
    sqaTestSenderExVlanId  OBJECT-TYPE
        SYNTAX Unsigned32    ( 0..4094 )
        MAX-ACCESS read-only
        STATUS current
        DESCRIPTION "sqa sender external vlan id"
        ::= {sqaTestSenderEntry 14} 
         --Priority8021p                             
    sqaTestSenderPriority8021p  OBJECT-TYPE
        SYNTAX Unsigned32    ( 0..7 )
        MAX-ACCESS read-only
        STATUS current
        DESCRIPTION "sqa sender priority8021p, default: 0"
        ::= {sqaTestSenderEntry 15} 
         --Dscp                           
    sqaTestSenderDscp  OBJECT-TYPE
        SYNTAX Unsigned32    ( 0..63 )
        MAX-ACCESS read-only
        STATUS current
        DESCRIPTION "sqa sender dscp, default: 0"
        ::= {sqaTestSenderEntry 16}
         --TpEnable
    sqaTestSenderTpEnable  OBJECT-TYPE
        SYNTAX TestEnableStatus
        MAX-ACCESS read-only
        STATUS current
        DESCRIPTION "sqa sender throughput enable"
        ::= {sqaTestSenderEntry 17}
         --TpRateType                             
    sqaTestSenderTpRateType  OBJECT-TYPE
        SYNTAX TestRateType
        MAX-ACCESS read-only
        STATUS current
        DESCRIPTION "sqa sender throughput rate type, 1: ir(default), 2: ulr"
        ::= {sqaTestSenderEntry 18} 
         --TpHighRate                             
    sqaTestSenderTpHighRate  OBJECT-TYPE
        SYNTAX Unsigned32  ( 0..10000000 )
        MAX-ACCESS read-only
        STATUS current
        DESCRIPTION "sqa sender throughput high rate, unit : kbps"
        ::= {sqaTestSenderEntry 19}  
         --TpLowRate                           
    sqaTestSenderTpLowRate  OBJECT-TYPE
        SYNTAX Unsigned32   ( 0..10000000 )
        MAX-ACCESS read-only
        STATUS current
        DESCRIPTION "sqa sender throughput low rate, unit : kbps"
        ::= {sqaTestSenderEntry 20}  
         
         --TpTimeOut                           
    sqaTestSenderTpTimeOut  OBJECT-TYPE
        SYNTAX Unsigned32   ( 1..60 )
        MAX-ACCESS read-only
        STATUS current
        DESCRIPTION "sqa sender throughput timeout, default: 4s, unit : s"
        ::= {sqaTestSenderEntry 21}
         --TpOneRateDuration                             
    sqaTestSenderTpOneRateDuration  OBJECT-TYPE
        SYNTAX Unsigned32   ( 1..60 )
        MAX-ACCESS read-only
        STATUS current
        DESCRIPTION "sqa sender throughput one rate duration, default: 4s, unit : s"
        ::= {sqaTestSenderEntry 22} 
         --TpDuration                             
    sqaTestSenderTpDuration  OBJECT-TYPE
        SYNTAX Unsigned32    (0 | 10..172800 )
        MAX-ACCESS read-only
        STATUS current
        DESCRIPTION "sqa sender throughput duration, 0: undefined(invalid), unit : s"
        ::= {sqaTestSenderEntry 23} 
         --TpPrecision                           
    sqaTestSenderTpPrecision  OBJECT-TYPE
        SYNTAX Unsigned32   ( 1..10000 )
        MAX-ACCESS read-only
        STATUS current
        DESCRIPTION "sqa sender throughput precision, default: 1000kbps, unit : kbps"
        ::= {sqaTestSenderEntry 24}
         --TpLossThreshold                           
    sqaTestSenderTpLossThreshold  OBJECT-TYPE
        SYNTAX Unsigned32    ( 0..100 )
        MAX-ACCESS read-only
        STATUS current
        DESCRIPTION "sqa sender throughput loss threshold, default: 0, unit : 1/10000"
        ::= {sqaTestSenderEntry 25}  
         --LossEnable                             
    sqaTestSenderLossEnable  OBJECT-TYPE
        SYNTAX TestEnableStatus
        MAX-ACCESS read-only
        STATUS current
        DESCRIPTION "sqa sender loss enable"
        ::= {sqaTestSenderEntry 26} 
         --LossRateType                             
    sqaTestSenderLossRateType  OBJECT-TYPE
        SYNTAX TestRateType
        MAX-ACCESS read-only
        STATUS current
        DESCRIPTION "sqa sender loss rate type, 1: ir(default), 2: ulr"
        ::= {sqaTestSenderEntry 27}  
         --LossRate                           
    sqaTestSenderLossRate  OBJECT-TYPE
        SYNTAX Unsigned32    ( 0..10000000 )
        MAX-ACCESS read-only
        STATUS current
        DESCRIPTION "sqa sender loss rate, default: 1000kbps, unit : kbps"
        ::= {sqaTestSenderEntry 28}  
         --LossTimeOut                           
    sqaTestSenderLossTimeOut  OBJECT-TYPE
        SYNTAX Unsigned32    ( 1..60 )
        MAX-ACCESS read-only
        STATUS current
        DESCRIPTION "sqa sender loss timeout, default: 4s, unit : s"
        ::= {sqaTestSenderEntry 29}
         --LossDuration
    sqaTestSenderLossDuration OBJECT-TYPE
        SYNTAX Unsigned32    ( 10..172800 )
        MAX-ACCESS read-only
        STATUS current
        DESCRIPTION "sqa sender loss duration, default: 60s, unit : s"
        ::= {sqaTestSenderEntry 30}

         --LossRatioThreshold                           
    sqaTestSenderLossRatioThreshold  OBJECT-TYPE
        SYNTAX Unsigned32    ( 0..100 )
        MAX-ACCESS read-only
        STATUS current
        DESCRIPTION "sqa sender loss ratio threshold, default: 0, unit : 1/10000"
        ::= {sqaTestSenderEntry 31}
         --DelayEnable                             
    sqaTestSenderDelayEnable  OBJECT-TYPE
        SYNTAX TestEnableStatus
        MAX-ACCESS read-only
        STATUS current
        DESCRIPTION "sqa sender delay enable"
        ::= {sqaTestSenderEntry 32} 
         --DelayRateType                             
    sqaTestSenderDelayRateType  OBJECT-TYPE
        SYNTAX TestRateType
        MAX-ACCESS read-only
        STATUS current
        DESCRIPTION "sqa sender delay rate type, 1: ir(default), 2: ulr"
        ::= {sqaTestSenderEntry 33} 
         --DelayRate                           
    sqaTestSenderDelayRate  OBJECT-TYPE
        SYNTAX Unsigned32   ( 0..10000000 )
        MAX-ACCESS read-only
        STATUS current
        DESCRIPTION "sqa sender delay rate, default: 1000kbps, unit : kbps"
        ::= {sqaTestSenderEntry 34}
         --DelayInterval                           
    sqaTestSenderDelayInterval  OBJECT-TYPE
        SYNTAX Unsigned32    ( 1..60 )
        MAX-ACCESS read-only
        STATUS current
        DESCRIPTION "sqa sender delay interval, default: 4s, unit : s"
        ::= {sqaTestSenderEntry 35}  
         --DelayDuration                             
    sqaTestSenderDelayDuration  OBJECT-TYPE
        SYNTAX Unsigned32    ( 10..172800 )
        MAX-ACCESS read-only
        STATUS current
        DESCRIPTION "sqa sender delay duration, default: 60s, unit : s"
        ::= {sqaTestSenderEntry 36} 
         --DelayThreshold                             
    sqaTestSenderDelayThreshold  OBJECT-TYPE
        SYNTAX Unsigned32     ( 1..1000000 )
        MAX-ACCESS read-only
        STATUS current
        DESCRIPTION "sqa sender delay threshold, default: 20000ns, unit : us"
        ::= {sqaTestSenderEntry 37}  
         --JitterThreshold                           
    sqaTestSenderJitterThreshold  OBJECT-TYPE
        SYNTAX Unsigned32     ( 1..1000000 )
        MAX-ACCESS read-only
        STATUS current
        DESCRIPTION "sqa sender jitter threshold, default: 25000ns, unit : us"
        ::= {sqaTestSenderEntry 38}  
         --PacketSize1                           
    sqaTestSenderPacketSize1  OBJECT-TYPE
        SYNTAX Unsigned32      ( 64..9216 )
        MAX-ACCESS read-only
        STATUS current
        DESCRIPTION "sqa sender packet size1, unit : byte"
        ::= {sqaTestSenderEntry 39}
         --PacketSize2
    sqaTestSenderPacketSize2 OBJECT-TYPE
        SYNTAX Unsigned32     ( 0 | 64..9216 )
        MAX-ACCESS read-only
        STATUS current
        DESCRIPTION "sqa sender packet size2, unit : byte"
        ::= {sqaTestSenderEntry 40}
         
         --PacketSize3
    sqaTestSenderPacketSize3  OBJECT-TYPE
        SYNTAX Unsigned32    ( 0 | 64..9216 )
        MAX-ACCESS read-only
        STATUS current
        DESCRIPTION "sqa sender packet size3, unit : byte"
        ::= {sqaTestSenderEntry 41}
         --PacketSize4
    sqaTestSenderPacketSize4 OBJECT-TYPE
        SYNTAX Unsigned32    ( 0 | 64..9216 )
        MAX-ACCESS read-only
        STATUS current
        DESCRIPTION "sqa sender packet size4, unit : byte"
        ::= {sqaTestSenderEntry 42}
         --PacketSize5
    sqaTestSenderPacketSize5  OBJECT-TYPE
        SYNTAX Unsigned32    ( 0 | 64..9216 )
        MAX-ACCESS read-only
        STATUS current
        DESCRIPTION "sqa sender packet size5, unit : byte"
        ::= {sqaTestSenderEntry 43}
         --PacketSize6
    sqaTestSenderPacketSize6 OBJECT-TYPE
        SYNTAX Unsigned32    ( 0 | 64..9216 )
        MAX-ACCESS read-only
        STATUS current
        DESCRIPTION "sqa sender packet size6, unit : byte"
        ::= {sqaTestSenderEntry 44}
         --PacketSize7        
    sqaTestSenderPacketSize7  OBJECT-TYPE
        SYNTAX Unsigned32    ( 0 | 64..9216 )
        MAX-ACCESS read-only
        STATUS current
        DESCRIPTION "sqa sender packet size7, unit : byte"
        ::= {sqaTestSenderEntry 45}
         --OnlineOfflineFlag                           
    sqaTestSenderOnlineOfflineFlag  OBJECT-TYPE
        SYNTAX TestOnlineState
        MAX-ACCESS read-only
        STATUS current
        DESCRIPTION "sqa sender online offline flag, 1: online, 2: offline"
        ::= {sqaTestSenderEntry 46}  
         --FreeArpEnable                             
    sqaTestSenderFreeArpEnable  OBJECT-TYPE
        SYNTAX TestEnableStatus
        MAX-ACCESS read-only
        STATUS current
        DESCRIPTION "sqa sender free arp enable"
        ::= {sqaTestSenderEntry 47} 
         --FreeArpInterval                             
    sqaTestSenderFreeArpInterval  OBJECT-TYPE
        SYNTAX Unsigned32    ( 1..14400 )
        MAX-ACCESS read-only
        STATUS current
        DESCRIPTION "sqa sender free arp interval, default: 30s, unit : s"
        ::= {sqaTestSenderEntry 48}  
         --TimeRange                           
    sqaTestSenderTimeRange  OBJECT-TYPE
        SYNTAX DisplayString    (SIZE(0..31))
        MAX-ACCESS read-only
        STATUS current
        DESCRIPTION "sqa sender timerange"
        ::= {sqaTestSenderEntry 49}
        
    --Reflector table
    sqaTestReflectorTable  OBJECT-TYPE
        SYNTAX SEQUENCE OF SqaTestReflectorEntry
        MAX-ACCESS not-accessible
        STATUS current
        DESCRIPTION "sqa generalflow reflector table"
        ::={sqaMib 20} 
    sqaTestReflectorEntry      OBJECT-TYPE
        SYNTAX SqaTestReflectorEntry
        MAX-ACCESS not-accessible
        STATUS current
        DESCRIPTION "sqa generalflow reflector entry"
        INDEX {sqaTestReflectorId} 
        ::={sqaTestReflectorTable 1}  
        
    SqaTestReflectorEntry::= 
        SEQUENCE
        {  
            sqaTestReflectorId
                Unsigned32,
            sqaTestReflectorRefMode
                ReflectorMode,
            sqaTestReflectorInterface
                DisplayString, 
            sqaTestReflectorTestMode
                TestTestMode,
            sqaTestReflectorDisNonTest8021p
                Unsigned32,
            sqaTestReflectorDisNonTestDscp
                Unsigned32,
            sqaTestReflectorAgeingTime
                Unsigned32,
            sqaTestReflectorSourceMac
                MacAddress,
            sqaTestReflectorDestinationMac
                MacAddress,  
            sqaTestReflectorSourceIp
                IpAddress,  
            sqaTestReflectorDestinationIp
                IpAddress,
            sqaTestReflectorSourcePort
                Unsigned32,
            sqaTestReflectorDestinationPort
                Unsigned32,
            sqaTestReflectorVlanId
                Unsigned32,
            sqaTestReflectorInternalVlanId
                Unsigned32,
            sqaTestReflectorExternalVlanId
                Unsigned32,
            sqaTestReflectorPriority8021p
                Unsigned32,
            sqaTestReflectorDscp
                Unsigned32,
            sqaTestReflectorOnOfflineFlag
                TestOnlineState,
            sqaTestReflectorFreeArpEnable
                TestEnableStatus,
            sqaTestReflectorFreeArpIp
                IpAddress,
            sqaTestReflectorFreeArpVlanId
                Unsigned32,
            sqaTestReflectorFreeArpInVlanId
                Unsigned32,
            sqaTestReflectorFreeArpExVlanId
                Unsigned32,
            sqaTestReflectorFreeArpInterval
                Unsigned32 
        }
        
         --Reflector ID
    sqaTestReflectorId  OBJECT-TYPE
        SYNTAX Unsigned32 ( 1..65535 )
        MAX-ACCESS not-accessible
        STATUS current
        DESCRIPTION "sqa reflector ID"
        ::= {sqaTestReflectorEntry 1}  
         --ReflectorMode                               
    sqaTestReflectorRefMode   OBJECT-TYPE
        SYNTAX ReflectorMode
        MAX-ACCESS read-only
        STATUS current
        DESCRIPTION "sqa reflector mode, 1: l2, 2: l3"
        ::= {sqaTestReflectorEntry 2}    
         --InboundInterface                          
    sqaTestReflectorInterface OBJECT-TYPE
        SYNTAX DisplayString    (SIZE(0..31))
        MAX-ACCESS read-only
        STATUS current
        DESCRIPTION "sqa reflector inbound interface"
        ::= {sqaTestReflectorEntry 3}  
         --TestMode                          
    sqaTestReflectorTestMode   OBJECT-TYPE
        SYNTAX TestTestMode
        MAX-ACCESS read-only
        STATUS current
        DESCRIPTION "sqa reflector test mode, 1: share-mode(default), 2: exclusive-mode"
        ::= {sqaTestReflectorEntry 4} 
         --DisNonTest8021p                          
    sqaTestReflectorDisNonTest8021p    OBJECT-TYPE
        SYNTAX Unsigned32    ( 0..7 | 255)
        MAX-ACCESS read-only
        STATUS current
        DESCRIPTION "sqa reflector disNonTest8021p, 255: undefined(invalid)"
        ::= {sqaTestReflectorEntry 5} 
         --DisNonTestDscp                         
    sqaTestReflectorDisNonTestDscp   OBJECT-TYPE
        SYNTAX Unsigned32    ( 0..63 | 255)
        MAX-ACCESS read-only
        STATUS current
        DESCRIPTION "sqa reflector disNonTestDscp, 255: undefined(invalid)"
        ::= {sqaTestReflectorEntry 6}  
         --AgeingTime                         
    sqaTestReflectorAgeingTime   OBJECT-TYPE
        SYNTAX Unsigned32    ( 0..173400)
        MAX-ACCESS read-only
        STATUS current
        DESCRIPTION "sqa reflector ageing time, 0 : continuous"
        ::= {sqaTestReflectorEntry 7} 
         --SourceMac                          
    sqaTestReflectorSourceMac   OBJECT-TYPE
        SYNTAX MacAddress
        MAX-ACCESS read-only
        STATUS current
        DESCRIPTION "sqa reflector source mac"
        ::= {sqaTestReflectorEntry 8}
         --DestinationMac
    sqaTestReflectorDestinationMac   OBJECT-TYPE
        SYNTAX MacAddress
        MAX-ACCESS read-only
        STATUS current
        DESCRIPTION "sqa reflector destination mac"
        ::= {sqaTestReflectorEntry 9} 
         --SourceIp                         
    sqaTestReflectorSourceIp   OBJECT-TYPE
        SYNTAX IpAddress
        MAX-ACCESS read-only
        STATUS current
        DESCRIPTION "sqa reflector source ip"
        ::= {sqaTestReflectorEntry 10}  
         --DestinationIp                         
    sqaTestReflectorDestinationIp   OBJECT-TYPE
        SYNTAX IpAddress
        MAX-ACCESS read-only
        STATUS current
        DESCRIPTION "sqa reflector destination ip"
        ::= {sqaTestReflectorEntry 11} 
         --SourcePort                         
    sqaTestReflectorSourcePort   OBJECT-TYPE
        SYNTAX Unsigned32   ( 1..65535)
        MAX-ACCESS read-only
        STATUS current
        DESCRIPTION "sqa reflector source port, default: 49184"
        ::= {sqaTestReflectorEntry 12}
         --DestinationPort
    sqaTestReflectorDestinationPort   OBJECT-TYPE
        SYNTAX Unsigned32    ( 1..65535 )
        MAX-ACCESS read-only
        STATUS current
        DESCRIPTION "sqa reflector destination port, default: 7"
        ::= {sqaTestReflectorEntry 13}     
         --VlanId                             
    sqaTestReflectorVlanId  OBJECT-TYPE
        SYNTAX Unsigned32    ( 0..4094 )
        MAX-ACCESS read-only
        STATUS current
        DESCRIPTION "sqa reflector vlan id"
        ::= {sqaTestReflectorEntry 14} 
         --InternalVlanId   
    sqaTestReflectorInternalVlanId  OBJECT-TYPE
        SYNTAX Unsigned32    ( 0..4094 )
        MAX-ACCESS read-only
        STATUS current
        DESCRIPTION "sqa reflector internal vlan id"
        ::= {sqaTestReflectorEntry 15} 
         --ExternalVlanId                          
    sqaTestReflectorExternalVlanId  OBJECT-TYPE
        SYNTAX Unsigned32    ( 0..4094 )
        MAX-ACCESS read-only
        STATUS current
        DESCRIPTION "sqa reflector external vlan id"
        ::= {sqaTestReflectorEntry 16} 
         --Priority8021p                          
    sqaTestReflectorPriority8021p  OBJECT-TYPE
        SYNTAX Unsigned32    ( 0..7 | 255)
        MAX-ACCESS read-only
        STATUS current
        DESCRIPTION "sqa reflector priority8021p, 255: undefined(invalid)"
        ::= {sqaTestReflectorEntry 17} 
         --Dscp                              
    sqaTestReflectorDscp   OBJECT-TYPE
        SYNTAX Unsigned32    ( 0..63 | 255)
        MAX-ACCESS read-only
        STATUS current
        DESCRIPTION "sqa reflector DSCP, 255: undefined(invalid)"
        ::= {sqaTestReflectorEntry 18}  
         --OnOfflineFlag                             
    sqaTestReflectorOnOfflineFlag  OBJECT-TYPE
        SYNTAX TestOnlineState
        MAX-ACCESS read-only
        STATUS current
        DESCRIPTION "sqa reflector online flag, 1: online, 2: offline"
        ::= {sqaTestReflectorEntry 19} 
        
         --FreeArpEnable  
    sqaTestReflectorFreeArpEnable  OBJECT-TYPE
        SYNTAX TestEnableStatus
        MAX-ACCESS read-only
        STATUS current
        DESCRIPTION "sqa reflector free arp enable state"
        ::= {sqaTestReflectorEntry 20}  
         --FreeArpIp                          
    sqaTestReflectorFreeArpIp  OBJECT-TYPE
        SYNTAX IpAddress
        MAX-ACCESS read-only
        STATUS current
        DESCRIPTION "sqa reflector free arp local ip address"
        ::= {sqaTestReflectorEntry 21}
         --FreeArpVlanId                              
    sqaTestReflectorFreeArpVlanId  OBJECT-TYPE
        SYNTAX Unsigned32   ( 0..4094 )
        MAX-ACCESS read-only
        STATUS current
        DESCRIPTION "sqa reflector free arp vlan id"
        ::= {sqaTestReflectorEntry 22} 
         --FreeArpInVlanId                            
    sqaTestReflectorFreeArpInVlanId  OBJECT-TYPE
        SYNTAX Unsigned32    ( 0..4094 )
        MAX-ACCESS read-only
        STATUS current
        DESCRIPTION "sqa reflector free arp internal vlan id"
        ::= {sqaTestReflectorEntry 23} 
         --FreeArpExVlanId                          
    sqaTestReflectorFreeArpExVlanId  OBJECT-TYPE
        SYNTAX Unsigned32   ( 0..4094 )
        MAX-ACCESS read-only
        STATUS current
        DESCRIPTION "sqa reflector free arp external vlan id"
        ::= {sqaTestReflectorEntry 24}
         --TpLossThreshold                           
    sqaTestReflectorFreeArpInterval  OBJECT-TYPE
        SYNTAX Unsigned32    ( 1..14400 )
        MAX-ACCESS read-only
        STATUS current
        DESCRIPTION "sqa reflector free arp send interval, unit : s"
        ::= {sqaTestReflectorEntry 25}  
        
    --Throughput result table
    sqaTestTpResultTable  OBJECT-TYPE
        SYNTAX SEQUENCE OF SqaTestTpResultEntry
        MAX-ACCESS not-accessible
        STATUS current
        DESCRIPTION "sqa generalflow throughput test result table"
        ::={sqaMib 21} 
    sqaTestTpResultEntry      OBJECT-TYPE
        SYNTAX SqaTestTpResultEntry
        MAX-ACCESS not-accessible
        STATUS current
        DESCRIPTION "sqa generalflow throughput test result entry"
        INDEX {sqaTestTpResultTestNum,
               sqaTestTpResultPacketSize} 
        ::={sqaTestTpResultTable 1}  
 
    SqaTestTpResultEntry::= 
        SEQUENCE
        {  
            sqaTestTpResultTestNum
                Unsigned32,
            sqaTestTpResultPacketSize
                Unsigned32,
            sqaTestTpResultUniInterface
                DisplayString, 
            sqaTestTpResultPriority8021p
                Unsigned32,
            sqaTestTpResultDscp
                Unsigned32,
            sqaTestTpResultPrecision
                Unsigned32,
            sqaTestTpResultTp
                Unsigned32,             
            sqaTestTpResultInfoRate
                Unsigned32,
            sqaTestTpResultLossRatio
                Unsigned32,
            sqaTestTpResultTestDuration
                Unsigned32,
            sqaTestTpResultStatus
                TpResultStatus                                        
        }
         --test num
    sqaTestTpResultTestNum  OBJECT-TYPE
        SYNTAX Unsigned32 ( 1..65535 )
        MAX-ACCESS not-accessible
        STATUS current
        DESCRIPTION "sqa generalflow throughput test number"
        ::= {sqaTestTpResultEntry 1}  
         --PacketSize                               
    sqaTestTpResultPacketSize   OBJECT-TYPE
        SYNTAX Unsigned32 ( 64..9216 )
        MAX-ACCESS not-accessible
        STATUS current
        DESCRIPTION "sqa generalflow throughput test packet size, unit : byte"
        ::= {sqaTestTpResultEntry 2}    
         --UniInterface                          
    sqaTestTpResultUniInterface OBJECT-TYPE
        SYNTAX DisplayString    (SIZE(0..31))
        MAX-ACCESS read-only
        STATUS current
        DESCRIPTION "sqa generalflow throughput test UNI interface"
        ::= {sqaTestTpResultEntry 3}
         --8021p  
    sqaTestTpResultPriority8021p   OBJECT-TYPE
        SYNTAX Unsigned32 ( 0..7 )
        MAX-ACCESS read-only
        STATUS current
        DESCRIPTION "sqa generalflow throughput test result test priority 8021p"
        ::= {sqaTestTpResultEntry 4} 
         --dscp                          
    sqaTestTpResultDscp   OBJECT-TYPE
        SYNTAX Unsigned32 ( 0..63 )
        MAX-ACCESS read-only
        STATUS current
        DESCRIPTION "sqa generalflow throughput test result test dscp"
        ::= {sqaTestTpResultEntry 5} 
         --Precision                          
    sqaTestTpResultPrecision   OBJECT-TYPE
        SYNTAX Unsigned32 ( 1..10000 )
        MAX-ACCESS read-only
        STATUS current
        DESCRIPTION "sqa generalflow throughput test result precision, unit : kbps"
        ::= {sqaTestTpResultEntry 6} 
         --Throughput                          
    sqaTestTpResultTp    OBJECT-TYPE
        SYNTAX Unsigned32    ( 0..1000000 )
        MAX-ACCESS read-only
        STATUS current
        DESCRIPTION "sqa generalflow throughput test Throughput, unit : kbps"
        ::= {sqaTestTpResultEntry 7} 
         --InfoRate                         
    sqaTestTpResultInfoRate   OBJECT-TYPE
        SYNTAX Unsigned32    ( 0..1000000 )
        MAX-ACCESS read-only
        STATUS current
        DESCRIPTION "sqa generalflow throughput test result info rate, unit : kbps"
        ::= {sqaTestTpResultEntry 8}  
         --LossRatio                         
    sqaTestTpResultLossRatio   OBJECT-TYPE
        SYNTAX Unsigned32    ( 0..10000 )
        MAX-ACCESS read-only
        STATUS current
        DESCRIPTION "sqa generalflow throughput test result loss ratio, unit : 1/10000"
        ::= {sqaTestTpResultEntry 9} 
         --Duration    
    sqaTestTpResultTestDuration   OBJECT-TYPE
        SYNTAX Unsigned32    ( 0..172800 )
        MAX-ACCESS read-only
        STATUS current
        DESCRIPTION "sqa generalflow throughput test duration, unit : s"
        ::= {sqaTestTpResultEntry 10} 
         --Status    
    sqaTestTpResultStatus   OBJECT-TYPE
        SYNTAX TpResultStatus
        MAX-ACCESS read-only
        STATUS current
        DESCRIPTION "sqa generalflow throughput test status"
        ::= {sqaTestTpResultEntry 11}

    --Loss result table
    sqaTestLossResultTable  OBJECT-TYPE
        SYNTAX SEQUENCE OF SqaTestLossResultEntry
        MAX-ACCESS not-accessible
        STATUS current
        DESCRIPTION "sqa generalflow loss test result table"
        ::={sqaMib 22} 
    sqaTestLossResultEntry      OBJECT-TYPE
        SYNTAX SqaTestLossResultEntry
        MAX-ACCESS not-accessible
        STATUS current
        DESCRIPTION "sqa generalflow loss test result entry"
        INDEX {sqaTestLossResultTestNum,
               sqaTestLossResultPacketSize} 
        ::={sqaTestLossResultTable 1}  
    
    SqaTestLossResultEntry::= 
        SEQUENCE
        {  
            sqaTestLossResultTestNum
                Unsigned32,
            sqaTestLossResultPacketSize
                Unsigned32,
            sqaTestLossResultUniInterface
                DisplayString,
            sqaTestLossResultPriority8021p
                Unsigned32,
            sqaTestLossResultDscp
                Unsigned32,
            sqaTestLossResultTestRate
                Unsigned32,
            sqaTestLossResultLossPktNumber
                Unsigned32,             
            sqaTestLossResultLossPktRatio
                Unsigned32,
            sqaTestLossResultTestDuration
                Unsigned32,
            sqaTestLossResultStatus
                TestResultStatus                                        
        }
         --test num
    sqaTestLossResultTestNum  OBJECT-TYPE
        SYNTAX Unsigned32 ( 1..65535 )
        MAX-ACCESS not-accessible
        STATUS current
        DESCRIPTION "sqa generalflow loss test number"
        ::= {sqaTestLossResultEntry 1}  
         --PacketSize                               
    sqaTestLossResultPacketSize   OBJECT-TYPE
        SYNTAX Unsigned32 ( 64..9216 )
        MAX-ACCESS not-accessible
        STATUS current
        DESCRIPTION "sqa generalflow loss test packet size, unit : byte"
        ::= {sqaTestLossResultEntry 2}    
         --UniInterface                          
    sqaTestLossResultUniInterface OBJECT-TYPE
        SYNTAX DisplayString    (SIZE(0..31))
        MAX-ACCESS read-only
        STATUS current
        DESCRIPTION "sqa generalflow loss test UNI interface"
        ::= {sqaTestLossResultEntry 3}
         --8021p  
    sqaTestLossResultPriority8021p   OBJECT-TYPE
        SYNTAX Unsigned32 ( 0..7 )
        MAX-ACCESS read-only
        STATUS current
        DESCRIPTION "sqa generalflow loss test result test priority 8021p"
        ::= {sqaTestLossResultEntry 4} 
         --dscp                          
    sqaTestLossResultDscp   OBJECT-TYPE
        SYNTAX Unsigned32 ( 0..63 )
        MAX-ACCESS read-only
        STATUS current
        DESCRIPTION "sqa generalflow loss test result test dscp"
        ::= {sqaTestLossResultEntry 5} 
         --Rate                          
    sqaTestLossResultTestRate   OBJECT-TYPE
        SYNTAX Unsigned32 ( 1..1000000 )
        MAX-ACCESS read-only
        STATUS current
        DESCRIPTION "sqa generalflow loss test result test rate, unit : kbps"
        ::= {sqaTestLossResultEntry 6} 
         --PktNumber                          
    sqaTestLossResultLossPktNumber    OBJECT-TYPE
        SYNTAX Unsigned32    ( 0..4294967295 )
        MAX-ACCESS read-only
        STATUS current
        DESCRIPTION "sqa generalflow loss test loss packet number"
        ::= {sqaTestLossResultEntry 7} 
         --Ratio                         
    sqaTestLossResultLossPktRatio   OBJECT-TYPE
        SYNTAX Unsigned32    ( 0..10000 )
        MAX-ACCESS read-only
        STATUS current
        DESCRIPTION "sqa generalflow loss test result loss packet ratio, unit : 1/10000"
        ::= {sqaTestLossResultEntry 8}  
         --duration                         
    sqaTestLossResultTestDuration   OBJECT-TYPE
        SYNTAX Unsigned32    ( 0..172800 )
        MAX-ACCESS read-only
        STATUS current
        DESCRIPTION "sqa generalflow loss test result duration, unit : s"
        ::= {sqaTestLossResultEntry 9} 
         --Status    
    sqaTestLossResultStatus   OBJECT-TYPE
        SYNTAX TestResultStatus
        MAX-ACCESS read-only
        STATUS current
        DESCRIPTION "sqa generalflow loss test status"
        ::= {sqaTestLossResultEntry 10}

    --Delay result table
    sqaTestDelayResultTable  OBJECT-TYPE
        SYNTAX SEQUENCE OF SqaTestDelayResultEntry
        MAX-ACCESS not-accessible
        STATUS current
        DESCRIPTION "sqa generalflow delay test result table"
        ::={sqaMib 23} 
    sqaTestDelayResultEntry      OBJECT-TYPE
        SYNTAX SqaTestDelayResultEntry
        MAX-ACCESS not-accessible
        STATUS current
        DESCRIPTION "sqa generalflow delay test result entry"
        INDEX {sqaTestDelayResultTestNum,
               sqaTestDelayResultPacketSize} 
        ::={sqaTestDelayResultTable 1}   
    
    SqaTestDelayResultEntry::= 
        SEQUENCE
        { 
            sqaTestDelayResultTestNum
                Unsigned32,
            sqaTestDelayResultPacketSize
                Unsigned32,
            sqaTestDelayResultUniInterface
                DisplayString,
            sqaTestDelayResultPriority8021p
                Unsigned32,
            sqaTestDelayResultDscp
                Unsigned32,
            sqaTestDelayResultTestRate
                Unsigned32,
            sqaTestDelayResultMinDelay
                Counter64,             
            sqaTestDelayResultMaxDelay
                Counter64,
            sqaTestDelayResultAvgDelay
                Counter64,
            sqaTestDelayResultMinJitter
                Counter64,             
            sqaTestDelayResultMaxJitter
                Counter64,
            sqaTestDelayResultAvgJitter
                Counter64,
            sqaTestDelayResultTestDuration
                Unsigned32,
            sqaTestDelayResultStatus
                TestResultStatus                                        
        }
         --test num
    sqaTestDelayResultTestNum  OBJECT-TYPE
        SYNTAX Unsigned32 ( 1..65535 )
        MAX-ACCESS not-accessible
        STATUS current
        DESCRIPTION "sqa generalflow delay test number"
        ::= {sqaTestDelayResultEntry 1}  
         --PacketSize                               
    sqaTestDelayResultPacketSize   OBJECT-TYPE
        SYNTAX Unsigned32 ( 64..9216 )
        MAX-ACCESS not-accessible
        STATUS current
        DESCRIPTION "sqa generalflow delay test packet size, unit : byte"
        ::= {sqaTestDelayResultEntry 2}    
         --UniInterface                          
    sqaTestDelayResultUniInterface OBJECT-TYPE
        SYNTAX DisplayString    (SIZE(0..31))
        MAX-ACCESS read-only
        STATUS current
        DESCRIPTION "sqa generalflow delay test UNI interface"
        ::= {sqaTestDelayResultEntry 3}
         --8021p                          
    sqaTestDelayResultPriority8021p   OBJECT-TYPE
        SYNTAX Unsigned32 ( 0..7 )
        MAX-ACCESS read-only
        STATUS current
        DESCRIPTION "sqa generalflow delay test result test priority 8021p"
        ::= {sqaTestDelayResultEntry 4} 
         --dscp                          
    sqaTestDelayResultDscp   OBJECT-TYPE
        SYNTAX Unsigned32 ( 0..63 )
        MAX-ACCESS read-only
        STATUS current
        DESCRIPTION "sqa generalflow delay test result test dscp"
        ::= {sqaTestDelayResultEntry 5} 
         --Rate                          
    sqaTestDelayResultTestRate   OBJECT-TYPE
        SYNTAX Unsigned32 ( 0..1000000 )
        MAX-ACCESS read-only
        STATUS current
        DESCRIPTION "sqa generalflow delay test result test rate, unit : kbps"
        ::= {sqaTestDelayResultEntry 6} 
         --MinDelay                          
    sqaTestDelayResultMinDelay    OBJECT-TYPE
        SYNTAX Counter64
        MAX-ACCESS read-only
        STATUS current
        DESCRIPTION "sqa generalflow delay test result min delay, unit : us"
        ::= {sqaTestDelayResultEntry 7} 
         --MaxDelay                         
    sqaTestDelayResultMaxDelay   OBJECT-TYPE
        SYNTAX Counter64
        MAX-ACCESS read-only
        STATUS current
        DESCRIPTION "sqa generalflow delay test result max delay, unit : us"
        ::= {sqaTestDelayResultEntry 8} 
         --AvgDelay 
    sqaTestDelayResultAvgDelay   OBJECT-TYPE
        SYNTAX Counter64
        MAX-ACCESS read-only
        STATUS current
        DESCRIPTION "sqa generalflow delay test result avg delay, unit : us"
        ::= {sqaTestDelayResultEntry 9} 
         --MinJitter                          
    sqaTestDelayResultMinJitter    OBJECT-TYPE
        SYNTAX Counter64
        MAX-ACCESS read-only
        STATUS current
        DESCRIPTION "sqa generalflow delay test result min jitter, unit : us"
        ::= {sqaTestDelayResultEntry 10} 
         --MaxJitter                         
    sqaTestDelayResultMaxJitter   OBJECT-TYPE
        SYNTAX Counter64
        MAX-ACCESS read-only
        STATUS current
        DESCRIPTION "sqa generalflow delay test result max jitter, unit : us"
        ::= {sqaTestDelayResultEntry 11} 
         --AvgJitter 
    sqaTestDelayResultAvgJitter   OBJECT-TYPE
        SYNTAX Counter64
        MAX-ACCESS read-only
        STATUS current
        DESCRIPTION "sqa generalflow delay test result avg jitter, unit : us"
        ::= {sqaTestDelayResultEntry 12} 
         --Duration                         
    sqaTestDelayResultTestDuration   OBJECT-TYPE
        SYNTAX Unsigned32    ( 0..172800 )
        MAX-ACCESS read-only
        STATUS current
        DESCRIPTION "sqa generalflow delay test result duration, unit : s"
        ::= {sqaTestDelayResultEntry 13} 
         --Status    
    sqaTestDelayResultStatus   OBJECT-TYPE
        SYNTAX TestResultStatus
        MAX-ACCESS read-only
        STATUS current
        DESCRIPTION "sqa generalflow delay test status"
        ::= {sqaTestDelayResultEntry 14}

    --Notifications
    zxr10SqaNotifications   OBJECT IDENTIFIER ::= { sqaMib 24 }

 zxr10SqaTestGeneralFlowFinish NOTIFICATION-TYPE
        OBJECTS {
                    sqaTestSenderTpEnable,
                    sqaTestSenderLossEnable,
                    sqaTestSenderDelayEnable
        }
     STATUS       current
     DESCRIPTION
         ""
     ::= { zxr10SqaNotifications 1 }
 zxr10SqaTestGeneralFlowFail NOTIFICATION-TYPE
        OBJECTS {
                    sqaTestSenderTpEnable,
                    sqaTestSenderLossEnable,
                    sqaTestSenderDelayEnable
        }
     STATUS       current
     DESCRIPTION
         ""
     ::= { zxr10SqaNotifications 2 }
  
 --Start or stop test.       
    sqaTestOperationTable  OBJECT-TYPE
        SYNTAX SEQUENCE OF SqaTestOperationEntry
        MAX-ACCESS not-accessible
        STATUS current  
        DESCRIPTION "SQA test operation configuration"                 
        ::={sqaMib 25}  
         
    sqaTestOperationEntry  OBJECT-TYPE
        SYNTAX SqaTestOperationEntry
        MAX-ACCESS not-accessible
        STATUS current
        DESCRIPTION "SQA test operation entity configuration table"
        INDEX { sqaOperationTestNum } 
        ::={sqaTestOperationTable 1}
          
    SqaTestOperationEntry ::=
        SEQUENCE {     
            sqaOperationTestNum
                Unsigned32,
            sqaTestOperation
                TestOperation
        } 
        --num                      
    sqaOperationTestNum  OBJECT-TYPE 
        SYNTAX Unsigned32 ( 1..65535 )   
        MAX-ACCESS not-accessible
        STATUS current
        DESCRIPTION "SQA test number.The range of this parameter depend on the device."
        ::= {sqaTestOperationEntry 1}

        --operation 
    sqaTestOperation  OBJECT-TYPE
        SYNTAX TestOperation
        MAX-ACCESS read-create
        STATUS current
        DESCRIPTION "SQA test operation type,1 means begin,2 means stop."
        ::= {sqaTestOperationEntry 2}  
 
 --UDP test config info       
    sqaUdpTestTable  OBJECT-TYPE
        SYNTAX SEQUENCE OF SqaUdpTestEntry
        MAX-ACCESS not-accessible
        STATUS current  
        DESCRIPTION "SQA UDP test entity configuration"                 
        ::={sqaMib 26}  
         
    sqaUdpTestEntry  OBJECT-TYPE
        SYNTAX SqaUdpTestEntry
        MAX-ACCESS not-accessible
        STATUS current
        DESCRIPTION "SQA UDP test entity configuration table"
        INDEX { sqaUdpTestNum } 
        ::={sqaUdpTestTable 1}
          
    SqaUdpTestEntry ::=
        SEQUENCE {     
            sqaUdpTestNum
                Unsigned32,
            sqaUdpTestVrf
                DisplayString,
            sqaUdpTestDesIP
                IpAddress,  
            sqaUdpTestDesPort
                Unsigned32,
            sqaUdpTestRepeat
                Unsigned32,
            sqaUdpTestSize
                Unsigned32,
            sqaUdpTestTos
                Unsigned32,
            sqaUdpTestInterval
                Unsigned32,
            sqaUdpTestRowStatus      
                RowStatus
        } 
        --num                      
    sqaUdpTestNum  OBJECT-TYPE 
        SYNTAX Unsigned32 ( 1..65535 )   
        MAX-ACCESS not-accessible
        STATUS current
        DESCRIPTION "SQA test number.The range of this parameter depend on the device."
        ::= {sqaUdpTestEntry 1}  

        --vrf            
    sqaUdpTestVrf  OBJECT-TYPE
        SYNTAX DisplayString (SIZE(1..32))
        MAX-ACCESS read-create
        STATUS current
        DESCRIPTION "The name of VRF,this string length ranges from 1 to 32."
        ::= {sqaUdpTestEntry 2}  
         --des ip 
    sqaUdpTestDesIP      OBJECT-TYPE
        SYNTAX IpAddress
        MAX-ACCESS read-create
        STATUS current
        DESCRIPTION "The destination IP address."
        ::= {sqaUdpTestEntry 3}
         --des port 
    sqaUdpTestDesPort    OBJECT-TYPE
        SYNTAX Unsigned32 ( 1025..65535 )
        MAX-ACCESS read-create
        STATUS current
        DESCRIPTION "The destination port number,ranges from 1025 to 65535."
        ::= {sqaUdpTestEntry 4}
         --repeat 
    sqaUdpTestRepeat      OBJECT-TYPE
        SYNTAX Unsigned32 ( 1..1000 )
        MAX-ACCESS read-create
        STATUS current
        DESCRIPTION "The number of repeat times,ranges from 1 to 1000(default:1)."
        ::={sqaUdpTestEntry 5}
         --size 
    sqaUdpTestSize         OBJECT-TYPE
        SYNTAX Unsigned32 ( 50..1500 )
        MAX-ACCESS read-create
        STATUS current
        DESCRIPTION "The size of UDP packet,ranges from 50 to 1500(default:50),unit:byte."
        ::={sqaUdpTestEntry 6}
                             
         --tos 
    sqaUdpTestTos          OBJECT-TYPE
        SYNTAX Unsigned32 ( 0..255 )
        MAX-ACCESS read-create
        STATUS current
        DESCRIPTION "The TOS value,ranges from 0 to 255(default:0)."
        ::={sqaUdpTestEntry 7}
         --interval 
    sqaUdpTestInterval     OBJECT-TYPE
        SYNTAX Unsigned32 ( 50..2000 )
        MAX-ACCESS read-create
        STATUS current
        DESCRIPTION "The sending period of UDP packets,ranges from 50 to 2000(default:100),unit:ms."
        ::={sqaUdpTestEntry 8}
       --Row status 
    sqaUdpTestRowStatus  OBJECT-TYPE
        SYNTAX  RowStatus
        MAX-ACCESS  read-create
        STATUS  current
        DESCRIPTION "Row status"
        ::= { sqaUdpTestEntry 9 }

 --UDP jitter test config info       
    sqaUdpJitterTestTable  OBJECT-TYPE
        SYNTAX SEQUENCE OF SqaUdpJitterTestEntry
        MAX-ACCESS not-accessible
        STATUS current  
        DESCRIPTION "SQA UDP test entity configuration"                 
        ::={sqaMib 27}  
         
    sqaUdpJitterTestEntry  OBJECT-TYPE
        SYNTAX SqaUdpJitterTestEntry
        MAX-ACCESS not-accessible
        STATUS current
        DESCRIPTION "SQA UDP jitter test entity configuration table"
        INDEX { sqaUdpJitterTestNum } 
        ::={sqaUdpJitterTestTable 1}
          
    SqaUdpJitterTestEntry ::=
        SEQUENCE {     
            sqaUdpJitterTestNum
                Unsigned32,
            sqaUdpJitterTestVrf
                DisplayString,
            sqaUdpJitterTestDesIP
                IpAddress,  
            sqaUdpJitterTestDesPort
                Unsigned32,
            sqaUdpJitterTestRepeat
                Unsigned32,
            sqaUdpJitterTestSize
                Unsigned32,
            sqaUdpJitterTestTos
                Unsigned32,
            sqaUdpJitterTestInterval
                Unsigned32,
            sqaUdpJitterTestRowStatus      
                RowStatus
        } 
        --num                      
    sqaUdpJitterTestNum  OBJECT-TYPE 
        SYNTAX Unsigned32 ( 1..65535 )   
        MAX-ACCESS not-accessible
        STATUS current
        DESCRIPTION "SQA test number.The range of this parameter depend on the device."
        ::= {sqaUdpJitterTestEntry 1}  

        --vrf            
    sqaUdpJitterTestVrf  OBJECT-TYPE
        SYNTAX DisplayString (SIZE(1..32))
        MAX-ACCESS read-create
        STATUS current
        DESCRIPTION "The name of VRF,this string length ranges from 1 to 32."
        ::= {sqaUdpJitterTestEntry 2}  
         --des ip 
    sqaUdpJitterTestDesIP      OBJECT-TYPE
        SYNTAX IpAddress
        MAX-ACCESS read-create
        STATUS current
        DESCRIPTION "The destination IP address."
        ::= {sqaUdpJitterTestEntry 3}
         --des port 
    sqaUdpJitterTestDesPort    OBJECT-TYPE
        SYNTAX Unsigned32 ( 1025..65535 )
        MAX-ACCESS read-create
        STATUS current
        DESCRIPTION "The destination port number,ranges from 1025 to 65535."
        ::= {sqaUdpJitterTestEntry 4}
         --repeat 
    sqaUdpJitterTestRepeat      OBJECT-TYPE
        SYNTAX Unsigned32 ( 1..1000 )
        MAX-ACCESS read-create
        STATUS current
        DESCRIPTION "The number of repeat times,ranges from 1 to 1000(default:1)."
        ::={sqaUdpJitterTestEntry 5}
         --size 
    sqaUdpJitterTestSize         OBJECT-TYPE
        SYNTAX Unsigned32 ( 50..1500 )
        MAX-ACCESS read-create
        STATUS current
        DESCRIPTION "The size of UDP packet,ranges from 50 to 1500(default:50),unit:byte."
        ::={sqaUdpJitterTestEntry 6}                    
         --tos 
    sqaUdpJitterTestTos          OBJECT-TYPE
        SYNTAX Unsigned32 ( 0..255 )
        MAX-ACCESS read-create
        STATUS current
        DESCRIPTION "The TOS value,ranges from 0 to 255(default:0)."
        ::={sqaUdpJitterTestEntry 7}

         --interval 
    sqaUdpJitterTestInterval     OBJECT-TYPE
        SYNTAX Unsigned32 ( 50..2000 )
        MAX-ACCESS read-create
        STATUS current
        DESCRIPTION "The sending period of UDP packets,ranges from 50 to 2000(default:100),unit:ms."
        ::={sqaUdpJitterTestEntry 8}
         --Row status 
    sqaUdpJitterTestRowStatus  OBJECT-TYPE
        SYNTAX  RowStatus
        MAX-ACCESS  read-create
        STATUS  current
        DESCRIPTION "Row status"
        ::= { sqaUdpJitterTestEntry 9 }
  
 --icmp  test config info       
    sqaIcmpTestTable  OBJECT-TYPE
        SYNTAX SEQUENCE OF SqaIcmpTestEntry
        MAX-ACCESS not-accessible
        STATUS current  
        DESCRIPTION "SQA ICMP test entity configuration"                 
        ::={sqaMib 28}  
         
    sqaIcmpTestEntry  OBJECT-TYPE
        SYNTAX SqaIcmpTestEntry
        MAX-ACCESS not-accessible
        STATUS current
        DESCRIPTION "SQA ICMP test entity configuration table"
        INDEX { sqaIcmpTestNum } 
        ::={sqaIcmpTestTable 1}
          
    SqaIcmpTestEntry ::=
        SEQUENCE {     
            sqaIcmpTestNum
                Unsigned32,
            sqaIcmpTestVrf
                DisplayString,
            sqaIcmpTestDesIP
                IpAddress,  
            sqaIcmpTestSorceIP
                IpAddress,
            sqaIcmpTestRepeat
                Unsigned32,
            sqaIcmpTestSize
                Unsigned32,
            sqaIcmpTestTos
                Unsigned32,
            sqaIcmpTestTtl
                Unsigned32,
            sqaIcmpTestInterval
                Unsigned32,
            sqaIcmpTestDscp
                Unsigned32,
            sqaIcmpTestRowStatus      
                RowStatus
        } 
        --num                      
    sqaIcmpTestNum  OBJECT-TYPE 
        SYNTAX Unsigned32 ( 1..65535 )   
        MAX-ACCESS not-accessible
        STATUS current
        DESCRIPTION "SQA test number.The range of this parameter depend on the device."
        ::= {sqaIcmpTestEntry 1}  
        --vrf            
    sqaIcmpTestVrf  OBJECT-TYPE
        SYNTAX DisplayString (SIZE(1..32))
        MAX-ACCESS read-create
        STATUS current
        DESCRIPTION "The name of VRF,this string length ranges from 1 to 32."
        ::= {sqaIcmpTestEntry 2}  
         --des ip 
    sqaIcmpTestDesIP      OBJECT-TYPE
        SYNTAX IpAddress
        MAX-ACCESS read-create
        STATUS current
        DESCRIPTION "The destination IP address."
        ::= {sqaIcmpTestEntry 3}
         --source ip 
    sqaIcmpTestSorceIP    OBJECT-TYPE
        SYNTAX IpAddress 
        MAX-ACCESS read-create
        STATUS current
        DESCRIPTION "The Source IP address."
        ::= {sqaIcmpTestEntry 4}
         --repeat 
    sqaIcmpTestRepeat      OBJECT-TYPE
        SYNTAX Unsigned32 ( 1..65535 )
        MAX-ACCESS read-create
        STATUS current
        DESCRIPTION "The number of repeat times,ranges from 1 to 65535(default:1)."
        ::={sqaIcmpTestEntry 5}
         --size 
    sqaIcmpTestSize         OBJECT-TYPE
        SYNTAX Unsigned32 ( 36..8192 )
        MAX-ACCESS read-create
        STATUS current
        DESCRIPTION "The size of ICMP packet,ranges from 36 to 8192(default:36),unit:byte."
        ::={sqaIcmpTestEntry 6}                    
         --tos 
    sqaIcmpTestTos          OBJECT-TYPE
        SYNTAX Unsigned32 ( 0..256 )
        MAX-ACCESS read-create
        STATUS current
        DESCRIPTION "The TOS value,ranges from 0 to 255(default:0),256 is the invalid value."
        ::={sqaIcmpTestEntry 7}
         --ttl 
    sqaIcmpTestTtl         OBJECT-TYPE
        SYNTAX Unsigned32 ( 1..255 )
        MAX-ACCESS read-create
        STATUS current
        DESCRIPTION "The TTL value,ranges from 1 to 255(default:255)."
        ::={sqaIcmpTestEntry 8}
         --interval 
    sqaIcmpTestInterval     OBJECT-TYPE
        SYNTAX Unsigned32 ( 50..65535 )
        MAX-ACCESS read-create
        STATUS current
        DESCRIPTION "The sending period of ICMP packets,ranges from 50 to 65535(default:100),unit:ms."
        ::={sqaIcmpTestEntry 9}
         --dscp 
    sqaIcmpTestDscp         OBJECT-TYPE
        SYNTAX Unsigned32 (0..63 | 255)
        MAX-ACCESS read-create
        STATUS current
        DESCRIPTION "The DSCP value,ranges from 0 to 63,255 is the invalid value."
        ::={sqaIcmpTestEntry 10}
        --Row status 
    sqaIcmpTestRowStatus  OBJECT-TYPE
        SYNTAX  RowStatus
        MAX-ACCESS  read-create
        STATUS  current
        DESCRIPTION "Row status"
        ::= { sqaIcmpTestEntry 11}

 --icmp jitter test config info       
    sqaIcmpJitterTestTable  OBJECT-TYPE
        SYNTAX SEQUENCE OF SqaIcmpJitterTestEntry
        MAX-ACCESS not-accessible
        STATUS current  
        DESCRIPTION "SQA ICMP jitter test entity configuration"                 
        ::={sqaMib 29}  
         
    sqaIcmpJitterTestEntry  OBJECT-TYPE
        SYNTAX SqaIcmpJitterTestEntry
        MAX-ACCESS not-accessible
        STATUS current
        DESCRIPTION "SQA ICMP jitter test entity configuration table"
        INDEX { sqaIcmpTestNum } 
        ::={sqaIcmpJitterTestTable 1}
          
    SqaIcmpJitterTestEntry ::=
        SEQUENCE {     
            sqaIcmpJitterTestNum
                Unsigned32,
            sqaIcmpJitterTestVrf
                DisplayString,
            sqaIcmpJitterTestDesIP
                IpAddress,  
            sqaIcmpJitterTestSorceIP
                IpAddress,
            sqaIcmpJitterTestRepeat
                Unsigned32,
            sqaIcmpJitterTestSize
                Unsigned32,
            sqaIcmpJitterTestTos
                Unsigned32,
            sqaIcmpJitterTestTtl
                Unsigned32,
            sqaIcmpJitterTestInterval
                Unsigned32,
            sqaIcmpJitterTestDscp
                Unsigned32,
            sqaIcmpJitterTestRowStatus      
                RowStatus
        } 
        --num                      
    sqaIcmpJitterTestNum  OBJECT-TYPE 
        SYNTAX Unsigned32 ( 1..65535 )   
        MAX-ACCESS not-accessible
        STATUS current
        DESCRIPTION "SQA test number.The range of this parameter depend on the device."
        ::= {sqaIcmpJitterTestEntry 1}  
        --vrf            
    sqaIcmpJitterTestVrf  OBJECT-TYPE
        SYNTAX DisplayString (SIZE(1..32))
        MAX-ACCESS read-create
        STATUS current
        DESCRIPTION "The name of VRF,this string length ranges from 1 to 32."
        ::= {sqaIcmpJitterTestEntry 2}  
         --des ip 
    sqaIcmpJitterTestDesIP      OBJECT-TYPE
        SYNTAX IpAddress
        MAX-ACCESS read-create
        STATUS current
        DESCRIPTION "The destination IP address."
        ::= {sqaIcmpJitterTestEntry 3}
         --source ip  
    sqaIcmpJitterTestSorceIP    OBJECT-TYPE
        SYNTAX IpAddress 
        MAX-ACCESS read-create
        STATUS current
        DESCRIPTION "The Source IP address."
        ::= {sqaIcmpJitterTestEntry 4}
         --repeat 
    sqaIcmpJitterTestRepeat      OBJECT-TYPE
        SYNTAX Unsigned32 ( 1..65535 )
        MAX-ACCESS read-create
        STATUS current
        DESCRIPTION "The number of repeat times,ranges from 1 to 65535(default:1)."
        ::={sqaIcmpJitterTestEntry 5}
         --size 
    sqaIcmpJitterTestSize         OBJECT-TYPE
        SYNTAX Unsigned32 ( 40..8192 )
        MAX-ACCESS read-create
        STATUS current
        DESCRIPTION "The size of ICMP packet,ranges from 40 to 8192(default:40),unit:byte."
        ::={sqaIcmpJitterTestEntry 6}                    
         --tos 
    sqaIcmpJitterTestTos          OBJECT-TYPE
        SYNTAX Unsigned32 ( 0..256 )
        MAX-ACCESS read-create
        STATUS current
        DESCRIPTION "The TOS value,ranges from 0 to 255(default:0),256 is the invalid value."
        ::={sqaIcmpJitterTestEntry 7}
         --ttl 
    sqaIcmpJitterTestTtl         OBJECT-TYPE
        SYNTAX Unsigned32 ( 1..255 )
        MAX-ACCESS read-create
        STATUS current
        DESCRIPTION "The TTL value,ranges from 1 to 255(default:255)."
        ::={sqaIcmpJitterTestEntry 8}
         --interval 
    sqaIcmpJitterTestInterval     OBJECT-TYPE
        SYNTAX Unsigned32 ( 50..65535 )
        MAX-ACCESS read-create
        STATUS current
        DESCRIPTION "The sending period of ICMP packets,ranges from 50 to 65535(default:100),unit:ms."
        ::={sqaIcmpJitterTestEntry 9}
         --dscp 
    sqaIcmpJitterTestDscp         OBJECT-TYPE
        SYNTAX Unsigned32 (0..63 | 255)
        MAX-ACCESS read-create
        STATUS current
        DESCRIPTION "The DSCP value,ranges from 0 to 63,255 is the invalid value."
        ::={sqaIcmpJitterTestEntry 10}
        --Row status 
    sqaIcmpJitterTestRowStatus  OBJECT-TYPE
        SYNTAX  RowStatus
        MAX-ACCESS  read-create
        STATUS  current
        DESCRIPTION "Row status"
        ::= { sqaIcmpJitterTestEntry 11}

END
