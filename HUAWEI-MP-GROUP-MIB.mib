-- ===========================================================================
-- Copyright (C) 2006 by  HUAWEI TECHNOLOGIES. All rights reserved.
-- 
-- Description: HUAWEI-MP-GROUP-MIB
-- Reference: 
-- Version: V1.0
-- History:  
-- created by huangjun 2010-09-24    
-- ===========================================================================

HUAWEI-MP-GROUP-MIB DEFINITIONS ::= BEGIN

IMPORTS   
       hwDatacomm
         FROM   HUAWEI-MIB      
         
			IpAddress, Unsigned32, OBJECT-TYPE, MODULE-IDENTITY, 
        NOTIFICATION-TYPE, TimeTicks, Integer32                       
            FROM SNMPv2-SMI                     
        MODULE-COMPLIANCE, OBJECT-GROUP,NOTIFICATION-GROUP
            FROM SNMPv2-CONF                     
			DisplayString, RowStatus, TruthValue, MacAddress, DateAndTime
				FROM SNMPv2-TC
            InetAddressType, InetAddress, InetPortNumber
                FROM INET-ADDRESS-MIB;                      
 
hwMpGroupMIB MODULE-IDENTITY
       LAST-UPDATED "201009240000Z" -- 24 sep 2010
       ORGANIZATION "Huawei Technologies Co.,Ltd."                
       CONTACT-INFO
              " R&D BeiJing, Huawei Technologies co.,Ltd.
		        Huawei Bld.,NO.3 Xinxi Rd., 
		        Shang-Di Information Industry Base,
		        Hai-Dian District Beijing P.R. China
		        Zip:100085 
		        Http://www.huawei.com                                       
                E-mail:support@huawei.com"
       DESCRIPTION
           ""
       ::= { hwDatacomm 223 }
  
  
hwMpGroupObjects                    OBJECT IDENTIFIER ::= { hwMpGroupMIB 1 }
hwMpGroupNotifications              OBJECT IDENTIFIER ::= { hwMpGroupMIB 2 }
hwMpGroupConformance                OBJECT IDENTIFIER ::= { hwMpGroupMIB 3 }



hwMpGroupTable OBJECT-TYPE
       SYNTAX SEQUENCE OF HwMpGroupEntry
       MAX-ACCESS not-accessible
       STATUS     current
       DESCRIPTION
             "MP group."
       ::= { hwMpGroupObjects 1 }
    hwMpGroupEntry OBJECT-TYPE
       SYNTAX     HwMpGroupEntry
       MAX-ACCESS not-accessible
       STATUS     current
       DESCRIPTION
             "An entry in this table configures the parameters of all
              MP, if partitions are being used."
       INDEX { hwMpGroupIfIndex }
       ::= { hwMpGroupTable 1 }

HwMpGroupEntry ::= SEQUENCE {    
       hwMpGroupIfIndex                   Integer32,
       hwMpGroupDiscriminator			  TruthValue,
       hwMpGroupDamping					  TruthValue,
       hwMpGroupDetectTime	              Unsigned32,  
       hwMpGroupFlappingCount			  Unsigned32,
       hwMpGroupDampingTime			      Unsigned32,
       hwMpGroupThresholdLeast			  Unsigned32,
       hwMpGroupMrru          			  Unsigned32,
       hwMpGroupFragmentThreshold		  INTEGER,
       hwMpGroupShortSequenceFlag		  TruthValue,
       hwMpGroupDropTimeout				  Unsigned32,
       hwMpGroupPktReassemblyQueueDepth	  INTEGER,
       hwMpGroupRowStatus                 RowStatus
}
  
 
 hwMpGroupIfIndex OBJECT-TYPE
       SYNTAX Integer32 (1..2147483647)
	   MAX-ACCESS read-only
		STATUS current
		DESCRIPTION
			"The value of this object identifies the Mp-group interface."
		::= { hwMpGroupEntry 1 }
 
  hwMpGroupDiscriminator OBJECT-TYPE
       SYNTAX     TruthValue
       MAX-ACCESS read-write
       STATUS     current
       DESCRIPTION
             "Enable the MP discriminator negotiation. "
       DEFVAL { false }
       ::= { hwMpGroupEntry 2 }
       
 hwMpGroupDamping OBJECT-TYPE
       SYNTAX     TruthValue
       MAX-ACCESS read-write
       STATUS     current
       DESCRIPTION
             "Enable the function of damping the son channel of the MP link .
             The default value is true(1)."
       DEFVAL { true }
       ::= { hwMpGroupEntry 3 }
       
   
hwMpGroupDetectTime OBJECT-TYPE
       SYNTAX      Unsigned32(0|30..3600)
       MAX-ACCESS read-write
       STATUS     current
       DESCRIPTION
             "Minimum UP time before damping the son channel of the MP
                    link. The value 0 is invalid, and the other values are valid default is 30s." 
       DEFVAL { 30 }
       ::= { hwMpGroupEntry 4 }
       
        
 hwMpGroupFlappingCount OBJECT-TYPE
       SYNTAX      Unsigned32(0..64)
       MAX-ACCESS read-write
       STATUS     current
       DESCRIPTION
             "Maximum number of flapping of the son channel in the
                 detect-time. The value 0 is invalid, and the other values are valid, default is 1."
       DEFVAL { 1 }

       ::= { hwMpGroupEntry 5 }
 
 
 hwMpGroupDampingTime OBJECT-TYPE
       SYNTAX      Unsigned32(0|60..86400)
       MAX-ACCESS read-write
       STATUS     current
       DESCRIPTION
             "Continuous UP time after the son channel of the MP link is
                     damped.  The value 0 is invalid, and the other values are valid, default is 60s."
       DEFVAL { 1 }
       ::= { hwMpGroupEntry 6 }
        
 hwMpGroupThresholdLeast OBJECT-TYPE
       SYNTAX      Unsigned32(1..128)
       MAX-ACCESS read-write
       STATUS     current
       DESCRIPTION
             "Value range of the minimum number of bindings of MP-Group
                  that MP can be used , default is 1 ."
       DEFVAL { 1 }              
       ::= { hwMpGroupEntry 7 }

  hwMpGroupMrru OBJECT-TYPE
       SYNTAX      Unsigned32(328..9216)
       MAX-ACCESS read-write
       STATUS     current
       DESCRIPTION
             "Mrru value."   
       ::= { hwMpGroupEntry 8 }
 
 hwMpGroupFragmentThreshold OBJECT-TYPE
       SYNTAX INTEGER { 
                  length128(1),
                  length256(2) ,
                  length512(3) ,
                  nofragment(4)
                       }
       MAX-ACCESS read-write
       STATUS     current
       DESCRIPTION
             "Fragment-threshold value(1-4): 1->128; 2->256; 3->512; 4->no
                fragment."
       ::= { hwMpGroupEntry 9  }

 hwMpGroupShortSequenceFlag OBJECT-TYPE
       SYNTAX     TruthValue
       MAX-ACCESS read-write
       STATUS     current
       DESCRIPTION
             "Enable short-sequence. "
       DEFVAL { false }
       ::= { hwMpGroupEntry 10 }
  			
 hwMpGroupDropTimeout OBJECT-TYPE
       SYNTAX      Unsigned32(10..100)
       MAX-ACCESS read-write
       STATUS     current
       DESCRIPTION
             "Drop-timeout value, ms as unit."   
       ::= { hwMpGroupEntry 11 }
 			
  hwMpGroupPktReassemblyQueueDepth OBJECT-TYPE
       SYNTAX INTEGER { 
                  depth256(1),
                  depth512(2) ,
                  depth1024(3) ,
                  depth2048(4),
                  depth4096(5)
                       }
       MAX-ACCESS read-write
       STATUS     current
       DESCRIPTION
             "max number of packets can be kept in the queue, 1:256, 2:512,
                3:1024, 4:2048, 5:4096."
       ::= { hwMpGroupEntry 12  }
 
 
 hwMpGroupRowStatus OBJECT-TYPE
       SYNTAX     RowStatus
       MAX-ACCESS read-write
       STATUS     current
       DESCRIPTION
             "An object that allows entries in this table to
              be created, modified and deleted using the RowStatus
              convention.
              A SET operation to any other attribute in this row, when
              this object is set to 'active' (1), MUST be rejected with
              an SNMP error (e.g., inconsistentValue).
              In order to perform a SET operation to any other attribute
              in this table the manager MUST set this object to
              notInService (2).  After setting the object back to
              'active' the implementation MAY tear down all the sessions
              that belong to this partition and recreate them, depending
              on what session attributes have been modified. "
       ::= { hwMpGroupEntry 50 }
        
                                           
-- Notifications
--
--for trap
hwMpGroupTrapOid   OBJECT IDENTIFIER ::= { hwMpGroupNotifications 0 }   


hwMpGroupGroups            OBJECT IDENTIFIER ::= { hwMpGroupConformance 1 }
hwMpGroupCompliances       OBJECT IDENTIFIER ::= { hwMpGroupConformance 2 }

hwMpGroupModuleCompliance MODULE-COMPLIANCE
       STATUS current
       DESCRIPTION
             ""
       MODULE 
       MANDATORY-GROUPS { 
                          hwMpGroupGroup
                         }

       ::= { hwMpGroupCompliances 1 }

-- units of conformance
hwMpGroupGroup OBJECT-GROUP
       OBJECTS {
                 hwMpGroupIfIndex,
                 hwMpGroupDiscriminator,
                 hwMpGroupDamping,
                 hwMpGroupDetectTime,  
                 hwMpGroupFlappingCount,
                 hwMpGroupDampingTime,
                 hwMpGroupThresholdLeast,
                 hwMpGroupMrru,
                 hwMpGroupFragmentThreshold,
                 hwMpGroupShortSequenceFlag,
                 hwMpGroupDropTimeout,
                 hwMpGroupPktReassemblyQueueDepth
               }
       STATUS current
       DESCRIPTION
             ""
       ::= { hwMpGroupGroups 1 }     



END
