-- file automatically created


TELDAT-TRAP-EAP-MIB DEFINITIONS ::= BEGIN


IMPORTS
	MODULE-IDENTITY,OBJECT-TYPE,OBJECT-IDENTITY,NOTIFICATION-TYPE,Integer32,IpAddress
		FROM SNMPv2-SMI
	DisplayString
		FROM SNMPv2-TC
	telEventTraps
		FROM TELDAT-MIB;


eapTrapsMIB MODULE-IDENTITY
    LAST-UPDATED "201401200930Z"
    ORGANIZATION "Teldat, S.A."
    CONTACT-INFO 
        "Teldat, S.A.
        Customer Service

        Postal: Parque Tecnologico de Madrid
                Tres Cantos 28760
                Madrid, SPAIN

        Tel.: +34 918 076 565

        http://www.teldat.com"
    DESCRIPTION
        "This Module Information Base file is defined for managing received
        SNMP notifications generated by the EAP event subsystem."
    REVISION "201401200930Z"
    DESCRIPTION "Initial implementation"
        ::= { telEventTraps 191 }


eapEventsGroup	OBJECT IDENTIFIER	::= { eapTrapsMIB 1 }

eapNotifications	OBJECT IDENTIFIER	::= { eapTrapsMIB 2 }
eapNotificationsPrefix	OBJECT IDENTIFIER	::= { eapNotifications 0 }

eapEventObjects1 OBJECT-IDENTITY
    STATUS current
    DESCRIPTION
        "Event EAP.1
        An EAP packet of the type indicated has just arrived for processing."
    ::= { eapEventsGroup 1 }

eap1-code-string OBJECT-TYPE
    SYNTAX DisplayString
    MAX-ACCESS accessible-for-notify
    STATUS current
    DESCRIPTION
        "Parameter 'code-string' in event EAP.1"
    ::= { eapEventObjects1 1 }

eap1-type-string OBJECT-TYPE
    SYNTAX DisplayString
    MAX-ACCESS accessible-for-notify
    STATUS current
    DESCRIPTION
        "Parameter 'type-string' in event EAP.1"
    ::= { eapEventObjects1 2 }

eap1-identificer OBJECT-TYPE
    SYNTAX Integer32
    MAX-ACCESS accessible-for-notify
    STATUS current
    DESCRIPTION
        "Parameter 'identificer' in event EAP.1"
    ::= { eapEventObjects1 3 }

eap1-length OBJECT-TYPE
    SYNTAX Integer32
    MAX-ACCESS accessible-for-notify
    STATUS current
    DESCRIPTION
        "Parameter 'length' in event EAP.1"
    ::= { eapEventObjects1 4 }

eap1-eap-ctrl OBJECT-TYPE
    SYNTAX Integer32
    MAX-ACCESS accessible-for-notify
    STATUS current
    DESCRIPTION
        "Parameter 'eap-ctrl' in event EAP.1"
    ::= { eapEventObjects1 5 }

eapEventObjects2 OBJECT-IDENTITY
    STATUS current
    DESCRIPTION
        "Event EAP.2
        An EAP packet of the type indicated has been transmitted."
    ::= { eapEventsGroup 2 }

eap2-code-string OBJECT-TYPE
    SYNTAX DisplayString
    MAX-ACCESS accessible-for-notify
    STATUS current
    DESCRIPTION
        "Parameter 'code-string' in event EAP.2"
    ::= { eapEventObjects2 1 }

eap2-type-string OBJECT-TYPE
    SYNTAX DisplayString
    MAX-ACCESS accessible-for-notify
    STATUS current
    DESCRIPTION
        "Parameter 'type-string' in event EAP.2"
    ::= { eapEventObjects2 2 }

eap2-identificer OBJECT-TYPE
    SYNTAX Integer32
    MAX-ACCESS accessible-for-notify
    STATUS current
    DESCRIPTION
        "Parameter 'identificer' in event EAP.2"
    ::= { eapEventObjects2 3 }

eap2-length OBJECT-TYPE
    SYNTAX Integer32
    MAX-ACCESS accessible-for-notify
    STATUS current
    DESCRIPTION
        "Parameter 'length' in event EAP.2"
    ::= { eapEventObjects2 4 }

eap2-eap-ctrl OBJECT-TYPE
    SYNTAX Integer32
    MAX-ACCESS accessible-for-notify
    STATUS current
    DESCRIPTION
        "Parameter 'eap-ctrl' in event EAP.2"
    ::= { eapEventObjects2 5 }

eapEventObjects3 OBJECT-IDENTITY
    STATUS current
    DESCRIPTION
        "Event EAP.3
        An EAP request was sent and no response was received. The packet is
        retransmitted."
    ::= { eapEventsGroup 3 }

eap3-retry-count OBJECT-TYPE
    SYNTAX Integer32
    MAX-ACCESS accessible-for-notify
    STATUS current
    DESCRIPTION
        "Parameter 'retry-count' in event EAP.3"
    ::= { eapEventObjects3 1 }

eap3-eap-ctrl OBJECT-TYPE
    SYNTAX Integer32
    MAX-ACCESS accessible-for-notify
    STATUS current
    DESCRIPTION
        "Parameter 'eap-ctrl' in event EAP.3"
    ::= { eapEventObjects3 2 }

eapEventObjects4 OBJECT-IDENTITY
    STATUS current
    DESCRIPTION
        "Event EAP.4
        An EAP request has been sent with no response for the maximum configured
        retries. The EAP session is closed."
    ::= { eapEventsGroup 4 }

eap4-eap-ctrl OBJECT-TYPE
    SYNTAX Integer32
    MAX-ACCESS accessible-for-notify
    STATUS current
    DESCRIPTION
        "Parameter 'eap-ctrl' in event EAP.4"
    ::= { eapEventObjects4 1 }

eapEventObjects5 OBJECT-IDENTITY
    STATUS current
    DESCRIPTION
        "Event EAP.5
        The received EAP identity can not be processed because it is longer
        than the available buffer."
    ::= { eapEventsGroup 5 }

eap5-Identity-len OBJECT-TYPE
    SYNTAX Integer32
    MAX-ACCESS accessible-for-notify
    STATUS current
    DESCRIPTION
        "Parameter 'Identity-len' in event EAP.5"
    ::= { eapEventObjects5 1 }

eap5-Available-len OBJECT-TYPE
    SYNTAX Integer32
    MAX-ACCESS accessible-for-notify
    STATUS current
    DESCRIPTION
        "Parameter 'Available-len' in event EAP.5"
    ::= { eapEventObjects5 2 }

eap5-eap-ctrl OBJECT-TYPE
    SYNTAX Integer32
    MAX-ACCESS accessible-for-notify
    STATUS current
    DESCRIPTION
        "Parameter 'eap-ctrl' in event EAP.5"
    ::= { eapEventObjects5 3 }

eapEventObjects6 OBJECT-IDENTITY
    STATUS current
    DESCRIPTION
        "Event EAP.6
        EAP control block created."
    ::= { eapEventsGroup 6 }

eap6-eap-ctrl OBJECT-TYPE
    SYNTAX Integer32
    MAX-ACCESS accessible-for-notify
    STATUS current
    DESCRIPTION
        "Parameter 'eap-ctrl' in event EAP.6"
    ::= { eapEventObjects6 1 }

eapEventObjects7 OBJECT-IDENTITY
    STATUS current
    DESCRIPTION
        "Event EAP.7
        EAP control block destroyed."
    ::= { eapEventsGroup 7 }

eap7-eap-ctrl OBJECT-TYPE
    SYNTAX Integer32
    MAX-ACCESS accessible-for-notify
    STATUS current
    DESCRIPTION
        "Parameter 'eap-ctrl' in event EAP.7"
    ::= { eapEventObjects7 1 }

eapEventObjects8 OBJECT-IDENTITY
    STATUS current
    DESCRIPTION
        "Event EAP.8
        The received EAP packet was discarded because an error ocurred while
        processing it."
    ::= { eapEventsGroup 8 }

eap8-error-string OBJECT-TYPE
    SYNTAX DisplayString
    MAX-ACCESS accessible-for-notify
    STATUS current
    DESCRIPTION
        "Parameter 'error-string' in event EAP.8"
    ::= { eapEventObjects8 1 }

eap8-eap-ctrl OBJECT-TYPE
    SYNTAX Integer32
    MAX-ACCESS accessible-for-notify
    STATUS current
    DESCRIPTION
        "Parameter 'eap-ctrl' in event EAP.8"
    ::= { eapEventObjects8 2 }


eapNotification1 NOTIFICATION-TYPE
    OBJECTS { 
              eap1-code-string, 
              eap1-type-string,
              eap1-identificer,
              eap1-length,
              eap1-eap-ctrl 
            }
    STATUS current
    DESCRIPTION
        "Notification of Event EAP.1

        Message: 'Received EAP $1/$2 Packet, identifier $3, length $4, eap-ctrl 0x$5'

        Parameters list:
              $1: eap1-code-string
              $2: eap1-type-string
              $3: eap1-identificer
              $4: eap1-length
              $5: eap1-eap-ctrl

        An EAP packet of the type indicated has just arrived for processing."
    ::= { eapNotificationsPrefix 1 }

eapNotification2 NOTIFICATION-TYPE
    OBJECTS { 
              eap2-code-string, 
              eap2-type-string,
              eap2-identificer,
              eap2-length,
              eap2-eap-ctrl 
            }
    STATUS current
    DESCRIPTION
        "Notification of Event EAP.2

        Message: 'Transmitted EAP $1/$2 Packet, identifier $3, length $4, eap-ctrl 0x$5'

        Parameters list:
              $1: eap2-code-string
              $2: eap2-type-string
              $3: eap2-identificer
              $4: eap2-length
              $5: eap2-eap-ctrl

        An EAP packet of the type indicated has been transmitted."
    ::= { eapNotificationsPrefix 2 }

eapNotification3 NOTIFICATION-TYPE
    OBJECTS { 
              eap3-retry-count, 
              eap3-eap-ctrl 
            }
    STATUS current
    DESCRIPTION
        "Notification of Event EAP.3

        Message: 'EAP Timeout retry $1, eap-ctrl 0x$2'

        Parameters list:
              $1: eap3-retry-count
              $2: eap3-eap-ctrl

        An EAP request was sent and no response was received. The packet is
        retransmitted."
    ::= { eapNotificationsPrefix 3 }

eapNotification4 NOTIFICATION-TYPE
    OBJECTS { 
              eap4-eap-ctrl 
            }
    STATUS current
    DESCRIPTION
        "Notification of Event EAP.4

        Message: 'EAP Timeout max retries reached, eap-ctrl 0x$1'

        Parameters list:
              $1: eap4-eap-ctrl

        An EAP request has been sent with no response for the maximum configured
        retries. The EAP session is closed."
    ::= { eapNotificationsPrefix 4 }

eapNotification5 NOTIFICATION-TYPE
    OBJECTS { 
              eap5-Identity-len, 
              eap5-Available-len,
              eap5-eap-ctrl 
            }
    STATUS current
    DESCRIPTION
        "Notification of Event EAP.5

        Message: 'Not enough space to store Identity len $1, available $2, eap-ctrl 0x$3'

        Parameters list:
              $1: eap5-Identity-len
              $2: eap5-Available-len
              $3: eap5-eap-ctrl

        The received EAP identity can not be processed because it is longer
        than the available buffer."
    ::= { eapNotificationsPrefix 5 }

eapNotification6 NOTIFICATION-TYPE
    OBJECTS { 
              eap6-eap-ctrl 
            }
    STATUS current
    DESCRIPTION
        "Notification of Event EAP.6

        Message: 'Created EAP ctrl 0x$1'

        Parameters list:
              $1: eap6-eap-ctrl

        EAP control block created."
    ::= { eapNotificationsPrefix 6 }

eapNotification7 NOTIFICATION-TYPE
    OBJECTS { 
              eap7-eap-ctrl 
            }
    STATUS current
    DESCRIPTION
        "Notification of Event EAP.7

        Message: 'Destroyed EAP ctrl 0x$1'

        Parameters list:
              $1: eap7-eap-ctrl

        EAP control block destroyed."
    ::= { eapNotificationsPrefix 7 }

eapNotification8 NOTIFICATION-TYPE
    OBJECTS { 
              eap8-error-string, 
              eap8-eap-ctrl 
            }
    STATUS current
    DESCRIPTION
        "Notification of Event EAP.8

        Message: 'Received EAP packet discarded ($1), eap-ctrl 0x$2'

        Parameters list:
              $1: eap8-error-string
              $2: eap8-eap-ctrl

        The received EAP packet was discarded because an error ocurred while
        processing it."
    ::= { eapNotificationsPrefix 8 }


END
