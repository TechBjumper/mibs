--*****************************************************************
-- ZXR10-TACPLUS-MIB
-- OAM
-- 2013-10-14 11:28  zhuhuaxing
-- Copyright (c) 1985-2013 by ZTE Corp.
-- All rights reserved. 
--*****************************************************************

ZXR10-TACPLUS-MIB DEFINITIONS ::= BEGIN

IMPORTS
    MODULE-IDENTITY,OBJECT-TYPE,enterprises,IpAddress,
    Unsigned32,Integer32
        FROM SNMPv2-SMI
    DisplayString,TEXTUAL-CONVENTION
        FROM SNMPv2-TC
    zxr10
        FROM ZXR10-SMI;

zxr10Tacplus MODULE-IDENTITY
        LAST-UPDATED "201310141000Z"
        ORGANIZATION "ZTE Corporation"
        CONTACT-INFO
            "       Zang Liang
            Tel:    +86-25-52870000
            E-Mail: zang.liang@zte.com.cn "
        DESCRIPTION
            "The MIB module to describe the TACACS+ protocol."

        REVISION "201310141000Z"
        DESCRIPTION
            "The Zxr10TacplusGroupServerEntry adds new leaf:
            zxr10TacplusGroupServerIfMaster"

        ::= { zxr10 1020 }

--******************************************************
--    he follow part defined some data types which will 
--    be used in this mib file later  
--****************************************************** 
TacGrpSvrMaster ::= TEXTUAL-CONVENTION
    STATUS       current
    DESCRIPTION
            "The true value of TACACS+ group server master flag"
    SYNTAX   INTEGER {master(1),slave(2)}
       
--******************************************************
-- the TACACS+ status information
--******************************************************
zxr10TacacsStatus  OBJECT-TYPE
        SYNTAX  INTEGER {
            disable(0),
            enable(1)
        }
        MAX-ACCESS  read-only
        STATUS  current
        DESCRIPTION
            "The TACACS+ status,where 0 means disable and 1 means enable"
        ::= { zxr10Tacplus  1 }

--******************************************************
-- the TACACS+ global key information
--******************************************************
zxr10TacacsGlobalKey  OBJECT-TYPE
        SYNTAX  DisplayString (SIZE(0..128)) 
        MAX-ACCESS  read-only
        STATUS  current
        DESCRIPTION
            "The TACACS+ global key"
        ::= { zxr10Tacplus  2 }

--******************************************************
-- the TACACS+ global packet information
--******************************************************
zxr10TacacsGlobalPacket  OBJECT-TYPE
        SYNTAX  Unsigned32
        MAX-ACCESS  read-only
        STATUS  current
        DESCRIPTION
            "The TACACS+ global packet"
            ::= { zxr10Tacplus  3 }

--******************************************************
-- the TACACS+ global timeout information
--******************************************************
zxr10TacacsGlobalTimeout  OBJECT-TYPE
        SYNTAX  Unsigned32
        MAX-ACCESS  read-only
        STATUS  current
        DESCRIPTION
            "The TACACS+ global timeout"
            ::= { zxr10Tacplus  4 }

--******************************************************
-- the TACACS+ client ipaddr information
--******************************************************
zxr10TacacsClientIpaddr  OBJECT-TYPE
        SYNTAX  IpAddress
        MAX-ACCESS  read-only
        STATUS  current
        DESCRIPTION
            "The TACACS+ client ipaddr"
            ::= { zxr10Tacplus  5 }

--******************************************************
-- the TACACS+ client port information
--******************************************************
        zxr10TacacsClientPort  OBJECT-TYPE
            SYNTAX  Unsigned32
            MAX-ACCESS  read-only
            STATUS  current
            DESCRIPTION
                "The TACACS+ client port"
                ::= { zxr10Tacplus  6 }	

--******************************************************
-- the TACACS+ server table
--******************************************************
zxr10TacacsServerTable OBJECT-TYPE
        SYNTAX  SEQUENCE OF Zxr10TacacsServerEntry
        MAX-ACCESS  not-accessible
        STATUS  current
        DESCRIPTION
            "A table containing TACACS+ server information."
            ::= { zxr10Tacplus 7 }

zxr10TacacsServerEntry OBJECT-TYPE
        SYNTAX  Zxr10TacacsServerEntry
        MAX-ACCESS  not-accessible
        STATUS  current
        DESCRIPTION
            "Information about the server of TACACS+."
        INDEX   { 
            zxr10TacacsServerAddress,zxr10TacacsServerVrfname,zxr10TacacsServerPort
        }
        ::= { zxr10TacacsServerTable 1 }

Zxr10TacacsServerEntry ::=
        SEQUENCE {
            zxr10TacacsServerAddress
                IpAddress,
            zxr10TacacsServerVrfname
                DisplayString,
            zxr10TacacsServerPort
                Unsigned32,
            zxr10TacacsServerKey
                DisplayString,
            zxr10TacacsServerTimeout
                Unsigned32					  
        }

zxr10TacacsServerAddress OBJECT-TYPE
        SYNTAX  IpAddress
        MAX-ACCESS  read-only
        STATUS  current
        DESCRIPTION
            "The TACACS+ server IP address."
        ::= { zxr10TacacsServerEntry 1 }
              
zxr10TacacsServerVrfname OBJECT-TYPE
        SYNTAX  DisplayString
        MAX-ACCESS  read-only
        STATUS  current
        DESCRIPTION
            "The TACACS+ server VRF name"
        ::= { zxr10TacacsServerEntry 2 }
              
zxr10TacacsServerPort OBJECT-TYPE
        SYNTAX  Unsigned32
        MAX-ACCESS  read-only
        STATUS  current
        DESCRIPTION
            "The TACACS+ server port"
        ::= { zxr10TacacsServerEntry 3 }

zxr10TacacsServerKey OBJECT-TYPE
        SYNTAX  DisplayString
        MAX-ACCESS  read-only
        STATUS  current
        DESCRIPTION
            "The TACACS+ server key"
        ::= { zxr10TacacsServerEntry 4 }

zxr10TacacsServerTimeout OBJECT-TYPE
        SYNTAX  Unsigned32
        MAX-ACCESS  read-only
        STATUS  current
        DESCRIPTION
            "The TACACS+ server timeout"
        ::= { zxr10TacacsServerEntry 5 }
			  
--******************************************************
 -- the TACACS+ group table
--******************************************************
zxr10TacplusGroupTable OBJECT-TYPE
        SYNTAX  SEQUENCE OF Zxr10TacplusGroupEntry
        MAX-ACCESS  not-accessible
        STATUS  current
        DESCRIPTION
            "A table containing TACACS+ group information."
        ::= { zxr10Tacplus 8 }

zxr10TacplusGroupEntry OBJECT-TYPE
        SYNTAX  Zxr10TacplusGroupEntry
        MAX-ACCESS  not-accessible
        STATUS  current
        DESCRIPTION
            "Information about the server of TACACS+ group."
            INDEX   { 
            zxr10TacplusGroupName
            }
        ::= { zxr10TacplusGroupTable 1 }

Zxr10TacplusGroupEntry ::=
        SEQUENCE {
            zxr10TacplusGroupName
            DisplayString
        }

zxr10TacplusGroupName OBJECT-TYPE
        SYNTAX  DisplayString
        MAX-ACCESS  read-only
        STATUS  current
        DESCRIPTION
            "The TACACS+ group name."
        ::= { zxr10TacplusGroupEntry 1 }

--******************************************************
-- the TACACS+ group server table
--******************************************************
zxr10TacplusGroupServerTable OBJECT-TYPE
        SYNTAX  SEQUENCE OF Zxr10TacplusGroupServerEntry
        MAX-ACCESS  not-accessible
        STATUS  current
        DESCRIPTION
            "A table containing TACACS+ group server information."
        ::= { zxr10Tacplus 9 }

zxr10TacplusGroupServerEntry OBJECT-TYPE
        SYNTAX  Zxr10TacplusGroupServerEntry
        MAX-ACCESS  not-accessible
        STATUS  current
        DESCRIPTION
            "Information about the server of TACACS+ group."
        INDEX   { 
            zxr10TacplusServerGroupName,zxr10TacplusGroupServerAddress,
            zxr10TacplusGroupServerVrfname,zxr10TacplusGroupServerPort
        }
        ::= { zxr10TacplusGroupServerTable 1 }

Zxr10TacplusGroupServerEntry ::=
        SEQUENCE {
            zxr10TacplusServerGroupName
                DisplayString,
            zxr10TacplusGroupServerAddress
                IpAddress,
            zxr10TacplusGroupServerVrfname
                DisplayString,
            zxr10TacplusGroupServerPort
                Unsigned32,
            zxr10TacplusGroupServerIfMaster
                TacGrpSvrMaster
        }

zxr10TacplusServerGroupName OBJECT-TYPE
        SYNTAX  DisplayString
        MAX-ACCESS  read-only
        STATUS  current
        DESCRIPTION
            "The TACACS+ group name."
        ::= { zxr10TacplusGroupServerEntry 1 }

zxr10TacplusGroupServerAddress OBJECT-TYPE
        SYNTAX  IpAddress
        MAX-ACCESS  read-only
        STATUS  current
        DESCRIPTION
            "The TACACS+ group server ipaddr."
        ::= { zxr10TacplusGroupServerEntry 2 }

zxr10TacplusGroupServerVrfname OBJECT-TYPE
        SYNTAX  DisplayString
        MAX-ACCESS  read-only
        STATUS  current
        DESCRIPTION
            "The TACACS+ group server VRF name."
        ::= { zxr10TacplusGroupServerEntry 3 }

zxr10TacplusGroupServerPort OBJECT-TYPE
        SYNTAX  Unsigned32
        MAX-ACCESS  read-only
        STATUS  current
        DESCRIPTION
            "The TACACS+ group server port."
        ::= { zxr10TacplusGroupServerEntry 4 }
			  
zxr10TacplusGroupServerIfMaster OBJECT-TYPE
        SYNTAX  TacGrpSvrMaster
        MAX-ACCESS  read-only
        STATUS  current
        DESCRIPTION
            "The TACACS+ group server if master server."
        ::= { zxr10TacplusGroupServerEntry 5 }

--******************************************************
-- the TACACS+ global deadtime information
--******************************************************
zxr10TacacsGlobalDeadtime  OBJECT-TYPE
        SYNTAX  Unsigned32
        MAX-ACCESS  read-only
        STATUS  current
        DESCRIPTION
            "The TACACS+ global deadtime"
            ::= { zxr10Tacplus  12 }

     END
