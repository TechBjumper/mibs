-- file automatically created


TELDAT-TRAP-WWAN-MIB DEFINITIONS ::= BEGIN


IMPORTS
	MODULE-IDENTITY,OBJECT-TYPE,OBJECT-IDENTITY,NOTIFICATION-TYPE,Integer32,IpAddress
		FROM SNMPv2-SMI
	DisplayString
		FROM SNMPv2-TC
	telEventTraps
		FROM TELDAT-MIB;


wwanTrapsMIB MODULE-IDENTITY
    LAST-UPDATED "201401200930Z"
    ORGANIZATION "Teldat, S.A."
    CONTACT-INFO 
        "Teldat, S.A.
        Customer Service

        Postal: Parque Tecnologico de Madrid
                Tres Cantos 28760
                Madrid, SPAIN

        Tel.: +34 918 076 565

        http://www.teldat.com"
    DESCRIPTION
        "This Module Information Base file is defined for managing received
        SNMP notifications generated by the WWAN event subsystem."
    REVISION "201401200930Z"
    DESCRIPTION "Initial implementation"
        ::= { telEventTraps 211 }


wwanEventsGroup	OBJECT IDENTIFIER	::= { wwanTrapsMIB 1 }

wwanNotifications	OBJECT IDENTIFIER	::= { wwanTrapsMIB 2 }
wwanNotificationsPrefix	OBJECT IDENTIFIER	::= { wwanNotifications 0 }

wwanEventObjects1 OBJECT-IDENTITY
    STATUS current
    DESCRIPTION
        "Event WWAN.1
        Generic informational event."
    ::= { wwanEventsGroup 1 }

wwan1-info-string OBJECT-TYPE
    SYNTAX DisplayString
    MAX-ACCESS accessible-for-notify
    STATUS current
    DESCRIPTION
        "Parameter 'info-string' in event WWAN.1"
    ::= { wwanEventObjects1 1 }

wwan1-ifcname OBJECT-TYPE
    SYNTAX DisplayString
    MAX-ACCESS accessible-for-notify
    STATUS current
    DESCRIPTION
        "Parameter 'ifcname' in event WWAN.1"
    ::= { wwanEventObjects1 2 }

wwanEventObjects2 OBJECT-IDENTITY
    STATUS current
    DESCRIPTION
        "Event WWAN.2
        Generic error report."
    ::= { wwanEventsGroup 2 }

wwan2-error-string OBJECT-TYPE
    SYNTAX DisplayString
    MAX-ACCESS accessible-for-notify
    STATUS current
    DESCRIPTION
        "Parameter 'error-string' in event WWAN.2"
    ::= { wwanEventObjects2 1 }

wwan2-ifcname OBJECT-TYPE
    SYNTAX DisplayString
    MAX-ACCESS accessible-for-notify
    STATUS current
    DESCRIPTION
        "Parameter 'ifcname' in event WWAN.2"
    ::= { wwanEventObjects2 2 }

wwanEventObjects3 OBJECT-IDENTITY
    STATUS current
    DESCRIPTION
        "Event WWAN.3
        Registration state has changed."
    ::= { wwanEventsGroup 3 }

wwan3-state OBJECT-TYPE
    SYNTAX DisplayString
    MAX-ACCESS accessible-for-notify
    STATUS current
    DESCRIPTION
        "Parameter 'state' in event WWAN.3"
    ::= { wwanEventObjects3 1 }

wwan3-ifcname OBJECT-TYPE
    SYNTAX DisplayString
    MAX-ACCESS accessible-for-notify
    STATUS current
    DESCRIPTION
        "Parameter 'ifcname' in event WWAN.3"
    ::= { wwanEventObjects3 2 }

wwanEventObjects4 OBJECT-IDENTITY
    STATUS current
    DESCRIPTION
        "Event WWAN.4
        The wireless wan interface now uses a different Public Land Mobile Network,
        (Mobile Operator) identified by the number displayed."
    ::= { wwanEventsGroup 4 }

wwan4-operator OBJECT-TYPE
    SYNTAX Integer32
    MAX-ACCESS accessible-for-notify
    STATUS current
    DESCRIPTION
        "Parameter 'operator' in event WWAN.4"
    ::= { wwanEventObjects4 1 }

wwan4-ifcname OBJECT-TYPE
    SYNTAX DisplayString
    MAX-ACCESS accessible-for-notify
    STATUS current
    DESCRIPTION
        "Parameter 'ifcname' in event WWAN.4"
    ::= { wwanEventObjects4 2 }

wwanEventObjects5 OBJECT-IDENTITY
    STATUS current
    DESCRIPTION
        "Event WWAN.5
        The wireless wan interface is connected to a different base station,
        identified by the Location Area Code (LAC) and the Cell Identifier code
        (CiD)."
    ::= { wwanEventsGroup 5 }

wwan5-location-area-code OBJECT-TYPE
    SYNTAX Integer32
    MAX-ACCESS accessible-for-notify
    STATUS current
    DESCRIPTION
        "Parameter 'location-area-code' in event WWAN.5"
    ::= { wwanEventObjects5 1 }

wwan5-cell-id OBJECT-TYPE
    SYNTAX Integer32
    MAX-ACCESS accessible-for-notify
    STATUS current
    DESCRIPTION
        "Parameter 'cell-id' in event WWAN.5"
    ::= { wwanEventObjects5 2 }

wwan5-ifcname OBJECT-TYPE
    SYNTAX DisplayString
    MAX-ACCESS accessible-for-notify
    STATUS current
    DESCRIPTION
        "Parameter 'ifcname' in event WWAN.5"
    ::= { wwanEventObjects5 3 }

wwanEventObjects6 OBJECT-IDENTITY
    STATUS current
    DESCRIPTION
        "Event WWAN.6
        Notify a change of the used wireless wan technology, which implies different
        radio bands, coding methods and therefore different data rates."
    ::= { wwanEventsGroup 6 }

wwan6-technology OBJECT-TYPE
    SYNTAX DisplayString
    MAX-ACCESS accessible-for-notify
    STATUS current
    DESCRIPTION
        "Parameter 'technology' in event WWAN.6"
    ::= { wwanEventObjects6 1 }

wwan6-ifcname OBJECT-TYPE
    SYNTAX DisplayString
    MAX-ACCESS accessible-for-notify
    STATUS current
    DESCRIPTION
        "Parameter 'ifcname' in event WWAN.6"
    ::= { wwanEventObjects6 2 }

wwanEventObjects7 OBJECT-IDENTITY
    STATUS current
    DESCRIPTION
        "Event WWAN.7
        Received Signal Strength Indication (RSSI) changed to the level
        displayed. This event depends of user's configuration thresholds and
        appears only if the used technology is GSM or GPRS."
    ::= { wwanEventsGroup 7 }

wwan7-rssi-level OBJECT-TYPE
    SYNTAX Integer32
    MAX-ACCESS accessible-for-notify
    STATUS current
    DESCRIPTION
        "Parameter 'rssi-level' in event WWAN.7"
    ::= { wwanEventObjects7 1 }

wwan7-ifcname OBJECT-TYPE
    SYNTAX DisplayString
    MAX-ACCESS accessible-for-notify
    STATUS current
    DESCRIPTION
        "Parameter 'ifcname' in event WWAN.7"
    ::= { wwanEventObjects7 2 }

wwanEventObjects8 OBJECT-IDENTITY
    STATUS current
    DESCRIPTION
        "Event WWAN.8
        Received Signal Code Power (RSCP) has changed to the level displayed or
        the EcNo ratio (received energy per chip divided by the power density in
        the band) has changed to the value displayed. This event depends of
        user's configuration thresholds and appears only if the used technology
        is UMTS, HSDPA or CDMA."
    ::= { wwanEventsGroup 8 }

wwan8-rscp-level OBJECT-TYPE
    SYNTAX Integer32
    MAX-ACCESS accessible-for-notify
    STATUS current
    DESCRIPTION
        "Parameter 'rscp-level' in event WWAN.8"
    ::= { wwanEventObjects8 1 }

wwan8-ecno-level OBJECT-TYPE
    SYNTAX Integer32
    MAX-ACCESS accessible-for-notify
    STATUS current
    DESCRIPTION
        "Parameter 'ecno-level' in event WWAN.8"
    ::= { wwanEventObjects8 2 }

wwan8-ifcname OBJECT-TYPE
    SYNTAX DisplayString
    MAX-ACCESS accessible-for-notify
    STATUS current
    DESCRIPTION
        "Parameter 'ifcname' in event WWAN.8"
    ::= { wwanEventObjects8 3 }

wwanEventObjects9 OBJECT-IDENTITY
    STATUS current
    DESCRIPTION
        "Event WWAN.9
        Active SIM is placed in the displayed socked."
    ::= { wwanEventsGroup 9 }

wwan9-sim-socket OBJECT-TYPE
    SYNTAX DisplayString
    MAX-ACCESS accessible-for-notify
    STATUS current
    DESCRIPTION
        "Parameter 'sim-socket' in event WWAN.9"
    ::= { wwanEventObjects9 1 }

wwan9-ifcname OBJECT-TYPE
    SYNTAX DisplayString
    MAX-ACCESS accessible-for-notify
    STATUS current
    DESCRIPTION
        "Parameter 'ifcname' in event WWAN.9"
    ::= { wwanEventObjects9 2 }

wwanEventObjects10 OBJECT-IDENTITY
    STATUS current
    DESCRIPTION
        "Event WWAN.10
        Interface call stated changed to the state displayed"
    ::= { wwanEventsGroup 10 }

wwan10-call-state-string OBJECT-TYPE
    SYNTAX DisplayString
    MAX-ACCESS accessible-for-notify
    STATUS current
    DESCRIPTION
        "Parameter 'call-state-string' in event WWAN.10"
    ::= { wwanEventObjects10 1 }

wwan10-call-state-num OBJECT-TYPE
    SYNTAX Integer32
    MAX-ACCESS accessible-for-notify
    STATUS current
    DESCRIPTION
        "Parameter 'call-state-num' in event WWAN.10"
    ::= { wwanEventObjects10 2 }

wwan10-ifcname OBJECT-TYPE
    SYNTAX DisplayString
    MAX-ACCESS accessible-for-notify
    STATUS current
    DESCRIPTION
        "Parameter 'ifcname' in event WWAN.10"
    ::= { wwanEventObjects10 3 }

wwanEventObjects11 OBJECT-IDENTITY
    STATUS current
    DESCRIPTION
        "Event WWAN.11
        A successful upgrade has been done to the displayed release"
    ::= { wwanEventsGroup 11 }

wwan11-frmwr-release OBJECT-TYPE
    SYNTAX DisplayString
    MAX-ACCESS accessible-for-notify
    STATUS current
    DESCRIPTION
        "Parameter 'frmwr-release' in event WWAN.11"
    ::= { wwanEventObjects11 1 }

wwan11-ifcname OBJECT-TYPE
    SYNTAX DisplayString
    MAX-ACCESS accessible-for-notify
    STATUS current
    DESCRIPTION
        "Parameter 'ifcname' in event WWAN.11"
    ::= { wwanEventObjects11 2 }

wwanEventObjects12 OBJECT-IDENTITY
    STATUS current
    DESCRIPTION
        "Event WWAN.12
        Current SIM is the configured as main"
    ::= { wwanEventsGroup 12 }

wwan12-sim-socket OBJECT-TYPE
    SYNTAX DisplayString
    MAX-ACCESS accessible-for-notify
    STATUS current
    DESCRIPTION
        "Parameter 'sim-socket' in event WWAN.12"
    ::= { wwanEventObjects12 1 }

wwan12-ifcname OBJECT-TYPE
    SYNTAX DisplayString
    MAX-ACCESS accessible-for-notify
    STATUS current
    DESCRIPTION
        "Parameter 'ifcname' in event WWAN.12"
    ::= { wwanEventObjects12 2 }

wwanEventObjects13 OBJECT-IDENTITY
    STATUS current
    DESCRIPTION
        "Event WWAN.13
        Current SIM is the configured as backup."
    ::= { wwanEventsGroup 13 }

wwan13-sim-socket OBJECT-TYPE
    SYNTAX DisplayString
    MAX-ACCESS accessible-for-notify
    STATUS current
    DESCRIPTION
        "Parameter 'sim-socket' in event WWAN.13"
    ::= { wwanEventObjects13 1 }

wwan13-ifcname OBJECT-TYPE
    SYNTAX DisplayString
    MAX-ACCESS accessible-for-notify
    STATUS current
    DESCRIPTION
        "Parameter 'ifcname' in event WWAN.13"
    ::= { wwanEventObjects13 2 }

wwanEventObjects14 OBJECT-IDENTITY
    STATUS current
    DESCRIPTION
        "Event WWAN.14
        A switching criteria is met and backup SIM is activated"
    ::= { wwanEventsGroup 14 }

wwan14-criteria OBJECT-TYPE
    SYNTAX DisplayString
    MAX-ACCESS accessible-for-notify
    STATUS current
    DESCRIPTION
        "Parameter 'criteria' in event WWAN.14"
    ::= { wwanEventObjects14 1 }

wwan14-sim-socket OBJECT-TYPE
    SYNTAX DisplayString
    MAX-ACCESS accessible-for-notify
    STATUS current
    DESCRIPTION
        "Parameter 'sim-socket' in event WWAN.14"
    ::= { wwanEventObjects14 2 }

wwan14-ifcname OBJECT-TYPE
    SYNTAX DisplayString
    MAX-ACCESS accessible-for-notify
    STATUS current
    DESCRIPTION
        "Parameter 'ifcname' in event WWAN.14"
    ::= { wwanEventObjects14 3 }

wwanEventObjects15 OBJECT-IDENTITY
    STATUS current
    DESCRIPTION
        "Event WWAN.15
        A return criteria is met and main SIM is activated"
    ::= { wwanEventsGroup 15 }

wwan15-criteria OBJECT-TYPE
    SYNTAX DisplayString
    MAX-ACCESS accessible-for-notify
    STATUS current
    DESCRIPTION
        "Parameter 'criteria' in event WWAN.15"
    ::= { wwanEventObjects15 1 }

wwan15-sim-socket OBJECT-TYPE
    SYNTAX DisplayString
    MAX-ACCESS accessible-for-notify
    STATUS current
    DESCRIPTION
        "Parameter 'sim-socket' in event WWAN.15"
    ::= { wwanEventObjects15 2 }

wwan15-ifcname OBJECT-TYPE
    SYNTAX DisplayString
    MAX-ACCESS accessible-for-notify
    STATUS current
    DESCRIPTION
        "Parameter 'ifcname' in event WWAN.15"
    ::= { wwanEventObjects15 3 }

wwanEventObjects16 OBJECT-IDENTITY
    STATUS current
    DESCRIPTION
        "Event WWAN.16
        A error is found and reported during SIM management"
    ::= { wwanEventsGroup 16 }

wwan16-error OBJECT-TYPE
    SYNTAX DisplayString
    MAX-ACCESS accessible-for-notify
    STATUS current
    DESCRIPTION
        "Parameter 'error' in event WWAN.16"
    ::= { wwanEventObjects16 1 }

wwan16-ifcname OBJECT-TYPE
    SYNTAX DisplayString
    MAX-ACCESS accessible-for-notify
    STATUS current
    DESCRIPTION
        "Parameter 'ifcname' in event WWAN.16"
    ::= { wwanEventObjects16 2 }


wwanNotification1 NOTIFICATION-TYPE
    OBJECTS { 
              wwan1-info-string, 
              wwan1-ifcname 
            }
    STATUS current
    DESCRIPTION
        "Notification of Event WWAN.1

        Message: '$1 intf $2'

        Parameters list:
              $1: wwan1-info-string
              $2: wwan1-ifcname

        Generic informational event."
    ::= { wwanNotificationsPrefix 1 }

wwanNotification2 NOTIFICATION-TYPE
    OBJECTS { 
              wwan2-error-string, 
              wwan2-ifcname 
            }
    STATUS current
    DESCRIPTION
        "Notification of Event WWAN.2

        Message: '$1 intf $2'

        Parameters list:
              $1: wwan2-error-string
              $2: wwan2-ifcname

        Generic error report."
    ::= { wwanNotificationsPrefix 2 }

wwanNotification3 NOTIFICATION-TYPE
    OBJECTS { 
              wwan3-state, 
              wwan3-ifcname 
            }
    STATUS current
    DESCRIPTION
        "Notification of Event WWAN.3

        Message: 'CHANGED Registration state to $1, on interface $2'

        Parameters list:
              $1: wwan3-state
              $2: wwan3-ifcname

        Registration state has changed."
    ::= { wwanNotificationsPrefix 3 }

wwanNotification4 NOTIFICATION-TYPE
    OBJECTS { 
              wwan4-operator, 
              wwan4-ifcname 
            }
    STATUS current
    DESCRIPTION
        "Notification of Event WWAN.4

        Message: 'CHANGED PLMN to $1, on interface $2'

        Parameters list:
              $1: wwan4-operator
              $2: wwan4-ifcname

        The wireless wan interface now uses a different Public Land Mobile Network,
        (Mobile Operator) identified by the number displayed."
    ::= { wwanNotificationsPrefix 4 }

wwanNotification5 NOTIFICATION-TYPE
    OBJECTS { 
              wwan5-location-area-code, 
              wwan5-cell-id,
              wwan5-ifcname 
            }
    STATUS current
    DESCRIPTION
        "Notification of Event WWAN.5

        Message: 'CHANGE Connected cell LAC $1 WWAN ID $2, on interface $3'

        Parameters list:
              $1: wwan5-location-area-code
              $2: wwan5-cell-id
              $3: wwan5-ifcname

        The wireless wan interface is connected to a different base station,
        identified by the Location Area Code (LAC) and the Cell Identifier code
        (CiD)."
    ::= { wwanNotificationsPrefix 5 }

wwanNotification6 NOTIFICATION-TYPE
    OBJECTS { 
              wwan6-technology, 
              wwan6-ifcname 
            }
    STATUS current
    DESCRIPTION
        "Notification of Event WWAN.6

        Message: 'CHANGED wireless wan technology to $1, on interface $2'

        Parameters list:
              $1: wwan6-technology
              $2: wwan6-ifcname

        Notify a change of the used wireless wan technology, which implies different
        radio bands, coding methods and therefore different data rates."
    ::= { wwanNotificationsPrefix 6 }

wwanNotification7 NOTIFICATION-TYPE
    OBJECTS { 
              wwan7-rssi-level, 
              wwan7-ifcname 
            }
    STATUS current
    DESCRIPTION
        "Notification of Event WWAN.7

        Message: 'CHANGED GSM/GPRS Coverage, RSSI $1 dBm, on interface $2'

        Parameters list:
              $1: wwan7-rssi-level
              $2: wwan7-ifcname

        Received Signal Strength Indication (RSSI) changed to the level
        displayed. This event depends of user's configuration thresholds and
        appears only if the used technology is GSM or GPRS."
    ::= { wwanNotificationsPrefix 7 }

wwanNotification8 NOTIFICATION-TYPE
    OBJECTS { 
              wwan8-rscp-level, 
              wwan8-ecno-level,
              wwan8-ifcname 
            }
    STATUS current
    DESCRIPTION
        "Notification of Event WWAN.8

        Message: 'CHANGED 3GPP Coverage, RSCP to $1 dBm and EcNo to $2 dB, on interface $3'

        Parameters list:
              $1: wwan8-rscp-level
              $2: wwan8-ecno-level
              $3: wwan8-ifcname

        Received Signal Code Power (RSCP) has changed to the level displayed or
        the EcNo ratio (received energy per chip divided by the power density in
        the band) has changed to the value displayed. This event depends of
        user's configuration thresholds and appears only if the used technology
        is UMTS, HSDPA or CDMA."
    ::= { wwanNotificationsPrefix 8 }

wwanNotification9 NOTIFICATION-TYPE
    OBJECTS { 
              wwan9-sim-socket, 
              wwan9-ifcname 
            }
    STATUS current
    DESCRIPTION
        "Notification of Event WWAN.9

        Message: 'CHANGED Used SIM. Used SIM is located in the $1 socket, on interface $2'

        Parameters list:
              $1: wwan9-sim-socket
              $2: wwan9-ifcname

        Active SIM is placed in the displayed socked."
    ::= { wwanNotificationsPrefix 9 }

wwanNotification10 NOTIFICATION-TYPE
    OBJECTS { 
              wwan10-call-state-string, 
              wwan10-call-state-num,
              wwan10-ifcname 
            }
    STATUS current
    DESCRIPTION
        "Notification of Event WWAN.10

        Message: 'CHANGED Call state to $1 ($2), on interface $3'

        Parameters list:
              $1: wwan10-call-state-string
              $2: wwan10-call-state-num
              $3: wwan10-ifcname

        Interface call stated changed to the state displayed"
    ::= { wwanNotificationsPrefix 10 }

wwanNotification11 NOTIFICATION-TYPE
    OBJECTS { 
              wwan11-frmwr-release, 
              wwan11-ifcname 
            }
    STATUS current
    DESCRIPTION
        "Notification of Event WWAN.11

        Message: 'CHANGED wireless wan module firmware to release $1, on interface $2'

        Parameters list:
              $1: wwan11-frmwr-release
              $2: wwan11-ifcname

        A successful upgrade has been done to the displayed release"
    ::= { wwanNotificationsPrefix 11 }

wwanNotification12 NOTIFICATION-TYPE
    OBJECTS { 
              wwan12-sim-socket, 
              wwan12-ifcname 
            }
    STATUS current
    DESCRIPTION
        "Notification of Event WWAN.12

        Message: 'Main SIM is $1 and now is active, on interface $2'

        Parameters list:
              $1: wwan12-sim-socket
              $2: wwan12-ifcname

        Current SIM is the configured as main"
    ::= { wwanNotificationsPrefix 12 }

wwanNotification13 NOTIFICATION-TYPE
    OBJECTS { 
              wwan13-sim-socket, 
              wwan13-ifcname 
            }
    STATUS current
    DESCRIPTION
        "Notification of Event WWAN.13

        Message: 'Backup SIM is $1, and now is active, on interface $2'

        Parameters list:
              $1: wwan13-sim-socket
              $2: wwan13-ifcname

        Current SIM is the configured as backup."
    ::= { wwanNotificationsPrefix 13 }

wwanNotification14 NOTIFICATION-TYPE
    OBJECTS { 
              wwan14-criteria, 
              wwan14-sim-socket,
              wwan14-ifcname 
            }
    STATUS current
    DESCRIPTION
        "Notification of Event WWAN.14

        Message: 'Switching criteria $1 is met. Switching to backup SIM ($2), on interface $3'

        Parameters list:
              $1: wwan14-criteria
              $2: wwan14-sim-socket
              $3: wwan14-ifcname

        A switching criteria is met and backup SIM is activated"
    ::= { wwanNotificationsPrefix 14 }

wwanNotification15 NOTIFICATION-TYPE
    OBJECTS { 
              wwan15-criteria, 
              wwan15-sim-socket,
              wwan15-ifcname 
            }
    STATUS current
    DESCRIPTION
        "Notification of Event WWAN.15

        Message: 'Return criteria $1 is met. Switching to main SIM ($2), on interface $3'

        Parameters list:
              $1: wwan15-criteria
              $2: wwan15-sim-socket
              $3: wwan15-ifcname

        A return criteria is met and main SIM is activated"
    ::= { wwanNotificationsPrefix 15 }

wwanNotification16 NOTIFICATION-TYPE
    OBJECTS { 
              wwan16-error, 
              wwan16-ifcname 
            }
    STATUS current
    DESCRIPTION
        "Notification of Event WWAN.16

        Message: 'SIM Management error $1, on interface $2'

        Parameters list:
              $1: wwan16-error
              $2: wwan16-ifcname

        A error is found and reported during SIM management"
    ::= { wwanNotificationsPrefix 16 }


END
