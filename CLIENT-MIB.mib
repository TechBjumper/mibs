-- Note:
-- This text file contains ASN.1 source describing MIB objects for SNMP.
-- The enterprise MIB described is subject to change in a future
-- release, and support for any object described in this MIB may be
-- removed in a future release, as standard MIBs in the management domain
-- described by this MIB become defined and published as Internet RFCs.

CLIENT-MIB DEFINITIONS  ::= BEGIN

IMPORTS

        enterprises, TimeTicks, Counter               FROM RFC1155-SMI
        OBJECT-TYPE                      FROM RFC-1212
        DisplayString                    FROM RFC1213-MIB
        Boolean                          FROM HOST-RESOURCES-V2-MIB
        KBytes                           FROM HOST-RESOURCES-MIB
        DateAndTime                      FROM HOST-RESOURCES-MIB
        InternationalDisplayString       FROM HOST-RESOURCES-MIB
        ProductID                        FROM HOST-RESOURCES-MIB;

        -- Define OIDs
  --    ccitt              OBJECT IDENTIFIER ::= { 0 }
  --    null               OBJECT IDENTIFIER ::= { ccitt 0 }
  --    iso                OBJECT IDENTIFIER ::= { 1 }
  --    org                OBJECT IDENTIFIER ::= { iso 3 }
  --    dod                OBJECT IDENTIFIER ::= { org 6 }
  --    internet           OBJECT IDENTIFIER ::= { dod 1 }
  --    private            OBJECT IDENTIFIER ::= { internet 4 }
  --    enterprises        OBJECT IDENTIFIER ::= { private 1 }
        ibm                OBJECT IDENTIFIER ::= { enterprises 2 }
        ibmProd            OBJECT IDENTIFIER ::= { ibm 6 }
        clientMgmtSubAgent OBJECT IDENTIFIER ::= { ibmProd 50 }
        clntSystem         OBJECT IDENTIFIER ::= { clientMgmtSubAgent 1 }
        clntHardware       OBJECT IDENTIFIER ::= { clientMgmtSubAgent 2 }
        clntSoftware       OBJECT IDENTIFIER ::= { clientMgmtSubAgent 3 }

--
-- The Client System Group
--
clntSystemTable   OBJECT-TYPE
        SYNTAX  SEQUENCE OF ClntSystemEntry
        ACCESS  not-accessible
        STATUS  mandatory
        DESCRIPTION
               "The (conceptual) table of client system information."
        ::= { clntSystem 1 }

clntSystemEntry   OBJECT-TYPE
        SYNTAX  ClntSystemEntry
        ACCESS  not-accessible
        STATUS  mandatory
        DESCRIPTION
               "A (conceptual) entry for one logical entry of
                client system information."
        INDEX { clntSystemIndex }
        ::= { clntSystemTable 1 }

ClntSystemEntry ::= SEQUENCE {
        clntSystemIndex            INTEGER,
        clntSysName                DisplayString,
        clntSysDescr               DisplayString,
        clntCommunity              DisplayString,
        clntIpAddress              DisplayString,
        clntAppnCpNetId            DisplayString,
        clntMemorySize             KBytes,
        clntSystemUpTime           TimeTicks,
        clntSystemStatus           INTEGER,
        clntSupportMibII           INTEGER,
        clntSupportHostMib         INTEGER,
        clntSupportAppnMib         INTEGER,
        clntSupportDmiMib          INTEGER,
        clntLastHwRefresh          DateAndTime,
        clntLastSwRefresh          DateAndTime,
        clntSysContact             DisplayString,
        clntSysLocation            DisplayString,
        clntMachineType            DisplayString,
        clntMachineModel           DisplayString,
        clntUserProfile            DisplayString,
        clntOwner                  DisplayString,
        clntOwnerPhone             DisplayString,
        clntOwnerOffice            DisplayString
 }

clntSystemIndex OBJECT-TYPE
    SYNTAX INTEGER (1..2147483647)
    ACCESS read-only
    STATUS mandatory
    DESCRIPTION
           "A unique value for each client node known to the host."
    ::= { clntSystemEntry 1 }

clntSysName OBJECT-TYPE
    SYNTAX  DisplayString (SIZE (0..255))
    ACCESS  read-only
    STATUS  mandatory
    DESCRIPTION
            "An administratively assigned name for the
            client node.  By convention, this is the client's
            fully qualified domain name."
    ::= { clntSystemEntry 2 }

clntSysDescr OBJECT-TYPE
    SYNTAX  DisplayString (SIZE (0..255))
    ACCESS  read-only
    STATUS  mandatory
    DESCRIPTION
            "A textual description of the client.  This value
            should include the full name and version
            identification of the system's hardware type,
            software operating system, and networking
            software.  It is mandatory that this only contain
            printable ASCII characters."
    ::= { clntSystemEntry 3 }

clntCommunity OBJECT-TYPE
    SYNTAX  DisplayString (SIZE (0..255))
    ACCESS  read-only
    STATUS  mandatory
    DESCRIPTION
            "Name of the community defined by the client."
    ::= { clntSystemEntry 4 }

clntIpAddress OBJECT-TYPE
    SYNTAX  DisplayString (SIZE (7..15))
    ACCESS  read-only
    STATUS  mandatory
    DESCRIPTION
            "An administratively assigned address for the
            client node.  This is the Internet Address for
            the client."
    ::= { clntSystemEntry 5 }

clntAppnCpNetId OBJECT-TYPE
    SYNTAX  DisplayString (SIZE (3..17))
    ACCESS  read-only
    STATUS  mandatory
    DESCRIPTION
            "An administratively assigned address for the
            client node.  This is the control point name and network ID."
    ::= { clntSystemEntry 6 }

clntMemorySize OBJECT-TYPE
    SYNTAX KBytes
    ACCESS read-only
    STATUS mandatory
    DESCRIPTION
           "The amount of physical main memory contained by
           the client."
    ::= { clntSystemEntry 7 }

clntSystemUpTime OBJECT-TYPE
    SYNTAX TimeTicks
    ACCESS read-only
    STATUS mandatory
    DESCRIPTION
           "The amount of time since the client was last initialized."
    ::= { clntSystemEntry 8 }

clntSystemStatus OBJECT-TYPE
    SYNTAX INTEGER {
             active(1),
             inactive(2)
           }
    ACCESS read-only
    STATUS mandatory
    DESCRIPTION
           "A status indication for the client."
    ::= { clntSystemEntry 9 }

clntSupportMibII OBJECT-TYPE
    SYNTAX INTEGER {
             yes(1),
             no(2)
           }
    ACCESS read-only
    STATUS mandatory
    DESCRIPTION
           "An indication that the client supports MIB-2 objects."
    ::= { clntSystemEntry 10 }

clntSupportHostMib OBJECT-TYPE
    SYNTAX INTEGER {
             yes(1),
             no(2)
           }
    ACCESS read-only
    STATUS mandatory
    DESCRIPTION
           "An indication that the client supports Host Resources MIB objects."
    ::= { clntSystemEntry 11 }

 clntSupportAppnMib OBJECT-TYPE
    SYNTAX INTEGER {
             yes(1),
             no(2)
           }
    ACCESS read-only
    STATUS mandatory
    DESCRIPTION
           "An indication that the client supports APPN MIB objects."
    ::= { clntSystemEntry 12 }

 clntSupportDmiMib OBJECT-TYPE
    SYNTAX INTEGER {
             yes(1),
             no(2)
           }
    ACCESS read-only
    STATUS mandatory
    DESCRIPTION
           "An indication that the client supports DMI MIB objects."
    ::= { clntSystemEntry 13 }

clntLastHwRefresh  OBJECT-TYPE
    SYNTAX DateAndTime
    ACCESS read-only
    STATUS mandatory
    DESCRIPTION
           "The last date at which the hardware information
            was refreshed for the client.

           If this information is not known, then this
           variable shall have the value corresponding to
           January 1, year 1970, 00:00:00.0, which is encoded
           as (hex)'07 B2 01 01 00 00 00 00'."
    ::= { clntSystemEntry 14 }

clntLastSwRefresh  OBJECT-TYPE
    SYNTAX DateAndTime
    ACCESS read-only
    STATUS mandatory
    DESCRIPTION
           "The last date at which the software information
            was refreshed for the client.

           If this information is not known, then this
           variable shall have the value corresponding to
           January 1, year 1970, 00:00:00.0, which is encoded
           as (hex)'07 B2 01 01 00 00 00 00'."
    ::= { clntSystemEntry 15 }

 clntSysContact OBJECT-TYPE
    SYNTAX  DisplayString (SIZE (0..255))
    ACCESS  read-only
    STATUS  mandatory
    DESCRIPTION
            "The textual identification of the contact person
            for the client, together with information
            on how to contact the person."
    ::= { clntSystemEntry 16 }

clntSysLocation OBJECT-TYPE
    SYNTAX  DisplayString (SIZE (0..255))
    ACCESS  read-only
    STATUS  mandatory
    DESCRIPTION
            "The physical location of the client (e.g.,
             building, floor, telephone...)."
    ::= { clntSystemEntry 17 }

clntMachineType    OBJECT-TYPE
    SYNTAX  DisplayString (SIZE (0..4))
    ACCESS  read-only
    STATUS  mandatory
    DESCRIPTION
            "The machine type of the client."
    ::= { clntSystemEntry 18 }

clntMachineModel   OBJECT-TYPE
    SYNTAX  DisplayString (SIZE (0..3))
    ACCESS  read-only
    STATUS  mandatory
    DESCRIPTION
            "The machine model of the client."
    ::= { clntSystemEntry 19 }

clntUserProfile   OBJECT-TYPE
    SYNTAX  DisplayString (SIZE (0..10))
    ACCESS  read-only
    STATUS  mandatory
    DESCRIPTION
            "The user profile for the client."
    ::= { clntSystemEntry 20 }

clntOwner          OBJECT-TYPE
    SYNTAX  DisplayString (SIZE (0..32))
    ACCESS  read-only
    STATUS  mandatory
    DESCRIPTION
            "The owner of the client."
    ::= { clntSystemEntry 21 }

clntOwnerPhone     OBJECT-TYPE
    SYNTAX  DisplayString (SIZE (0..32))
    ACCESS  read-only
    STATUS  mandatory
    DESCRIPTION
            "The owner's phone number for the client."
    ::= { clntSystemEntry 22 }

clntOwnerOffice   OBJECT-TYPE
    SYNTAX  DisplayString (SIZE (0..32))
    ACCESS  read-only
    STATUS  mandatory
    DESCRIPTION
            "The owner's office information for the client."
    ::= { clntSystemEntry 23 }

--
-- The Client Hardware Group
--
--
-- Client Storage Table (part of Client Hardware Group)
--
clntStorageTable   OBJECT-TYPE
        SYNTAX  SEQUENCE OF ClntStorageEntry
        ACCESS  not-accessible
        STATUS  mandatory
        DESCRIPTION
               "The (conceptual) table of logical storage areas on
                the client.

                An entry shall be placed in the storage table for
                each logical area of storage that is allocated and
                has fixed resource limits.  The amount of storage
                represented in an entity is the amount actually
                usable by the requesting entity, and excludes loss
                due to formatting or file system reference
                information.

                These entries are associated with logical storage
                areas, as might be seen by an application, rather
                than physical storage entities which are typically
                seen by an operating system.  Storage such as
                tapes and floppies without file systems on them
                are typically not allocated in chunks by the
                operating system to requesting applications, and
                therefore shouldn't appear in this table.
                Examples of valid storage for this table include
                disk partitions, file systems, ram (for some
                architectures this is further segmented into
                regular memory, extended memory, and so on),
                backing store for virtual memory ('swap space').

                This table is intended to be a useful diagnostic
                for 'out of memory' and 'out of buffers' types of
                failures.  In addition, it can be a useful
                performance monitoring tool for tracking memory,
                disk, or buffer usage. "
        ::= { clntHardware 1 }

clntStorageEntry   OBJECT-TYPE
        SYNTAX  ClntStorageEntry
        ACCESS  not-accessible
        STATUS  mandatory
        DESCRIPTION
               "A (conceptual) entry for one logical storage area
                on the client.  The clntSystemIndex represents an
                entry in the clntSystemTable that corresponds
                to the clntStorageEntry.

                As an example, an instance of the clntStorageType
                object might be named hrStorageType.3.1"

        INDEX { clntSystemIndex, clntStorageIndex }
        ::= { clntStorageTable 1 }

ClntStorageEntry ::= SEQUENCE {
        clntStorageIndex                INTEGER,
        clntStorageType                 OBJECT IDENTIFIER,
        clntStorageDescr                DisplayString,
        clntStorageAllocationUnits      INTEGER,
        clntStorageSize                 INTEGER,
        clntStorageUsed                 INTEGER,
        clntStorageAllocationFailures   Counter
 }

clntStorageIndex OBJECT-TYPE
    SYNTAX INTEGER (1..2147483647)
    ACCESS read-only
    STATUS mandatory
    DESCRIPTION
           "A unique value for each logical storage area
           contained by the client."
    ::= { clntStorageEntry 1 }

clntStorageType OBJECT-TYPE
    SYNTAX OBJECT IDENTIFIER
    ACCESS read-only
    STATUS mandatory
    DESCRIPTION
           "The type of storage represented by this entry."
    ::= { clntStorageEntry 2 }

clntStorageDescr OBJECT-TYPE
    SYNTAX DisplayString (SIZE (0..128))
    ACCESS read-only
    STATUS mandatory
    DESCRIPTION
           "A description of the type and instance of the
           storage described by this entry."
    ::= { clntStorageEntry 3 }

clntStorageAllocationUnits OBJECT-TYPE
    SYNTAX      INTEGER (1..2147483647)
    ACCESS      read-only
    STATUS      mandatory
    DESCRIPTION
            "The size, in bytes, of the data objects allocated
            from this pool.  If this entry is monitoring
            sectors, blocks, buffers, or packets, for example,
            this number will commonly be greater than one.
            Otherwise this number will typically be one."
    ::= { clntStorageEntry 4 }

clntStorageSize OBJECT-TYPE
    SYNTAX INTEGER (0..2147483647)
    ACCESS read-only
    STATUS mandatory
    DESCRIPTION
           "The size of the storage represented by this entry,
           in units of clntStorageAllocationUnits."
    ::= { clntStorageEntry 5 }

clntStorageUsed OBJECT-TYPE
    SYNTAX INTEGER (0..2147483647)
    ACCESS read-only
    STATUS mandatory
    DESCRIPTION
           "The amount of the storage represented by this
           entry that is allocated, in units of
           clntStorageAllocationUnits."
    ::= { clntStorageEntry 6 }

clntStorageAllocationFailures OBJECT-TYPE
    SYNTAX Counter
    ACCESS read-only
    STATUS mandatory
    DESCRIPTION
           "The number of requests for storage represented by
           this entry that could not be honored due to not
           enough storage.  It should be noted that as this
           object has a SYNTAX of Counter, that it does not
           have a defined initial value.  However, it is
           recommended that this object be initialized to
           zero."
    ::= { clntStorageEntry 7 }

--
-- Client Device Table (part of Client Hardware Group)
--
-- The device group is useful for identifying and diagnosing the
-- devices on a system.  The clntDeviceTable contains common
-- information for any type of device.  In addition, some devices
-- have device-specific tables for more detailed information.  More
-- such tables may be defined in the future for other device types.
--
clntDeviceTable OBJECT-TYPE
    SYNTAX SEQUENCE OF ClntDeviceEntry
    ACCESS not-accessible
    STATUS mandatory
    DESCRIPTION
           "The (conceptual) table of devices contained by the
           client."
    ::= { clntHardware 2 }

clntDeviceEntry OBJECT-TYPE
    SYNTAX ClntDeviceEntry
    ACCESS not-accessible
    STATUS mandatory
    DESCRIPTION
           "A (conceptual) entry for one device contained by
           the client."
    INDEX { clntSystemIndex, clntDeviceIndex }
    ::= { clntDeviceTable 1 }

ClntDeviceEntry ::= SEQUENCE {
        clntDeviceIndex           INTEGER,
        clntDeviceType            OBJECT IDENTIFIER,
        clntDeviceDescr           DisplayString,
        clntDeviceID              ProductID,
        clntDeviceStatus          INTEGER,
        clntDeviceErrors          Counter
    }

clntDeviceIndex OBJECT-TYPE
    SYNTAX INTEGER (1..2147483647)
    ACCESS read-only
    STATUS mandatory
    DESCRIPTION
           "A unique value for each device contained by the
           client.  The value for each device must remain
           constant at least from one re-initialization of the
           agent to the next re-initialization."
    ::= { clntDeviceEntry 1 }

clntDeviceType OBJECT-TYPE
    SYNTAX OBJECT IDENTIFIER
    ACCESS read-only
    STATUS mandatory
    DESCRIPTION
           "An indication of the type of device.

           If this value is 'hrDeviceProcessor { hrDeviceTypes
           3 }' then an entry exists in the clntProcessorTable
           which corresponds to this device.

           If this value is 'hrDeviceNetwork { hrDeviceTypes 4
           }', then an entry exists in the clntNetworkTable
           which corresponds to this device.

           If this value is 'hrDevicePrinter { hrDeviceTypes 5
           }', then an entry exists in the clntPrinterTable
           which corresponds to this device.

           If this value is 'hrDeviceDiskStorage { hrDeviceTypes
           6 }', then an entry exists in the clntDiskStorageTable
           which corresponds to this device."
    ::= { clntDeviceEntry 2 }

clntDeviceDescr OBJECT-TYPE
    SYNTAX DisplayString (SIZE (0..64))
    ACCESS read-only
    STATUS mandatory
    DESCRIPTION
           "A textual description of this device, including
           the device's manufacturer and revision, and
           optionally, its serial number."
    ::= { clntDeviceEntry 3 }

clntDeviceID OBJECT-TYPE
    SYNTAX ProductID
    ACCESS read-only
    STATUS mandatory
    DESCRIPTION
           "The product ID for this device."
    ::= { clntDeviceEntry 4 }

clntDeviceStatus OBJECT-TYPE
     SYNTAX  INTEGER {
          unknown(1),
          running(2),
          warning(3),
          testing(4),
          down(5)
     }
     ACCESS  read-only
     STATUS  mandatory
     DESCRIPTION
           "The current operational state of the device
           described by this row of the table.  A value
           unknown(1) indicates that the current state of the
           device is unknown.  running(2) indicates that the
           device is up and running and that no unusual error
           conditions are known.  The warning(3) state
           indicates that agent has been informed of an
           unusual error condition by the operational software
           (e.g., a disk device driver) but that the device is
           still 'operational'.  An example would be high
           number of soft errors on a disk.  A value of
           testing(4), indicates that the device is not
           available for use because it is in the testing
           state.  The state of down(5) is used only when the
           agent has been informed that the device is not
           available for any use."
     ::= { clntDeviceEntry 5 }

clntDeviceErrors OBJECT-TYPE
    SYNTAX Counter
    ACCESS read-only
    STATUS mandatory
    DESCRIPTION
            "The number of errors detected on this device.  It
            should be noted that as this object has a SYNTAX
            of Counter, that it does not have a defined
            initial value.  However, it is recommended that
            this object be initialized to zero."
    ::= { clntDeviceEntry 6 }

--
-- Client Processor Table (part of Client Hardware Group)
--
clntProcessorTable OBJECT-TYPE
    SYNTAX SEQUENCE OF ClntProcessorEntry
    ACCESS not-accessible
    STATUS mandatory
    DESCRIPTION
           "The (conceptual) table of processors contained by
           the client.

           Note that this table is potentially sparse: a
           (conceptual) entry exists only if the correspondent
           value of the clntDeviceType object is
           'hrDeviceProcessor'."
    ::= { clntHardware 3 }

clntProcessorEntry OBJECT-TYPE
    SYNTAX ClntProcessorEntry
    ACCESS not-accessible
    STATUS mandatory
    DESCRIPTION
           "A (conceptual) entry for one processor contained
           by the client.  The clntSystemIndex, which represents an
           entry in the clntSystemTable, and the clntDeviceIndex,
           which represents an entry in the clntDeviceTable,
           combined corresponds to the clntProcessorEntry.

           As an example of how objects in this table are
           named, an instance of the clntProcessorFrwID object
           might be named clntProcessorFrwID.3.1"
    INDEX { clntSystemIndex, clntDeviceIndex  }
    ::= { clntProcessorTable 1 }

ClntProcessorEntry ::= SEQUENCE {
        clntProcessorFrwID            ProductID,
        clntProcessorLoad             INTEGER
    }

clntProcessorFrwID OBJECT-TYPE
    SYNTAX ProductID
    ACCESS read-only
    STATUS mandatory
    DESCRIPTION
           "The product ID of the firmware associated with the
           processor."
    ::= { clntProcessorEntry 1 }

clntProcessorLoad OBJECT-TYPE
    SYNTAX INTEGER (0..100)
    ACCESS read-only
    STATUS mandatory
    DESCRIPTION
           "The average, over the last minute, of the
           percentage of time that this processor was not
           idle."
    ::= { clntProcessorEntry 2 }

--
-- Client Network Table (part of Client Hardware Group)
--
clntNetworkTable OBJECT-TYPE
    SYNTAX SEQUENCE OF ClntNetworkEntry
    ACCESS not-accessible
    STATUS mandatory
    DESCRIPTION
           "The (conceptual) table of network devices
           contained by the client.

           Note that this table is potentially sparse: a
           (conceptual) entry exists only if the correspondent
           value of the clntDeviceType object is
           'hrDeviceNetwork'."
    ::= { clntHardware 4 }

clntNetworkEntry OBJECT-TYPE
    SYNTAX ClntNetworkEntry
    ACCESS not-accessible
    STATUS mandatory
    DESCRIPTION
           "A (conceptual) entry for one network device contained
           by the client.  The clntSystemIndex, which represents an
           entry in the clntSystemTable, and the clntDeviceIndex,
           which represents an entry in the clntDeviceTable,
           combined corresponds to the clntNetworkEntry.

           As an example of how objects in this table are
           named, an instance of the clntNetworkIfIndex object
           might be named clntNetworkIfIndex.3.1"
    INDEX { clntSystemIndex, clntDeviceIndex  }
    ::= { clntNetworkTable 1 }

ClntNetworkEntry ::= SEQUENCE {
        clntNetworkIfIndex      INTEGER
    }

clntNetworkIfIndex OBJECT-TYPE
    SYNTAX INTEGER
    ACCESS read-only
    STATUS mandatory
    DESCRIPTION
           "The value of ifIndex which corresponds to this
           network device."
    ::= { clntNetworkEntry 1 }

--
-- Client Printer Table (part of Client Hardware Group)
--
clntPrinterTable OBJECT-TYPE
    SYNTAX SEQUENCE OF ClntPrinterEntry
    ACCESS not-accessible
    STATUS mandatory
    DESCRIPTION
           "The (conceptual) table of printers local to the
           client.

           Note that this table is potentially sparse: a
           (conceptual) entry exists only if the correspondent
           value of the clntDeviceType object is 'hrDevicePrinter'."
    ::= { clntHardware 5 }

clntPrinterEntry OBJECT-TYPE
    SYNTAX ClntPrinterEntry
    ACCESS not-accessible
    STATUS mandatory
    DESCRIPTION
           "A (conceptual) entry for one printer local to the
           client. The clntSystemIndex, which represents an
           entry in the clntSystemTable, and the clntDeviceIndex,
           which represents an entry in the clntDeviceTable,
           combined corresponds to the clntPrinterEntry.

           As an example of how objects in this table are
           named, an instance of the clntPrinterStatus object
           might be named clntPrinterStatus.3.1"
    INDEX { clntSystemIndex, clntDeviceIndex  }
    ::= { clntPrinterTable 1 }

ClntPrinterEntry ::= SEQUENCE {
        clntPrinterStatus             INTEGER,
        clntPrinterDetectedErrorState OCTET STRING
    }

clntPrinterStatus OBJECT-TYPE
    SYNTAX INTEGER {
        other(1),
        unknown(2),
        idle(3),
        printing(4),
        warmup(5)
    }
    ACCESS read-only
    STATUS mandatory
    DESCRIPTION
            "The current status of this printer device.  When
            in the idle(3), printing(4), or warmup(5) state,
            the corresponding clntDeviceStatus should be
            running(2) or warning(3).  When in the unknown
            state, the corresponding clntDeviceStatus should be
            unknown(1)."
     ::= { clntPrinterEntry 1 }

clntPrinterDetectedErrorState OBJECT-TYPE
    SYNTAX OCTET STRING
    ACCESS read-only
    STATUS mandatory
    DESCRIPTION
            "This object represents any error conditions
            detected by the printer.  The error conditions are
            encoded as bits in an octet string, with the
            following definitions:

                 Condition         Bit #    clntDeviceStatus

                 lowPaper          0        warning(3)
                 noPaper           1        down(5)
                 lowToner          2        warning(3)
                 noToner           3        down(5)
                 doorOpen          4        down(5)
                 jammed            5        down(5)
                 offline           6        down(5)
                 serviceRequested  7        warning(3)

            If multiple conditions are currently detected and
            the clntDeviceStatus would not otherwise be
            unknown(1) or testing(4), the clntDeviceStatus shall
            correspond to the worst state of those indicated,
            where down(5) is worse than warning(3) which is
            worse than running(2).

            Bits are numbered starting with the most
            significant bit of the first byte being bit 0, the
            least significant bit of the first byte being bit
            7, the most significant bit of the second byte
            being bit 8, and so on.  A one bit encodes that
            the condition was detected, while a zero bit
            encodes that the condition was not detected.

            This object is useful for alerting an operator to
            specific warning or error conditions that may
            occur, especially those requiring human
            intervention."
    ::= { clntPrinterEntry 2 }

--
-- Client Disk Storage Table (part of Client Hardware Group)
--
clntDiskStorageTable OBJECT-TYPE
    SYNTAX SEQUENCE OF ClntDiskStorageEntry
    ACCESS not-accessible
    STATUS mandatory
    DESCRIPTION
           "The (conceptual) table of long-term storage
           devices contained by the client.  In particular, disk
           devices accessed remotely over a network are not
           included here.

           Note that this table is potentially sparse: a
           (conceptual) entry exists only if the correspondent
           value of the clntDeviceType object is 'hrDeviceDiskStorage'."
    ::= { clntHardware 6 }

clntDiskStorageEntry OBJECT-TYPE
    SYNTAX ClntDiskStorageEntry
    ACCESS not-accessible
    STATUS mandatory
    DESCRIPTION
           "A (conceptual) entry for one long-term storage
           device contained by the client.  The clntSystemIndex, which
           represents an entry in the clntSystemTable, and the
           clntDeviceIndex, which represents an entry in the
           clntDeviceTable, combined corresponds to the
           clntDiskStorageEntry.

           As an example of how objects in this table are
           named, an instance of the clntDiskStorageCapacity
           object might be named clntDiskStorageCapacity.3.1"
    INDEX { clntSystemIndex, clntDeviceIndex  }
    ::= { clntDiskStorageTable 1 }

ClntDiskStorageEntry ::= SEQUENCE {
        clntDiskStorageAccess         INTEGER,
        clntDiskStorageMedia          INTEGER,
        clntDiskStorageRemoveble      Boolean,
        clntDiskStorageCapacity       KBytes
    }

clntDiskStorageAccess OBJECT-TYPE
    SYNTAX INTEGER {
                    readWrite(1),
                    readOnly(2)
            }
    ACCESS read-only
    STATUS mandatory
    DESCRIPTION
           "An indication if this long-term storage device is
           readable and writable or only readable.  This
           should reflect the media type, any write protect
           mechanism, and any device configuration that
           affects the entire device."
    ::= { clntDiskStorageEntry 1 }

clntDiskStorageMedia OBJECT-TYPE
    SYNTAX INTEGER {
                other(1),
                unknown(2),
                hardDisk(3),
                floppyDisk(4),
                opticalDiskROM(5),
                opticalDiskWORM(6),     -- Write Once Read Many
                opticalDiskRW(7),
                ramDisk(8)
            }
    ACCESS read-only
    STATUS mandatory
    DESCRIPTION
           "An indication of the type of media used in this
           long-term storage device."
    ::= { clntDiskStorageEntry 2 }

clntDiskStorageRemoveble OBJECT-TYPE
    SYNTAX Boolean
    ACCESS read-only
    STATUS mandatory
    DESCRIPTION
            "Denotes whether or not the disk media may be
            removed from the drive."
    ::= { clntDiskStorageEntry 3 }

clntDiskStorageCapacity OBJECT-TYPE
    SYNTAX KBytes
    ACCESS read-only
    STATUS mandatory
    DESCRIPTION
           "The total size for this long-term storage device."
    ::= { clntDiskStorageEntry 4 }

--
-- Client Partition Table (part of Client Hardware Group)
--
clntPartitionTable OBJECT-TYPE
    SYNTAX SEQUENCE OF ClntPartitionEntry
    ACCESS not-accessible
    STATUS mandatory
    DESCRIPTION
           "The (conceptual) table of partitions for long-term
           storage devices contained by the client.  In
           particular, partitions accessed remotely over a
           network are not included here."
    ::= { clntHardware 7 }

clntPartitionEntry OBJECT-TYPE
    SYNTAX ClntPartitionEntry
    ACCESS not-accessible
    STATUS mandatory
    DESCRIPTION
           "A (conceptual) entry for one partition.  The
           clntSystemIndex, which represents an entry in the
           clntSystemTable, and the clntDeviceIndex, which  represents
           an entry in the clntDeviceTable, combined corresponds
           to the clntPartitionEntry.

           As an example of how objects in this table are
           named, an instance of the clntPartitionSize object
           might be named clntPartitionSize.3.1.1"
    INDEX { clntSystemIndex, clntDeviceIndex, clntPartitionIndex  }
    ::= { clntPartitionTable 1 }

ClntPartitionEntry ::= SEQUENCE {
        clntPartitionIndex           INTEGER,
        clntPartitionLabel           InternationalDisplayString,
        clntPartitionID              OCTET STRING,
        clntPartitionSize            KBytes,
        clntPartitionFSIndex         INTEGER
    }

clntPartitionIndex OBJECT-TYPE
    SYNTAX INTEGER (1..2147483647)
    ACCESS read-only
    STATUS mandatory
    DESCRIPTION
           "A unique value for each partition on this long-
           term storage device.  The value for each long-term
           storage device must remain constant at least from
           one re-initialization of the agent to the next
           re-initialization."
    ::= { clntPartitionEntry 1 }

clntPartitionLabel OBJECT-TYPE
    SYNTAX InternationalDisplayString (SIZE (0..128))
    ACCESS read-only
    STATUS mandatory
    DESCRIPTION
           "A textual description of this partition."
    ::= { clntPartitionEntry 2 }

clntPartitionID OBJECT-TYPE
    SYNTAX OCTET STRING
    ACCESS read-only
    STATUS mandatory
    DESCRIPTION
           "A descriptor which uniquely represents this
           partition to the responsible operating system.  On
           some systems, this might take on a binary
           representation."
    ::= { clntPartitionEntry 3 }

clntPartitionSize OBJECT-TYPE
    SYNTAX KBytes
    ACCESS read-only
    STATUS mandatory
    DESCRIPTION
            "The size of this partition."
    ::= { clntPartitionEntry 4 }

clntPartitionFSIndex OBJECT-TYPE
    SYNTAX INTEGER (0..2147483647)
    ACCESS read-only
    STATUS mandatory
    DESCRIPTION
            "The index of the file system mounted on this
            partition.  If no file system is mounted on this
            partition, then this value shall be zero.  Note
            that multiple partitions may point to one file
            system, denoting that that file system resides on
            those partitions.  Multiple file systems may not
            reside on one partition."
    ::= { clntPartitionEntry 5 }

--
-- Client File System Table (part of Client Hardware Group)
--
clntFSTable OBJECT-TYPE
    SYNTAX SEQUENCE OF ClntFSEntry
    ACCESS not-accessible
    STATUS mandatory
    DESCRIPTION
            "The (conceptual) table of file systems local to
            this client or remotely mounted from a file server.
            File systems that are in only one user's
            environment on a multi-user system will not be
            included in this table."
    ::= { clntHardware 8 }

clntFSEntry OBJECT-TYPE
    SYNTAX ClntFSEntry
    ACCESS not-accessible
    STATUS mandatory
    DESCRIPTION
            "A (conceptual) entry for one file system local to
            this client or remotely mounted from a file server.
            File systems that are in only one user's
            environment on a multi-user system will not be
            included in this table.

            As an example of how objects in this table are
            named, an instance of the clntFSMountPoint object
            might be named clntFSMountPoint.3.1"
    INDEX { clntSystemIndex, clntFSIndex }
    ::= { clntFSTable 1 }

ClntFSEntry ::= SEQUENCE {
        clntFSIndex                   INTEGER,
        clntFSMountPoint              InternationalDisplayString,
        clntFSRemoteMountPoint        InternationalDisplayString,
        clntFSType                    OBJECT IDENTIFIER,
        clntFSAccess                  INTEGER,
        clntFSBootable                Boolean,
        clntFSStorageIndex            INTEGER,
        clntFSLastFullBackupDate      DateAndTime,
        clntFSLastPartialBackupDate   DateAndTime
    }

clntFSIndex OBJECT-TYPE
    SYNTAX INTEGER (1..2147483647)
    ACCESS read-only
    STATUS mandatory
    DESCRIPTION
            "A unique value for each file system local to this
            client.  The value for each file system must remain
            constant at least from one re-initialization of
            the agent to the next re-initialization."
    ::= { clntFSEntry 1 }

clntFSMountPoint OBJECT-TYPE
    SYNTAX InternationalDisplayString (SIZE(0..128))
    ACCESS read-only
    STATUS mandatory
    DESCRIPTION
            "The path name of the root of this file system."
    ::= { clntFSEntry 2 }

clntFSRemoteMountPoint OBJECT-TYPE
    SYNTAX InternationalDisplayString (SIZE(0..128))
    ACCESS read-only
    STATUS mandatory
    DESCRIPTION
            "A description of the name and/or address of the
            server that this file system is mounted from.
            This may also include parameters such as the mount
            point on the remote file system.  If this is not a
            remote file system, this string should have a
            length of zero."
    ::= { clntFSEntry 3 }

clntFSType OBJECT-TYPE
    SYNTAX OBJECT IDENTIFIER
    ACCESS read-only
    STATUS mandatory
    DESCRIPTION
           "The value of this object identifies the type of
           this file system."
    ::= { clntFSEntry 4 }

clntFSAccess OBJECT-TYPE
    SYNTAX INTEGER {
            readWrite(1),
            readOnly(2)
        }
    ACCESS read-only
    STATUS mandatory
    DESCRIPTION
           "An indication if this file system is logically
           configured by the operating system to be readable
           and writable or only readable.  This does not
           represent any local access-control policy, except
           one that is applied to the file system as a whole."
    ::= { clntFSEntry 5 }

clntFSBootable OBJECT-TYPE
    SYNTAX Boolean
    ACCESS read-only
    STATUS mandatory
    DESCRIPTION
           "A flag indicating whether this file system is
           bootable."
    ::= { clntFSEntry 6 }

clntFSStorageIndex OBJECT-TYPE
    SYNTAX INTEGER (0..2147483647)
    ACCESS read-only
    STATUS mandatory
    DESCRIPTION
            "The index of the clntStorageEntry that represents
            information about this file system.  If there is
            no such information available, then this value
            shall be zero.  The relevant storage entry will be
            useful in tracking the percent usage of this file
            system and diagnosing errors that may occur when
            it runs out of space."
    ::= { clntFSEntry 7 }

clntFSLastFullBackupDate OBJECT-TYPE
    SYNTAX DateAndTime
    ACCESS read-write
    STATUS mandatory
    DESCRIPTION
           "The last date at which this complete file system
           was copied to another storage device for backup.
           This information is useful for ensuring that
           backups are being performed regularly.

           If this information is not known, then this
           variable shall have the value corresponding to
           January 1, year 1970, 00:00:00.0, which is encoded
           as (hex)'07 B2 01 01 00 00 00 00'."
    ::= { clntFSEntry 8 }

clntFSLastPartialBackupDate OBJECT-TYPE
    SYNTAX DateAndTime
    ACCESS read-write
    STATUS mandatory
    DESCRIPTION
           "The last date at which a portion of this file
           system was copied to another storage device for
           backup.  This information is useful for ensuring
           that backups are being performed regularly.

           If this information is not known, then this
           variable shall have the value corresponding to
           January 1, year 1970, 00:00:00.0, which is encoded
           as (hex)'07 B2 01 01 00 00 00 00'."
    ::= { clntFSEntry 9 }

--
-- The Client Software Group
--
-- Client Software Installed Table (part of Client Software Group)
--
-- The clntSWInstalledTable contains an entry for each piece
-- of software installed in long-term storage (e.g. a disk
-- drive) locally on the client.  Note that this does not
-- include software loadable remotely from a network server.
--
-- This table is useful for identifying and investigating
-- software on a client and for diagnosing incompatibility
-- and version mismatch problems between various pieces
-- of hardware and software.
--
clntSWInstalledTable OBJECT-TYPE
    SYNTAX SEQUENCE OF ClntSWInstalledEntry
    ACCESS not-accessible
    STATUS mandatory
    DESCRIPTION
           "The (conceptual) table of software installed on the
           client."
    ::= { clntSoftware 1 }

clntSWInstalledEntry OBJECT-TYPE
    SYNTAX ClntSWInstalledEntry
    ACCESS not-accessible
    STATUS mandatory
    DESCRIPTION
           "A (conceptual) entry for a piece of software installed
           on the client. The clntSystemIndex represents an entry
           in the clntSystemTable that corresponds to the
           clntSWInstalledEntry."
    INDEX { clntSystemIndex, clntSWInstalledIndex }
    ::= { clntSWInstalledTable 1 }

ClntSWInstalledEntry ::= SEQUENCE {
        clntSWInstalledIndex       INTEGER,
        clntSWInstalledManf        DisplayString(SIZE(0..64)),
        clntSWInstalledID          ProductID,
        clntSWInstalledVersion     DisplayString(SIZE(0..64)),
        clntSWInstalledDateTime    DateAndTime,
        clntSWInstalledType        INTEGER,
        clntSWInstalledPath        DisplayString(SIZE(0..255)),
        clntSWInstalledOption      DisplayString(SIZE(0..16)),
        clntSWInstalledLoad        DisplayString(SIZE(0..16)),
        clntSWInstalledStatus      INTEGER,
        clntSWInstalledSoftwareName     DisplayString(SIZE(0..64)),
        clntSWInstalledSerialNumber     DisplayString(SIZE(0..64))
    }

clntSWInstalledIndex OBJECT-TYPE
    SYNTAX INTEGER (1..2147483647)
    ACCESS read-only
    STATUS mandatory
    DESCRIPTION
            "A unique value for each piece of software installed
            on the client."
    ::= {  clntSWInstalledEntry 1 }

clntSWInstalledManf  OBJECT-TYPE
    SYNTAX DisplayString(SIZE(0..64))
    ACCESS read-only
    STATUS mandatory
    DESCRIPTION
           "A textual description of the manufacturer for this
           installed piece of software.

           If this information is not known, this string should
           have a length of zero."
    ::= { clntSWInstalledEntry 2 }

clntSWInstalledID OBJECT-TYPE
    SYNTAX ProductID
    ACCESS read-only
    STATUS mandatory
    DESCRIPTION
           "The product ID of this installed piece of software."
    ::= { clntSWInstalledEntry 3 }

clntSWInstalledVersion OBJECT-TYPE
    SYNTAX DisplayString(SIZE(0..64))
    ACCESS read-only
    STATUS mandatory
    DESCRIPTION
           "The version of this installed piece of software.

           If this information is not known, this string should
           have a length of zero."
    ::= { clntSWInstalledEntry 4 }

clntSWInstalledDateTime OBJECT-TYPE
    SYNTAX DateAndTime
    ACCESS read-only
    STATUS mandatory
    DESCRIPTION
           "The last modification date of this application as
           it would appear in a directory listing.

           If this information is not known, then this
           variable shall have the value corresponding to
           January 1, year 1970, 00:00:00.0, which is encoded
           as (hex)'07 B2 01 01 00 00 00 00'."
    ::= { clntSWInstalledEntry 5 }

clntSWInstalledType  OBJECT-TYPE
    SYNTAX INTEGER {
              unknown(1),
              operatingSystem(2),
              deviceDriver(3),
              application(4)
        }
    ACCESS read-only
    STATUS mandatory
    DESCRIPTION
           "The type of this software."
    ::= { clntSWInstalledEntry 6 }

clntSWInstalledPath  OBJECT-TYPE
    SYNTAX DisplayString(SIZE(0..255))
    ACCESS read-only
    STATUS mandatory
    DESCRIPTION
           "The path where this piece of software is installed.
            This should be the fully qualified path on the client."
    ::= { clntSWInstalledEntry 7 }

clntSWInstalledOption OBJECT-TYPE
    SYNTAX DisplayString(SIZE(0..16))
    ACCESS read-only
    STATUS mandatory
    DESCRIPTION
           "The option of the software installed."
    ::= { clntSWInstalledEntry 8 }

clntSWInstalledLoad OBJECT-TYPE
    SYNTAX DisplayString (SIZE(0..16))
    ACCESS read-only
    STATUS mandatory
    DESCRIPTION
           "The load of the software installed."
    ::= { clntSWInstalledEntry 9 }

clntSWInstalledStatus   OBJECT-TYPE
    SYNTAX INTEGER {
          unknown(1),
          installed(2),
          damaged(3)
    }
    ACCESS read-only
    STATUS mandatory
    DESCRIPTION
           "The current state of the software installed."
    ::= { clntSWInstalledEntry 10 }

clntSWInstalledSoftwareName   OBJECT-TYPE
 SYNTAX DisplayString(SIZE(0..64))
    ACCESS read-only
    STATUS mandatory
    DESCRIPTION
           "The Software Name of this installed piece of software.

           If this information is not known, this string should
           have a length of zero."
    ::= { clntSWInstalledEntry 11 }

clntSWInstalledSerialNumber   OBJECT-TYPE
 SYNTAX DisplayString(SIZE(0..64))
    ACCESS read-only
    STATUS mandatory
    DESCRIPTION
           "The Serial Number of this installed piece of software.

           If this information is not known, this string should
           have a length of zero."
    ::= { clntSWInstalledEntry 12 }

--
-- Client Software Fix Table (part of Client Software Group)
--
clntSWFixTable OBJECT-TYPE
    SYNTAX SEQUENCE OF ClntSWFixEntry
    ACCESS not-accessible
    STATUS mandatory
    DESCRIPTION
           "The (conceptual) table of software fixes on the
           client."
    ::= { clntSoftware 3 }

clntSWFixEntry OBJECT-TYPE
    SYNTAX ClntSWFixEntry
    ACCESS not-accessible
    STATUS mandatory
    DESCRIPTION
           "A (conceptual) entry for each software fix on the client.
           The clntSystemIndex, which represents an entry in the
           clntSystemTable, and the clntSWInstalledIndex, which
           represents an entry in the clntSWInstalledTable, combined
           corresponds to the clntSWFixEntry."
    INDEX { clntSystemIndex, clntSWInstalledIndex, clntSWFixIndex }
    ::= { clntSWFixTable 1 }

ClntSWFixEntry ::= SEQUENCE {
        clntSWFixIndex        INTEGER,
        clntSWFixID           DisplayString(SIZE(0..16))
    }

clntSWFixIndex OBJECT-TYPE
    SYNTAX INTEGER (1..2147483647)
    ACCESS read-only
    STATUS mandatory
    DESCRIPTION
       "A unique value for each software fix installed on
       this client."
    ::= {  clntSWFixEntry 1 }

clntSWFixID    OBJECT-TYPE
    SYNTAX DisplayString (SIZE(0..16))
    ACCESS read-only
    STATUS mandatory
    DESCRIPTION
           "A value which identifies a fix to a piece of
           installed software."
    ::= { clntSWFixEntry 2 }

END
