-- Title:      ATMEL  Private MIB                                          


--Firmaware Version 1.4 14/5/2001


ATMEL-MIB DEFINITIONS ::= BEGIN

IMPORTS
	OBJECT-TYPE, IpAddress
		FROM SNMPv2-SMI
	TRAP-TYPE
		FROM RFC-1215
;
--IMPORTS
--	enterprises,Counter
--FROM RFC1155-SMI
--	DisplayString
--FROM RFC1213-MIB;
--	TRAP-TYPE
--FROM RFC-1215;


--MacAddress ::= IMPLICIT OCTET STRING (SIZE(6))
DisplayString ::= OCTET STRING

internet      OBJECT IDENTIFIER ::= { iso org(3) dod(6) 1 }
directory     OBJECT IDENTIFIER ::= { internet 1 }
mgmt          OBJECT IDENTIFIER ::= { internet 2 }
experimental  OBJECT IDENTIFIER ::= { internet 3 }
private       OBJECT IDENTIFIER ::= { internet 4 }
enterprises   OBJECT IDENTIFIER ::= { private 1 }

--atmel       OBJECT IDENTIFIER ::= { enterprises 410 } 
atmel       OBJECT IDENTIFIER ::= { enterprises 12350 }
atmelmib    OBJECT IDENTIFIER ::= { atmel 1}
atmelSys	OBJECT IDENTIFIER ::= {atmelmib 1}
wireless	OBJECT IDENTIFIER ::= {atmelmib 2}
traps 	OBJECT IDENTIFIER ::= {atmelmib 3 }



--*************************** System***************************
--****************************************************************



sysCtrlGRP OBJECT IDENTIFIER ::= {atmelSys 1}

sysDescr OBJECT-TYPE
    SYNTAX  DisplayString (SIZE (0..255))
    ACCESS  read-only
    STATUS  mandatory
       DESCRIPTION
         "A textual description of the entity.  This value
          should include the full name and version
          identification of the system's hardware type,
          software operating-system, and networking
          software.  It is mandatory that this only contain
          printable ASCII characters."
	::= { sysCtrlGRP 1 } 


sysReset OBJECT-TYPE
	SYNTAX INTEGER {enable(1)}
	ACCESS  read-write
	STATUS  mandatory
	DESCRIPTION       
	"By setting this attribute enable(1), a reset command to 
	the system is issued." 
	::= { sysCtrlGRP 2 } 

sysTrapSwitch OBJECT-TYPE
	SYNTAX INTEGER {enable(1),disable(2)}
	ACCESS read-write
	STATUS mandatory
	DESCRIPTION
	"This attribute enables the transmission of SNMP.V1 TRAPs."
	::= {sysCtrlGRP 3}

sysLoadDefaults OBJECT-TYPE
	SYNTAX INTEGER { enable(1)}
	ACCESS  read-write
	STATUS  mandatory
	DESCRIPTION       
	"Setting this attribute to enable(1), will cause the system to load
	the factory default values of all the operational parameters." 
	::= { sysCtrlGRP 4 }

sysDeviceInfo 	OBJECT-TYPE
			SYNTAX OCTET STRING (SIZE (92))
			ACCESS read-write
			STATUS mandatory
			DESCRIPTION	 
			"First 92 bytes of Hardware device configuration struct.
				 HARD_CONFIGURATION_STUCT{
					unsigned long StructVersion;
	
					unsigned char MacAddress[6];
					unsigned char Channel;
					unsigned char RegulatoryDomain;
	
					unsigned long ProductType;
					unsigned char OEMname[32];
					unsigned long OEMID;
					unsigned char ProductName[32];
					unsigned long HardwareRevision;

					unsigned char PID_VID[4];	//Product ID/ Vendor ID
	
					unsigned int  sysOIDSize;
					unsigned short sysOID[16];
	
					unsigned char  CountryCode[3];
					unsigned char  Reserved1;
					unsigned short ChannelInformation;
					unsigned char  Reserved2[2];
					char  	   TxPower[14];	

					unsigned char Reserved3[10];
				} "

			::= {sysCtrlGRP 5 }

sysUpload OBJECT-TYPE
	SYNTAX INTEGER {enable(1)}
	ACCESS  read-write
	STATUS  mandatory
	DESCRIPTION       
	"By setting this attribute enable(1), a Upload configuration command to 
	the system is issued." 
	::= { sysCtrlGRP 6 } 
                   
siteSurveyCommand OBJECT-TYPE
	SYNTAX INTEGER {enable(1)}
	ACCESS  read-write
	STATUS  mandatory
	DESCRIPTION       
	"By setting this attribute enable(1), a Site Survey command to 
	the system is issued." 
	::= { sysCtrlGRP 7 } 

sysDeviceMoreInfo	OBJECT-TYPE
			SYNTAX OCTET STRING (SIZE (32))
			ACCESS read-write
			STATUS mandatory
			DESCRIPTION	 
			"Last 32 bytes of Hardware device configuration struct.
				 HARD_CONFIGURATION_STUCT{
					unsigned long StructVersion;
	
					unsigned char MacAddress[6];
					unsigned char Channel;
					unsigned char RegulatoryDomain;
	
					unsigned long ProductType;
					unsigned char OEMname[32];
					unsigned long OEMID;
					unsigned char ProductName[32];
					unsigned long HardwareRevision;

					unsigned char PID_VID[4];	//Product ID/ Vendor ID
	
					unsigned int  sysOIDSize;
					unsigned short sysOID[16];
	
					unsigned char  CountryCode[3];
					unsigned char  Reserved1;
					unsigned short ChannelInformation;
					unsigned char  Reserved2[2];
					char  	   TxPower[14];	

					unsigned char Reserved3[10];
				} "

			::= {sysCtrlGRP 8 }


                      

-- BridgingLevel

operBridgingLevel OBJECT IDENTIFIER ::= {atmelSys 2}

operIPAddress OBJECT-TYPE
		SYNTAX IpAddress
		ACCESS read-write
		STATUS mandatory
		DESCRIPTION	 
		"The IP address of this device used over its Ethernet
		or Wireless LAN port."
		::= { operBridgingLevel 1 }

operIPMask OBJECT-TYPE
	    SYNTAX  IpAddress
	    ACCESS  read-write
	    STATUS  mandatory
	    DESCRIPTION
	    "The IP Network mask used by the IP entity when accessing
	    devices through any of its LAN Ports (Ethernet or WLAN)."
	    ::= { operBridgingLevel 2}

operEthernetAddress OBJECT-TYPE
	    SYNTAX  OCTET STRING (SIZE (6))
	    ACCESS  read-only
	    STATUS  mandatory
	    DESCRIPTION
	    "The MAC Address of the Ethernet interface."
	    ::= { operBridgingLevel 3}


operGateway OBJECT-TYPE
		SYNTAX IpAddress
		ACCESS read-write
		STATUS mandatory
		DESCRIPTION	 
		"Gateway default IP address."
		::= { operBridgingLevel 4 }

operDHCP OBJECT-TYPE
		SYNTAX	INTEGER {enable(1),disable(2)}
		ACCESS read-write
		STATUS mandatory
		DESCRIPTION	 
		"When setting this attribute to enable(1), the system will
		enable DHCP protocol."
		::= { operBridgingLevel 5 }

operPrimaryPort OBJECT-TYPE
		SYNTAX	INTEGER {ethernet(1),wireless(2)}
		ACCESS read-write
		STATUS mandatory
		DESCRIPTION	 
		"This attribute indicates the primaty port.Ethernet or Wireless."
		::= { operBridgingLevel 6 }

operConfigurationPort OBJECT-TYPE
		SYNTAX	INTEGER {ethernet(1),wireless(2),both(3)}
		ACCESS read-write
		STATUS mandatory
		DESCRIPTION	 
		"This attribute indicates the Configuration port.Ethernet or Wireless or Both of them."
		::= { operBridgingLevel 7 }

operTrapPort OBJECT-TYPE
		SYNTAX	INTEGER 
		ACCESS read-write
		STATUS mandatory
		DESCRIPTION	 
		"This attribute indicates the Trap port."
		::= { operBridgingLevel 8 }



-- Filtering



operFiltering OBJECT IDENTIFIER ::= {atmelSys 3}

operIPFilter OBJECT-TYPE
		SYNTAX	INTEGER {enable(1), disable(2)}
		ACCESS read-write
		STATUS mandatory
		DESCRIPTION	 
		"When setting this attribute to enable(1), the system will
		filter out all non IP-traffic."
		::= { operFiltering 1 }
      
operForwarbBcast OBJECT-TYPE
		SYNTAX	INTEGER {enable(1), disable(2)}
		ACCESS read-write
		STATUS mandatory
		DESCRIPTION	 
		"When setting this attribute to disable(2), the system will not
		forward broadcast traffic to the Wireless Port."
		::= { operFiltering 2 }
                                                     
operSendBackBcast OBJECT-TYPE
		SYNTAX	INTEGER {enable(1), disable(2)}
		ACCESS read-write
		STATUS mandatory
		DESCRIPTION	 
		"When setting this attribute to disable(2), the system will not
		send back broadcast traffic to the Wireless Port."
		::= { operFiltering 3 }
                 
operSendBackUnicast OBJECT-TYPE
		SYNTAX	INTEGER {enable(1), disable(2)}
		ACCESS read-write
		STATUS mandatory
		DESCRIPTION	 
		"When setting this attribute to disable(2), the system will not
		send back unicast traffic to the Wireless Port."
		::= { operFiltering 4 }


-- Bridge Operational Mode


operBridgeOperationalMode OBJECT IDENTIFIER ::= {atmelSys 4}


bridgeOperationalMode OBJECT-TYPE
		SYNTAX	INTEGER {wbpoint2multipoint(1), ap(2), apclient(3),  wbpoint2point(4), wrepeater(5)}
		ACCESS read-write
		STATUS mandatory
		DESCRIPTION	 
		"The Operational Mode of Bridge. Access Point, Access Point client, Wireless Bridge Point to Point, Wireless Bridge Point to MultiPoint."
		::= { operBridgeOperationalMode 1 }

bridgeRemoteBridgeBSSID OBJECT-TYPE
		SYNTAX	OCTET STRING (SIZE (6))
		ACCESS read-write
		STATUS mandatory
		DESCRIPTION	 
		"The Preferred BSSID if the device is at Access Point client mode
		or the remote Mac if the device is at Wireless Bridge Point to Point mode."
		::= { operBridgeOperationalMode 2 }



-- Static


dot1dStatic OBJECT IDENTIFIER ::= {atmelSys 5}


staticMacFilterNum OBJECT-TYPE
      SYNTAX  INTEGER 
      ACCESS  read-write
      STATUS  mandatory
      DESCRIPTION
      "This parameter's value indicates the number of the currently
      static MAC filters."
      ::= { dot1dStatic 1 }


          dot1dStaticTable OBJECT-TYPE
              SYNTAX  SEQUENCE OF Dot1dStaticEntry
              ACCESS  not-accessible
              STATUS  mandatory
              DESCRIPTION
                      "A table containing filtering information
                      configured into the bridge by (local or network)
                      management specifying the set of ports to which
                      frames received from specific ports and containing
                      specific destination addresses are allowed to be
                      forwarded.  The value of zero in this table as the
                      port number from which frames with a specific
                      destination address are received, is used to
                      specify all ports for which there is no specific
                      entry in this table for that particular
                      destination address.  Entries are valid for
                      unicast and for group/broadcast addresses."
              REFERENCE
                      "IEEE 802.1D-1990: Section 6.7.2"
              ::= { dot1dStatic 2 }

          dot1dStaticEntry OBJECT-TYPE
              SYNTAX  Dot1dStaticEntry
              ACCESS  not-accessible
              STATUS  mandatory
              DESCRIPTION
                      "Filtering information configured into the bridge
                      by (local or network) management specifying the
                      set of ports to which frames received from a
                      specific port and containing a specific
                      destination address are allowed to be forwarded."
              REFERENCE
                      "IEEE 802.1D-1990: Section 6.7.2"
              INDEX   { dot1dStaticAddress}--, dot1dStaticReceivePort }
              ::= { dot1dStaticTable 1 }

          Dot1dStaticEntry ::=
              SEQUENCE {
                  dot1dStaticAddress
                      OCTET STRING (SIZE (6))
--                  dot1dStaticReceivePort
--                     INTEGER,
--                  dot1dStaticAllowedToGoTo
--                      INTEGER,
--                  dot1dStaticStatus
--                      INTEGER
              }

          dot1dStaticAddress OBJECT-TYPE
              SYNTAX  OCTET STRING (SIZE (6))
              ACCESS  read-write
              STATUS  mandatory
              DESCRIPTION
                      "The destination MAC address in a frame to which
                      this entry's filtering information applies.  This
                      object can take the value of a unicast address, a
                      group address or the broadcast address."
              REFERENCE
                      "IEEE 802.1D-1990: Section 3.9.1, 3.9.2"
              ::= { dot1dStaticEntry 1 }

--          dot1dStaticReceivePort OBJECT-TYPE
--              SYNTAX  INTEGER
--              ACCESS  read-write
--              STATUS  mandatory
--              DESCRIPTION
--                      "Either the value '0', or the port number of the
--                      port from which a frame must be received in order
--                      for this entry's filtering information to apply.
--                      A value of zero indicates that this entry applies
--                      on all ports of the bridge for which there is no
--                      other applicable entry."
--              ::= { dot1dStaticEntry 2 }

--          dot1dStaticAllowedToGoTo OBJECT-TYPE
--              SYNTAX  INTEGER
--              ACCESS  read-write
--              STATUS  mandatory
--              DESCRIPTION
--                      "The set of ports to which frames received from a
--                      specific port and destined for a specific MAC
--                      address, are allowed to be forwarded.  Each octet
--                      within the value of this object specifies a set of
--                      eight ports, with the first octet specifying ports
--                      1 through 8, the second octet specifying ports 9
--                      through 16, etc.  Within each octet, the most
--                      significant bit represents the lowest numbered
--                      port, and the least significant bit represents the
--                      highest numbered port.  Thus, each port of the
--                      bridge is represented by a single bit within the
--                      value of this object.  If that bit has a value of
--                      '1' then that port is included in the set of
--                      ports; the port is not included if its bit has a
--                      value of '0'.  (Note that the setting of the bit
--                      corresponding to the port from which a frame is
--                      received is irrelevant.)  The default value of
--                      this object is a string of ones of appropriate
--                      length."
--              ::= { dot1dStaticEntry 3 }
--
--          dot1dStaticStatus OBJECT-TYPE
--              SYNTAX  INTEGER {
--                          other(1),
--                          invalid(2),
--                          permanent(3),
--                          deleteOnReset(4),
--                          deleteOnTimeout(5)
--                      }
--              ACCESS  read-write
--              STATUS  mandatory
--              DESCRIPTION
--                      "This object indicates the status of this entry.
--                      The default value is permanent(3).
--                           other(1) - this entry is currently in use but
--                                the conditions under which it will
--                                remain so are different from each of the
--                                following values.
--                           invalid(2) - writing this value to the object
--                                removes the corresponding entry.
--                           permanent(3) - this entry is currently in use
--                                and will remain so after the next reset
--                                of the bridge.
--                           deleteOnReset(4) - this entry is currently in
--                                use and will remain so until the next
--                                reset of the bridge.
--                           deleteOnTimeout(5) - this entry is currently
--                                in use and will remain so until it is
--                                aged out."
--              ::= { dot1dStaticEntry 4 }



-- Protocol Filtering


protocolFilterGRP OBJECT IDENTIFIER ::= {atmelSys 6}

protocolFilterNum OBJECT-TYPE
      SYNTAX  INTEGER 
      ACCESS  read-write
      STATUS  mandatory
      DESCRIPTION
      "This parameter's value indicates the number of the currently
      protocol filters."
      ::= { protocolFilterGRP 1 }




          protocolFilterTable OBJECT-TYPE
              SYNTAX  SEQUENCE OF ProtocolFilterEntry
              ACCESS  not-accessible
              STATUS  mandatory
              DESCRIPTION
                      "A table containing filtering information
                      configured into the bridge by (local or network)
                      management specifying the set of protocol filter."
              ::= { protocolFilterGRP 2 }

          protocolFilterEntry OBJECT-TYPE
              SYNTAX  ProtocolFilterEntry
              ACCESS  not-accessible
              STATUS  mandatory
              DESCRIPTION
                      "Filtering information configured into the bridge
                      by (local or network) management specifying the
                      set of protocol filter."
--              INDEX   { ProtocolFilterCode }
              ::= { protocolFilterTable 1 }

          ProtocolFilterEntry ::=
              SEQUENCE {
                  protocolFilterCode
                      OCTET STRING (SIZE (2)),
                  protocolFilterDescription
                      DisplayString (SIZE (0..255)),
                  protocolFilterActivity
                      INTEGER
              }

          protocolFilterCode OBJECT-TYPE
              SYNTAX  OCTET STRING (SIZE (2))
              ACCESS  read-write
              STATUS  mandatory
              DESCRIPTION
                      "The protocol code configured into the bridge
                      by (local or network) management specifying the
                      set of protocol filter."
              ::= { protocolFilterEntry 1 }

          protocolFilterDescription OBJECT-TYPE
              SYNTAX  DisplayString (SIZE (0..255))
              ACCESS  read-write
              STATUS  mandatory
              DESCRIPTION
                      "A textual description of the protocol."
              ::= { protocolFilterEntry 2 }

          protocolFilterActivity OBJECT-TYPE
              SYNTAX  INTEGER {enable(1),disable(2)}
              ACCESS  read-write
              STATUS  mandatory
              DESCRIPTION
                      "This object indicates the status of this filter."
              ::= { protocolFilterEntry 3 }



-- Ethernet STATISTICS


ethStatisticsGRP OBJECT IDENTIFIER ::= {atmelSys 7}

ethRxStatistics OBJECT-TYPE
		SYNTAX OCTET STRING (SIZE (64))
		ACCESS read-only
		STATUS mandatory
		DESCRIPTION	 
		"Ethernet Rx Statistics
		EthernetRxStatistics{
			unsigned long	TotalBytesRx;
			unsigned long	TotalPacketsRx;
			unsigned long	PacketCRCErrorRx;
			unsigned long	MulticastPacketRx;
			unsigned long	BroadcastPacketRx;
			unsigned long	ControlFramesRx;
			unsigned long	PauseFramesRx;
			unsigned long	UnknownOPCodeRx;
			unsigned long	AlignmentRxError;
			unsigned long	LengthOutOfRangeRx;
			unsigned long	CodeErrorRx;
			unsigned long	FalseCarrierRx;
			unsigned long	UndersizePacketsRx;
			unsigned long	OversizePacketsRx;
			unsigned long	TotalFragmentsRx;
			unsigned long	TotalJabberRx;
		}"
		::= {ethStatisticsGRP 1 }

ethTxStatistics OBJECT-TYPE
		SYNTAX OCTET STRING (SIZE (56))
		ACCESS read-only
		STATUS mandatory
		DESCRIPTION	 
		"Ethernet Tx Statistics
		EthernetTxStatistics{
			unsigned long	TotalBytesTx;
			unsigned long	TotalPacketsTx;
			unsigned long	PacketCRCErrorTx;
			unsigned long	MulticastPacketTx;
			unsigned long	BroadcastPacketTx;
			unsigned long	UnicastPacketTx;
			unsigned long	PauseFramesTx;
			unsigned long	SingleDeferPacketTx;
			unsigned long	MultiDeferPacketsTx;
			unsigned long	SingleCollisionsTx;
			unsigned long	MultiCollisionsTx;
			unsigned long	LateCollisionsTx;
			unsigned long	ExcessiveCollisionTx;
			unsigned long	TotalCollisionsTx;
		}"

		::= {ethStatisticsGRP 2 }





-- Test Mode Settings


testModeSettingsGRP OBJECT IDENTIFIER ::= {atmelSys 8}

testModeOnOff 	OBJECT-TYPE
				SYNTAX INTEGER {enable(1),disable(2)}
				ACCESS read-write
				STATUS mandatory
				DESCRIPTION	 
				"When setting this attribute to enable(1), the device be
				at test mode."
				::= { testModeSettingsGRP 1 }


testModeCommandStruct 	OBJECT-TYPE
				SYNTAX OCTET STRING (SIZE (20))
				ACCESS read-write
				STATUS mandatory
				DESCRIPTION	 
				"
				typedef struct __CONT_PKT_TX
				{
					UINT8	Channel;
					UINT8	Antenna;
					UINT8	TxPower;
					UINT8	TxRate;
				
					UINT8	TxFilter;
					UINT8	Reserved;
					UINT16	IFrameTime;
				
					UINT32	FrameLength;
					UINT32	FramesToTransmit;
					
					UINT8	Pattern;
					UINT8	Reserved1[3];
				}CONT_PKT_TX;
				"
				::= {testModeSettingsGRP 2 }

testModeRadioConfiguration 	OBJECT-TYPE
					SYNTAX OCTET STRING (SIZE (47))
					ACCESS read-write
					STATUS mandatory
					DESCRIPTION	 
					"Configuration of radio derived from tests. CR17 Reg 1-14, CR20 Reg 1-14, CR21 Reg 1-14, CR1, CR2, CR3, CR28, CR29"
					::= {testModeSettingsGRP 8 }

testModeStatistics	 	OBJECT-TYPE
					SYNTAX OCTET STRING (SIZE (12))
					ACCESS read-only
					STATUS mandatory
					DESCRIPTION	 
					"Statistics derive from tests
					TestModeStatistics{
						unsigned long SuccessFrames;
						unsigned long FailedFrames;
						unsigned long PacketsTx;
					} "

					::= {testModeSettingsGRP 9 }




-- Authorized Settings


authorizedSettingsGRP OBJECT IDENTIFIER ::= {atmelSys 9}

authorizedUserPass 	OBJECT-TYPE
				SYNTAX OCTET STRING (SIZE (16))
				ACCESS read-write
				STATUS mandatory
				DESCRIPTION	 
				"The community name of User."
				::= {authorizedSettingsGRP 1 }


authorizedAdminPass 	OBJECT-TYPE
				SYNTAX OCTET STRING (SIZE (16))
				ACCESS read-write
				STATUS mandatory
				DESCRIPTION	 
				"The community name of Administrator."
				::= {authorizedSettingsGRP 2 }


authorizedManufactPass 	OBJECT-TYPE
				SYNTAX OCTET STRING (SIZE (16))
				ACCESS read-write
				STATUS mandatory
				DESCRIPTION	 
				"The community name of Manufacturer."
				::= {authorizedSettingsGRP 3 }


--*************************** wireless ***************************
--****************************************************************

-- Operational Settings


operationalSettingsGRP OBJECT IDENTIFIER ::= {wireless 1}


operChannelID  OBJECT-TYPE
	SYNTAX  INTEGER  {
			channel1(1),
			channel2(2),
			channel3(3),
			channel4(4),
			channel5(5),
			channel6(6),
			channel7(7),
			channel8(8),
			channel9(9),
			channel10(10),
			channel11(11),
			channel12(12),
			channel13(13),
			channel14(14)
		}
	ACCESS  read-write
	STATUS  mandatory
	DESCRIPTION
		"The operating frequency channel. Valid numbers
		are	as defind in ISO/IEC 8802-11:1999, 15.4.6.2."
	::= { operationalSettingsGRP 1 }


operESSIDLength OBJECT-TYPE
     SYNTAX  INTEGER
     ACCESS  read-write    
     STATUS  mandatory
     DESCRIPTION
     "The ESSID Length"
     ::= {operationalSettingsGRP 2 }     

operESSID OBJECT-TYPE
     SYNTAX  OCTET STRING (SIZE (32))
     ACCESS  read-write    
     STATUS  mandatory
     DESCRIPTION
     "The network name. The size of the network name
     should not be more than 32 characters long."
     ::= {operationalSettingsGRP 3 }     


operRTSThreshold OBJECT-TYPE
		SYNTAX	INTEGER  
		ACCESS read-write
		STATUS mandatory
		DESCRIPTION	 
		"This attribute indicates the number of bytes in an 
		MPDU (frame), above which an RTS/CTS handshake will be
		performed. Setting this attribute to be larger than the
		maximum frame size, will prevent the RTS/CTS handshake 
		for frames trassmitted by this station."
	::= {operationalSettingsGRP 4 }


operFragmentationThreshold OBJECT-TYPE
		SYNTAX	INTEGER  
		ACCESS read-write
		STATUS mandatory
		DESCRIPTION	 
		"This attribute indicates the number of bytes in an 
		MPDU (frame), above which MPDU fragmentation will be
		performed."
	::= {operationalSettingsGRP 5 }
	

operPreambleType OBJECT-TYPE
      SYNTAX  INTEGER {
			shortpreamble(1),
			longpreamble(2)
		}
      ACCESS  read-write
      STATUS  mandatory
      DESCRIPTION
      "This parameter's value indicates the Preamble Type of device. Short or Long."
	      ::= {operationalSettingsGRP 6 }


operAuthenticationType OBJECT-TYPE
		SYNTAX	INTEGER {
      	openSystem(1),
      	sharedKey(2),
      	bothType(3)
      	}
		ACCESS read-write
		STATUS mandatory
		DESCRIPTION	 
		"This attribute indicates the authentication algorithm
		used during the authentication sequence.
		The value of this attribute is one of the following:
		1 - Open System,
		2 - Shared Key
		3 - Both Type "
		::= {operationalSettingsGRP 7 }


operBasicRates OBJECT-TYPE
		SYNTAX OCTET STRING (SIZE (4))
		ACCESS read-write
		STATUS mandatory
		DESCRIPTION	 
		"This attribute indicates the basic and supported rates of Access Point.Valid format
		is as defind in ISO/IEC 8802-11:1999"
		::= { operationalSettingsGRP 8 }


operAutoRateFallBack OBJECT-TYPE
		SYNTAX INTEGER {enable(1),disable(2)}
		ACCESS read-write
		STATUS mandatory
		DESCRIPTION	 
		"This attribute indicates if Auto Rate Fall Back is enable or disable."
		::= {operationalSettingsGRP 9 }

operAccessPointName OBJECT-TYPE
     SYNTAX  OCTET STRING (SIZE (32))
     ACCESS  read-write    
     STATUS  mandatory
     DESCRIPTION
     "The AP name."
     ::= {operationalSettingsGRP 10 }     

operSSIDBroadcasting OBJECT-TYPE
		SYNTAX INTEGER {enable(1),disable(2)}
		ACCESS read-write
		STATUS mandatory
		DESCRIPTION	 
		"This attribute indicates if SSID is broadcasting or not."
		::= {operationalSettingsGRP 11 }

operAntennaSettings OBJECT-TYPE
		SYNTAX INTEGER
		ACCESS read-write
		STATUS mandatory
		DESCRIPTION	 
		"."
		::= {operationalSettingsGRP 12 }

operInterRoaming OBJECT-TYPE
		SYNTAX INTEGER
		ACCESS read-write
		STATUS mandatory
		DESCRIPTION	 
		"."
		::= {operationalSettingsGRP 13 }

operBeaconPeriod OBJECT-TYPE
		SYNTAX INTEGER
		ACCESS read-write
		STATUS mandatory
		DESCRIPTION	 
		"."
		::= {operationalSettingsGRP 14 }

operDTIM OBJECT-TYPE
		SYNTAX INTEGER
		ACCESS read-write
		STATUS mandatory
		DESCRIPTION	 
		"."
		::= {operationalSettingsGRP 15 }



-- Privacy


privacyGRP OBJECT IDENTIFIER ::= { wireless 2 }



defaultWEPKey1 OBJECT-TYPE
    SYNTAX OCTET STRING (SIZE (13))
    ACCESS  write-only
    STATUS  mandatory
    DESCRIPTION    
    "A WEP default secret key value."
    ::= { privacyGRP 1 }    

defaultWEPKey2 OBJECT-TYPE
    SYNTAX OCTET STRING (SIZE (13))
    ACCESS  write-only
    STATUS  mandatory
    DESCRIPTION    
    "A WEP default secret key value."
    ::= { privacyGRP 2 }    

defaultWEPKey3 OBJECT-TYPE
    SYNTAX OCTET STRING (SIZE (13))
    ACCESS  write-only
    STATUS  mandatory
    DESCRIPTION    
    "A WEP default secret key value."
    ::= { privacyGRP 3 }    

defaultWEPKey4 OBJECT-TYPE
    SYNTAX OCTET STRING (SIZE (13))
    ACCESS  write-only
    STATUS  mandatory
    DESCRIPTION    
    "A WEP default secret key value."
    ::= { privacyGRP 4 }    



privacyWEPEnable OBJECT-TYPE
		SYNTAX INTEGER {enable64(1),disable(2),enable128(3) }
		ACCESS read-write
		STATUS mandatory
		DESCRIPTION	 
		"This attribute, when enable64(1) or enable128(3), indicates that the 802.11
		standard encryption mechanism (WEP) is implemented. WEP64, WEP128 or disable"
		::= {privacyGRP 5}


privacyDefaultWEPKeyID OBJECT-TYPE
		SYNTAX INTEGER   (1..4)
		ACCESS read-write
		STATUS mandatory
		DESCRIPTION
		"This attribute shall indicate the use of the first, second,
		third or fourth DefaultWEPKey when set to values of one, two,
		three or four."
		::= {privacyGRP 6}


-- STATISTICS


wlstatisticsGRP OBJECT IDENTIFIER ::= {wireless 3}

wirelessStatistics OBJECT-TYPE
		SYNTAX OCTET STRING (SIZE (88))
		ACCESS read-only
		STATUS mandatory
		DESCRIPTION	 
		"Wireless Statistics. 22 elements(ULONG)
		WirelessStatistics{
			unsigned long	UnicastTransmittedPackets;
			unsigned long	BroadcastTransmittedPacets;
			unsigned long	MulticastTransmittedPackets;
			unsigned long	TransmittedBeacon;
			unsigned long	TransmittedACK;
			unsigned long	TransmittedRTS;
			unsigned long	TransmittedCTS;
			unsigned long	UnicastReceivedPackets;
			unsigned long	BroadcastReceivedPackets;
			unsigned long	MulticastReceivedPackets;
			unsigned long	ReceivedBeacon;
			unsigned long	ReceivedACK;
			unsigned long	ReceivedRTS;
			unsigned long	ReceivedCTS;
			unsigned long	ACKFailure;
			unsigned long	CTSFailure;
			unsigned long	RetryPackets;
			unsigned long	ReceivedDuplicate;
			unsigned long	FailedPackets;
			unsigned long	AgedPackets;
			unsigned long	FCSError;
			unsigned long	InvalidPLCP;
		} "
		::= {wlstatisticsGRP 1 }


-- Site Survey

wlSiteSurveyGRP OBJECT IDENTIFIER ::= {wireless 4}

channelStatus OBJECT-TYPE
		SYNTAX OCTET STRING (SIZE (14))
		ACCESS read-only
		STATUS mandatory
		DESCRIPTION	 
		"."
		::= {wlSiteSurveyGRP 1}


-- Associated Station
--

associatedStationsGRP OBJECT IDENTIFIER ::= {wireless 5}

associatedSTAsNum OBJECT-TYPE
      SYNTAX  INTEGER (1..2007)
      ACCESS  read-only
      STATUS  mandatory
      DESCRIPTION
      "This parameter's value indicates the number of the currently
      associated STAtions. Associated STAtions should not be more
      than 2007."
      ::= { associatedStationsGRP 1 }

		
associatedSTAsInfo	OBJECT-TYPE
	    SYNTAX	OCTET STRING (SIZE (24))
	    ACCESS  read-only
	    STATUS  mandatory
	    DESCRIPTION
	    "The associated STAtion's Information.
		AssociatedSTAsInfo{
			unsigned sort Num;
			unsigned char MacAddress[6];
		} "
	    ::= { associatedStationsGRP 2 }
		

--Authorized Mac Addresses

authorizedMacAddressesGRP OBJECT IDENTIFIER ::= {wireless 6}

authorizationMacEnable OBJECT-TYPE
		SYNTAX INTEGER (1..3)
		ACCESS read-write
		STATUS mandatory
		DESCRIPTION	 
		"When setting this attribute to 1, the Authorization Mac Address Table will be enabled in allow mode.
		 When setting this attribute to 3, the Authorization Mac Address Table will be enabled in deny mode."
		::= {authorizedMacAddressesGRP 1}


authorizedMac	OBJECT-TYPE
	    SYNTAX	OCTET STRING (SIZE (12))
	    ACCESS  read-write
	    STATUS  mandatory
	    DESCRIPTION
	    "The Authorized Wireless Mac Addresses
		AuthorizedMacTableString{
			unsigned sort Action; //Set 0x01 or Get 0x02
			unsigned sort NumOfAllTableAddresses;
			unsigned sort NumOfCurrentAddress;
			unsigned char MacAddress[6];
		} "

	    ::= { authorizedMacAddressesGRP 2 }

-- KNOWN ACCESS POINTS


wlKnownAPGRP OBJECT IDENTIFIER ::= {wireless 7}

wirelessKnownAPs OBJECT-TYPE
		SYNTAX OCTET STRING (SIZE (160))
		ACCESS read-only
		STATUS mandatory
		DESCRIPTION	 
		"."
		::= {wlKnownAPGRP 1 }

selectedBSSListNumber OBJECT-TYPE
		SYNTAX INTEGER
		ACCESS write-only
		STATUS mandatory
		DESCRIPTION	 
		"."
		::= {wlKnownAPGRP 2 }


-- Advanced Privacy


advancedPrivacyGRP OBJECT IDENTIFIER ::= { wireless 8 }

dot1xEnable OBJECT-TYPE
		SYNTAX INTEGER {enable(1),disable(2), mixed-environment(3)}
		ACCESS read-write
		STATUS mandatory
		DESCRIPTION	 
		"."
		::= {advancedPrivacyGRP 1}

broadcastKeyPeriod OBJECT-TYPE
		SYNTAX INTEGER  
		ACCESS read-write
		STATUS mandatory
		DESCRIPTION	 
		"."
		::= {advancedPrivacyGRP 2}

serverIP OBJECT-TYPE
		SYNTAX IpAddress
		ACCESS read-write
		STATUS mandatory
		DESCRIPTION	 
		"."
		::= {advancedPrivacyGRP 3}

serverSecret OBJECT-TYPE
    		SYNTAX OCTET STRING (SIZE (16))
		ACCESS  write-only
		STATUS  mandatory
		DESCRIPTION    
		"."
		::= {advancedPrivacyGRP 4}    



--*************************** Traps ***************************
--*************************************************************

trapSTAMacAddress OBJECT-TYPE
	SYNTAX OCTET STRING (SIZE (6))
	ACCESS read-only
	STATUS mandatory
	DESCRIPTION	 
	"The MAC address of a station device"

	::= {traps 1}



-- BroadcastKeyPeriod

trapReassociation TRAP-TYPE
	ENTERPRISE atmel
	VARIABLES { trapSTAMacAddress }
	DESCRIPTION
	"This trap message is sent when a STAtion's reassosiation
	request is received."
	::= 1

trapRoamOut TRAP-TYPE
	ENTERPRISE atmel
	VARIABLES { trapSTAMacAddress }
	DESCRIPTION
	"This trap message is used to indicate that a STAtion has
	roamed out of the Wireless bridge's coverage area."
	::= 2

trapAssociation TRAP-TYPE
	ENTERPRISE atmel
	VARIABLES { trapSTAMacAddress }
	DESCRIPTION
	"Indicates the reception of an association request packet
	and	the sender STAtion's successful association with the
	Access Point."
	::= 3
	
trapDisassociation TRAP-TYPE
	ENTERPRISE atmel
	VARIABLES { trapSTAMacAddress }
	DESCRIPTION
	"This trap message is sent when a disassociation notification
	packet is received from a STAtion."
	::= 4

trapAssociationExpire TRAP-TYPE
	ENTERPRISE atmel
	VARIABLES { trapSTAMacAddress }
	DESCRIPTION
	"This trap message is sent when the association's maximum time interval expires for
	an associated STAtion."
	::= 5

trapReset TRAP-TYPE
	ENTERPRISE atmel
	VARIABLES { sysReset }
	DESCRIPTION
	"This trap message is sent when Access Point Resets."
	::= 6

trapSettingPingIPAddress TRAP-TYPE
	ENTERPRISE atmel
	VARIABLES { operIPAddress }
	DESCRIPTION
	"This trap message is sent when the Access Point IP address
	is set with the transmition of a ping message."
	::= 7

trapStartUp TRAP-TYPE
	ENTERPRISE atmel
	--VARIABLES { }
	DESCRIPTION
	"This trap message is sent when Access Point Starts Up."
	::= 8

trapFailedToEraseFlash TRAP-TYPE
	ENTERPRISE atmel
	--VARIABLES { }
	DESCRIPTION
	"This trap message is sent when Access Point Failed To Erase Flash."
	::= 9

trapAPClientScanning TRAP-TYPE
	ENTERPRISE atmel
	--VARIABLES { }
	DESCRIPTION
	"Access Point Client is scanning..."
	::= 10

trapAPClientAuthenticating TRAP-TYPE
	ENTERPRISE atmel
	VARIABLES { bridgeRemoteBridgeBSSID }
	DESCRIPTION
	"Access Point Client is authenticating with the AP."
	::= 11

trapAPClientAssociating TRAP-TYPE
	ENTERPRISE atmel
	VARIABLES { bridgeRemoteBridgeBSSID }
	DESCRIPTION
	"Access Point Client is associating with the AP."
	::= 12

trapAPClientReAssociating TRAP-TYPE
	ENTERPRISE atmel
	VARIABLES { bridgeRemoteBridgeBSSID }
	DESCRIPTION
	"Access Point Client is reassociating with the AP."
	::= 13

trapAPClientAuthenticationFailed TRAP-TYPE
	ENTERPRISE atmel
	VARIABLES { bridgeRemoteBridgeBSSID }
	DESCRIPTION
	"Access Point Client has failed authenticating with the AP."
	::= 14

trapAPClientAssociationFailed TRAP-TYPE
	ENTERPRISE atmel
	VARIABLES { bridgeRemoteBridgeBSSID }
	DESCRIPTION
	"Access Point Client has failed associating with the AP."
	::= 15

trapAPClientConnected TRAP-TYPE
	ENTERPRISE atmel
	VARIABLES { bridgeRemoteBridgeBSSID }
	DESCRIPTION
	"Access Point Client has been connected with the AP."
	::= 16

trapAPClientDisconnected TRAP-TYPE
	ENTERPRISE atmel
	VARIABLES { bridgeRemoteBridgeBSSID }
	DESCRIPTION
	"Access Point Client has been disconnected from the AP."
	::= 17                         
	
trapAPClientScanFailed	TRAP-TYPE
	ENTERPRISE atmel
	--VARIABLES { }
	DESCRIPTION
	"Access Point Client has failed scanning!"
	::= 18                         
			 
trapAPClientJoinFailed	TRAP-TYPE
	ENTERPRISE atmel
	--VARIABLES { }
	DESCRIPTION
	"Access Point Client has failed joining!"
	::= 19       

trapAPClientJoining	TRAP-TYPE
	ENTERPRISE atmel
	--VARIABLES { }
	DESCRIPTION
	"Access Point Client is in join state."
	::= 20       

END
