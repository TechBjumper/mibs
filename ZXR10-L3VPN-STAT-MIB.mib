--  ************************************************
--  $Id: ZXR10-MPLS-L3VPN-STATIS.mib 3 2005-07-26 01:34:21Z taowq $
--
--  ZXR10-MPLS-L3VPN.mib: ZXR10 MPLS L3VPN query  MIB file
--
--  Jul. 2005, Tao wenqiang
--
--  Copyright(c) 2005 by ZTE Corporaton
--  All rights reservered
--
--  ************************************************

ZXR10-L3VPN-STAT-MIB DEFINITIONS ::= BEGIN

IMPORTS
    MODULE-IDENTITY,
    OBJECT-TYPE,
    Integer32,
    IpAddress,
    Unsigned32,
    Counter64
        FROM SNMPv2-SMI
    DisplayString
        FROM SNMPv2-TC
    zxr10L3vpn
        FROM ZXR10-SMI;

    zxr10MplsL3vpnStatisMIB MODULE-IDENTITY
       LAST-UPDATED "201612220000Z"
    ORGANIZATION "ZTE Corporation"
    CONTACT-INFO
        "ZTE Corporation
         Nanjing Institute of ZTE Corporation

         No.68 Zijinghua Rd. Yuhuatai District, Nanjing, China

         Tel: +86-25-52870000"

    DESCRIPTION
        "ZXROS v4.6.03 Mpls L3vpn query and configuration MIB"
    REVISION "201609020000Z" 
    DESCRIPTION
       "add a new zxr10L3vpnPeerPolStatisObjects about mpls l3vpn peer policy traffics.
        "
    REVISION "201304100000Z"  -- April 10, 2013
    DESCRIPTION
       "modify: zxr10L3vpnStatisVpnID,
                    zxr10L3vpnStatisVpnName,
                    zxr10L3vpnStatisRecvPkts,
                    zxr10L3vpnStatisRecvBytes,
                    zxr10L3vpnStatisSndPkts ,
                    zxr10L3vpnStatisSndBytes
        "
    REVISION "200509260000Z"  -- September 26, 2005
    DESCRIPTION
       ""

    ::= { zxr10L3vpn 1 }


    -- 1.3.6.1.4.1.3902.3.105.1.1
    zxr10L3vpnStatisObjects   OBJECT IDENTIFIER ::= { zxr10MplsL3vpnStatisMIB 1 }
    -- 1.3.6.1.4.1.3902.3.105.1.2
    zxr10L3vpnPeerPolStatisObjects   OBJECT IDENTIFIER ::= { zxr10MplsL3vpnStatisMIB 2 }


---

    zxr10L3vpnStatisTable  OBJECT-TYPE
        SYNTAX  SEQUENCE OF Zxr10L3vpnStatisEntry
        MAX-ACCESS  not-accessible
        STATUS  current
        DESCRIPTION
            "Mpls L3vpn instance query table"
        ::= { zxr10L3vpnStatisObjects 1 }

    zxr10L3vpnStatisEntry  OBJECT-TYPE
        SYNTAX  Zxr10L3vpnStatisEntry
        MAX-ACCESS  not-accessible
        STATUS  current
        DESCRIPTION
            "Information of Mpls L3vpn instance configured on a PE"
        INDEX  { zxr10L3vpnStatisVpnID }
        ::= { zxr10L3vpnStatisTable 1 }

    Zxr10L3vpnStatisEntry ::=
        SEQUENCE {
           zxr10L3vpnStatisVpnID
                Unsigned32,     
            zxr10L3vpnStatisVpnName
                DisplayString,
            zxr10L3vpnStatisRecvPkts
                Counter64,
            zxr10L3vpnStatisRecvBytes
                Counter64,
            zxr10L3vpnStatisSndPkts
                Counter64,
            zxr10L3vpnStatisSndBytes
                Counter64
    }    
    
    zxr10L3vpnStatisVpnID  OBJECT-TYPE
        SYNTAX  Unsigned32
        MAX-ACCESS  read-only
        STATUS  current
        DESCRIPTION
            "VPN ID"
        ::= { zxr10L3vpnStatisEntry 1 }

    zxr10L3vpnStatisVpnName  OBJECT-TYPE
        SYNTAX   DisplayString (SIZE(0..32))
        MAX-ACCESS  read-only
        STATUS  current
        DESCRIPTION
            "VRF name"
        ::= { zxr10L3vpnStatisEntry 2 }

    zxr10L3vpnStatisRecvPkts  OBJECT-TYPE
        SYNTAX  Counter64
        MAX-ACCESS  read-only
        STATUS  current
        DESCRIPTION
        "Number of packets received by the l3vpn instance"
         ::= { zxr10L3vpnStatisEntry 3 }

    zxr10L3vpnStatisRecvBytes  OBJECT-TYPE
        SYNTAX   Counter64
        MAX-ACCESS  read-only
        STATUS  current
        DESCRIPTION
        "Number of bytes received by the l3vpn instance"
         ::= { zxr10L3vpnStatisEntry 4 }

    zxr10L3vpnStatisSndPkts  OBJECT-TYPE
        SYNTAX   Counter64
        MAX-ACCESS  read-only
        STATUS  current
        DESCRIPTION
        "Number of packets sent by the l3vpn instance"
         ::= { zxr10L3vpnStatisEntry 5 }

    zxr10L3vpnStatisSndBytes  OBJECT-TYPE
        SYNTAX   Counter64
        MAX-ACCESS  read-only
        STATUS  current
        DESCRIPTION
        "Number of bytes sent by the l3vpn instance"
         ::= { zxr10L3vpnStatisEntry 6 }

--   
--
    -- 1.3.6.1.4.1.3902.3.105.1.2.1
    zxr10L3vpnPeerPolicyStatisTable  OBJECT-TYPE
        SYNTAX  SEQUENCE OF Zxr10L3vpnPeerPolicyStatisEntry
        MAX-ACCESS  not-accessible
        STATUS  current
        DESCRIPTION
            "Mpls L3vpn peer policy query table"
        ::= { zxr10L3vpnPeerPolStatisObjects 1 }
    -- 1.3.6.1.4.1.3902.3.105.1.2.1.1
    zxr10L3vpnPeerPolicyStatisEntry  OBJECT-TYPE
        SYNTAX  Zxr10L3vpnPeerPolicyStatisEntry
        MAX-ACCESS  not-accessible
        STATUS  current
        DESCRIPTION
            "Traffic information of MPLS L3VPN peer policy"
        INDEX  { zxr10L3vpnPeerPolStatisVpnName,
                 zxr10L3vpnPeerPolStatisPeerAddr,
                 zxr10L3vpnPeerPolStatisPriority
                 }
        ::= { zxr10L3vpnPeerPolicyStatisTable 1 }

    Zxr10L3vpnPeerPolicyStatisEntry ::=
        SEQUENCE {           
           zxr10L3vpnPeerPolStatisVpnName
                DisplayString,
           zxr10L3vpnPeerPolStatisPeerAddr
                IpAddress,
           zxr10L3vpnPeerPolStatisPriority
                Integer32,
           zxr10L3vpnPeerPolStatisOutPkts
                Counter64,
           zxr10L3vpnPeerPolStatisOutBytes
                Counter64, 
           zxr10L3vpnPeerPolStatisVpnID  
               Unsigned32
               }
      -- 1.3.6.1.4.1.3902.3.105.1.2.1.1.1  
    zxr10L3vpnPeerPolStatisVpnName  OBJECT-TYPE
        SYNTAX   DisplayString (SIZE(0..32))
        MAX-ACCESS  not-accessible
        STATUS  current
        DESCRIPTION
        "VRF name"
         ::= { zxr10L3vpnPeerPolicyStatisEntry 1 }
      -- 1.3.6.1.4.1.3902.3.105.1.2.1.1.2  
    zxr10L3vpnPeerPolStatisPeerAddr OBJECT-TYPE
        SYNTAX IpAddress
        MAX-ACCESS  not-accessible
        STATUS  current
        DESCRIPTION
            "VPN peer addr"
        ::= { zxr10L3vpnPeerPolicyStatisEntry 2 }
      -- 1.3.6.1.4.1.3902.3.105.1.2.1.1.3  
    zxr10L3vpnPeerPolStatisPriority OBJECT-TYPE
        SYNTAX Integer32 (0..7)
        MAX-ACCESS  not-accessible
        STATUS  current
        DESCRIPTION
            "Priority"
        ::= { zxr10L3vpnPeerPolicyStatisEntry 3 }
      -- 1.3.6.1.4.1.3902.3.105.1.2.1.1.4  
    zxr10L3vpnPeerPolStatisOutPkts  OBJECT-TYPE
        SYNTAX  Counter64
        MAX-ACCESS  read-only
        STATUS  current
        DESCRIPTION
        "Number of packets sent by the L3VPN peer"
         ::= { zxr10L3vpnPeerPolicyStatisEntry 4 }
      -- 1.3.6.1.4.1.3902.3.105.1.2.1.1.5  
    zxr10L3vpnPeerPolStatisOutBytes  OBJECT-TYPE
        SYNTAX   Counter64
        MAX-ACCESS  read-only
        STATUS  current
        DESCRIPTION
        "Number of bytes sent by the L3VPN peer"
         ::= { zxr10L3vpnPeerPolicyStatisEntry 5 }
      -- 1.3.6.1.4.1.3902.3.105.1.2.1.1.6  
    zxr10L3vpnPeerPolStatisVpnID  OBJECT-TYPE
        SYNTAX  Unsigned32
        MAX-ACCESS  read-only
        STATUS  current
        DESCRIPTION
            "VPN ID"
        ::= { zxr10L3vpnPeerPolicyStatisEntry 6 }
--

END
