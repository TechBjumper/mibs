-- file automatically created


TELDAT-TRAP-IP6-MIB DEFINITIONS ::= BEGIN


IMPORTS
	MODULE-IDENTITY,OBJECT-TYPE,OBJECT-IDENTITY,NOTIFICATION-TYPE,Integer32,IpAddress
		FROM SNMPv2-SMI
	DisplayString
		FROM SNMPv2-TC
	telEventTraps
		FROM TELDAT-MIB;


ip6TrapsMIB MODULE-IDENTITY
    LAST-UPDATED "201401200930Z"
    ORGANIZATION "Teldat, S.A."
    CONTACT-INFO 
        "Teldat, S.A.
        Customer Service

        Postal: Parque Tecnologico de Madrid
                Tres Cantos 28760
                Madrid, SPAIN

        Tel.: +34 918 076 565

        http://www.teldat.com"
    DESCRIPTION
        "This Module Information Base file is defined for managing received
        SNMP notifications generated by the IP6 event subsystem."
    REVISION "201401200930Z"
    DESCRIPTION "Initial implementation"
        ::= { telEventTraps 134 }


ip6EventsGroup	OBJECT IDENTIFIER	::= { ip6TrapsMIB 1 }

ip6Notifications	OBJECT IDENTIFIER	::= { ip6TrapsMIB 2 }
ip6NotificationsPrefix	OBJECT IDENTIFIER	::= { ip6Notifications 0 }

ip6EventObjects1 OBJECT-IDENTITY
    STATUS current
    DESCRIPTION
        "Event IP6.1
        This message is generated when an IPv6 packet is received."
    ::= { ip6EventsGroup 1 }

ip61-source-ip6-address OBJECT-TYPE
    SYNTAX DisplayString
    MAX-ACCESS accessible-for-notify
    STATUS current
    DESCRIPTION
        "Parameter 'source-ip6-address' in event IP6.1"
    ::= { ip6EventObjects1 1 }

ip61-destination-ip6-address OBJECT-TYPE
    SYNTAX DisplayString
    MAX-ACCESS accessible-for-notify
    STATUS current
    DESCRIPTION
        "Parameter 'destination-ip6-address' in event IP6.1"
    ::= { ip6EventObjects1 2 }

ip61-interface OBJECT-TYPE
    SYNTAX DisplayString
    MAX-ACCESS accessible-for-notify
    STATUS current
    DESCRIPTION
        "Parameter 'interface' in event IP6.1"
    ::= { ip6EventObjects1 3 }

ip6EventObjects2 OBJECT-IDENTITY
    STATUS current
    DESCRIPTION
        "Event IP6.2
        This message is generated by the stub IP6 forwarder for each packet
        which is received on an interface for which IP is not enabled."
    ::= { ip6EventsGroup 2 }

ip62-source-ip6-address OBJECT-TYPE
    SYNTAX DisplayString
    MAX-ACCESS accessible-for-notify
    STATUS current
    DESCRIPTION
        "Parameter 'source-ip6-address' in event IP6.2"
    ::= { ip6EventObjects2 1 }

ip62-destination-ip6-address OBJECT-TYPE
    SYNTAX DisplayString
    MAX-ACCESS accessible-for-notify
    STATUS current
    DESCRIPTION
        "Parameter 'destination-ip6-address' in event IP6.2"
    ::= { ip6EventObjects2 2 }

ip62-interface OBJECT-TYPE
    SYNTAX DisplayString
    MAX-ACCESS accessible-for-notify
    STATUS current
    DESCRIPTION
        "Parameter 'interface' in event IP6.2"
    ::= { ip6EventObjects2 3 }

ip6EventObjects3 OBJECT-IDENTITY
    STATUS current
    DESCRIPTION
        "Event IP6.3
        This message is generated when a packet has an incorrect version
        number."
    ::= { ip6EventsGroup 3 }

ip63-source-ip6-address OBJECT-TYPE
    SYNTAX DisplayString
    MAX-ACCESS accessible-for-notify
    STATUS current
    DESCRIPTION
        "Parameter 'source-ip6-address' in event IP6.3"
    ::= { ip6EventObjects3 1 }

ip63-destination-ip6-address OBJECT-TYPE
    SYNTAX DisplayString
    MAX-ACCESS accessible-for-notify
    STATUS current
    DESCRIPTION
        "Parameter 'destination-ip6-address' in event IP6.3"
    ::= { ip6EventObjects3 2 }

ip63-version-number OBJECT-TYPE
    SYNTAX Integer32
    MAX-ACCESS accessible-for-notify
    STATUS current
    DESCRIPTION
        "Parameter 'version-number' in event IP6.3"
    ::= { ip6EventObjects3 3 }

ip63-interface OBJECT-TYPE
    SYNTAX DisplayString
    MAX-ACCESS accessible-for-notify
    STATUS current
    DESCRIPTION
        "Parameter 'interface' in event IP6.3"
    ::= { ip6EventObjects3 4 }

ip6EventObjects4 OBJECT-IDENTITY
    STATUS current
    DESCRIPTION
        "Event IP6.4
        This message is generated when the packet length specified in
        the header is greater than the packet buffer length."
    ::= { ip6EventsGroup 4 }

ip64-source-ip6-address OBJECT-TYPE
    SYNTAX DisplayString
    MAX-ACCESS accessible-for-notify
    STATUS current
    DESCRIPTION
        "Parameter 'source-ip6-address' in event IP6.4"
    ::= { ip6EventObjects4 1 }

ip64-destination-ip6-address OBJECT-TYPE
    SYNTAX DisplayString
    MAX-ACCESS accessible-for-notify
    STATUS current
    DESCRIPTION
        "Parameter 'destination-ip6-address' in event IP6.4"
    ::= { ip6EventObjects4 2 }

ip64-specified-length OBJECT-TYPE
    SYNTAX Integer32
    MAX-ACCESS accessible-for-notify
    STATUS current
    DESCRIPTION
        "Parameter 'specified-length' in event IP6.4"
    ::= { ip6EventObjects4 3 }

ip64-true-length OBJECT-TYPE
    SYNTAX Integer32
    MAX-ACCESS accessible-for-notify
    STATUS current
    DESCRIPTION
        "Parameter 'true-length' in event IP6.4"
    ::= { ip6EventObjects4 4 }

ip64-interface OBJECT-TYPE
    SYNTAX DisplayString
    MAX-ACCESS accessible-for-notify
    STATUS current
    DESCRIPTION
        "Parameter 'interface' in event IP6.4"
    ::= { ip6EventObjects4 5 }

ip6EventObjects5 OBJECT-IDENTITY
    STATUS current
    DESCRIPTION
        "Event IP6.5
        This message is generated when a packet's indicated length
        is below the minimum possible length. The packet is discarded."
    ::= { ip6EventsGroup 5 }

ip65-source-ip6-address OBJECT-TYPE
    SYNTAX DisplayString
    MAX-ACCESS accessible-for-notify
    STATUS current
    DESCRIPTION
        "Parameter 'source-ip6-address' in event IP6.5"
    ::= { ip6EventObjects5 1 }

ip65-destination-ip6-address OBJECT-TYPE
    SYNTAX DisplayString
    MAX-ACCESS accessible-for-notify
    STATUS current
    DESCRIPTION
        "Parameter 'destination-ip6-address' in event IP6.5"
    ::= { ip6EventObjects5 2 }

ip65-specified-length OBJECT-TYPE
    SYNTAX Integer32
    MAX-ACCESS accessible-for-notify
    STATUS current
    DESCRIPTION
        "Parameter 'specified-length' in event IP6.5"
    ::= { ip6EventObjects5 3 }

ip65-true-length OBJECT-TYPE
    SYNTAX Integer32
    MAX-ACCESS accessible-for-notify
    STATUS current
    DESCRIPTION
        "Parameter 'true-length' in event IP6.5"
    ::= { ip6EventObjects5 4 }

ip65-interface OBJECT-TYPE
    SYNTAX DisplayString
    MAX-ACCESS accessible-for-notify
    STATUS current
    DESCRIPTION
        "Parameter 'interface' in event IP6.5"
    ::= { ip6EventObjects5 5 }

ip6EventObjects6 OBJECT-IDENTITY
    STATUS current
    DESCRIPTION
        "Event IP6.6
        This message is generated for each packet which has passed
        first-level reasonableness checks."
    ::= { ip6EventsGroup 6 }

ip66-source-ip6-address OBJECT-TYPE
    SYNTAX DisplayString
    MAX-ACCESS accessible-for-notify
    STATUS current
    DESCRIPTION
        "Parameter 'source-ip6-address' in event IP6.6"
    ::= { ip6EventObjects6 1 }

ip66-destination-ip6-address OBJECT-TYPE
    SYNTAX DisplayString
    MAX-ACCESS accessible-for-notify
    STATUS current
    DESCRIPTION
        "Parameter 'destination-ip6-address' in event IP6.6"
    ::= { ip6EventObjects6 2 }

ip6EventObjects7 OBJECT-IDENTITY
    STATUS current
    DESCRIPTION
        "Event IP6.7
        This message is generated when an IP packet needs to be
        fragmented for transmission."
    ::= { ip6EventsGroup 7 }

ip67-source-ip6-address OBJECT-TYPE
    SYNTAX DisplayString
    MAX-ACCESS accessible-for-notify
    STATUS current
    DESCRIPTION
        "Parameter 'source-ip6-address' in event IP6.7"
    ::= { ip6EventObjects7 1 }

ip67-destination-ip6-address OBJECT-TYPE
    SYNTAX DisplayString
    MAX-ACCESS accessible-for-notify
    STATUS current
    DESCRIPTION
        "Parameter 'destination-ip6-address' in event IP6.7"
    ::= { ip6EventObjects7 2 }

ip67-packet-length OBJECT-TYPE
    SYNTAX Integer32
    MAX-ACCESS accessible-for-notify
    STATUS current
    DESCRIPTION
        "Parameter 'packet-length' in event IP6.7"
    ::= { ip6EventObjects7 3 }

ip6EventObjects8 OBJECT-IDENTITY
    STATUS current
    DESCRIPTION
        "Event IP6.8
        This message is generated when a multicast packet arrives for an
        unknown protocol."
    ::= { ip6EventsGroup 8 }

ip68-source-ip6-address OBJECT-TYPE
    SYNTAX DisplayString
    MAX-ACCESS accessible-for-notify
    STATUS current
    DESCRIPTION
        "Parameter 'source-ip6-address' in event IP6.8"
    ::= { ip6EventObjects8 1 }

ip68-destination-ip6-address OBJECT-TYPE
    SYNTAX DisplayString
    MAX-ACCESS accessible-for-notify
    STATUS current
    DESCRIPTION
        "Parameter 'destination-ip6-address' in event IP6.8"
    ::= { ip6EventObjects8 2 }

ip68-protocol OBJECT-TYPE
    SYNTAX Integer32
    MAX-ACCESS accessible-for-notify
    STATUS current
    DESCRIPTION
        "Parameter 'protocol' in event IP6.8"
    ::= { ip6EventObjects8 3 }

ip6EventObjects9 OBJECT-IDENTITY
    STATUS current
    DESCRIPTION
        "Event IP6.9
        This message is generated when a packet arrives for an
        unknown protocol. The packet was destined for the router."
    ::= { ip6EventsGroup 9 }

ip69-source-ip6-address OBJECT-TYPE
    SYNTAX DisplayString
    MAX-ACCESS accessible-for-notify
    STATUS current
    DESCRIPTION
        "Parameter 'source-ip6-address' in event IP6.9"
    ::= { ip6EventObjects9 1 }

ip69-destination-ip6-address OBJECT-TYPE
    SYNTAX DisplayString
    MAX-ACCESS accessible-for-notify
    STATUS current
    DESCRIPTION
        "Parameter 'destination-ip6-address' in event IP6.9"
    ::= { ip6EventObjects9 2 }

ip69-protocol OBJECT-TYPE
    SYNTAX Integer32
    MAX-ACCESS accessible-for-notify
    STATUS current
    DESCRIPTION
        "Parameter 'protocol' in event IP6.9"
    ::= { ip6EventObjects9 3 }

ip6EventObjects10 OBJECT-IDENTITY
    STATUS current
    DESCRIPTION
        "Event IP6.10
        This message is generated for each packet destined for the router."
    ::= { ip6EventsGroup 10 }

ip610-protocol OBJECT-TYPE
    SYNTAX Integer32
    MAX-ACCESS accessible-for-notify
    STATUS current
    DESCRIPTION
        "Parameter 'protocol' in event IP6.10"
    ::= { ip6EventObjects10 1 }

ip610-source-ip6-address OBJECT-TYPE
    SYNTAX DisplayString
    MAX-ACCESS accessible-for-notify
    STATUS current
    DESCRIPTION
        "Parameter 'source-ip6-address' in event IP6.10"
    ::= { ip6EventObjects10 2 }

ip6EventObjects11 OBJECT-IDENTITY
    STATUS current
    DESCRIPTION
        "Event IP6.11
        This message is generated when a received packet's destination address
        is not valid. The packet is discarded."
    ::= { ip6EventsGroup 11 }

ip611-destination-ip6-address OBJECT-TYPE
    SYNTAX DisplayString
    MAX-ACCESS accessible-for-notify
    STATUS current
    DESCRIPTION
        "Parameter 'destination-ip6-address' in event IP6.11"
    ::= { ip6EventObjects11 1 }

ip6EventObjects12 OBJECT-IDENTITY
    STATUS current
    DESCRIPTION
        "Event IP6.12
        This message is generated when a packet is discarded because its Hop
        Limit field is zero."
    ::= { ip6EventsGroup 12 }

ip612-source-ip6-address OBJECT-TYPE
    SYNTAX DisplayString
    MAX-ACCESS accessible-for-notify
    STATUS current
    DESCRIPTION
        "Parameter 'source-ip6-address' in event IP6.12"
    ::= { ip6EventObjects12 1 }

ip612-destination-i6p-address OBJECT-TYPE
    SYNTAX DisplayString
    MAX-ACCESS accessible-for-notify
    STATUS current
    DESCRIPTION
        "Parameter 'destination-i6p-address' in event IP6.12"
    ::= { ip6EventObjects12 2 }

ip6EventObjects13 OBJECT-IDENTITY
    STATUS current
    DESCRIPTION
        "Event IP6.13
        This message is generated when a packet is discarded because one of its
        extension headers is not valid."
    ::= { ip6EventsGroup 13 }

ip613-source-ip6-address OBJECT-TYPE
    SYNTAX DisplayString
    MAX-ACCESS accessible-for-notify
    STATUS current
    DESCRIPTION
        "Parameter 'source-ip6-address' in event IP6.13"
    ::= { ip6EventObjects13 1 }

ip613-destination-ip6-address OBJECT-TYPE
    SYNTAX DisplayString
    MAX-ACCESS accessible-for-notify
    STATUS current
    DESCRIPTION
        "Parameter 'destination-ip6-address' in event IP6.13"
    ::= { ip6EventObjects13 2 }

ip613-extension-header OBJECT-TYPE
    SYNTAX DisplayString
    MAX-ACCESS accessible-for-notify
    STATUS current
    DESCRIPTION
        "Parameter 'extension-header' in event IP6.13"
    ::= { ip6EventObjects13 3 }

ip6EventObjects14 OBJECT-IDENTITY
    STATUS current
    DESCRIPTION
        "Event IP6.14
        This message is generated when an extension header of a packet has
        been processed correctly."
    ::= { ip6EventsGroup 14 }

ip614-source-ip6-address OBJECT-TYPE
    SYNTAX DisplayString
    MAX-ACCESS accessible-for-notify
    STATUS current
    DESCRIPTION
        "Parameter 'source-ip6-address' in event IP6.14"
    ::= { ip6EventObjects14 1 }

ip614-destination-ip6-address OBJECT-TYPE
    SYNTAX DisplayString
    MAX-ACCESS accessible-for-notify
    STATUS current
    DESCRIPTION
        "Parameter 'destination-ip6-address' in event IP6.14"
    ::= { ip6EventObjects14 2 }

ip614-extension-header OBJECT-TYPE
    SYNTAX DisplayString
    MAX-ACCESS accessible-for-notify
    STATUS current
    DESCRIPTION
        "Parameter 'extension-header' in event IP6.14"
    ::= { ip6EventObjects14 3 }

ip6EventObjects15 OBJECT-IDENTITY
    STATUS current
    DESCRIPTION
        "Event IP6.15
        This message is generated when an IPv6 packet is sent to eth-out funtion."
    ::= { ip6EventsGroup 15 }

ip615-source-ip6-address OBJECT-TYPE
    SYNTAX DisplayString
    MAX-ACCESS accessible-for-notify
    STATUS current
    DESCRIPTION
        "Parameter 'source-ip6-address' in event IP6.15"
    ::= { ip6EventObjects15 1 }

ip615-destination-ip6-address OBJECT-TYPE
    SYNTAX DisplayString
    MAX-ACCESS accessible-for-notify
    STATUS current
    DESCRIPTION
        "Parameter 'destination-ip6-address' in event IP6.15"
    ::= { ip6EventObjects15 2 }

ip615-interface OBJECT-TYPE
    SYNTAX DisplayString
    MAX-ACCESS accessible-for-notify
    STATUS current
    DESCRIPTION
        "Parameter 'interface' in event IP6.15"
    ::= { ip6EventObjects15 3 }

ip6EventObjects16 OBJECT-IDENTITY
    STATUS current
    DESCRIPTION
        "Event IP6.16
        This message is generated when an extern IPv6 is queued."
    ::= { ip6EventsGroup 16 }

ip616-size-of-queue OBJECT-TYPE
    SYNTAX Integer32
    MAX-ACCESS accessible-for-notify
    STATUS current
    DESCRIPTION
        "Parameter 'size-of-queue' in event IP6.16"
    ::= { ip6EventObjects16 1 }

ip616-source-ip6-address OBJECT-TYPE
    SYNTAX DisplayString
    MAX-ACCESS accessible-for-notify
    STATUS current
    DESCRIPTION
        "Parameter 'source-ip6-address' in event IP6.16"
    ::= { ip6EventObjects16 2 }

ip616-destination-ip6-address OBJECT-TYPE
    SYNTAX DisplayString
    MAX-ACCESS accessible-for-notify
    STATUS current
    DESCRIPTION
        "Parameter 'destination-ip6-address' in event IP6.16"
    ::= { ip6EventObjects16 3 }

ip6EventObjects17 OBJECT-IDENTITY
    STATUS current
    DESCRIPTION
        "Event IP6.17
        This message is generated when an IPv6 packet is removed fron the queue."
    ::= { ip6EventsGroup 17 }

ip617-size-of-queue OBJECT-TYPE
    SYNTAX Integer32
    MAX-ACCESS accessible-for-notify
    STATUS current
    DESCRIPTION
        "Parameter 'size-of-queue' in event IP6.17"
    ::= { ip6EventObjects17 1 }

ip617-source-ip6-address OBJECT-TYPE
    SYNTAX DisplayString
    MAX-ACCESS accessible-for-notify
    STATUS current
    DESCRIPTION
        "Parameter 'source-ip6-address' in event IP6.17"
    ::= { ip6EventObjects17 2 }

ip617-destination-ip6-address OBJECT-TYPE
    SYNTAX DisplayString
    MAX-ACCESS accessible-for-notify
    STATUS current
    DESCRIPTION
        "Parameter 'destination-ip6-address' in event IP6.17"
    ::= { ip6EventObjects17 3 }

ip6EventObjects18 OBJECT-IDENTITY
    STATUS current
    DESCRIPTION
        "Event IP6.18
        This message is generated when an IPv6 packet is processes."
    ::= { ip6EventsGroup 18 }

ip618-source-ip6-address OBJECT-TYPE
    SYNTAX DisplayString
    MAX-ACCESS accessible-for-notify
    STATUS current
    DESCRIPTION
        "Parameter 'source-ip6-address' in event IP6.18"
    ::= { ip6EventObjects18 1 }

ip618-destination-ip6-address OBJECT-TYPE
    SYNTAX DisplayString
    MAX-ACCESS accessible-for-notify
    STATUS current
    DESCRIPTION
        "Parameter 'destination-ip6-address' in event IP6.18"
    ::= { ip6EventObjects18 2 }

ip618-interface OBJECT-TYPE
    SYNTAX DisplayString
    MAX-ACCESS accessible-for-notify
    STATUS current
    DESCRIPTION
        "Parameter 'interface' in event IP6.18"
    ::= { ip6EventObjects18 3 }

ip6EventObjects19 OBJECT-IDENTITY
    STATUS current
    DESCRIPTION
        "Event IP6.19
        This message is generated when an intern IPv6 is queued."
    ::= { ip6EventsGroup 19 }

ip619-size-of-queue OBJECT-TYPE
    SYNTAX Integer32
    MAX-ACCESS accessible-for-notify
    STATUS current
    DESCRIPTION
        "Parameter 'size-of-queue' in event IP6.19"
    ::= { ip6EventObjects19 1 }

ip619-source-ip6-address OBJECT-TYPE
    SYNTAX DisplayString
    MAX-ACCESS accessible-for-notify
    STATUS current
    DESCRIPTION
        "Parameter 'source-ip6-address' in event IP6.19"
    ::= { ip6EventObjects19 2 }

ip619-destination-ip6-address OBJECT-TYPE
    SYNTAX DisplayString
    MAX-ACCESS accessible-for-notify
    STATUS current
    DESCRIPTION
        "Parameter 'destination-ip6-address' in event IP6.19"
    ::= { ip6EventObjects19 3 }

ip6EventObjects20 OBJECT-IDENTITY
    STATUS current
    DESCRIPTION
        "Event IP6.20
        This message is generated when an extern IPv6 is queued."
    ::= { ip6EventsGroup 20 }

ip620-size-of-queue OBJECT-TYPE
    SYNTAX Integer32
    MAX-ACCESS accessible-for-notify
    STATUS current
    DESCRIPTION
        "Parameter 'size-of-queue' in event IP6.20"
    ::= { ip6EventObjects20 1 }

ip620-source-ip6-address OBJECT-TYPE
    SYNTAX DisplayString
    MAX-ACCESS accessible-for-notify
    STATUS current
    DESCRIPTION
        "Parameter 'source-ip6-address' in event IP6.20"
    ::= { ip6EventObjects20 2 }

ip620-destination-ip6-address OBJECT-TYPE
    SYNTAX DisplayString
    MAX-ACCESS accessible-for-notify
    STATUS current
    DESCRIPTION
        "Parameter 'destination-ip6-address' in event IP6.20"
    ::= { ip6EventObjects20 3 }

ip620-interface OBJECT-TYPE
    SYNTAX DisplayString
    MAX-ACCESS accessible-for-notify
    STATUS current
    DESCRIPTION
        "Parameter 'interface' in event IP6.20"
    ::= { ip6EventObjects20 4 }

ip6EventObjects21 OBJECT-IDENTITY
    STATUS current
    DESCRIPTION
        "Event IP6.21
        This message is generated when an IPv6 packet is removed fron the queue."
    ::= { ip6EventsGroup 21 }

ip621-size-of-queue OBJECT-TYPE
    SYNTAX Integer32
    MAX-ACCESS accessible-for-notify
    STATUS current
    DESCRIPTION
        "Parameter 'size-of-queue' in event IP6.21"
    ::= { ip6EventObjects21 1 }

ip621-source-ip6-address OBJECT-TYPE
    SYNTAX DisplayString
    MAX-ACCESS accessible-for-notify
    STATUS current
    DESCRIPTION
        "Parameter 'source-ip6-address' in event IP6.21"
    ::= { ip6EventObjects21 2 }

ip621-destination-ip6-address OBJECT-TYPE
    SYNTAX DisplayString
    MAX-ACCESS accessible-for-notify
    STATUS current
    DESCRIPTION
        "Parameter 'destination-ip6-address' in event IP6.21"
    ::= { ip6EventObjects21 3 }

ip621-interface OBJECT-TYPE
    SYNTAX DisplayString
    MAX-ACCESS accessible-for-notify
    STATUS current
    DESCRIPTION
        "Parameter 'interface' in event IP6.21"
    ::= { ip6EventObjects21 4 }

ip6EventObjects22 OBJECT-IDENTITY
    STATUS current
    DESCRIPTION
        "Event IP6.22
        This message is generated when an IPv6 packet is processes."
    ::= { ip6EventsGroup 22 }

ip622-source-ip6-address OBJECT-TYPE
    SYNTAX DisplayString
    MAX-ACCESS accessible-for-notify
    STATUS current
    DESCRIPTION
        "Parameter 'source-ip6-address' in event IP6.22"
    ::= { ip6EventObjects22 1 }

ip622-destination-ip6-address OBJECT-TYPE
    SYNTAX DisplayString
    MAX-ACCESS accessible-for-notify
    STATUS current
    DESCRIPTION
        "Parameter 'destination-ip6-address' in event IP6.22"
    ::= { ip6EventObjects22 2 }

ip622-interface OBJECT-TYPE
    SYNTAX DisplayString
    MAX-ACCESS accessible-for-notify
    STATUS current
    DESCRIPTION
        "Parameter 'interface' in event IP6.22"
    ::= { ip6EventObjects22 3 }

ip6EventObjects23 OBJECT-IDENTITY
    STATUS current
    DESCRIPTION
        "Event IP6.23
        This message is generated when an extension header of a packet has
        been processed correctly."
    ::= { ip6EventsGroup 23 }

ip623-source-ip6-address OBJECT-TYPE
    SYNTAX DisplayString
    MAX-ACCESS accessible-for-notify
    STATUS current
    DESCRIPTION
        "Parameter 'source-ip6-address' in event IP6.23"
    ::= { ip6EventObjects23 1 }

ip623-destination-ip6-address OBJECT-TYPE
    SYNTAX DisplayString
    MAX-ACCESS accessible-for-notify
    STATUS current
    DESCRIPTION
        "Parameter 'destination-ip6-address' in event IP6.23"
    ::= { ip6EventObjects23 2 }

ip623-extension-header OBJECT-TYPE
    SYNTAX DisplayString
    MAX-ACCESS accessible-for-notify
    STATUS current
    DESCRIPTION
        "Parameter 'extension-header' in event IP6.23"
    ::= { ip6EventObjects23 3 }

ip6EventObjects24 OBJECT-IDENTITY
    STATUS current
    DESCRIPTION
        "Event IP6.24
        This message is generates when a pachet is discarded; it is shown the 
        cause why the packet is discarded."
    ::= { ip6EventsGroup 24 }

ip624-source-ip6-address OBJECT-TYPE
    SYNTAX DisplayString
    MAX-ACCESS accessible-for-notify
    STATUS current
    DESCRIPTION
        "Parameter 'source-ip6-address' in event IP6.24"
    ::= { ip6EventObjects24 1 }

ip624-destination-ip6-address OBJECT-TYPE
    SYNTAX DisplayString
    MAX-ACCESS accessible-for-notify
    STATUS current
    DESCRIPTION
        "Parameter 'destination-ip6-address' in event IP6.24"
    ::= { ip6EventObjects24 2 }

ip624-cause OBJECT-TYPE
    SYNTAX DisplayString
    MAX-ACCESS accessible-for-notify
    STATUS current
    DESCRIPTION
        "Parameter 'cause' in event IP6.24"
    ::= { ip6EventObjects24 3 }

ip6EventObjects25 OBJECT-IDENTITY
    STATUS current
    DESCRIPTION
        "Event IP6.25
        This message is generated when an IPv6 packet is finally transmitted."
    ::= { ip6EventsGroup 25 }

ip625-source-ip6-address OBJECT-TYPE
    SYNTAX DisplayString
    MAX-ACCESS accessible-for-notify
    STATUS current
    DESCRIPTION
        "Parameter 'source-ip6-address' in event IP6.25"
    ::= { ip6EventObjects25 1 }

ip625-destination-ip6-address OBJECT-TYPE
    SYNTAX DisplayString
    MAX-ACCESS accessible-for-notify
    STATUS current
    DESCRIPTION
        "Parameter 'destination-ip6-address' in event IP6.25"
    ::= { ip6EventObjects25 2 }

ip625-interface OBJECT-TYPE
    SYNTAX DisplayString
    MAX-ACCESS accessible-for-notify
    STATUS current
    DESCRIPTION
        "Parameter 'interface' in event IP6.25"
    ::= { ip6EventObjects25 3 }

ip6EventObjects70 OBJECT-IDENTITY
    STATUS current
    DESCRIPTION
        "Event IP6.70
        The link layer data of the IP routing cache entry for the listed
        destination has been cleared. The IP address corresponding to the
        cleared next-hop link layer data is also shown."
    ::= { ip6EventsGroup 70 }

ip670-destination-ip6-address OBJECT-TYPE
    SYNTAX DisplayString
    MAX-ACCESS accessible-for-notify
    STATUS current
    DESCRIPTION
        "Parameter 'destination-ip6-address' in event IP6.70"
    ::= { ip6EventObjects70 1 }

ip670-next-hop-ip6-address OBJECT-TYPE
    SYNTAX DisplayString
    MAX-ACCESS accessible-for-notify
    STATUS current
    DESCRIPTION
        "Parameter 'next-hop-ip6-address' in event IP6.70"
    ::= { ip6EventObjects70 2 }


ip6Notification1 NOTIFICATION-TYPE
    OBJECTS { 
              ip61-source-ip6-address, 
              ip61-destination-ip6-address,
              ip61-interface 
            }
    STATUS current
    DESCRIPTION
        "Notification of Event IP6.1

        Message: 'received packet from $1 for $2 interface $3'

        Parameters list:
              $1: ip61-source-ip6-address
              $2: ip61-destination-ip6-address
              $3: ip61-interface

        This message is generated when an IPv6 packet is received."
    ::= { ip6NotificationsPrefix 1 }

ip6Notification2 NOTIFICATION-TYPE
    OBJECTS { 
              ip62-source-ip6-address, 
              ip62-destination-ip6-address,
              ip62-interface 
            }
    STATUS current
    DESCRIPTION
        "Notification of Event IP6.2

        Message: 'Discarded packet from $1 for $2 interface $3, no IP6 on interface'

        Parameters list:
              $1: ip62-source-ip6-address
              $2: ip62-destination-ip6-address
              $3: ip62-interface

        This message is generated by the stub IP6 forwarder for each packet
        which is received on an interface for which IP is not enabled."
    ::= { ip6NotificationsPrefix 2 }

ip6Notification3 NOTIFICATION-TYPE
    OBJECTS { 
              ip63-source-ip6-address, 
              ip63-destination-ip6-address,
              ip63-version-number,
              ip63-interface 
            }
    STATUS current
    DESCRIPTION
        "Notification of Event IP6.3

        Message: 'Discarded packet from $1 for $2: bad version number ($3) in packet from interface $4'

        Parameters list:
              $1: ip63-source-ip6-address
              $2: ip63-destination-ip6-address
              $3: ip63-version-number
              $4: ip63-interface

        This message is generated when a packet has an incorrect version
        number."
    ::= { ip6NotificationsPrefix 3 }

ip6Notification4 NOTIFICATION-TYPE
    OBJECTS { 
              ip64-source-ip6-address, 
              ip64-destination-ip6-address,
              ip64-specified-length,
              ip64-true-length,
              ip64-interface 
            }
    STATUS current
    DESCRIPTION
        "Notification of Event IP6.4

        Message: 'Discarded packet from $1 for $2: packet truncated from $3 to $4 bytes interface $5'

        Parameters list:
              $1: ip64-source-ip6-address
              $2: ip64-destination-ip6-address
              $3: ip64-specified-length
              $4: ip64-true-length
              $5: ip64-interface

        This message is generated when the packet length specified in
        the header is greater than the packet buffer length."
    ::= { ip6NotificationsPrefix 4 }

ip6Notification5 NOTIFICATION-TYPE
    OBJECTS { 
              ip65-source-ip6-address, 
              ip65-destination-ip6-address,
              ip65-specified-length,
              ip65-true-length,
              ip65-interface 
            }
    STATUS current
    DESCRIPTION
        "Notification of Event IP6.5

        Message: 'Discarded packet from $1 for $2: too short length of $3 to $4 bytes interface $5'

        Parameters list:
              $1: ip65-source-ip6-address
              $2: ip65-destination-ip6-address
              $3: ip65-specified-length
              $4: ip65-true-length
              $5: ip65-interface

        This message is generated when a packet's indicated length
        is below the minimum possible length. The packet is discarded."
    ::= { ip6NotificationsPrefix 5 }

ip6Notification6 NOTIFICATION-TYPE
    OBJECTS { 
              ip66-source-ip6-address, 
              ip66-destination-ip6-address 
            }
    STATUS current
    DESCRIPTION
        "Notification of Event IP6.6

        Message: 'accept packet from $1 for $2'

        Parameters list:
              $1: ip66-source-ip6-address
              $2: ip66-destination-ip6-address

        This message is generated for each packet which has passed
        first-level reasonableness checks."
    ::= { ip6NotificationsPrefix 6 }

ip6Notification7 NOTIFICATION-TYPE
    OBJECTS { 
              ip67-source-ip6-address, 
              ip67-destination-ip6-address,
              ip67-packet-length 
            }
    STATUS current
    DESCRIPTION
        "Notification of Event IP6.7

        Message: 'Packet from $1 for $2 of length $3 requires fragmentation'

        Parameters list:
              $1: ip67-source-ip6-address
              $2: ip67-destination-ip6-address
              $3: ip67-packet-length

        This message is generated when an IP packet needs to be
        fragmented for transmission."
    ::= { ip6NotificationsPrefix 7 }

ip6Notification8 NOTIFICATION-TYPE
    OBJECTS { 
              ip68-source-ip6-address, 
              ip68-destination-ip6-address,
              ip68-protocol 
            }
    STATUS current
    DESCRIPTION
        "Notification of Event IP6.8

        Message: 'Multicast packet from $1, for $2, protocol $3 no reg'

        Parameters list:
              $1: ip68-source-ip6-address
              $2: ip68-destination-ip6-address
              $3: ip68-protocol

        This message is generated when a multicast packet arrives for an
        unknown protocol."
    ::= { ip6NotificationsPrefix 8 }

ip6Notification9 NOTIFICATION-TYPE
    OBJECTS { 
              ip69-source-ip6-address, 
              ip69-destination-ip6-address,
              ip69-protocol 
            }
    STATUS current
    DESCRIPTION
        "Notification of Event IP6.9

        Message: 'Packet from $1, for $2, protocol $3 not reg'

        Parameters list:
              $1: ip69-source-ip6-address
              $2: ip69-destination-ip6-address
              $3: ip69-protocol

        This message is generated when a packet arrives for an
        unknown protocol. The packet was destined for the router."
    ::= { ip6NotificationsPrefix 9 }

ip6Notification10 NOTIFICATION-TYPE
    OBJECTS { 
              ip610-protocol, 
              ip610-source-ip6-address 
            }
    STATUS current
    DESCRIPTION
        "Notification of Event IP6.10

        Message: 'Received packet for protocol $1 from $2'

        Parameters list:
              $1: ip610-protocol
              $2: ip610-source-ip6-address

        This message is generated for each packet destined for the router."
    ::= { ip6NotificationsPrefix 10 }

ip6Notification11 NOTIFICATION-TYPE
    OBJECTS { 
              ip611-destination-ip6-address 
            }
    STATUS current
    DESCRIPTION
        "Notification of Event IP6.11

        Message: 'Bad destination address $1'

        Parameters list:
              $1: ip611-destination-ip6-address

        This message is generated when a received packet's destination address
        is not valid. The packet is discarded."
    ::= { ip6NotificationsPrefix 11 }

ip6Notification12 NOTIFICATION-TYPE
    OBJECTS { 
              ip612-source-ip6-address, 
              ip612-destination-i6p-address 
            }
    STATUS current
    DESCRIPTION
        "Notification of Event IP6.12

        Message: 'Hop Limit zero on packet from $1 for $2'

        Parameters list:
              $1: ip612-source-ip6-address
              $2: ip612-destination-i6p-address

        This message is generated when a packet is discarded because its Hop
        Limit field is zero."
    ::= { ip6NotificationsPrefix 12 }

ip6Notification13 NOTIFICATION-TYPE
    OBJECTS { 
              ip613-source-ip6-address, 
              ip613-destination-ip6-address,
              ip613-extension-header 
            }
    STATUS current
    DESCRIPTION
        "Notification of Event IP6.13

        Message: 'Packet from $1 for $2: bad $3 header'

        Parameters list:
              $1: ip613-source-ip6-address
              $2: ip613-destination-ip6-address
              $3: ip613-extension-header

        This message is generated when a packet is discarded because one of its
        extension headers is not valid."
    ::= { ip6NotificationsPrefix 13 }

ip6Notification14 NOTIFICATION-TYPE
    OBJECTS { 
              ip614-source-ip6-address, 
              ip614-destination-ip6-address,
              ip614-extension-header 
            }
    STATUS current
    DESCRIPTION
        "Notification of Event IP6.14

        Message: 'Pachet from $1 for $2: OK $3 Header'

        Parameters list:
              $1: ip614-source-ip6-address
              $2: ip614-destination-ip6-address
              $3: ip614-extension-header

        This message is generated when an extension header of a packet has
        been processed correctly."
    ::= { ip6NotificationsPrefix 14 }

ip6Notification15 NOTIFICATION-TYPE
    OBJECTS { 
              ip615-source-ip6-address, 
              ip615-destination-ip6-address,
              ip615-interface 
            }
    STATUS current
    DESCRIPTION
        "Notification of Event IP6.15

        Message: 'Send packet from $1 for $2 interface $3'

        Parameters list:
              $1: ip615-source-ip6-address
              $2: ip615-destination-ip6-address
              $3: ip615-interface

        This message is generated when an IPv6 packet is sent to eth-out funtion."
    ::= { ip6NotificationsPrefix 15 }

ip6Notification16 NOTIFICATION-TYPE
    OBJECTS { 
              ip616-size-of-queue, 
              ip616-source-ip6-address,
              ip616-destination-ip6-address 
            }
    STATUS current
    DESCRIPTION
        "Notification of Event IP6.16

        Message: 'queue extern packet (ip6q: $1) from $2 for $3 '

        Parameters list:
              $1: ip616-size-of-queue
              $2: ip616-source-ip6-address
              $3: ip616-destination-ip6-address

        This message is generated when an extern IPv6 is queued."
    ::= { ip6NotificationsPrefix 16 }

ip6Notification17 NOTIFICATION-TYPE
    OBJECTS { 
              ip617-size-of-queue, 
              ip617-source-ip6-address,
              ip617-destination-ip6-address 
            }
    STATUS current
    DESCRIPTION
        "Notification of Event IP6.17

        Message: 'remove queue packet (ip6q: $1) from $2 for $3'

        Parameters list:
              $1: ip617-size-of-queue
              $2: ip617-source-ip6-address
              $3: ip617-destination-ip6-address

        This message is generated when an IPv6 packet is removed fron the queue."
    ::= { ip6NotificationsPrefix 17 }

ip6Notification18 NOTIFICATION-TYPE
    OBJECTS { 
              ip618-source-ip6-address, 
              ip618-destination-ip6-address,
              ip618-interface 
            }
    STATUS current
    DESCRIPTION
        "Notification of Event IP6.18

        Message: 'Process packet from $1 for $2 interface $3'

        Parameters list:
              $1: ip618-source-ip6-address
              $2: ip618-destination-ip6-address
              $3: ip618-interface

        This message is generated when an IPv6 packet is processes."
    ::= { ip6NotificationsPrefix 18 }

ip6Notification19 NOTIFICATION-TYPE
    OBJECTS { 
              ip619-size-of-queue, 
              ip619-source-ip6-address,
              ip619-destination-ip6-address 
            }
    STATUS current
    DESCRIPTION
        "Notification of Event IP6.19

        Message: 'queue intern packet (ip6q: $1) from $2 for $3'

        Parameters list:
              $1: ip619-size-of-queue
              $2: ip619-source-ip6-address
              $3: ip619-destination-ip6-address

        This message is generated when an intern IPv6 is queued."
    ::= { ip6NotificationsPrefix 19 }

ip6Notification20 NOTIFICATION-TYPE
    OBJECTS { 
              ip620-size-of-queue, 
              ip620-source-ip6-address,
              ip620-destination-ip6-address,
              ip620-interface 
            }
    STATUS current
    DESCRIPTION
        "Notification of Event IP6.20

        Message: 'queue extern packet (ip6lq: $1) from $2 for $3 interface $4'

        Parameters list:
              $1: ip620-size-of-queue
              $2: ip620-source-ip6-address
              $3: ip620-destination-ip6-address
              $4: ip620-interface

        This message is generated when an extern IPv6 is queued."
    ::= { ip6NotificationsPrefix 20 }

ip6Notification21 NOTIFICATION-TYPE
    OBJECTS { 
              ip621-size-of-queue, 
              ip621-source-ip6-address,
              ip621-destination-ip6-address,
              ip621-interface 
            }
    STATUS current
    DESCRIPTION
        "Notification of Event IP6.21

        Message: 'remove queue packet (ip6lq: $1) from $2 for $3 interface $4'

        Parameters list:
              $1: ip621-size-of-queue
              $2: ip621-source-ip6-address
              $3: ip621-destination-ip6-address
              $4: ip621-interface

        This message is generated when an IPv6 packet is removed fron the queue."
    ::= { ip6NotificationsPrefix 21 }

ip6Notification22 NOTIFICATION-TYPE
    OBJECTS { 
              ip622-source-ip6-address, 
              ip622-destination-ip6-address,
              ip622-interface 
            }
    STATUS current
    DESCRIPTION
        "Notification of Event IP6.22

        Message: 'Process packet from $1 for $2 interface $3'

        Parameters list:
              $1: ip622-source-ip6-address
              $2: ip622-destination-ip6-address
              $3: ip622-interface

        This message is generated when an IPv6 packet is processes."
    ::= { ip6NotificationsPrefix 22 }

ip6Notification23 NOTIFICATION-TYPE
    OBJECTS { 
              ip623-source-ip6-address, 
              ip623-destination-ip6-address,
              ip623-extension-header 
            }
    STATUS current
    DESCRIPTION
        "Notification of Event IP6.23

        Message: 'Packet from $1 for $2: $3 Header'

        Parameters list:
              $1: ip623-source-ip6-address
              $2: ip623-destination-ip6-address
              $3: ip623-extension-header

        This message is generated when an extension header of a packet has
        been processed correctly."
    ::= { ip6NotificationsPrefix 23 }

ip6Notification24 NOTIFICATION-TYPE
    OBJECTS { 
              ip624-source-ip6-address, 
              ip624-destination-ip6-address,
              ip624-cause 
            }
    STATUS current
    DESCRIPTION
        "Notification of Event IP6.24

        Message: 'Discard packet from $1 for $2 cause $3'

        Parameters list:
              $1: ip624-source-ip6-address
              $2: ip624-destination-ip6-address
              $3: ip624-cause

        This message is generates when a pachet is discarded; it is shown the 
        cause why the packet is discarded."
    ::= { ip6NotificationsPrefix 24 }

ip6Notification25 NOTIFICATION-TYPE
    OBJECTS { 
              ip625-source-ip6-address, 
              ip625-destination-ip6-address,
              ip625-interface 
            }
    STATUS current
    DESCRIPTION
        "Notification of Event IP6.25

        Message: 'Send packet $1 for $2 interface $3'

        Parameters list:
              $1: ip625-source-ip6-address
              $2: ip625-destination-ip6-address
              $3: ip625-interface

        This message is generated when an IPv6 packet is finally transmitted."
    ::= { ip6NotificationsPrefix 25 }

ip6Notification26 NOTIFICATION-TYPE
    STATUS current
    DESCRIPTION
        "Notification of Event IP6.26

        Message: '---'

        ???"
    ::= { ip6NotificationsPrefix 26 }

ip6Notification27 NOTIFICATION-TYPE
    STATUS current
    DESCRIPTION
        "Notification of Event IP6.27

        Message: '---'

        ???"
    ::= { ip6NotificationsPrefix 27 }

ip6Notification28 NOTIFICATION-TYPE
    STATUS current
    DESCRIPTION
        "Notification of Event IP6.28

        Message: '---'

        ???"
    ::= { ip6NotificationsPrefix 28 }

ip6Notification29 NOTIFICATION-TYPE
    STATUS current
    DESCRIPTION
        "Notification of Event IP6.29

        Message: '---'

        ???"
    ::= { ip6NotificationsPrefix 29 }

ip6Notification30 NOTIFICATION-TYPE
    STATUS current
    DESCRIPTION
        "Notification of Event IP6.30

        Message: '---'

        ???"
    ::= { ip6NotificationsPrefix 30 }

ip6Notification31 NOTIFICATION-TYPE
    STATUS current
    DESCRIPTION
        "Notification of Event IP6.31

        Message: '---'

        ???"
    ::= { ip6NotificationsPrefix 31 }

ip6Notification32 NOTIFICATION-TYPE
    STATUS current
    DESCRIPTION
        "Notification of Event IP6.32

        Message: '---'

        ???"
    ::= { ip6NotificationsPrefix 32 }

ip6Notification33 NOTIFICATION-TYPE
    STATUS current
    DESCRIPTION
        "Notification of Event IP6.33

        Message: '---'

        ???"
    ::= { ip6NotificationsPrefix 33 }

ip6Notification34 NOTIFICATION-TYPE
    STATUS current
    DESCRIPTION
        "Notification of Event IP6.34

        Message: '---'

        ???"
    ::= { ip6NotificationsPrefix 34 }

ip6Notification35 NOTIFICATION-TYPE
    STATUS current
    DESCRIPTION
        "Notification of Event IP6.35

        Message: '---'

        ???"
    ::= { ip6NotificationsPrefix 35 }

ip6Notification36 NOTIFICATION-TYPE
    STATUS current
    DESCRIPTION
        "Notification of Event IP6.36

        Message: '---'

        ???"
    ::= { ip6NotificationsPrefix 36 }

ip6Notification37 NOTIFICATION-TYPE
    STATUS current
    DESCRIPTION
        "Notification of Event IP6.37

        Message: '---'

        ???"
    ::= { ip6NotificationsPrefix 37 }

ip6Notification38 NOTIFICATION-TYPE
    STATUS current
    DESCRIPTION
        "Notification of Event IP6.38

        Message: '---'

        ???"
    ::= { ip6NotificationsPrefix 38 }

ip6Notification39 NOTIFICATION-TYPE
    STATUS current
    DESCRIPTION
        "Notification of Event IP6.39

        Message: '---'

        ???"
    ::= { ip6NotificationsPrefix 39 }

ip6Notification40 NOTIFICATION-TYPE
    STATUS current
    DESCRIPTION
        "Notification of Event IP6.40

        Message: '---'

        ???"
    ::= { ip6NotificationsPrefix 40 }

ip6Notification41 NOTIFICATION-TYPE
    STATUS current
    DESCRIPTION
        "Notification of Event IP6.41

        Message: '---'

        ???"
    ::= { ip6NotificationsPrefix 41 }

ip6Notification42 NOTIFICATION-TYPE
    STATUS current
    DESCRIPTION
        "Notification of Event IP6.42

        Message: '---'

        ???"
    ::= { ip6NotificationsPrefix 42 }

ip6Notification43 NOTIFICATION-TYPE
    STATUS current
    DESCRIPTION
        "Notification of Event IP6.43

        Message: '---'

        ???"
    ::= { ip6NotificationsPrefix 43 }

ip6Notification44 NOTIFICATION-TYPE
    STATUS current
    DESCRIPTION
        "Notification of Event IP6.44

        Message: '---'

        ???"
    ::= { ip6NotificationsPrefix 44 }

ip6Notification45 NOTIFICATION-TYPE
    STATUS current
    DESCRIPTION
        "Notification of Event IP6.45

        Message: '---'

        ???"
    ::= { ip6NotificationsPrefix 45 }

ip6Notification46 NOTIFICATION-TYPE
    STATUS current
    DESCRIPTION
        "Notification of Event IP6.46

        Message: '---'

        ???"
    ::= { ip6NotificationsPrefix 46 }

ip6Notification47 NOTIFICATION-TYPE
    STATUS current
    DESCRIPTION
        "Notification of Event IP6.47

        Message: '---'

        ???"
    ::= { ip6NotificationsPrefix 47 }

ip6Notification48 NOTIFICATION-TYPE
    STATUS current
    DESCRIPTION
        "Notification of Event IP6.48

        Message: '---'

        ???"
    ::= { ip6NotificationsPrefix 48 }

ip6Notification49 NOTIFICATION-TYPE
    STATUS current
    DESCRIPTION
        "Notification of Event IP6.49

        Message: '---'

        ???"
    ::= { ip6NotificationsPrefix 49 }

ip6Notification50 NOTIFICATION-TYPE
    STATUS current
    DESCRIPTION
        "Notification of Event IP6.50

        Message: '---'

        ???"
    ::= { ip6NotificationsPrefix 50 }

ip6Notification51 NOTIFICATION-TYPE
    STATUS current
    DESCRIPTION
        "Notification of Event IP6.51

        Message: '---'

        ???"
    ::= { ip6NotificationsPrefix 51 }

ip6Notification52 NOTIFICATION-TYPE
    STATUS current
    DESCRIPTION
        "Notification of Event IP6.52

        Message: '---'

        ???"
    ::= { ip6NotificationsPrefix 52 }

ip6Notification53 NOTIFICATION-TYPE
    STATUS current
    DESCRIPTION
        "Notification of Event IP6.53

        Message: '---'

        ???"
    ::= { ip6NotificationsPrefix 53 }

ip6Notification54 NOTIFICATION-TYPE
    STATUS current
    DESCRIPTION
        "Notification of Event IP6.54

        Message: '---'

        ???"
    ::= { ip6NotificationsPrefix 54 }

ip6Notification55 NOTIFICATION-TYPE
    STATUS current
    DESCRIPTION
        "Notification of Event IP6.55

        Message: '---'

        ???"
    ::= { ip6NotificationsPrefix 55 }

ip6Notification56 NOTIFICATION-TYPE
    STATUS current
    DESCRIPTION
        "Notification of Event IP6.56

        Message: '---'

        ???"
    ::= { ip6NotificationsPrefix 56 }

ip6Notification57 NOTIFICATION-TYPE
    STATUS current
    DESCRIPTION
        "Notification of Event IP6.57

        Message: '---'

        ???"
    ::= { ip6NotificationsPrefix 57 }

ip6Notification58 NOTIFICATION-TYPE
    STATUS current
    DESCRIPTION
        "Notification of Event IP6.58

        Message: '---'

        ???"
    ::= { ip6NotificationsPrefix 58 }

ip6Notification59 NOTIFICATION-TYPE
    STATUS current
    DESCRIPTION
        "Notification of Event IP6.59

        Message: '---'

        ???"
    ::= { ip6NotificationsPrefix 59 }

ip6Notification60 NOTIFICATION-TYPE
    STATUS current
    DESCRIPTION
        "Notification of Event IP6.60

        Message: '---'

        ???"
    ::= { ip6NotificationsPrefix 60 }

ip6Notification61 NOTIFICATION-TYPE
    STATUS current
    DESCRIPTION
        "Notification of Event IP6.61

        Message: '---'

        ???"
    ::= { ip6NotificationsPrefix 61 }

ip6Notification62 NOTIFICATION-TYPE
    STATUS current
    DESCRIPTION
        "Notification of Event IP6.62

        Message: '---'

        ???"
    ::= { ip6NotificationsPrefix 62 }

ip6Notification63 NOTIFICATION-TYPE
    STATUS current
    DESCRIPTION
        "Notification of Event IP6.63

        Message: '---'

        ???"
    ::= { ip6NotificationsPrefix 63 }

ip6Notification64 NOTIFICATION-TYPE
    STATUS current
    DESCRIPTION
        "Notification of Event IP6.64

        Message: '---'

        ???"
    ::= { ip6NotificationsPrefix 64 }

ip6Notification65 NOTIFICATION-TYPE
    STATUS current
    DESCRIPTION
        "Notification of Event IP6.65

        Message: '---'

        ???"
    ::= { ip6NotificationsPrefix 65 }

ip6Notification66 NOTIFICATION-TYPE
    STATUS current
    DESCRIPTION
        "Notification of Event IP6.66

        Message: '---'

        ???"
    ::= { ip6NotificationsPrefix 66 }

ip6Notification67 NOTIFICATION-TYPE
    STATUS current
    DESCRIPTION
        "Notification of Event IP6.67

        Message: '---'

        ???"
    ::= { ip6NotificationsPrefix 67 }

ip6Notification68 NOTIFICATION-TYPE
    STATUS current
    DESCRIPTION
        "Notification of Event IP6.68

        Message: '---'

        ???"
    ::= { ip6NotificationsPrefix 68 }

ip6Notification69 NOTIFICATION-TYPE
    STATUS current
    DESCRIPTION
        "Notification of Event IP6.69

        Message: '---'

        ???"
    ::= { ip6NotificationsPrefix 69 }

ip6Notification70 NOTIFICATION-TYPE
    OBJECTS { 
              ip670-destination-ip6-address, 
              ip670-next-hop-ip6-address 
            }
    STATUS current
    DESCRIPTION
        "Notification of Event IP6.70

        Message: 'routing cache entry for destination $1 via node $2 cleared'

        Parameters list:
              $1: ip670-destination-ip6-address
              $2: ip670-next-hop-ip6-address

        The link layer data of the IP routing cache entry for the listed
        destination has been cleared. The IP address corresponding to the
        cleared next-hop link layer data is also shown."
    ::= { ip6NotificationsPrefix 70 }

ip6Notification71 NOTIFICATION-TYPE
    STATUS current
    DESCRIPTION
        "Notification of Event IP6.71

        Message: '---'

        ???"
    ::= { ip6NotificationsPrefix 71 }

ip6Notification72 NOTIFICATION-TYPE
    STATUS current
    DESCRIPTION
        "Notification of Event IP6.72

        Message: '---'

        ???"
    ::= { ip6NotificationsPrefix 72 }

ip6Notification73 NOTIFICATION-TYPE
    STATUS current
    DESCRIPTION
        "Notification of Event IP6.73

        Message: '---'

        ???"
    ::= { ip6NotificationsPrefix 73 }

ip6Notification74 NOTIFICATION-TYPE
    STATUS current
    DESCRIPTION
        "Notification of Event IP6.74

        Message: '---'

        ???"
    ::= { ip6NotificationsPrefix 74 }

ip6Notification75 NOTIFICATION-TYPE
    STATUS current
    DESCRIPTION
        "Notification of Event IP6.75

        Message: '---'

        ???"
    ::= { ip6NotificationsPrefix 75 }

ip6Notification76 NOTIFICATION-TYPE
    STATUS current
    DESCRIPTION
        "Notification of Event IP6.76

        Message: '---'

        ???"
    ::= { ip6NotificationsPrefix 76 }

ip6Notification77 NOTIFICATION-TYPE
    STATUS current
    DESCRIPTION
        "Notification of Event IP6.77

        Message: '---'

        ???"
    ::= { ip6NotificationsPrefix 77 }

ip6Notification78 NOTIFICATION-TYPE
    STATUS current
    DESCRIPTION
        "Notification of Event IP6.78

        Message: '---'

        ???"
    ::= { ip6NotificationsPrefix 78 }

ip6Notification79 NOTIFICATION-TYPE
    STATUS current
    DESCRIPTION
        "Notification of Event IP6.79

        Message: '---'

        ???"
    ::= { ip6NotificationsPrefix 79 }

ip6Notification80 NOTIFICATION-TYPE
    STATUS current
    DESCRIPTION
        "Notification of Event IP6.80

        Message: '---'

        ???"
    ::= { ip6NotificationsPrefix 80 }

ip6Notification81 NOTIFICATION-TYPE
    STATUS current
    DESCRIPTION
        "Notification of Event IP6.81

        Message: '---'

        ???"
    ::= { ip6NotificationsPrefix 81 }

ip6Notification82 NOTIFICATION-TYPE
    STATUS current
    DESCRIPTION
        "Notification of Event IP6.82

        Message: '---'

        ???"
    ::= { ip6NotificationsPrefix 82 }

ip6Notification83 NOTIFICATION-TYPE
    STATUS current
    DESCRIPTION
        "Notification of Event IP6.83

        Message: '---'

        ???"
    ::= { ip6NotificationsPrefix 83 }

ip6Notification84 NOTIFICATION-TYPE
    STATUS current
    DESCRIPTION
        "Notification of Event IP6.84

        Message: '---'

        ???"
    ::= { ip6NotificationsPrefix 84 }

ip6Notification85 NOTIFICATION-TYPE
    STATUS current
    DESCRIPTION
        "Notification of Event IP6.85

        Message: '---'

        ???"
    ::= { ip6NotificationsPrefix 85 }

ip6Notification86 NOTIFICATION-TYPE
    STATUS current
    DESCRIPTION
        "Notification of Event IP6.86

        Message: '---'

        ???"
    ::= { ip6NotificationsPrefix 86 }

ip6Notification87 NOTIFICATION-TYPE
    STATUS current
    DESCRIPTION
        "Notification of Event IP6.87

        Message: '---'

        ???"
    ::= { ip6NotificationsPrefix 87 }

ip6Notification88 NOTIFICATION-TYPE
    STATUS current
    DESCRIPTION
        "Notification of Event IP6.88

        Message: '---'

        ???"
    ::= { ip6NotificationsPrefix 88 }

ip6Notification89 NOTIFICATION-TYPE
    STATUS current
    DESCRIPTION
        "Notification of Event IP6.89

        Message: '---'

        ???"
    ::= { ip6NotificationsPrefix 89 }

ip6Notification90 NOTIFICATION-TYPE
    STATUS current
    DESCRIPTION
        "Notification of Event IP6.90

        Message: '---'

        ???"
    ::= { ip6NotificationsPrefix 90 }

ip6Notification91 NOTIFICATION-TYPE
    STATUS current
    DESCRIPTION
        "Notification of Event IP6.91

        Message: '---'

        ???"
    ::= { ip6NotificationsPrefix 91 }

ip6Notification92 NOTIFICATION-TYPE
    STATUS current
    DESCRIPTION
        "Notification of Event IP6.92

        Message: '---'

        ???"
    ::= { ip6NotificationsPrefix 92 }

ip6Notification93 NOTIFICATION-TYPE
    STATUS current
    DESCRIPTION
        "Notification of Event IP6.93

        Message: '---'

        ???"
    ::= { ip6NotificationsPrefix 93 }

ip6Notification94 NOTIFICATION-TYPE
    STATUS current
    DESCRIPTION
        "Notification of Event IP6.94

        Message: '---'

        ???"
    ::= { ip6NotificationsPrefix 94 }

ip6Notification95 NOTIFICATION-TYPE
    STATUS current
    DESCRIPTION
        "Notification of Event IP6.95

        Message: '---'

        ???"
    ::= { ip6NotificationsPrefix 95 }

ip6Notification96 NOTIFICATION-TYPE
    STATUS current
    DESCRIPTION
        "Notification of Event IP6.96

        Message: '---'

        ???"
    ::= { ip6NotificationsPrefix 96 }

ip6Notification97 NOTIFICATION-TYPE
    STATUS current
    DESCRIPTION
        "Notification of Event IP6.97

        Message: '---'

        ???"
    ::= { ip6NotificationsPrefix 97 }

ip6Notification98 NOTIFICATION-TYPE
    STATUS current
    DESCRIPTION
        "Notification of Event IP6.98

        Message: '---'

        ???"
    ::= { ip6NotificationsPrefix 98 }

ip6Notification99 NOTIFICATION-TYPE
    STATUS current
    DESCRIPTION
        "Notification of Event IP6.99

        Message: '---'

        ???"
    ::= { ip6NotificationsPrefix 99 }

ip6Notification100 NOTIFICATION-TYPE
    STATUS current
    DESCRIPTION
        "Notification of Event IP6.100

        Message: '---'

        ???"
    ::= { ip6NotificationsPrefix 100 }

ip6Notification101 NOTIFICATION-TYPE
    STATUS current
    DESCRIPTION
        "Notification of Event IP6.101

        Message: '---'

        ???"
    ::= { ip6NotificationsPrefix 101 }

ip6Notification102 NOTIFICATION-TYPE
    STATUS current
    DESCRIPTION
        "Notification of Event IP6.102

        Message: '---'

        ???"
    ::= { ip6NotificationsPrefix 102 }

ip6Notification103 NOTIFICATION-TYPE
    STATUS current
    DESCRIPTION
        "Notification of Event IP6.103

        Message: '---'

        ???"
    ::= { ip6NotificationsPrefix 103 }

ip6Notification104 NOTIFICATION-TYPE
    STATUS current
    DESCRIPTION
        "Notification of Event IP6.104

        Message: '---'

        ???"
    ::= { ip6NotificationsPrefix 104 }

ip6Notification105 NOTIFICATION-TYPE
    STATUS current
    DESCRIPTION
        "Notification of Event IP6.105

        Message: '---'

        ???"
    ::= { ip6NotificationsPrefix 105 }

ip6Notification106 NOTIFICATION-TYPE
    STATUS current
    DESCRIPTION
        "Notification of Event IP6.106

        Message: '---'

        ???"
    ::= { ip6NotificationsPrefix 106 }

ip6Notification107 NOTIFICATION-TYPE
    STATUS current
    DESCRIPTION
        "Notification of Event IP6.107

        Message: '---'

        ???"
    ::= { ip6NotificationsPrefix 107 }

ip6Notification108 NOTIFICATION-TYPE
    STATUS current
    DESCRIPTION
        "Notification of Event IP6.108

        Message: '---'

        ???"
    ::= { ip6NotificationsPrefix 108 }

ip6Notification109 NOTIFICATION-TYPE
    STATUS current
    DESCRIPTION
        "Notification of Event IP6.109

        Message: '---'

        ???"
    ::= { ip6NotificationsPrefix 109 }

ip6Notification110 NOTIFICATION-TYPE
    STATUS current
    DESCRIPTION
        "Notification of Event IP6.110

        Message: '---'

        ???"
    ::= { ip6NotificationsPrefix 110 }

ip6Notification111 NOTIFICATION-TYPE
    STATUS current
    DESCRIPTION
        "Notification of Event IP6.111

        Message: '---'

        ???"
    ::= { ip6NotificationsPrefix 111 }

ip6Notification112 NOTIFICATION-TYPE
    STATUS current
    DESCRIPTION
        "Notification of Event IP6.112

        Message: '---'

        ???"
    ::= { ip6NotificationsPrefix 112 }

ip6Notification113 NOTIFICATION-TYPE
    STATUS current
    DESCRIPTION
        "Notification of Event IP6.113

        Message: '---'

        ???"
    ::= { ip6NotificationsPrefix 113 }

ip6Notification114 NOTIFICATION-TYPE
    STATUS current
    DESCRIPTION
        "Notification of Event IP6.114

        Message: '---'

        ???"
    ::= { ip6NotificationsPrefix 114 }

ip6Notification115 NOTIFICATION-TYPE
    STATUS current
    DESCRIPTION
        "Notification of Event IP6.115

        Message: '---'

        ???"
    ::= { ip6NotificationsPrefix 115 }

ip6Notification116 NOTIFICATION-TYPE
    STATUS current
    DESCRIPTION
        "Notification of Event IP6.116

        Message: '---'

        ???"
    ::= { ip6NotificationsPrefix 116 }

ip6Notification117 NOTIFICATION-TYPE
    STATUS current
    DESCRIPTION
        "Notification of Event IP6.117

        Message: '---'

        ???"
    ::= { ip6NotificationsPrefix 117 }

ip6Notification118 NOTIFICATION-TYPE
    STATUS current
    DESCRIPTION
        "Notification of Event IP6.118

        Message: '---'

        ???"
    ::= { ip6NotificationsPrefix 118 }

ip6Notification119 NOTIFICATION-TYPE
    STATUS current
    DESCRIPTION
        "Notification of Event IP6.119

        Message: '---'

        ???"
    ::= { ip6NotificationsPrefix 119 }

ip6Notification120 NOTIFICATION-TYPE
    STATUS current
    DESCRIPTION
        "Notification of Event IP6.120

        Message: '---'

        ???"
    ::= { ip6NotificationsPrefix 120 }

ip6Notification121 NOTIFICATION-TYPE
    STATUS current
    DESCRIPTION
        "Notification of Event IP6.121

        Message: '---'

        ???"
    ::= { ip6NotificationsPrefix 121 }

ip6Notification122 NOTIFICATION-TYPE
    STATUS current
    DESCRIPTION
        "Notification of Event IP6.122

        Message: '---'

        ???"
    ::= { ip6NotificationsPrefix 122 }

ip6Notification123 NOTIFICATION-TYPE
    STATUS current
    DESCRIPTION
        "Notification of Event IP6.123

        Message: '---'

        ???"
    ::= { ip6NotificationsPrefix 123 }

ip6Notification124 NOTIFICATION-TYPE
    STATUS current
    DESCRIPTION
        "Notification of Event IP6.124

        Message: '---'

        ???"
    ::= { ip6NotificationsPrefix 124 }

ip6Notification125 NOTIFICATION-TYPE
    STATUS current
    DESCRIPTION
        "Notification of Event IP6.125

        Message: '---'

        ???"
    ::= { ip6NotificationsPrefix 125 }

ip6Notification126 NOTIFICATION-TYPE
    STATUS current
    DESCRIPTION
        "Notification of Event IP6.126

        Message: '---'

        ???"
    ::= { ip6NotificationsPrefix 126 }

ip6Notification127 NOTIFICATION-TYPE
    STATUS current
    DESCRIPTION
        "Notification of Event IP6.127

        Message: '---'

        ???"
    ::= { ip6NotificationsPrefix 127 }

ip6Notification128 NOTIFICATION-TYPE
    STATUS current
    DESCRIPTION
        "Notification of Event IP6.128

        Message: '---'

        ???"
    ::= { ip6NotificationsPrefix 128 }

ip6Notification129 NOTIFICATION-TYPE
    STATUS current
    DESCRIPTION
        "Notification of Event IP6.129

        Message: '---'

        ???"
    ::= { ip6NotificationsPrefix 129 }

ip6Notification130 NOTIFICATION-TYPE
    STATUS current
    DESCRIPTION
        "Notification of Event IP6.130

        Message: '---'

        ???"
    ::= { ip6NotificationsPrefix 130 }

ip6Notification131 NOTIFICATION-TYPE
    STATUS current
    DESCRIPTION
        "Notification of Event IP6.131

        Message: '---'

        ???"
    ::= { ip6NotificationsPrefix 131 }

ip6Notification132 NOTIFICATION-TYPE
    STATUS current
    DESCRIPTION
        "Notification of Event IP6.132

        Message: '---'

        ???"
    ::= { ip6NotificationsPrefix 132 }

ip6Notification133 NOTIFICATION-TYPE
    STATUS current
    DESCRIPTION
        "Notification of Event IP6.133

        Message: '---'

        ???"
    ::= { ip6NotificationsPrefix 133 }

ip6Notification134 NOTIFICATION-TYPE
    STATUS current
    DESCRIPTION
        "Notification of Event IP6.134

        Message: '---'

        ???"
    ::= { ip6NotificationsPrefix 134 }

ip6Notification135 NOTIFICATION-TYPE
    STATUS current
    DESCRIPTION
        "Notification of Event IP6.135

        Message: '---'

        ???"
    ::= { ip6NotificationsPrefix 135 }

ip6Notification136 NOTIFICATION-TYPE
    STATUS current
    DESCRIPTION
        "Notification of Event IP6.136

        Message: '---'

        ???"
    ::= { ip6NotificationsPrefix 136 }

ip6Notification137 NOTIFICATION-TYPE
    STATUS current
    DESCRIPTION
        "Notification of Event IP6.137

        Message: '---'

        ???"
    ::= { ip6NotificationsPrefix 137 }

ip6Notification138 NOTIFICATION-TYPE
    STATUS current
    DESCRIPTION
        "Notification of Event IP6.138

        Message: '---'

        ???"
    ::= { ip6NotificationsPrefix 138 }

ip6Notification139 NOTIFICATION-TYPE
    STATUS current
    DESCRIPTION
        "Notification of Event IP6.139

        Message: '---'

        ???"
    ::= { ip6NotificationsPrefix 139 }

ip6Notification140 NOTIFICATION-TYPE
    STATUS current
    DESCRIPTION
        "Notification of Event IP6.140

        Message: '---'

        ???"
    ::= { ip6NotificationsPrefix 140 }

ip6Notification141 NOTIFICATION-TYPE
    STATUS current
    DESCRIPTION
        "Notification of Event IP6.141

        Message: '---'

        ???"
    ::= { ip6NotificationsPrefix 141 }

ip6Notification142 NOTIFICATION-TYPE
    STATUS current
    DESCRIPTION
        "Notification of Event IP6.142

        Message: '---'

        ???"
    ::= { ip6NotificationsPrefix 142 }

ip6Notification143 NOTIFICATION-TYPE
    STATUS current
    DESCRIPTION
        "Notification of Event IP6.143

        Message: '---'

        ???"
    ::= { ip6NotificationsPrefix 143 }

ip6Notification144 NOTIFICATION-TYPE
    STATUS current
    DESCRIPTION
        "Notification of Event IP6.144

        Message: '---'

        ???"
    ::= { ip6NotificationsPrefix 144 }

ip6Notification145 NOTIFICATION-TYPE
    STATUS current
    DESCRIPTION
        "Notification of Event IP6.145

        Message: '---'

        ???"
    ::= { ip6NotificationsPrefix 145 }

ip6Notification146 NOTIFICATION-TYPE
    STATUS current
    DESCRIPTION
        "Notification of Event IP6.146

        Message: '---'

        ???"
    ::= { ip6NotificationsPrefix 146 }

ip6Notification147 NOTIFICATION-TYPE
    STATUS current
    DESCRIPTION
        "Notification of Event IP6.147

        Message: '---'

        ???"
    ::= { ip6NotificationsPrefix 147 }

ip6Notification148 NOTIFICATION-TYPE
    STATUS current
    DESCRIPTION
        "Notification of Event IP6.148

        Message: '---'

        ???"
    ::= { ip6NotificationsPrefix 148 }

ip6Notification149 NOTIFICATION-TYPE
    STATUS current
    DESCRIPTION
        "Notification of Event IP6.149

        Message: '---'

        ???"
    ::= { ip6NotificationsPrefix 149 }

ip6Notification150 NOTIFICATION-TYPE
    STATUS current
    DESCRIPTION
        "Notification of Event IP6.150

        Message: '---'

        ???"
    ::= { ip6NotificationsPrefix 150 }

ip6Notification151 NOTIFICATION-TYPE
    STATUS current
    DESCRIPTION
        "Notification of Event IP6.151

        Message: '---'

        ???"
    ::= { ip6NotificationsPrefix 151 }

ip6Notification152 NOTIFICATION-TYPE
    STATUS current
    DESCRIPTION
        "Notification of Event IP6.152

        Message: '---'

        ???"
    ::= { ip6NotificationsPrefix 152 }

ip6Notification153 NOTIFICATION-TYPE
    STATUS current
    DESCRIPTION
        "Notification of Event IP6.153

        Message: '---'

        ???"
    ::= { ip6NotificationsPrefix 153 }

ip6Notification154 NOTIFICATION-TYPE
    STATUS current
    DESCRIPTION
        "Notification of Event IP6.154

        Message: '---'

        ???"
    ::= { ip6NotificationsPrefix 154 }

ip6Notification155 NOTIFICATION-TYPE
    STATUS current
    DESCRIPTION
        "Notification of Event IP6.155

        Message: '---'

        ???"
    ::= { ip6NotificationsPrefix 155 }

ip6Notification156 NOTIFICATION-TYPE
    STATUS current
    DESCRIPTION
        "Notification of Event IP6.156

        Message: '---'

        ???"
    ::= { ip6NotificationsPrefix 156 }

ip6Notification157 NOTIFICATION-TYPE
    STATUS current
    DESCRIPTION
        "Notification of Event IP6.157

        Message: '---'

        ???"
    ::= { ip6NotificationsPrefix 157 }

ip6Notification158 NOTIFICATION-TYPE
    STATUS current
    DESCRIPTION
        "Notification of Event IP6.158

        Message: '---'

        ???"
    ::= { ip6NotificationsPrefix 158 }

ip6Notification159 NOTIFICATION-TYPE
    STATUS current
    DESCRIPTION
        "Notification of Event IP6.159

        Message: '---'

        ???"
    ::= { ip6NotificationsPrefix 159 }

ip6Notification160 NOTIFICATION-TYPE
    STATUS current
    DESCRIPTION
        "Notification of Event IP6.160

        Message: '---'

        ???"
    ::= { ip6NotificationsPrefix 160 }

ip6Notification161 NOTIFICATION-TYPE
    STATUS current
    DESCRIPTION
        "Notification of Event IP6.161

        Message: '---'

        ???"
    ::= { ip6NotificationsPrefix 161 }

ip6Notification162 NOTIFICATION-TYPE
    STATUS current
    DESCRIPTION
        "Notification of Event IP6.162

        Message: '---'

        ???"
    ::= { ip6NotificationsPrefix 162 }

ip6Notification163 NOTIFICATION-TYPE
    STATUS current
    DESCRIPTION
        "Notification of Event IP6.163

        Message: '---'

        ???"
    ::= { ip6NotificationsPrefix 163 }

ip6Notification164 NOTIFICATION-TYPE
    STATUS current
    DESCRIPTION
        "Notification of Event IP6.164

        Message: '---'

        ???"
    ::= { ip6NotificationsPrefix 164 }

ip6Notification165 NOTIFICATION-TYPE
    STATUS current
    DESCRIPTION
        "Notification of Event IP6.165

        Message: '---'

        ???"
    ::= { ip6NotificationsPrefix 165 }

ip6Notification166 NOTIFICATION-TYPE
    STATUS current
    DESCRIPTION
        "Notification of Event IP6.166

        Message: '---'

        ???"
    ::= { ip6NotificationsPrefix 166 }

ip6Notification167 NOTIFICATION-TYPE
    STATUS current
    DESCRIPTION
        "Notification of Event IP6.167

        Message: '---'

        ???"
    ::= { ip6NotificationsPrefix 167 }

ip6Notification168 NOTIFICATION-TYPE
    STATUS current
    DESCRIPTION
        "Notification of Event IP6.168

        Message: '---'

        ???"
    ::= { ip6NotificationsPrefix 168 }

ip6Notification169 NOTIFICATION-TYPE
    STATUS current
    DESCRIPTION
        "Notification of Event IP6.169

        Message: '---'

        ???"
    ::= { ip6NotificationsPrefix 169 }

ip6Notification170 NOTIFICATION-TYPE
    STATUS current
    DESCRIPTION
        "Notification of Event IP6.170

        Message: '---'

        ???"
    ::= { ip6NotificationsPrefix 170 }

ip6Notification171 NOTIFICATION-TYPE
    STATUS current
    DESCRIPTION
        "Notification of Event IP6.171

        Message: '---'

        ???"
    ::= { ip6NotificationsPrefix 171 }

ip6Notification172 NOTIFICATION-TYPE
    STATUS current
    DESCRIPTION
        "Notification of Event IP6.172

        Message: '---'

        ???"
    ::= { ip6NotificationsPrefix 172 }

ip6Notification173 NOTIFICATION-TYPE
    STATUS current
    DESCRIPTION
        "Notification of Event IP6.173

        Message: '---'

        ???"
    ::= { ip6NotificationsPrefix 173 }

ip6Notification174 NOTIFICATION-TYPE
    STATUS current
    DESCRIPTION
        "Notification of Event IP6.174

        Message: '---'

        ???"
    ::= { ip6NotificationsPrefix 174 }

ip6Notification175 NOTIFICATION-TYPE
    STATUS current
    DESCRIPTION
        "Notification of Event IP6.175

        Message: '---'

        ???"
    ::= { ip6NotificationsPrefix 175 }

ip6Notification176 NOTIFICATION-TYPE
    STATUS current
    DESCRIPTION
        "Notification of Event IP6.176

        Message: '---'

        ???"
    ::= { ip6NotificationsPrefix 176 }

ip6Notification177 NOTIFICATION-TYPE
    STATUS current
    DESCRIPTION
        "Notification of Event IP6.177

        Message: '---'

        ???"
    ::= { ip6NotificationsPrefix 177 }

ip6Notification178 NOTIFICATION-TYPE
    STATUS current
    DESCRIPTION
        "Notification of Event IP6.178

        Message: '---'

        ???"
    ::= { ip6NotificationsPrefix 178 }

ip6Notification179 NOTIFICATION-TYPE
    STATUS current
    DESCRIPTION
        "Notification of Event IP6.179

        Message: '---'

        ???"
    ::= { ip6NotificationsPrefix 179 }

ip6Notification180 NOTIFICATION-TYPE
    STATUS current
    DESCRIPTION
        "Notification of Event IP6.180

        Message: '---'

        ???"
    ::= { ip6NotificationsPrefix 180 }

ip6Notification181 NOTIFICATION-TYPE
    STATUS current
    DESCRIPTION
        "Notification of Event IP6.181

        Message: '---'

        ???"
    ::= { ip6NotificationsPrefix 181 }

ip6Notification182 NOTIFICATION-TYPE
    STATUS current
    DESCRIPTION
        "Notification of Event IP6.182

        Message: '---'

        ???"
    ::= { ip6NotificationsPrefix 182 }

ip6Notification183 NOTIFICATION-TYPE
    STATUS current
    DESCRIPTION
        "Notification of Event IP6.183

        Message: '---'

        ???"
    ::= { ip6NotificationsPrefix 183 }

ip6Notification184 NOTIFICATION-TYPE
    STATUS current
    DESCRIPTION
        "Notification of Event IP6.184

        Message: '---'

        ???"
    ::= { ip6NotificationsPrefix 184 }

ip6Notification185 NOTIFICATION-TYPE
    STATUS current
    DESCRIPTION
        "Notification of Event IP6.185

        Message: '---'

        ???"
    ::= { ip6NotificationsPrefix 185 }

ip6Notification186 NOTIFICATION-TYPE
    STATUS current
    DESCRIPTION
        "Notification of Event IP6.186

        Message: '---'

        ???"
    ::= { ip6NotificationsPrefix 186 }

ip6Notification187 NOTIFICATION-TYPE
    STATUS current
    DESCRIPTION
        "Notification of Event IP6.187

        Message: '---'

        ???"
    ::= { ip6NotificationsPrefix 187 }

ip6Notification188 NOTIFICATION-TYPE
    STATUS current
    DESCRIPTION
        "Notification of Event IP6.188

        Message: '---'

        ???"
    ::= { ip6NotificationsPrefix 188 }

ip6Notification189 NOTIFICATION-TYPE
    STATUS current
    DESCRIPTION
        "Notification of Event IP6.189

        Message: '---'

        ???"
    ::= { ip6NotificationsPrefix 189 }

ip6Notification190 NOTIFICATION-TYPE
    STATUS current
    DESCRIPTION
        "Notification of Event IP6.190

        Message: '---'

        ???"
    ::= { ip6NotificationsPrefix 190 }

ip6Notification191 NOTIFICATION-TYPE
    STATUS current
    DESCRIPTION
        "Notification of Event IP6.191

        Message: '---'

        ???"
    ::= { ip6NotificationsPrefix 191 }

ip6Notification192 NOTIFICATION-TYPE
    STATUS current
    DESCRIPTION
        "Notification of Event IP6.192

        Message: '---'

        ???"
    ::= { ip6NotificationsPrefix 192 }

ip6Notification193 NOTIFICATION-TYPE
    STATUS current
    DESCRIPTION
        "Notification of Event IP6.193

        Message: '---'

        ???"
    ::= { ip6NotificationsPrefix 193 }

ip6Notification194 NOTIFICATION-TYPE
    STATUS current
    DESCRIPTION
        "Notification of Event IP6.194

        Message: '---'

        ???"
    ::= { ip6NotificationsPrefix 194 }

ip6Notification195 NOTIFICATION-TYPE
    STATUS current
    DESCRIPTION
        "Notification of Event IP6.195

        Message: '---'

        ???"
    ::= { ip6NotificationsPrefix 195 }

ip6Notification196 NOTIFICATION-TYPE
    STATUS current
    DESCRIPTION
        "Notification of Event IP6.196

        Message: '---'

        ???"
    ::= { ip6NotificationsPrefix 196 }

ip6Notification197 NOTIFICATION-TYPE
    STATUS current
    DESCRIPTION
        "Notification of Event IP6.197

        Message: '---'

        ???"
    ::= { ip6NotificationsPrefix 197 }

ip6Notification198 NOTIFICATION-TYPE
    STATUS current
    DESCRIPTION
        "Notification of Event IP6.198

        Message: '---'

        ???"
    ::= { ip6NotificationsPrefix 198 }

ip6Notification199 NOTIFICATION-TYPE
    STATUS current
    DESCRIPTION
        "Notification of Event IP6.199

        Message: '---'

        ???"
    ::= { ip6NotificationsPrefix 199 }

ip6Notification200 NOTIFICATION-TYPE
    STATUS current
    DESCRIPTION
        "Notification of Event IP6.200

        Message: '---'

        ???"
    ::= { ip6NotificationsPrefix 200 }


END
