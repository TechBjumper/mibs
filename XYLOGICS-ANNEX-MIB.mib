--                                                                             
 --	Xylogics Annex Private Enterprise MIB                                       
 --                                                                             
 --	Copyright 1989, Xylogics, Inc.  ALL RIGHTS RESERVED.                        
 --                                                                             
 --	ALL RIGHTS RESERVED. Licensed Material - Property of Xylogics, Inc.         
 --	This software is made available solely pursuant to the terms of a           
 --	software license agreement which governs its use.                           
 --	Unauthorized duplication, distribution or sale are strictly prohibited.     
 --                                                                             
 --	This information is subject to change without notice, and should            
 --	not be construed as a commitment by Xylogics, Inc.  Xylogics, Inc.,         
 --	assumes no responsibility for any errors that may appear in this            
 --	document.                                                                   
 --                                                                             
 --	$Id: annex-mib.txt,v 1.9 91/04/17 10:43:55 barnes REL $                     
 --                                                                             
                                                                                
 -- overview                                                                    
                                                                                
  XYLOGICS-ANNEX-MIB DEFINITIONS ::= BEGIN                                      
                                                                                
   IMPORTS                                                                      
                 enterprises, NetworkAddress, IpAddress,                        
                                 Counter, Gauge, TimeTicks                      
                         FROM RFC1155-SMI                                       
                 OBJECT-TYPE                                                    
                         FROM RFC-1212;                                         
                                                                                
   xylogics	OBJECT IDENTIFIER ::= { enterprises 15 }                            
                                                                                
   prod		OBJECT IDENTIFIER ::= { xylogics 1 }                                   
   prodannex	OBJECT-TYPE                                                        
 		SYNTAX OCTET STRING                                                          
 		ACCESS read-only                                                             
 		STATUS mandatory                                                             
DESCRIPTION ""
 		::= { prod 1 }                                                               
                                                                                
   annex		OBJECT IDENTIFIER ::= { xylogics 2 }                                  
                                                                                
   hw		OBJECT IDENTIFIER ::= { annex 1 }                                        
   sw		OBJECT IDENTIFIER ::= { annex 2 }                                        
   ports		OBJECT IDENTIFIER ::= { annex 3 }                                     
                                                                                
 -- the hw group                                                                
                                                                                
   hwType	OBJECT-TYPE                                                           
 		SYNTAX INTEGER {                                                             
 			err(1),                                                                     
 			annexI(11),                                                                 
 			annexII(16),                                                                
 			annexX25(23),                                                               
 			annex3(42),
 
                        microannex(52)
                                                                  
 		}                                                                            
 		ACCESS read-only                                                             
 		STATUS mandatory                                                             
DESCRIPTION ""
 		::= { hw 1 }                                                                 
                                                                                
   hwRev		OBJECT-TYPE                                                           
 		SYNTAX OCTET STRING                                                          
 		ACCESS read-only                                                             
 		STATUS mandatory                                                             
DESCRIPTION ""
 		::= { hw 2 }                                                                 
                                                                                
   romRev	OBJECT-TYPE                                                           
   		-- Note: old Annex-Is cannot return this value                             
 		SYNTAX OCTET STRING                                                          
 		ACCESS read-only                                                             
 		STATUS mandatory                                                             
DESCRIPTION ""
 		::= { hw 3 }                                                                 
                                                                                
   serialNumber	OBJECT-TYPE                                                     
 		SYNTAX INTEGER                                                               
 		ACCESS read-only                                                             
 		STATUS mandatory                                                             
DESCRIPTION ""
 		::= { hw 4 }                                                                 
                                                                                
   memorySize	OBJECT-TYPE                                                       
 		SYNTAX INTEGER                                                               
 		ACCESS read-only                                                             
 		STATUS mandatory                                                             
DESCRIPTION ""
 		::= { hw 5 }                                                                 
                                                                                
 -- the sw group                                                                
                                                                                
   swType	OBJECT-TYPE                                                           
 		SYNTAX INTEGER {                                                             
 			err(1),                                                                     
 			annexImx(11),                                                               
 			annexIux(13),                                                               
 			annexIImx(16),                                                              
 			annexIIux(17),                                                              
 			annexX25(23),                                                               
 			annex3ux(42),                                                               
 			annex3mx(43),                                                                
                        microannexux(52)
 		}                                                                            
 		ACCESS read-only                                                             
 		STATUS mandatory                                                             
DESCRIPTION ""
 		::= { sw 1 }                                                                 
                                                                                
   swRevMajor	OBJECT-TYPE                                                       
 		SYNTAX INTEGER                                                               
 		ACCESS read-only                                                             
 		STATUS mandatory                                                             
DESCRIPTION ""
 		::= { sw 2 }                                                                 
                                                                                
   swRevMinor	OBJECT-TYPE                                                       
 		SYNTAX INTEGER                                                               
 		ACCESS read-only                                                             
 		STATUS mandatory                                                             
DESCRIPTION ""
 		::= { sw 3 }                                                                 
                                                                                
   swBuild	OBJECT-TYPE                                                          
 		SYNTAX OCTET STRING                                                          
 		ACCESS read-only                                                             
 		STATUS mandatory                                                             
DESCRIPTION ""
 		::= { sw 4 }                                                                 
                                                                                
   imageName	OBJECT-TYPE                                                        
   		-- Note: old Annex-Is cannot return this value                             
 		SYNTAX OCTET STRING                                                          
 		ACCESS read-only                                                             
 		STATUS mandatory                                                             
DESCRIPTION ""
 		::= { sw 5 }                                                                 
                                                                                
   bootHost	OBJECT-TYPE                                                         
   		-- Note: old Annex-Is cannot return this value                             
 		SYNTAX IpAddress                                                             
 		ACCESS read-only                                                             
 		STATUS mandatory                                                             
DESCRIPTION ""
 		::= { sw 6 }                                                                 
                                                                                
   defaultDomain	OBJECT-TYPE                                                    
 		SYNTAX OCTET STRING                                                          
 		ACCESS read-only                                                             
 		STATUS mandatory                                                             
DESCRIPTION ""
 		::= { sw 7 }                                                                 
                                                                                
   currentDate	OBJECT-TYPE                                                      
 		SYNTAX OCTET STRING                                                          
 		ACCESS read-only                                                             
 		STATUS mandatory                                                             
DESCRIPTION ""
 		::= { sw 8 }                                                                 
                                                                                
   usableMemory	OBJECT-TYPE                                                     
 		SYNTAX INTEGER                                                               
 		ACCESS read-only                                                             
 		STATUS mandatory                                                             
DESCRIPTION ""
 		::= { sw 9 }                                                                 
                                                                                
   freeMemory	OBJECT-TYPE                                                       
 		SYNTAX Gauge                                                                 
 		ACCESS read-only                                                             
 		STATUS mandatory                                                             
DESCRIPTION ""
 		::= { sw 10 }                                                                
                                                                                
   minFreeMemory	OBJECT-TYPE                                                    
 		SYNTAX INTEGER                                                               
 		ACCESS read-only                                                             
 		STATUS mandatory                                                             
DESCRIPTION ""
 		::= { sw 11 }                                                                
                                                                                
   cpuUtilization	OBJECT-TYPE                                                   
 		SYNTAX Gauge                                                                 
 		ACCESS read-only                                                             
 		STATUS mandatory                                                             
DESCRIPTION ""
 		::= { sw 12 }                                                                
                                                                                
   maxProcs	OBJECT-TYPE                                                         
 		SYNTAX INTEGER                                                               
 		ACCESS read-only                                                             
 		STATUS mandatory                                                             
DESCRIPTION ""
 		::= { sw 13 }                                                                
                                                                                
   mostProcs	OBJECT-TYPE                                                        
 		SYNTAX INTEGER                                                               
 		ACCESS read-only                                                             
 		STATUS mandatory                                                             
DESCRIPTION ""
 		::= { sw 14 }                                                                
                                                                                
   activeProcs	OBJECT-TYPE                                                      
 		SYNTAX Gauge                                                                 
 		ACCESS read-only                                                             
 		STATUS mandatory                                                             
DESCRIPTION ""
 		::= { sw 15 }                                                                
                                                                                
   cpuReschedsI	OBJECT-TYPE                                                     
 		SYNTAX Gauge                                                                 
 		ACCESS read-only                                                             
 		STATUS mandatory                                                             
DESCRIPTION ""
 		::= { sw 16 }                                                                
                                                                                
   cpuReschedsT	OBJECT-TYPE                                                     
 		SYNTAX Counter                                                               
 		ACCESS read-only                                                             
 		STATUS mandatory                                                             
DESCRIPTION ""
 		::= { sw 17 }                                                                
                                                                                
   contextSwI	OBJECT-TYPE                                                       
 		SYNTAX Gauge                                                                 
 		ACCESS read-only                                                             
 		STATUS mandatory                                                             
DESCRIPTION ""
 		::= { sw 18 }                                                                
                                                                                
   contextSwT	OBJECT-TYPE                                                       
 		SYNTAX Counter                                                               
 		ACCESS read-only                                                             
 		STATUS mandatory                                                             
DESCRIPTION ""
 		::= { sw 19 }                                                                
                                                                                
   cpuActivatesI	OBJECT-TYPE                                                    
 		SYNTAX Gauge                                                                 
 		ACCESS read-only                                                             
 		STATUS mandatory                                                             
DESCRIPTION ""
 		::= { sw 20 }                                                                
                                                                                
   cpuActivatesT	OBJECT-TYPE                                                    
 		SYNTAX Counter                                                               
 		ACCESS read-only                                                             
 		STATUS mandatory                                                             
DESCRIPTION ""
 		::= { sw 21 }                                                                
 	                                                                              
   cBlocksTotal	OBJECT-TYPE                                                     
 		SYNTAX INTEGER                                                               
 		ACCESS read-only                                                             
 		STATUS mandatory                                                             
DESCRIPTION ""
 		::= { sw 22 }                                                                
 	                                                                              
   cBlocksFree	OBJECT-TYPE                                                      
 		SYNTAX INTEGER                                                               
 		ACCESS read-only                                                             
 		STATUS mandatory                                                             
DESCRIPTION ""
 		::= { sw 23 }                                                                
 	                                                                              
   cBlocksMinFree	OBJECT-TYPE                                                   
 		SYNTAX INTEGER                                                               
 		ACCESS read-only                                                             
 		STATUS mandatory                                                             
DESCRIPTION ""
 		::= { sw 24 }                                                                
 	                                                                              
   cBlocksDenied	OBJECT-TYPE                                                    
 		SYNTAX Counter                                                               
 		ACCESS read-only                                                             
 		STATUS mandatory                                                             
DESCRIPTION ""
 		::= { sw 25 }                                                                
                                                                                
   maxCallouts	OBJECT-TYPE                                                      
 		SYNTAX INTEGER                                                               
 		ACCESS read-only                                                             
 		STATUS mandatory                                                             
DESCRIPTION ""
 		::= { sw 26 }                                                                
                                                                                
   leastCallouts	OBJECT-TYPE                                                    
 		SYNTAX INTEGER                                                               
 		ACCESS read-only                                                             
 		STATUS mandatory                                                             
DESCRIPTION ""
 		::= { sw 27 }                                                                
                                                                                
   freeCallouts	OBJECT-TYPE                                                     
 		SYNTAX Gauge                                                                 
 		ACCESS read-only                                                             
 		STATUS mandatory                                                             
DESCRIPTION ""
 		::= { sw 28 }                                                                
                                                                                
 -- the ports group                                                             
                                                                                
   totalPorts	OBJECT-TYPE                                                       
 		SYNTAX INTEGER                                                               
 		ACCESS read-only                                                             
 		STATUS mandatory                                                             
DESCRIPTION ""
 		::= { ports 1 }                                                              
                                                                                
   totalCharsIn	OBJECT-TYPE                                                     
 		SYNTAX Counter                                                               
 		ACCESS read-only                                                             
 		STATUS mandatory                                                             
DESCRIPTION ""
 		::= { ports 2 }                                                              
                                                                                
   totalCharsOut	OBJECT-TYPE                                                    
 		SYNTAX Counter                                                               
 		ACCESS read-only                                                             
 		STATUS mandatory                                                             
DESCRIPTION ""
 		::= { ports 3 }                                                              
                                                                                
   totalErrsParity	OBJECT-TYPE                                                  
 		SYNTAX Counter                                                               
 		ACCESS read-only                                                             
 		STATUS mandatory                                                             
DESCRIPTION ""
 		::= { ports 4 }                                                              
                                                                                
   totalErrsOverrun	OBJECT-TYPE                                                 
 		SYNTAX Counter                                                               
 		ACCESS read-only                                                             
 		STATUS mandatory                                                             
DESCRIPTION ""
 		::= { ports 5 }                                                              
                                                                                
   totalErrsFraming	OBJECT-TYPE                                                 
 		SYNTAX Counter                                                               
 		ACCESS read-only                                                             
 		STATUS mandatory                                                             
DESCRIPTION ""
 		::= { ports 6 }                                                              
                                                                                
   portTable	OBJECT-TYPE                                                        
 		SYNTAX SEQUENCE OF PortEntry                                                 
 		ACCESS not-accessible                                                        
 		STATUS mandatory                                                             
DESCRIPTION ""
 		::= { ports 7 }                                                              
                                                                                
   portEntry	OBJECT-TYPE                                                        
 		SYNTAX PortEntry                                                             
 		ACCESS not-accessible                                                        
 		STATUS mandatory                                                             
DESCRIPTION ""
 		::= { portTable 1 }                                                          
                                                                                
   PortEntry	::= SEQUENCE {                                                     
 	portIndex	INTEGER,                                                            
 	iSpeed		INTEGER,                                                              
 	oSpeed		INTEGER,                                                              
 	ctrlLines	INTEGER,                                                            
 	flowTypeIn	INTEGER,                                                           
 	flowTypeOut	INTEGER,                                                          
 	bitsPerChar	INTEGER,                                                          
 	stopBits	INTEGER,                                                             
 	parity		INTEGER,                                                              
 	modemDCD	INTEGER,                                                             
 	modemDTR	INTEGER,                                                             
 	modemCTS	INTEGER,                                                             
 	modemRTS	INTEGER,                                                             
 	charsIn		Counter,                                                             
 	charsOut	Counter,                                                             
 	errsParity	Counter,                                                           
 	errsOverrun	Counter,                                                          
 	errsFraming	Counter,                                                          
 	inCC		Gauge,                                                                  
 	outCC		Gauge                                                                  
   }                                                                            
                                                                                
   portIndex	OBJECT-TYPE                                                        
 		SYNTAX INTEGER                                                               
 		ACCESS read-only                                                             
 		STATUS mandatory                                                             
DESCRIPTION ""
 		::= { portEntry 1 }                                                          
                                                                                
   iSpeed	OBJECT-TYPE                                                           
 		SYNTAX INTEGER                                                               
 			-- 50(1), 75(2), 110(3), 134(4), 150(5), 200(6), 300(7),                    
 			-- 600(8), 1200(9), 1800(10), 2000(11), 2400(12),                           
 			-- 3600(13), 4800(14), 7200(15), 9600(16), 19200(17),                       
 			-- 38400(18), idle(254), autobaud(255)                                      
 		ACCESS read-only                                                             
 		STATUS mandatory                                                             
DESCRIPTION ""
 		::= { portEntry 2 }                                                          
 	                                                                              
   oSpeed	OBJECT-TYPE                                                           
 		SYNTAX INTEGER                                                               
 			-- 50(1), 75(2), 110(3), 134(4), 150(5), 200(6), 300(7),                    
 			-- 600(8), 1200(9), 1800(10), 2000(11), 2400(12),                           
 			-- 3600(13), 4800(14), 7200(15), 9600(16), 19200(17),                       
 			-- 38400(18), idle(254), autobaud(255)                                      
 		ACCESS read-only                                                             
 		STATUS mandatory                                                             
DESCRIPTION ""
 		::= { portEntry 3 }                                                          
                                                                                
   ctrlLines	OBJECT-TYPE                                                        
 		SYNTAX INTEGER {                                                             
 			none(1),                                                                    
 			dcddtr(2),                                                                  
 			ctsrts(3),                                                                  
 			both(4)                                                                     
 		}                                                                            
 		ACCESS read-only                                                             
 		STATUS mandatory                                                             
DESCRIPTION ""
 		::= { portEntry 4 }                                                          
                                                                                
   flowTypeIn	OBJECT-TYPE                                                       
 		SYNTAX INTEGER {                                                             
 			none(1),                                                                    
 			xonxoff(2),                                                                 
 			eia(3),                                                                     
 			bell(4)                                                                     
 		}                                                                            
 		ACCESS read-only                                                             
 		STATUS mandatory                                                             
DESCRIPTION ""
 		::= { portEntry 5 }                                                          
                                                                                
   flowTypeOut	OBJECT-TYPE                                                      
 		SYNTAX INTEGER {                                                             
 			none(1),                                                                    
 			xonxoff(2),                                                                 
 			eia(3),                                                                     
 			bell(4)                                                                     
 		}                                                                            
 		ACCESS read-only                                                             
 		STATUS mandatory                                                             
DESCRIPTION ""
 		::= { portEntry 6 }                                                          
                                                                                
   bitsPerChar	OBJECT-TYPE                                                      
 		SYNTAX INTEGER {                                                             
 			five(1),                                                                    
 			six(2),                                                                     
 			seven(3),                                                                   
 			eight(4)                                                                    
 		}                                                                            
 		ACCESS read-only                                                             
 		STATUS mandatory                                                             
DESCRIPTION ""
 		::= { portEntry 7 }                                                          
                                                                                
   stopBits	OBJECT-TYPE                                                         
 		SYNTAX INTEGER {                                                             
 			one(1),                                                                     
 			onefive(2),                                                                 
 			two(3)                                                                      
 		}                                                                            
 		ACCESS read-only                                                             
 		STATUS mandatory                                                             
DESCRIPTION ""
 		::= { portEntry 8 }                                                          
                                                                                
   parity	OBJECT-TYPE                                                           
 		SYNTAX INTEGER {                                                             
 			none(1),                                                                    
 			even(2),                                                                    
 			odd(3),                                                                     
 			mark(4),                                                                    
 			space(5)                                                                    
 		}                                                                            
 		ACCESS read-only                                                             
 		STATUS mandatory                                                             
DESCRIPTION ""
 		::= { portEntry 9 }                                                          
                                                                                
   modemDCD	OBJECT-TYPE                                                         
 		SYNTAX INTEGER { unused(1), lo(2), hi(3) }                                   
 		ACCESS read-only                                                             
 		STATUS mandatory                                                             
DESCRIPTION ""
 		::= { portEntry 10 }                                                         
                                                                                
   modemDTR	OBJECT-TYPE                                                         
 		SYNTAX INTEGER { unused(1), lo(2), hi(3) }                                   
 		ACCESS read-only                                                             
 		STATUS mandatory                                                             
DESCRIPTION ""
 		::= { portEntry 11 }                                                         
                                                                                
   modemCTS	OBJECT-TYPE                                                         
 		SYNTAX INTEGER { unused(1), lo(2), hi(3) }                                   
 		ACCESS read-only                                                             
 		STATUS mandatory                                                             
DESCRIPTION ""
 		::= { portEntry 12 }                                                         
                                                                                
   modemRTS	OBJECT-TYPE                                                         
 		SYNTAX INTEGER { unused(1), lo(2), hi(3) }                                   
 		ACCESS read-only                                                             
 		STATUS mandatory                                                             
DESCRIPTION ""
 		::= { portEntry 13 }                                                         
                                                                                
   charsIn	OBJECT-TYPE                                                          
 		SYNTAX Counter                                                               
 		ACCESS read-only                                                             
 		STATUS mandatory                                                             
DESCRIPTION ""
 		::= { portEntry 14 }                                                         
                                                                                
   charsOut	OBJECT-TYPE                                                         
 		SYNTAX Counter                                                               
 		ACCESS read-only                                                             
 		STATUS mandatory                                                             
DESCRIPTION ""
 		::= { portEntry 15 }                                                         
                                                                                
   errsParity	OBJECT-TYPE                                                       
 		SYNTAX Counter                                                               
 		ACCESS read-only                                                             
 		STATUS mandatory                                                             
DESCRIPTION ""
 		::= { portEntry 16 }                                                         
                                                                                
   errsOverrun	OBJECT-TYPE                                                      
 		SYNTAX Counter                                                               
 		ACCESS read-only                                                             
 		STATUS mandatory                                                             
DESCRIPTION ""
 		::= { portEntry 17 }                                                         
                                                                                
   errsFraming	OBJECT-TYPE                                                      
 		SYNTAX Counter                                                               
 		ACCESS read-only                                                             
 		STATUS mandatory                                                             
DESCRIPTION ""
 		::= { portEntry 18 }                                                         
                                                                                
   inCC		OBJECT-TYPE                                                            
 		SYNTAX Gauge                                                                 
 		ACCESS read-only                                                             
 		STATUS mandatory                                                             
DESCRIPTION ""
 		::= { portEntry 19 }                                                         
                                                                                
   outCC		OBJECT-TYPE                                                           
 		SYNTAX Gauge                                                                 
 		ACCESS read-only                                                             
 		STATUS mandatory                                                             
DESCRIPTION ""
 		::= { portEntry 20 }                                                         
                                                                                
   END
