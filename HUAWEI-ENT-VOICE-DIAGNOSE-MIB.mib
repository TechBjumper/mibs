-- ============================================================================
-- Copyright (C) 2011 by HUAWEI TECHNOLOGIES. All rights reserved.
--
-- Description:
-- Reference:
-- Version: V1.0
-- History:
-- ============================================================================

HUAWEI-ENT-VOICE-DIAGNOSE-MIB DEFINITIONS ::= BEGIN
    IMPORTS
        MODULE-IDENTITY, OBJECT-TYPE, NOTIFICATION-TYPE, private, Integer32, Unsigned32
            FROM SNMPv2-SMI
        MODULE-COMPLIANCE, OBJECT-GROUP, NOTIFICATION-GROUP
            FROM SNMPv2-CONF
        TEXTUAL-CONVENTION
            FROM SNMPv2-TC
        IpAddress, TimeTicks, Counter32
            FROM SNMPv2-SMI
        RowStatus, DisplayString
            FROM SNMPv2-TC
        hwDatacomm
            FROM HUAWEI-MIB;

hwEntVoiceDiagnoseMIB MODULE-IDENTITY
    LAST-UPDATED "201107010000Z"
    ORGANIZATION 
              "Huawei Technologies Co.,Ltd."
    CONTACT-INFO 
              "Huawei Industrial Base                
              Bantian, Longgang                     
              Shenzhen 518129                       
              People's Republic of China            
              Website: http://www.huawei.com        
              Email: support@huawei.com             
              "  
    DESCRIPTION
        "Huawei VOICE DIAGNOSE mib."

-- Revision history

    REVISION     "201107010000Z"
    DESCRIPTION  "V1.0, create this file."

::= { hwDatacomm 314 }

    --==

    hwEntPotsCircuitTestTable OBJECT IDENTIFIER  ::= { hwEntVoiceDiagnoseMIB 1 }

    hwEntPotsCircuitTestOprType OBJECT-TYPE
        SYNTAX INTEGER { stop(1), start(2) }
        MAX-ACCESS read-write
        STATUS current
        DESCRIPTION
            "Indicates the operation type."
        ::= { hwEntPotsCircuitTestTable 1 }

    hwEntPotsCircuitTestPort OBJECT-TYPE
        SYNTAX Integer32
        MAX-ACCESS read-write
        STATUS current
        DESCRIPTION
            "Indicates the test port.
                bits 31-24:  reserved
                bits 23-16: slot index
                bits 15-8: subcard index
                bits 7-0:  port index
            "
    ::= { hwEntPotsCircuitTestTable 2 }

    hwEntPotsCircuitTestBusyFlag OBJECT-TYPE
        SYNTAX INTEGER {cancel(1), busytest(2), force(3), defer(4)}
        MAX-ACCESS read-write
        STATUS current
        DESCRIPTION
            "Indicates the process method, when the test port is busy."
    ::= { hwEntPotsCircuitTestTable 3 }

    hwEntPotsCircuitTestTimeOut OBJECT-TYPE
        SYNTAX Integer32 (1..1440)
        MAX-ACCESS read-write
        STATUS current
        DESCRIPTION
            "Indicates the time out of busy. (Unit: min)
            Default: 30"
    ::= { hwEntPotsCircuitTestTable 4 }

    hwEntPotsCircuitTestTimeProc OBJECT-TYPE
        SYNTAX INTEGER { noTest(1), mandatoryTest(2) }
        MAX-ACCESS read-write
        STATUS current
        DESCRIPTION
            "Indicates the process method afert time out."
    ::= { hwEntPotsCircuitTestTable 5 }

    hwEntPotsCircuitTestStatus OBJECT-TYPE
        SYNTAX INTEGER { normal(1), testfail(2), portbusy(3), outoftime(4), testingAbnormal(5), testcanceled(6) }
        MAX-ACCESS read-only
        STATUS current
        DESCRIPTION
            "Indicates the test result."
    ::= { hwEntPotsCircuitTestTable 6 }

    hwEntPotsCircuitTestDigitalVoltageResult OBJECT-TYPE
        SYNTAX INTEGER { normal(1), abnormal (2), notTested(3)}
        MAX-ACCESS read-only
        STATUS current
        DESCRIPTION
            "Indicates the test result of digital voltage."
    ::= { hwEntPotsCircuitTestTable 7 }

    hwEntPotsCircuitTestLowBatteryResult OBJECT-TYPE
        SYNTAX INTEGER { normal(1), abnormal (2), notTested(3)}
        MAX-ACCESS read-only
        STATUS current
        DESCRIPTION
            "Indicates the test result of low battery."
    ::= { hwEntPotsCircuitTestTable 8 }

    hwEntPotsCircuitTestHighBatteryResult OBJECT-TYPE
        SYNTAX INTEGER { normal(1), abnormal (2), notTested(3)}
        MAX-ACCESS read-only
        STATUS current
        DESCRIPTION
            "Indicates the test result of high battery."
    ::= { hwEntPotsCircuitTestTable 9 }

    hwEntPotsCircuitTestPositiveBatteryResult OBJECT-TYPE
        SYNTAX INTEGER { normal(1), abnormal (2), notTested(3)}
        MAX-ACCESS read-only
        STATUS current
        DESCRIPTION
            "Indicates the test result of positive battery.
             Default: enable(1)"
    ::= { hwEntPotsCircuitTestTable 10 }

    hwEntPotsCircuitTestVAGResult OBJECT-TYPE
        SYNTAX INTEGER { normal(1), abnormal (2), notTested(3)}
        MAX-ACCESS read-only
        STATUS current
        DESCRIPTION
            "Indicates the test result of a-ground voltage."
    ::= { hwEntPotsCircuitTestTable 11 }

    hwEntPotsCircuitTestVBGResult OBJECT-TYPE
        SYNTAX INTEGER { normal(1), abnormal (2), notTested(3)}
        MAX-ACCESS read-only
        STATUS current
        DESCRIPTION
             "Indicates the test result of b-ground voltage."
    ::= { hwEntPotsCircuitTestTable 12 }
    
   hwEntPotsCircuitTestLoopCurrentResult  OBJECT-TYPE
        SYNTAX INTEGER { normal(1), abnormal (2), notTested(3)}
        MAX-ACCESS read-only
        STATUS current
        DESCRIPTION
             "Indicates the test result of loop current."
    ::= { hwEntPotsCircuitTestTable 13 }
    
   hwEntPotsCircuitTestFeederVoltageResult   OBJECT-TYPE
        SYNTAX INTEGER { normal(1), abnormal (2), notTested(3)}
        MAX-ACCESS read-only
        STATUS current
        DESCRIPTION
             "Indicates the test result of feeder voltage."
    ::= { hwEntPotsCircuitTestTable 14 }
    
   hwEntPotsCircuitTestRingingCurrentVoltageResult  OBJECT-TYPE
        SYNTAX INTEGER { normal(1), abnormal (2), notTested(3)}
        MAX-ACCESS read-only
        STATUS current
        DESCRIPTION
             "Indicates the test result of ringing current voltage."
    ::= { hwEntPotsCircuitTestTable 15 }
    
   hwEntPotsCircuitTestRingingCurrentFrequencyResult OBJECT-TYPE
        SYNTAX INTEGER { normal(1), abnormal (2), notTested(3)}
        MAX-ACCESS read-only
        STATUS current
        DESCRIPTION
             "Indicates the test result of ringing current frequency."
    ::= { hwEntPotsCircuitTestTable 16 }
    
   hwEntPotsCircuitTestFeedervoltageValue OBJECT-TYPE
        SYNTAX Integer32
        MAX-ACCESS read-only
        STATUS current
        DESCRIPTION
             "Indicates the feeder voltage. (Unit: v)"
    ::= { hwEntPotsCircuitTestTable 17 }
    
   hwEntPotsCircuitTestRingingCurrentVoltageValue OBJECT-TYPE
        SYNTAX Integer32
        MAX-ACCESS read-only
        STATUS current
        DESCRIPTION
             "Indicates the ringing current voltage. (Unit: v)"
    ::= { hwEntPotsCircuitTestTable 18 }    
    
   hwEntPotsCircuitTestLoopCurrentValue OBJECT-TYPE
        SYNTAX Integer32
        MAX-ACCESS read-only
        STATUS current
        DESCRIPTION
             "Indicates the loop current. (Unit: mA)"
    ::= { hwEntPotsCircuitTestTable 19 }

   --==
    
   hwEntPotsLoopTestTable OBJECT IDENTIFIER  ::= { hwEntVoiceDiagnoseMIB 2 }

   hwEntPotsLoopTestOprType OBJECT-TYPE
        SYNTAX INTEGER { stop(1), start(2) }
        MAX-ACCESS read-write
        STATUS current
        DESCRIPTION
             "Indicates the operation type"
    ::= { hwEntPotsLoopTestTable 1 }
    
   hwEntPotsLoopTestPort OBJECT-TYPE
        SYNTAX Integer32
        MAX-ACCESS read-write
        STATUS current
        DESCRIPTION
             "Indicates the test port.
                bits 31-24:  reserved
                bits 23-16: slot index
                bits 15-8: subcard index
                bits 7-0:  port index
             "
    ::= { hwEntPotsLoopTestTable 2 }
    
   hwEntPotsLoopTestBusyFlag OBJECT-TYPE
        SYNTAX INTEGER { cancel(1), busytest(2), force(3), defer(4) }
        MAX-ACCESS read-write
        STATUS current
        DESCRIPTION
             "Indicates the process method, when the test port is busy."
    ::= { hwEntPotsLoopTestTable 3 }
    
   hwEntPotsLoopTestTimeOut OBJECT-TYPE
        SYNTAX Integer32 (1..1440)
        MAX-ACCESS read-write
        STATUS current
        DESCRIPTION
             "Indicates the time out of busy. (Unit: min)
              Default: 30"
    ::= { hwEntPotsLoopTestTable 4 }

   hwEntPotsLoopTestTimeProc OBJECT-TYPE
        SYNTAX INTEGER { noTest(1), mandatoryTest(2) }
        MAX-ACCESS read-write
        STATUS current
        DESCRIPTION
             "Indicates the process method, after the time out of busy."
    ::= { hwEntPotsLoopTestTable 5 }

   hwEntPotsLoopTestVoltage OBJECT-TYPE
        SYNTAX INTEGER { noSelect(1), select(2) }
        MAX-ACCESS read-write
        STATUS current
        DESCRIPTION
             "Indicates the test result of voltage."
    ::= { hwEntPotsLoopTestTable 6 }
    
   hwEntPotsLoopTestResistance OBJECT-TYPE
        SYNTAX INTEGER { noSelect(1), select(2) }
        MAX-ACCESS read-write
        STATUS current
        DESCRIPTION
             "Indicates the test result of resistance."
    ::= { hwEntPotsLoopTestTable 7 }
    
   hwEntPotsLoopTestCapacitance OBJECT-TYPE
        SYNTAX INTEGER { noSelect(1), select(2) }
        MAX-ACCESS read-write
        STATUS current
        DESCRIPTION
             "Indicates the test result of capacitance."
    ::= { hwEntPotsLoopTestTable 8 }
    
   hwEntPotsLoopTestLoopResistance OBJECT-TYPE
        SYNTAX INTEGER { noSelect(1), select(2) }
        MAX-ACCESS read-write
        STATUS current
        DESCRIPTION
             "Indicates the test result of loop resistance."
    ::= { hwEntPotsLoopTestTable 9 }
   
    hwEntPotsLoopTestInverseResistance OBJECT-TYPE
        SYNTAX INTEGER { noSelect(1), select(2) }
        MAX-ACCESS read-write
        STATUS current
        DESCRIPTION
             "Indicates the test result of inverse resistance."
    ::= { hwEntPotsLoopTestTable 10 }
    
    hwEntPotsLoopTestStatus OBJECT-TYPE
        SYNTAX INTEGER { normal(1), testFail(2), portBusy(3), outofTime(4), testingAbnormal(5), testCanceled(6) }
        MAX-ACCESS read-only
        STATUS current
        DESCRIPTION
             "Indicates the test status."
    ::= { hwEntPotsLoopTestTable 11 }
    
    hwEntPotsLoopTestConclusion OBJECT-TYPE
        SYNTAX Integer32 (1..28)
        MAX-ACCESS read-only
        STATUS current
        DESCRIPTION
             "Indicates the test conclusion."
    ::= { hwEntPotsLoopTestTable 12 }
    
    hwEntPotsLoopTestACAGnd OBJECT-TYPE
        SYNTAX Integer32
        MAX-ACCESS read-only
        STATUS current
        DESCRIPTION
             "Indicates the a-ground AC voltage. (Unit: v)"
    ::= { hwEntPotsLoopTestTable 13 }
    
    hwEntPotsLoopTestACBGnd OBJECT-TYPE
        SYNTAX Integer32
        MAX-ACCESS read-only
        STATUS current
        DESCRIPTION
             "Indicates the b-ground AC voltage. (Unit: v)"
    ::= { hwEntPotsLoopTestTable 14 }  
    
    hwEntPotsLoopTestACAB OBJECT-TYPE
        SYNTAX Integer32
        MAX-ACCESS read-only
        STATUS current
        DESCRIPTION
             "Indicates the a-b AC voltage. (Unit: v)"
    ::= { hwEntPotsLoopTestTable 15 }  
    
    hwEntPotsLoopTestDCAGnd OBJECT-TYPE
        SYNTAX Integer32
        MAX-ACCESS read-only
        STATUS current
        DESCRIPTION
             "Indicates the a-ground DC voltage. (Unit: v)"
    ::= { hwEntPotsLoopTestTable 16 }
    
    hwEntPotsLoopTestDCBGnd OBJECT-TYPE
        SYNTAX Integer32
        MAX-ACCESS read-only
        STATUS current
        DESCRIPTION
             "Indicates the b-ground DC voltage. (Unit: v)"
    ::= { hwEntPotsLoopTestTable 17 }
    
    hwEntPotsLoopTestDCAB OBJECT-TYPE
        SYNTAX Integer32
        MAX-ACCESS read-only
        STATUS current
        DESCRIPTION
             "Indicates the a-b DC voltage. (Unit: v)"
    ::= { hwEntPotsLoopTestTable 18 }
    
    hwEntPotsLoopTestRAGnd OBJECT-TYPE
        SYNTAX Integer32
        MAX-ACCESS read-only
        STATUS current
        DESCRIPTION
             "Indicates the a-ground resistance. (Unit: )"
    ::= { hwEntPotsLoopTestTable 19 }
    
    hwEntPotsLoopTestRBGnd OBJECT-TYPE
        SYNTAX Integer32
        MAX-ACCESS read-only
        STATUS current
        DESCRIPTION
             "Indicates the b-ground resistance. (Unit: )"
    ::= { hwEntPotsLoopTestTable 20 }
    
    hwEntPotsLoopTestRAB OBJECT-TYPE
        SYNTAX Integer32
        MAX-ACCESS read-only
        STATUS current
        DESCRIPTION
             "Indicates the a-b resistance. (Unit: )"
    ::= { hwEntPotsLoopTestTable 21 }
    
    hwEntPotsLoopTestCAGnd OBJECT-TYPE
        SYNTAX Integer32
        MAX-ACCESS read-only
        STATUS current
        DESCRIPTION
             "Indicates the a-ground capacitance. (Unit: F)"
    ::= { hwEntPotsLoopTestTable 22 }
    
    hwEntPotsLoopTestCBGnd OBJECT-TYPE
        SYNTAX Integer32
        MAX-ACCESS read-only
        STATUS current
        DESCRIPTION
             "Indicates the b-ground capacitance. (Unit: F)"
    ::= { hwEntPotsLoopTestTable 23 }
    
    hwEntPotsLoopTestCAB OBJECT-TYPE
        SYNTAX Integer32
        MAX-ACCESS read-only
        STATUS current
        DESCRIPTION
             "Indicates the a-b capacitance. (Unit: F)"
    ::= { hwEntPotsLoopTestTable 24 }
    
    hwEntPotsLoopTestLR OBJECT-TYPE
        SYNTAX Integer32
        MAX-ACCESS read-only
        STATUS current
        DESCRIPTION
             "Indicates the loop resistance. (Unit: )"
    ::= { hwEntPotsLoopTestTable 25 }
    
    hwEntPotsLoopTestRRevPole OBJECT-TYPE
        SYNTAX Integer32
        MAX-ACCESS read-only
        STATUS current
        DESCRIPTION
             "Indicates the rev pole resistance. (Unit: )"
    ::= { hwEntPotsLoopTestTable 26 }
    
    hwEntPotsLoopTestMSocket OBJECT-TYPE
        SYNTAX INTEGER  { notConnected(1), connected(2) }
        MAX-ACCESS read-only
        STATUS current
        DESCRIPTION
             "Indicates the MSocket."
    ::= { hwEntPotsLoopTestTable 27 }
    
    --==
    
    hwEntPotsPathTestTable OBJECT IDENTIFIER  ::= { hwEntVoiceDiagnoseMIB 3 }
   
    hwEntPotsPathTestPort OBJECT-TYPE
        SYNTAX Integer32
        MAX-ACCESS read-write
        STATUS current
        DESCRIPTION
             "Indicates the test port.
                bits 31-24: reserved
                bits 23-16: slot index
                bits 15-8: subcard index
                bits 7-0: port index
             "
    ::= { hwEntPotsPathTestTable 1 }  
    
    hwEntPotsPathTestMode OBJECT-TYPE
        SYNTAX INTEGER { hardware(1), business(2) }
        MAX-ACCESS read-write
        STATUS current
        DESCRIPTION
             "Indicates the test type."
    ::= { hwEntPotsPathTestTable 2 }  
    
    hwEntPotsPathTestAssistPort OBJECT-TYPE
        SYNTAX Integer32
        MAX-ACCESS read-write
        STATUS current
        DESCRIPTION
             "Indicates the assist port. 
                bits 31-24: reserved
                bits 23-16: slot index
                bits 15-8: subcard index
                bits 7-0: port index
             "
    ::= { hwEntPotsPathTestTable 3 } 
    
    hwEntPotsPathTestDestTelno OBJECT-TYPE
        SYNTAX DisplayString(SIZE (1..32))
        MAX-ACCESS read-write
        STATUS current
        DESCRIPTION
             "Indicates the destination telephone number."
    ::= { hwEntPotsPathTestTable 4 } 
    
    hwEntPotsPathTestOprType OBJECT-TYPE
        SYNTAX INTEGER { stop(1), start(2) }
        MAX-ACCESS read-write
        STATUS current
        DESCRIPTION
             "Indicates the operation type."
    ::= { hwEntPotsPathTestTable 5 }
        
    
    hwEntPotsPathTestResult OBJECT-TYPE
        SYNTAX Integer32  (1..23)
        MAX-ACCESS read-only
        STATUS current
        DESCRIPTION
             "Indicates the test result."
    ::= { hwEntPotsPathTestTable 6 }
    
    --== 
          
    hwEntLineTestConfigTable OBJECT IDENTIFIER  ::= { hwEntVoiceDiagnoseMIB 4 }
 
    hwEntLineTestACVolGate OBJECT-TYPE
        SYNTAX Integer32 (0..2147483647)
        MAX-ACCESS read-write
        STATUS current
        DESCRIPTION
             "Indicates the AC voltage gate. (Unit: v)
              Default: 55"
    ::= { hwEntLineTestConfigTable 1 }
    
    hwEntLineTestDCVolGate OBJECT-TYPE
        SYNTAX Integer32 (0..2147483647)
        MAX-ACCESS read-write
        STATUS current
        DESCRIPTION
             "Indicates the DC voltage gate. (Unit: v)
              Default: 40"
    ::= { hwEntLineTestConfigTable 2 }
    
    hwEntLineTestResistGate OBJECT-TYPE
        SYNTAX Integer32 (0..2147483647)
        MAX-ACCESS read-write
        STATUS current
        DESCRIPTION
             "Indicates the resistance gate. (Unit: )
              Default: 20000"
    ::= { hwEntLineTestConfigTable 3 }
    
    hwEntLineTestOffHookRABLow OBJECT-TYPE
        SYNTAX Integer32 (0..2147483647)
        MAX-ACCESS read-write
        STATUS current
        DESCRIPTION
             "Indicates the low limit of a-b resistance in off hook. (Unit: )
              Default: 100"
    ::= { hwEntLineTestConfigTable 4 }
    
    hwEntLineTestOffHookRABUp OBJECT-TYPE
        SYNTAX Integer32 (0..2147483647)
        MAX-ACCESS read-write
        STATUS current
        DESCRIPTION
             "Indicates the up limit of a-b resistance in off hook. (Unit: )
              Default: 100000"
    ::= { hwEntLineTestConfigTable 5 }
    
    hwEntLineTestLRLow OBJECT-TYPE
        SYNTAX Integer32 (0..2147483647)
        MAX-ACCESS read-write
        STATUS current
        DESCRIPTION
             "Indicates the low limit of loop resistance. (Unit: )
              Default: 100"
    ::= { hwEntLineTestConfigTable 6 }
    
    hwEntLineTestLRLUp OBJECT-TYPE
        SYNTAX Integer32 (0..2147483647)
        MAX-ACCESS read-write
        STATUS current
        DESCRIPTION
             "Indicates the up limit of loop resistance. (Unit: )
              Default: 2000"
    ::= { hwEntLineTestConfigTable 7 }
    
    hwEntLineTestSelfMixRAB OBJECT-TYPE
        SYNTAX Integer32 (0..2147483647)
        MAX-ACCESS read-write
        STATUS current
        DESCRIPTION
             "Indicates the a-b resistance of mix. (Unit: )
              Default: 2000"
    ::= { hwEntLineTestConfigTable 8 }
    
    hwEntLineTestInsRABLow OBJECT-TYPE
        SYNTAX Integer32 (0..2147483647)
        MAX-ACCESS read-write
        STATUS current
        DESCRIPTION
             "Indicates the low limit of a-b resistance. (Unit: )
              Default: 2000"
    ::= { hwEntLineTestConfigTable 9 }
    
    hwEntLineTestInsRABUp OBJECT-TYPE
        SYNTAX Integer32 (0..2147483647)
        MAX-ACCESS read-write
        STATUS current
        DESCRIPTION
             "Indicates the up limit of a-b resistance. (Unit: )
              Default: 20000"
    ::= { hwEntLineTestConfigTable 10 }
    
    hwEntLineTestCapACUpGate OBJECT-TYPE
        SYNTAX Integer32 (0..2147483647)
        MAX-ACCESS read-write
        STATUS current
        DESCRIPTION
             "Indicates the ground capacitance up gate. (Unit: nF)
              Default: 700"
    ::= { hwEntLineTestConfigTable 11 }
    
    hwEntLineTestCapGroundNormalGate OBJECT-TYPE
        SYNTAX Integer32 (0..2147483647)
        MAX-ACCESS read-write
        STATUS current
        DESCRIPTION
             "Indicates the ground capacitance normal gate. (Unit: nF)
              Default: 200"
    ::= { hwEntLineTestConfigTable 12 }
    
    hwEntLineTestCapACLowGate OBJECT-TYPE
        SYNTAX Integer32 (0..2147483647)
        MAX-ACCESS read-write
        STATUS current
        DESCRIPTION
             "Indicates the ground capacitance low gate. (Unit: nF)
              Default: 350"
    ::= { hwEntLineTestConfigTable 13 }
    
    hwEntLineTestCapGroundNormalSmallGate OBJECT-TYPE
        SYNTAX Integer32 (0..2147483647)
        MAX-ACCESS read-write
        STATUS current
        DESCRIPTION
             "Indicates the ground capacitance normal small gate. (Unit: nF)
              Default: 350"
    ::= { hwEntLineTestConfigTable 14 }
    
    hwEntLineTestAdjustCAB OBJECT-TYPE
        SYNTAX Integer32 (0..10000000)
        MAX-ACCESS read-write
        STATUS current
        DESCRIPTION
             "Indicates the a-b adjest capacitance. (Unit: nF)"
    ::= { hwEntLineTestConfigTable 15 }
    
    hwEntLineTestAdjustCAG OBJECT-TYPE
        SYNTAX Integer32 (0..10000000)
        MAX-ACCESS read-write
        STATUS current
        DESCRIPTION
             "Indicates the a-ground adjest capacitance. (Unit: nF)"
    ::= { hwEntLineTestConfigTable 16 }
    
    hwEntLineTestAdjustCBG OBJECT-TYPE
        SYNTAX Integer32 (0..10000000)
        MAX-ACCESS read-write
        STATUS current
        DESCRIPTION
             "Indicates the b-ground adjest capacitance. (Unit: nF)"
    ::= { hwEntLineTestConfigTable 17 }
    
    hwEntLineTestAdjustRAB OBJECT-TYPE
        SYNTAX Integer32 (0..10000000)
        MAX-ACCESS read-write
        STATUS current
        DESCRIPTION
             "Indicates the a-b adjest resistance. (Unit: )"
    ::= { hwEntLineTestConfigTable 18 }    
    
    hwEntLineTestAdjustCutPort OBJECT-TYPE
        SYNTAX Integer32 (0..10000000)
        MAX-ACCESS read-write
        STATUS current
        DESCRIPTION
             "Indicates the adjest cut port.
               bits 31-24:  reserved
               bits 23-16: slot index
               bits 15-8: subcard index
               bits 7-0:  port index
              "
    ::= { hwEntLineTestConfigTable 19 }    
    
    hwEntLineTestAdjustSelfMixPort OBJECT-TYPE
        SYNTAX Integer32 (0..10000000)
        MAX-ACCESS read-write
        STATUS current
        DESCRIPTION
             "Indicates the adjest self mix port.
               bits 31-24:  reserved
               bits 23-16: slot index
               bits 15-8: subcard index
               bits 7-0:  port index
              "
    ::= { hwEntLineTestConfigTable 20 }   
    
    --==
    
    hwEntCallerEmulateTable  OBJECT-TYPE   
     SYNTAX      SEQUENCE OF HwEntCallerEmulateEntry
     MAX-ACCESS  not-accessible
     STATUS      current
     DESCRIPTION
       "
       A list of hwEntCallerEmulateEntry objects.
       "
     ::= { hwEntVoiceDiagnoseMIB 5 } 
    
    hwEntCallerEmulateEntry OBJECT-TYPE
     SYNTAX      HwEntCallerEmulateEntry
     MAX-ACCESS  not-accessible
     STATUS      current
     DESCRIPTION
       "
       A list of hwEntCallerEmulateEntry objects.
       "
     INDEX    {
               hwEntCallerEmulatePort
              }
     ::= { hwEntCallerEmulateTable 1 }
     
   HwEntCallerEmulateEntry ::=
     SEQUENCE
     {
       hwEntCallerEmulatePort            Integer32,
       hwEntCallerEmulateOprType         INTEGER,
       hwEntCallerEmulateTelno           DisplayString,
       hwEntCallerEmulateStatus          Integer32
     }
     
    hwEntCallerEmulatePort OBJECT-TYPE
        SYNTAX Integer32
        MAX-ACCESS read-only
        STATUS current
        DESCRIPTION
             "Indicates the caller port.
               bits 31-24:  reserved
               bits 23-16: slot index
               bits 15-8: subcard index
               bits 7-0:  port index
              "
    ::= { hwEntCallerEmulateEntry 1 } 
    
    hwEntCallerEmulateOprType  OBJECT-TYPE
        SYNTAX INTEGER { stop(1), start(2) }
        MAX-ACCESS read-write
        STATUS current
        DESCRIPTION
             "Indicates the operation type."
    ::= { hwEntCallerEmulateEntry 2 } 
    
    hwEntCallerEmulateTelno  OBJECT-TYPE
        SYNTAX DisplayString(SIZE (1..32))
        MAX-ACCESS read-write
        STATUS current
        DESCRIPTION
             "Indicates the telephone number."
    ::= { hwEntCallerEmulateEntry 3 } 
    
    hwEntCallerEmulateStatus  OBJECT-TYPE
        SYNTAX Integer32 (19..21)
        MAX-ACCESS read-only
        STATUS current
        DESCRIPTION
             "Indicates the test status."
    ::= { hwEntCallerEmulateEntry 4 } 
    
    --==
    
    hwEntCalledEmulateTable  OBJECT-TYPE   
     SYNTAX      SEQUENCE OF HwEntCalledEmulateEntry
     MAX-ACCESS  not-accessible
     STATUS      current
     DESCRIPTION
       "
       A list of hwEntCalledEmulateEntry objects.
       "
     ::= { hwEntVoiceDiagnoseMIB 6 } 
    
    hwEntCalledEmulateEntry OBJECT-TYPE
     SYNTAX      HwEntCalledEmulateEntry
     MAX-ACCESS  not-accessible
     STATUS      current
     DESCRIPTION
       "A list of hwEntCalledEmulateEntry objects."
     INDEX    {
               hwEntCalledEmulatePort
              }
     ::= { hwEntCalledEmulateTable 1 }
     
   HwEntCalledEmulateEntry ::=
     SEQUENCE
     {
       hwEntCalledEmulatePort            Integer32,
       hwEntCalledEmulateOprType         INTEGER,
       hwEntCalledEmulateStatus          Integer32
     }
    
    hwEntCalledEmulatePort OBJECT-TYPE
        SYNTAX Integer32
        MAX-ACCESS read-only
        STATUS current
        DESCRIPTION
             "Indicates the caller port.
               bits 31-24:  reserved
               bits 23-16: slot index
               bits 15-8: subcard index
               bits 7-0:  port index
              "
    ::= { hwEntCalledEmulateEntry 1 } 
    
    hwEntCalledEmulateOprType  OBJECT-TYPE
        SYNTAX INTEGER { stop(1), start(2) }
        MAX-ACCESS read-write
        STATUS current
        DESCRIPTION
             "Indicates the operation type."
    ::= { hwEntCalledEmulateEntry 2 } 
    
    hwEntCalledEmulateStatus  OBJECT-TYPE
        SYNTAX Integer32 (17..19)
        MAX-ACCESS read-only
        STATUS current
        DESCRIPTION
             "Indicates the test status."
    ::= { hwEntCalledEmulateEntry 3 }

    --==
    
    hwEntCallEmulateTable  OBJECT-TYPE   
     SYNTAX      SEQUENCE OF HwEntCallEmulateEntry
     MAX-ACCESS  not-accessible
     STATUS      current
     DESCRIPTION
       "
       A list of hwEntCallEmulateEntry objects.
       "
     ::= { hwEntVoiceDiagnoseMIB 7 } 
    
    hwEntCallEmulateEntry OBJECT-TYPE
     SYNTAX      HwEntCallEmulateEntry
     MAX-ACCESS  not-accessible
     STATUS      current
     DESCRIPTION
       "A list of hwEntCallEmulateEntry objects."
     INDEX    {
               hwEntCallEmulateIndex
              }
     ::= { hwEntCallEmulateTable 1 }
     
   HwEntCallEmulateEntry ::=
     SEQUENCE
     {
       hwEntCallEmulateIndex              Integer32,
       hwEntCallEmulateOprType            INTEGER,
       hwEntCallEmulateCallerPort         Integer32,
       hwEntCallEmulateCalledPort         Integer32,
       hwEntCallEmulateCalledTelno        DisplayString,
       hwEntCallEmulateStatus             Integer32,
       hwEntCallEmulateResult             Integer32
     }
        
    hwEntCallEmulateIndex  OBJECT-TYPE
        SYNTAX Integer32
        MAX-ACCESS read-only
        STATUS current
        DESCRIPTION
             "Indicates the test index."
    ::= { hwEntCallEmulateEntry 1 }

    hwEntCallEmulateOprType  OBJECT-TYPE
        SYNTAX INTEGER  { stop(1), start(2) }
        MAX-ACCESS read-write
        STATUS current
        DESCRIPTION
             "Indicates the operation type."
    ::= { hwEntCallEmulateEntry 2 }

    hwEntCallEmulateCallerPort  OBJECT-TYPE
        SYNTAX Integer32
        MAX-ACCESS read-write
        STATUS current
        DESCRIPTION
             "Indicates the calller port."
    ::= { hwEntCallEmulateEntry 3 }
    
    hwEntCallEmulateCalledPort  OBJECT-TYPE
        SYNTAX Integer32
        MAX-ACCESS read-write
        STATUS current
        DESCRIPTION
             "Indicates the callled port."
    ::= { hwEntCallEmulateEntry 4 }
    
    hwEntCallEmulateCalledTelno OBJECT-TYPE
        SYNTAX DisplayString(SIZE (1..32))
        MAX-ACCESS read-write
        STATUS current
        DESCRIPTION
             "Indicates the telephone number."
    ::= { hwEntCallEmulateEntry 5 }
    
    hwEntCallEmulateStatus  OBJECT-TYPE
        SYNTAX Integer32  (1..6)
        MAX-ACCESS read-only
        STATUS current
        DESCRIPTION
             "Indicates the call status."
    ::= { hwEntCallEmulateEntry 6 }
    
    hwEntCallEmulateResult  OBJECT-TYPE
        SYNTAX Integer32  (1..6)
        MAX-ACCESS read-only
        STATUS current
        DESCRIPTION
             "Indicates the call result."
    ::= { hwEntCallEmulateEntry 7 }
   
    hwEntVoiceTestTraps OBJECT IDENTIFIER ::= { hwEntVoiceDiagnoseMIB 8 }
    
    hwEntPotsCircuitTestTrap NOTIFICATION-TYPE
        OBJECTS { hwEntPotsCircuitTestPort, hwEntPotsCircuitTestStatus, hwEntPotsCircuitTestDigitalVoltageResult,hwEntPotsCircuitTestLowBatteryResult, hwEntPotsCircuitTestHighBatteryResult,
                  hwEntPotsCircuitTestPositiveBatteryResult, hwEntPotsCircuitTestVAGResult, hwEntPotsCircuitTestVBGResult, hwEntPotsCircuitTestLoopCurrentResult, hwEntPotsCircuitTestFeederVoltageResult,
                  hwEntPotsCircuitTestRingingCurrentVoltageResult, hwEntPotsCircuitTestRingingCurrentFrequencyResult, hwEntPotsCircuitTestFeedervoltageValue, hwEntPotsCircuitTestRingingCurrentVoltageValue,
                  hwEntPotsCircuitTestLoopCurrentValue }
        STATUS current
        DESCRIPTION 
                "circuit test result."
        ::= { hwEntVoiceTestTraps 1 }
    
    hwEntPotsLoopTestTrap NOTIFICATION-TYPE
        OBJECTS { hwEntPotsLoopTestPort, hwEntPotsLoopTestStatus, hwEntPotsLoopTestConclusion,hwEntPotsLoopTestACAGnd, hwEntPotsLoopTestACBGnd,
                  hwEntPotsLoopTestACAB, hwEntPotsLoopTestDCAGnd, hwEntPotsLoopTestDCBGnd, hwEntPotsLoopTestDCAB, hwEntPotsLoopTestRAGnd,
                  hwEntPotsLoopTestRBGnd, hwEntPotsLoopTestRAB, hwEntPotsLoopTestCAGnd, hwEntPotsLoopTestCBGnd, hwEntPotsLoopTestCAB,
                  hwEntPotsLoopTestLR, hwEntPotsLoopTestRRevPole, hwEntPotsLoopTestMSocket }
        STATUS current
        DESCRIPTION 
                "Loop test result."
        ::= { hwEntVoiceTestTraps 2 }
      
   hwEntPotsPathTestTrap NOTIFICATION-TYPE
        OBJECTS { hwEntPotsPathTestPort, hwEntPotsPathTestResult, hwEntPotsPathTestAssistPort }
        STATUS current
        DESCRIPTION 
                "Path test result."
        ::= { hwEntVoiceTestTraps 3 }
        
   hwEntCallEmulateTrap NOTIFICATION-TYPE
        OBJECTS { hwEntCallEmulateCallerPort, hwEntCallEmulateCalledPort, hwEntCallEmulateResult }
        STATUS current
        DESCRIPTION 
                "Call emulate result."
        ::= { hwEntVoiceTestTraps 4 }
  
   
    --  ============== conformance information ==============
        hwEntVoiceDiagnoseConformance OBJECT IDENTIFIER ::= { hwEntVoiceDiagnoseMIB 9 }
        
        
        hwEntVoiceDiagnoseCompliances OBJECT IDENTIFIER ::= { hwEntVoiceDiagnoseConformance 1 }
        hwEntVoiceDiagnoseCompliance MODULE-COMPLIANCE
               STATUS      current
               DESCRIPTION
                   "The compliance statement for systems supporting 
                the this module."

               MODULE      -- this module
               MANDATORY-GROUPS    {hwEntPotsCircuitTestGroup, hwEntPotsLoopTestGroup, hwEntPotsPathTestGroup,
                              hwEntLineTestConfigGroup, hwEntCallerEmulateGroup, hwEntCalledEmulateGroup,
                              hwEntCallEmulateGroup, hwEntVoiceTestTrapDefineGroup}  
                                               
              ::= { hwEntVoiceDiagnoseCompliances 1 }  
              
          
        --  ============== groups ==============  
        hwEntVoiceDiagnoseGroups OBJECT IDENTIFIER ::= { hwEntVoiceDiagnoseConformance 2 } 
        
        hwEntPotsCircuitTestGroup OBJECT-GROUP
            OBJECTS {
                hwEntPotsCircuitTestOprType,
                hwEntPotsCircuitTestPort,
                hwEntPotsCircuitTestBusyFlag,
                hwEntPotsCircuitTestTimeOut,
                hwEntPotsCircuitTestTimeProc,
                hwEntPotsCircuitTestStatus,
                hwEntPotsCircuitTestDigitalVoltageResult,
                hwEntPotsCircuitTestLowBatteryResult,
                hwEntPotsCircuitTestHighBatteryResult,
                hwEntPotsCircuitTestPositiveBatteryResult,
                hwEntPotsCircuitTestVAGResult,
                hwEntPotsCircuitTestVBGResult,
                hwEntPotsCircuitTestLoopCurrentResult,
                hwEntPotsCircuitTestFeederVoltageResult,
                hwEntPotsCircuitTestRingingCurrentVoltageResult,
                hwEntPotsCircuitTestRingingCurrentFrequencyResult,
                hwEntPotsCircuitTestFeedervoltageValue,
                hwEntPotsCircuitTestRingingCurrentVoltageValue,
                hwEntPotsCircuitTestLoopCurrentValue
                
             }       
            STATUS current
            DESCRIPTION 
                "The hwEntPotsCircuitTest group."
            ::= { hwEntVoiceDiagnoseGroups 1 }


        hwEntPotsLoopTestGroup OBJECT-GROUP
            OBJECTS {
	        hwEntPotsLoopTestOprType,
	        hwEntPotsLoopTestPort,
	        hwEntPotsLoopTestBusyFlag,
	        hwEntPotsLoopTestTimeOut,
	        hwEntPotsLoopTestTimeProc,
	        hwEntPotsLoopTestVoltage,
	        hwEntPotsLoopTestResistance,
	        hwEntPotsLoopTestCapacitance,
	        hwEntPotsLoopTestLoopResistance,
	        hwEntPotsLoopTestInverseResistance,
	        hwEntPotsLoopTestStatus,
	        hwEntPotsLoopTestConclusion,
	        hwEntPotsLoopTestACAGnd,
	        hwEntPotsLoopTestACBGnd,
	        hwEntPotsLoopTestACAB,
	        hwEntPotsLoopTestDCAGnd,
	        hwEntPotsLoopTestDCBGnd,
	        hwEntPotsLoopTestDCAB,
	        hwEntPotsLoopTestRAGnd,
	        hwEntPotsLoopTestRBGnd,
	        hwEntPotsLoopTestRAB,
	        hwEntPotsLoopTestCAGnd,
	        hwEntPotsLoopTestCBGnd,
	        hwEntPotsLoopTestCAB,
	        hwEntPotsLoopTestLR,
	        hwEntPotsLoopTestRRevPole,
	        hwEntPotsLoopTestMSocket               
	     }                  
            STATUS current
            DESCRIPTION 
                "The hwEntPotsLoopTest group."
            ::= { hwEntVoiceDiagnoseGroups 2 }
            
        hwEntPotsPathTestGroup OBJECT-GROUP
            OBJECTS {
	       hwEntPotsPathTestPort,
	       hwEntPotsPathTestMode,
	       hwEntPotsPathTestAssistPort,
	       hwEntPotsPathTestDestTelno,
	       hwEntPotsPathTestOprType,
	       hwEntPotsPathTestResult
	       	       
	     }            
            STATUS current
            DESCRIPTION 
                "The hwEntPotsPathTest group."
            ::= { hwEntVoiceDiagnoseGroups 3 }
            
        hwEntLineTestConfigGroup OBJECT-GROUP
            OBJECTS { 
                  hwEntLineTestACVolGate,
                  hwEntLineTestDCVolGate,
                  hwEntLineTestResistGate,
                  hwEntLineTestOffHookRABLow,
                  hwEntLineTestOffHookRABUp,
                  hwEntLineTestLRLow,
                  hwEntLineTestLRLUp,
                  hwEntLineTestSelfMixRAB,
                  hwEntLineTestInsRABLow,
                  hwEntLineTestInsRABUp,
                  hwEntLineTestCapACUpGate,
                  hwEntLineTestCapGroundNormalGate,
                  hwEntLineTestCapACLowGate,
                  hwEntLineTestCapGroundNormalSmallGate,
                  hwEntLineTestAdjustCAB,
                  hwEntLineTestAdjustCAG,
                  hwEntLineTestAdjustCBG,
                  hwEntLineTestAdjustRAB,
                  hwEntLineTestAdjustCutPort,
                  hwEntLineTestAdjustSelfMixPort
                              
                    }            
            STATUS current
            DESCRIPTION 
                "The EntLineTest Config group."
            ::= { hwEntVoiceDiagnoseGroups 4 }
            
        hwEntCallerEmulateGroup OBJECT-GROUP
            OBJECTS { 
               hwEntCallerEmulatePort,
	       hwEntCallerEmulateOprType,
	       hwEntCallerEmulateTelno,
	       hwEntCallerEmulateStatus             
                }
            STATUS current
            DESCRIPTION 
                "The EntCaller Emulate Group."
            ::= { hwEntVoiceDiagnoseGroups 5 }
            
        hwEntCalledEmulateGroup OBJECT-GROUP
           OBJECTS {
	       hwEntCalledEmulatePort,
	       hwEntCalledEmulateOprType,
	       hwEntCalledEmulateStatus
	     }
            STATUS current
            DESCRIPTION 
                "The EntCalled Emulate group."
            ::= { hwEntVoiceDiagnoseGroups 6 }             
                    
        hwEntCallEmulateGroup OBJECT-GROUP
            OBJECTS { 
               hwEntCallEmulateIndex,
	       hwEntCallEmulateOprType,
	       hwEntCallEmulateCallerPort,
	       hwEntCallEmulateCalledPort,
	       hwEntCallEmulateCalledTelno,
	       hwEntCallEmulateStatus,
	       hwEntCallEmulateResult
                    }            
            STATUS current
            DESCRIPTION 
                "The EntCallEmulate group."
            ::= { hwEntVoiceDiagnoseGroups 7 }            
 
        hwEntVoiceTestTrapDefineGroup NOTIFICATION-GROUP
            NOTIFICATIONS {
	       hwEntPotsCircuitTestTrap,
	       hwEntPotsLoopTestTrap,
	       hwEntPotsPathTestTrap,
	       hwEntCallEmulateTrap
	     }       
            STATUS current
            DESCRIPTION 
                "The EntVoiceTest Trap group."
            ::= { hwEntVoiceDiagnoseGroups 8 } 
            
                               
        --  ============== conformance information define end ==============    
    
END
