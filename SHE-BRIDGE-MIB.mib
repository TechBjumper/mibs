--
-- she-bridge-mib.mib
-- MIB generated by MG-SOFT Visual MIB Builder Version 6.0  Build 88
-- Monday, January 18, 2010 at 11:44:00
--

-- Start of ClearCase branch-information of current release:
--  she-bridge-mib.mib   /main/she_main_grf/she_r2.8_grf/20
-- End of ClearCase branch-information.

	SHE-BRIDGE-MIB DEFINITIONS ::= BEGIN
 
		IMPORTS
			she			
				FROM AN-MIB			
			entPhysicalIndex, PhysicalIndex			
				FROM ENTITY-MIB			
			ifIndex, InterfaceIndex			
				FROM IF-MIB			
			sheAlarmTimeAndDate, sheAlarmReportingSource, sheAlarmReportingSourceType, sheAlarmSeverity, SheAlarmSevProfileIndex			
				FROM SHE-ALARMING-MIB			
			SheControlStatusType, SheEnableType, ShePermissionType, SheAdminStateType			
				FROM SHE-TC-MIB			
			OBJECT-GROUP, MODULE-COMPLIANCE, NOTIFICATION-GROUP			
				FROM SNMPv2-CONF			
			TimeTicks, IpAddress, Integer32, Unsigned32, Gauge32, 
			Counter32, Counter64, OBJECT-TYPE, MODULE-IDENTITY, NOTIFICATION-TYPE			
				FROM SNMPv2-SMI			
			TruthValue, DisplayString, TEXTUAL-CONVENTION			
				FROM SNMPv2-TC;
	
	
		sheBridgeMib MODULE-IDENTITY 
			LAST-UPDATED "201001181600Z"		-- January 18, 2010 at 16:00 GMT
			ORGANIZATION 
				"Nokia Siemens Networks"
			CONTACT-INFO 
				"Gerd Barchmann
				COO BCS BBA RD SDE
				
				gerd.barchmann@nsn.com
				+49 3834 555654"
			DESCRIPTION 
				"This MIB contains all needed informations about bridgePorts and
				all supported she bridgeing features."
			REVISION "200506010951Z"		-- June 01, 2005 at 09:51 GMT
			DESCRIPTION 
				"Change contens of mstp-notifications.
				Change limit for sheQueueWeight - 0 is not valid.
				Change sequence of bits for sheLagPortPartnerAdminState
				and sheLagPortPartnerOperState.
				Define size for sheIgmpProviderControlProxyIpAddress."
			REVISION "200506081002Z"		-- June 08, 2005 at 10:02 GMT
			DESCRIPTION 
				"Change syntax for sheBridgePortMcastGroupPackageList.
				Change definition for SheLagStateType.
				Add new entrys in sheBridgePort-table to configure special features.
				Add new values for BridgePortUsage-Type.
				Add new table and controlgroup for sheBridgeMacProfile for feature IpoA.
				Add new entry sheVlanDefaultGateway in sheVlanTable to support IpoA mode.
				New Rule portFlowControl03(18) to set PVID on the basis of Ethertyp and portindex.
				New genericRule type defined.
				Add value ranges to meteringprofile-table."
			REVISION "200506241031Z"		-- June 24, 2005 at 10:31 GMT
			DESCRIPTION 
				"Add new values in SheDhcpRelayAgentOptionType to support
				simplified Dhcp Relay Agent.
				Change SheHostConfigurationProtocolType to support DHCP and PPPoE
				on the same port.
				Add entry in sheVlanTable for additional PPPoE-Provider-Index. New
				control request to configure this entry.
				Modify description for sheBridgeBaseOuterPVID.
				Add new rules and new Attributes to sheRuleAndMetering-table.
				New entry sheIgmpMaxJoinedSubscriber in sheIgmpBase. Add also new controlrequest
				to modify this entry."
			REVISION "200507081402Z"		-- July 08, 2005 at 14:02 GMT
			DESCRIPTION 
				"Define a value range for sheIgmpMaxJoinedSubscriber.
				Add comment for activation of IPoA-mode (BridgePortTable)."
			REVISION "200507230959Z"		-- July 23, 2005 at 09:59 GMT
			DESCRIPTION 
				"Change sheRuletable. 
				Add some entrys and change descriptions.
				All new values only used for generic rule types (expert mode)!
				New value in sheIgmpGroupTable for information about
				currently supplied card's."
			REVISION "200508121001Z"		-- August 12, 2005 at 10:01 GMT
			DESCRIPTION 
				"Add new values in sheBridgeBase-Group.
				Add values to sheBridgePortCreated-notification.
				Delete value CpuPermit from sheFdb-Table.
				Change range and default for sheErpDomainWaitToRestoreTime.
				Change range for sheDhcpRelayRemoteId to 6..64."
			REVISION "200508241052Z"		-- August 24, 2005 at 10:52 GMT
			DESCRIPTION 
				"Change description for BridgePortMode."
			REVISION "200509061026Z"		-- September 06, 2005 at 10:26 GMT
			DESCRIPTION 
				"Add comment for autogenerate of valid macaddress for IPoA mode.
				Add sheVlanPPPoEProviderIndex to VlanCreated-Trap.
				Add controlrequest-type modifyRule and corresponding notification.
				Change name and description for sheIgmpPortGroupsTimeSinceLastMembRep to
				sheIgmpPortGroupsTimeFirstMembRep."
			REVISION "200603161554Z"		-- March 16, 2006 at 15:54 GMT
			DESCRIPTION 
				"sheArpVlanTable and sheArpVlanControl node were added in to support
				the vlan arp flooding control."
			REVISION "200608161314Z"		-- August 16, 2006 at 13:14 GMT
			DESCRIPTION 
				"Take over by Gerd Barchmann for R2.5."
			REVISION "200609141534Z"		-- September 14, 2006 at 15:34 GMT
			DESCRIPTION 
				"Use sheVlanIndex as index for 	sheDhcpFloodVlanIdTable and
				sheIgmpFloodVlanTable.
				Add new features from SHE R2.3 MIB version 152 (BridgeBase, Vlan, Fdb)."
			REVISION "200610171149Z"		-- October 17, 2006 at 11:49 GMT
			DESCRIPTION 
				"Merge update for new SHE R2.3 MIB-Version 153.
				Merge update for new SHE R2.3 MIB-Version 154."
			REVISION "200611221256Z"		-- November 22, 2006 at 12:56 GMT
			DESCRIPTION 
				"Minor changes for backward compatibility.
				Add bridgePort-mode PPPoA.
				Add index parameter to sheUmasControl-Group.
				Merge new data for IGMP from SHE MIB release 155 for R2.3."
			REVISION "200612131022Z"		-- December 13, 2006 at 10:22 GMT
			DESCRIPTION 
				"Change parameter sequence for some bridgePort-Trap's.
				Modify comment for sheReducedQueuePriorityTable.
				Add new values to sheVLanTable for protocol handling 
				configuration of DHCP, PPPoE ,ARP and IGMP on vlan base."
			REVISION "200701221430Z"		-- January 22, 2007 at 14:30 GMT
			DESCRIPTION 
				"Correct range for sheIgmpProviderQueryInterval, IgmpProviderQueryResponseInterval,
				sheIgmpProviderStartupQueryInterval and IgmpProviderLastMemberQueryInterval.
				Some of the new values in sheVlanTable for protocol handling on vlan base removed again. The
				other ons will be supported with release R2.5.1.
				Remove not usable BridgePort-Tagging modes!
				Add an VlanServiceType value.
				Add vlan identifier to the list of available values for sheBridgeBaseCircuitIdFormat and
				sheBridgeBaseRemoteIdFormat.
				Correct Description for QueuePerformanceCounters.
				Introduce new sheBridgeIUProfileTable for IU specific Bridge-Configurations.
				Merge with SHE2.3 MIB release 156."
			REVISION "200703051024Z"		-- March 05, 2007 at 10:24 GMT
			DESCRIPTION 
				"Modify Range and description for sheBridgePortMaxLearnPermitCount."
			REVISION "200703211453Z"		-- March 21, 2007 at 14:53 GMT
			DESCRIPTION 
				"Modify index value for sheCebsVirtualMacAddressTable."
			REVISION "200703281019Z"		-- March 28, 2007 at 10:19 GMT
			DESCRIPTION 
				"New Release R2.5.2:
				Modify maximum range for sheBridgePortMaxLearnPermitCount.
				Expand MAT for TCom requirement.
				Expand QueueConfiguration per card.
				Modify MeterProfileConfiguration for more flexible configuration
				of policing/shaping for DS/US. "
			REVISION "200704121021Z"		-- April 12, 2007 at 10:21 GMT
			DESCRIPTION 
				"Modifications after review of AFI MIB release SHE R2.5.2.
				New attribute in sheLagGroupTable."
			REVISION "200704271558Z"		-- April 27, 2007 at 15:58 GMT
			DESCRIPTION 
				"Add attribute to sheVlan-table to support McastFlood configuration.
				Modify description for support of sheVlanMulticastPermission attribute in R2.5.2.
				Modify descriptions for support of some sheDhcpProviderTable attributes in R2.5.2.
				Merge MIB 159 for late feature of R2.3 for common MIB version (BridgePortTable, UMAS)."
			REVISION "200705090838Z"		-- May 09, 2007 at 08:38 GMT
			DESCRIPTION 
				"Modify configuration for DsShaping per Port/Queue.
				Add parameters to sheBridgePortTable for individual multicast configuration.
				Modify descriptions for support of some sheDhcpProviderTable attributes in R2.5.2."
			REVISION "200705101053Z"		-- May 10, 2007 at 10:53 GMT
			DESCRIPTION 
				"Remove not longer needed shaping parameter from sheMeterProfileTable."
			REVISION "200705231107Z"		-- May 23, 2007 at 11:07 GMT
			DESCRIPTION 
				"Add new detailed ReqResult-Values.
				Remove support for sheIgmpMaxJoinedSubscribers.
				Add new value sheDhcpBcastTranslationDs to dhcp provider table.
				Change default value for sheVlanServiceType.
				Enable/disable MAT per Vlan. Mat per BridgePort is not longer supported."
			REVISION "200706060901Z"		-- June 06, 2007 at 09:01 GMT
			DESCRIPTION 
				"Correct only descriptions regarding SHE version change R2.5.2->R2.6."
			REVISION "200707091618Z"		-- July 09, 2007 at 16:18 GMT
			DESCRIPTION 
				"Correct description for textual convention SheDhcpRelayAdminStateType.
				Correct syntax for sheIgmpProfileVlanInnerVlanId.
				Correct range for sheMatBaseDslamId."
			REVISION "200707190901Z"		-- July 19, 2007 at 09:01 GMT
			DESCRIPTION 
				"Correct ranges for shapingprofile parameters.
				Merge MIB release for SHE R2.4 ->
				-sheBridgePortIgmpSubscriberAccessMode added into sheBridgePortTable.
				-sheIgmpProviderVlanMulticastLimitation added into sheIgmpProfileTable.
				-sheIgmpProfileVlanForkingMode added into sheIgmpProfileVlanTable, controlgroup and trap.
				-sheErpDomainGlobalGroup and sheErpDomainGlobalControl added."
			REVISION "200708101348Z"		-- August 10, 2007 at 13:48 GMT
			DESCRIPTION 
				"Correct objectlist for sheIgmpProfileVlanEntryCreated-trap."
			REVISION "200709131029Z"		-- September 13, 2007 at 10:29 GMT
			DESCRIPTION 
				"Modify description for sheVlanServiceTagOnly.
				Merge modification from new R2.4 MIB proposal (not supported by R2.6). "
			REVISION "200710241000Z"		-- October 24, 2007 at 10:00 GMT
			DESCRIPTION 
				"R2.7. Minor descriptional changes.
				Expand index of sheMatTable."
			REVISION "200710241117Z"		-- October 24, 2007 at 11:17 GMT
			DESCRIPTION 
				"New release SHE R2.8 supported.
				Add functions in sheBridgePortTable and BridgeBase.
				Add option to sheDhcpRelayAgentOptionType.
				Add functions in sheDhcpProviderTable.
				Add functions in sheIgmpProfileTable.
				Add support for IGMPv3."
			REVISION "200711141137Z"		-- November 14, 2007 at 11:37 GMT
			DESCRIPTION 
				"Correct syntax for sheMatControlReqResult.
				Modify index value for sheMatTable again.
				Update parameter for IGMPv3 support.
				Modify parameter description for sheDhcpBcastTranslationDs
				and sheDhcpCebsMacTranslation.
				Modify parameter names for sheBridgePortPriorityMap usage.
				Correct syntax and description for sheIgmpMaxJoinedGroup."
			REVISION "200711221024Z"		-- November 22, 2007 at 10:24 GMT
			DESCRIPTION 
				"Restore Vlan-Configuration for DHCP again.
				Rename IgmpSourceIpTable."
			REVISION "200712051018Z"		-- December 05, 2007 at 10:18 GMT
			DESCRIPTION 
				"Add parameter for NodeIdentifier to DHCP provider configuration.
				Add vlan-id for DHCP snooping table (CO hiX13600).
				Modify parameter list for Bridge CircuitId and RemoteId configuration."
			REVISION "200712181515Z"		-- December 18, 2007 at 15:15 GMT
			DESCRIPTION 
				"Made config for DhcpUseInnerTag global and separate config for PPPoE providers.
				Made config for IgmpUseInnerTag global.
				Expand BridgePortPriorityOptions configuration.
				Expand sheMatTranslationMode with mode thsNoIndexOffset."
			REVISION "200801071435Z"		-- January 07, 2008 at 14:35 GMT
			DESCRIPTION 
				"Modify PortPriorityOptions parameter.
				Modify RuleGenericMatchAction parameter."
			REVISION "200801150957Z"		-- January 15, 2008 at 09:57 GMT
			DESCRIPTION 
				"Expand BridgePort multicast configuration.
				Modify RuleGenericMatchAction parameter and add new RuleTablePattern.
				Modify ShapingProfileAssignment.
				"
			REVISION "200801281415Z"		-- January 28, 2008 at 14:15 GMT
			DESCRIPTION 
				"Correct sheIgmpModeModified trap.
				Remove last modifications for RuleGenericMatchAction parameter.
				Define new fixedRuleTypes for feature Policing per COS, Protokoll or Vlan."
			REVISION "200802251429Z"		-- February 25, 2008 at 14:29 GMT
			DESCRIPTION 
				"Modify AC feature for MC traffic on bridgeport and igmp provider side.
				Expand IGMP port statistic's for CA and AC counter.
				CEBS support by SHE system only if CXU types CXU_B, CXU_B1 or CXU_C are used (like R2.7)!"
			REVISION "200803200948Z"		-- March 20, 2008 at 09:48 GMT
			DESCRIPTION 
				"Add parameter to BridgeIUProfile for used MAT type selection.
				Add new BridgePortMCastTable + controlgroup to support new R2.8 Mcast parameters.
				Add/Modify parameters to IgmpBase, IgmpProvider and IgmpGroup to support IGMPv3 in R2.8.
				Add detailed failure returncode definitions to ReqResult enum. The scheduled support release is not defined yet."
			REVISION "200804181308Z"		-- April 18, 2008 at 13:08 GMT
			DESCRIPTION 
				"Correct description for sheIgmpDoubleTaggingControlRequest
				and sheIgmpGroupControlRequest.
				Modify description for BridgeBase CircuitId and RemoteId.
				Add parameter to vlan table for configuration of servicename.
				Modify description for sheBridgePortPriorityMapTable: default profile with index 1 can't be deleted.
				Add new parameter sheBridgePortMCastMinUCBandwithLimit to bridgePort MCast configuration table.
				Merge vlan parameter for uplink vlan translation from R2.6 RP2.
				"
			REVISION "200805281145Z"		-- May 28, 2008 at 11:45 GMT
			DESCRIPTION 
				"New parameters for CardQueueConfigurationTable to support HQS mode.
				New EthertypMapping configuration to support EthertypVlan mapping per bridgeport.
				New IpAntispoofing configuration to support IPAS per bridgeport.
				Expand parameter list for StaticIp configuration.
				Define new fixedRuleTypes for feature RateLimiting IGMP.
				New dhcp base parameter for StationMove feature enable/disable.
				Move ReplaceVlanTag parameter to IUPofileTable."
			REVISION "200806301119Z"		-- June 30, 2008 at 11:19 GMT
			DESCRIPTION 
				"Correct stationMoveModified trap.
				Correct syntax and description for sheBridgePortMCastAllowedVlanIdList.
				Assign DscpPriorityMapProfile via IUProfile configuration (add on).
				Correct CardQueueConfiguration table parameter list.
				Modify ShapingProfile assignment for 'perDslPort' usage."
			REVISION "200807141254Z"		-- July 14, 2008 at 12:54 GMT
			DESCRIPTION 
				"Move some R2.8 Mcast releated bridgeport parameter from sheBridgePortMCastConfigTable
				to new sheIgmpBridgePortProviderTable under the sheIgmp subtree -> new group sheIgmpBridgePortConfig.
				Move some new R2.8 parameters from sheIgmpProvileTable to sheIgmpProfileVlanTable."
			REVISION "200807251139Z"		-- July 25, 2008 at 11:39 GMT
			DESCRIPTION 
				"Modify syntax of sheIgmpPortGroupsStpIpAddress.
				The sheBridgePortReplaceVlanTag is used again for enable/disable the feature."
			REVISION "200808281034Z"		-- August 28, 2008 at 10:34 GMT
			DESCRIPTION 
				"Correct possible number accesible premium and non-premium Igmp groups per bridgePort.
				Correct the default mc bandwith limit per bridgePort to 'unlimited' - switch off ac feature.
				Correct description of sheBridgePortControlReplaceVlanTag."
			REVISION "200810071427Z"		-- October 07, 2008 at 14:27 GMT
			DESCRIPTION 
				"Correct IGMP trap parameter list: 
				- sheIgmpProfileVlanEntryCreated  
				- sheIgmpProfileVlanEntryModified.
				Correct syntax for parameters from sheCardQueueConfigurationTable."
			REVISION "200811061009Z"		-- November 06, 2008 at 10:09 GMT
			DESCRIPTION 
				"Modify remarks from ACI.
				Add new parameter to dhcp provider table.
				Modify comment for DhcpAdminState settings."
			REVISION "200811271540Z"		-- November 27, 2008 at 15:40 GMT
			DESCRIPTION 
				"Correct description of bridgePort inner and outer priorityOption setting.
				Correct description of queue weight and watermark settings.
				Correct description of igmp stats controlRequest commands.
				Remove 0 as possible value for sourceIp setting during igmpGroup configuration.
				Correct description of sheLagGroupCollectorMaxDelay - any modification will be ignored.
				Add new group sheBridgeExtResidentialConfig only supported by hiX5608!"
			REVISION "200901221445Z"		-- January 22, 2009 at 14:45 GMT
			DESCRIPTION 
				"Modify syntax for sheDhcpFloodVlanEnabled to enable the flooding
				for DHCP and PPPoE separatly.
				Expand IgmpProvider and IgmpGroup table with new parameter DefaultSourceIpList.
				New command for FdbTable refresh.
				New command for MatTable refresh.
				Add new value for circuitId/RemoteId definition.
				Expand length of circuitId and remoteId bridgeBase parameter."
			REVISION "200903021000Z"		-- March 02, 2009 at 10:00 GMT
			DESCRIPTION 
				"Correct description and default for sheIgmpProviderVlanMulticastLimitation.
				Move sheIgmpProviderDefaultSourceIdList to corresponding sheIgmpProfileVlanTable.
				Modify second index for sheIgmpPortGroupTable and add parameters.
				Expand range for sheBridgeBaseControlMaxHostName to 64.
				Correct default value sheBridgePortLeaveMode."
			REVISION "200904220823Z"		-- April 22, 2009 at 08:23 GMT
			DESCRIPTION 
				"R2.8 BFR2.0 MIB-Update.
				Correct wrong syntaxtype of sheErpDomainGlobalControlMacLearningDelay.
				Modify syntax for sheBridgePortMaxLearnPermitCount.
				Add missed parameter in sheFdbTable.
				DHCP provider config does still not need VlanId config (like R2.6).
				Add new cistPort parameter for support only by 5608 R1.3.
				Add new FdbControl parameter for support only by 5608 R1.3."
			REVISION "200906031640Z"		-- June 03, 2009 at 16:40 GMT
			DESCRIPTION 
				"Correct BridgeBaseModified trap parameter list. No change inside NE.
				Define default values for queue watermark settings.
				"
			REVISION "200908121445Z"		-- August 12, 2009 at 14:45 GMT
			DESCRIPTION 
				"Remove not supported R2.8 parameter for BaseMaxIpUni command and trap."
			REVISION "200909221622Z"		-- September 22, 2009 at 16:22 GMT
			DESCRIPTION 
				"Correct description for sheBridgePortMode.
				Correct description for sheVlanTunnelingL2Protocol and
				sheVlanDefaultGateway.
				Expand valid range for sheBridgePortIpAddressPermitCount to 64."
			REVISION "200911171626Z"		-- November 17, 2009 at 16:26 GMT
			DESCRIPTION 
				"Correct CircuitId and RemoteId format according TR101.
				Modify syntax for sheBcscVendorSpecific.
				Correct usable range for sheRuleControlTosPattern."
			REVISION "201001181125Z"		-- January 18, 2010 at 11:25 GMT
			DESCRIPTION 
				"Add new table for dynamic UMAS configuration per VLAN (CR#003659).
				Remove wildcard option from fdbTable refresh commands."
			::= { she 4 }

		
	
--
-- Type definitions
--
	
		SheBridgeModeType ::= INTEGER
			{
			basicMode(1),
			diffServMode(2),
			enhancedMode(3)
			}

		SheBridgeTaggingModeType ::= INTEGER
			{
			singleTag(1),
			doubleTag(2)
			}

		SheBridgeSharedVlanLearningType ::= INTEGER
			{
			disabled(0),
			enabled(1)
			}

		SheBridgeMacAntiSpoofingType ::= INTEGER
			{
			disabled(0),
			enabled(1)
			}

		SheBridgeRoutingModeType ::= INTEGER
			{
			residential(0),
			unrestricted(1),
			default(2)
			}

		SheBridgeDlfFilterType ::= INTEGER
			{
			disable(0),
			enable(1)
			}

		SheBridgeUnknownMulticastFilterType ::= INTEGER
			{
			disable(0),
			enable(1),
			enableDs(2),
			enableUs(3)
			}

		SheBridgeControlRequestType ::= INTEGER
			{
			none(0),
			noRequest(1),
			setBridgeMode(101),
			setBridgeTaggingMode(102),
			setBridgeMirrorPort(103),
			setBridgeOuterVlanDefaults(104),
			setBridgeCircuitIdFormat(105),
			setBridgeSharedVlanLearning(106),
			setBridgeRemoteIdFormat(107),
			setBridgeStagTPID(108),
			setBridgeMacAntiSpoofing(109),
			setBridgePortVLANDefaults(110),
			setBridgePortUsage(111),
			setBridgePortHostConfigurationProtocol(112),
			setBridgePortMaxLearnPermitCount(113),
			setBridgePortMcastGroupPackageList(114),
			setBridgePortFeature(115),
			setBridgePortCircuitId(116),
			setBridgePortRemoteId(117),
			clearBridgePortCircuitId(118),
			clearBridgePortRemoteId(119),
			setBridgeMacProfileSrcMacAddress(120),
			setBridgePortInnerPVID(121),
			setBridgeRoutingMode(122),
			setBridgeMaxHostName(123),
			setBridgeDlfFilter(124),
			setBridgeUnknownMulticastFilter(125),
			setBridgePortInnerPriority(126),
			setBridgePortIpoaProviderRouterIpAddress(127),
			setBridgeIpoaArpReqInterval(128),
			setBridgeIUProfilePPPoASrcMacAddress(131),
			setBridgeIUProfileUsedMATBasis(132),
			setBridgeIUProfileReplaceVlanTag(133),
			setBridgeIUProfileDscpPriorityMapProfileIndex(134),
			setBridgePortMcastParameter(135),
			setBridgePortIgmpSubscriberAccessMode(136),
			setBridgePortPriorityOptions(141),
			setBridgePortMatEnabled(142),
			setBridgePortIpAddressPermitCount(143),
			createBridgePortPrioMapEntry(151),
			deleteBridgePortPrioMapEntry(152),
			modifyBridgePortPrioMapEntry(153),
			setBridgePortExtMCastParameter(162),
			setBridgePortIpAsMode(165),
			setBridgePortEtypeVlanMapping(166),
			createEtypeVlanMapProfEntry(171),
			modifyEtypeVlanMapProfEntry(172),
			deleteEtypeVlanMapProfEntry(173),
			createVlan(201),
			deleteVlan(202),
			setVlanName(203),
			setVlanPorts(204),
			setVlanMulticastPermission(206),
			setVlanDhcpProviderIndex(207),
			setVlanDefaultGateway(208),
			setVlanPPPoEProviderIndex(209),
			setVlanMgmtVlan(210),
			setVlanServiceTagOnly(211),
			setVlanAgeingTime(212),
			setVlanRoutingMode(213),
			setVlanTunnelingL2Protocol(214),
			setVlanServiceType(215),
			setVlanDlfFlood(216),
			addVlanPorts(222),
			deleteVlanPorts(223),
			setVlanCCMode(230),
			setVlanRouted(231),
			setVlanMcastFlood(232),
			setVlanMatEnable(233),
			setVlanTranslation(235),
			modifySubportServiceName(242),
			clearRuleMatchCounter(299),
			modifyRule(300),
			createRule(301),
			deleteRule(302),
			createMeterProfile(303),
			deleteMeterProfile(304),
			modifyMeterProfile(305),
			setFdbBaseAgeingTime(401),
			setFdbBaseLearningUplink(402),
			refreshFdbTable(403),
			createFdbStaticEntry(404),
			createBcscEntry(501),
			modifyBcscEntry(502),
			deleteBcscEntry(503),
			modifyLagGroupEntry(601),
			modifyLagPortEntry(602),
			assignBridgePortToLag(603),
			unassignBridgePortFromLag(604),
			setDhcpAdminState(701),
			createDhcpProviderEntry(702),
			modifyDhcpProviderEntry(703),
			deleteDhcpProviderEntry(704),
			setDhcpRemoteId(705),
			deleteSnoopEntry(706),
			ipAntiSpoofingSet(707),
			ipAntiSpoofingGracePeriodSet(708),
			setDhcpFloodVlanId(709),
			setDhcpTagForProtocol(715),
			setDhcpStationMove(716),
			setIgmpMode(725),
			createIgmpProviderEntry(726),
			modifyIgmpProviderEntry(727),
			deleteIgmpProviderEntry(728),
			createIgmpProfileVlanEntry(729),
			deleteIgmpProfileVlanEntry(730),
			modifyIgmpProfileVlanDot1p(731),
			createIgmpGroupEntry(732),
			modifyIgmpGroupEntry(733),
			deleteIgmpGroupEntry(734),
			createIgmpMcastGroupPackageEntry(735),
			deleteIgmpMcastGroupPackageEntry(736),
			createPmObject(737),
			modifyPmObject(738),
			deletePmObject(739),
			setIgmpMaxJoinedSubscribers(740),
			clearIgmpStats(742),
			setIgmpProviderChannelAdmission(743),
			setIgmpMcastChannelParameter(744),
			setIgmpMaxJoinedGroup(745),
			modifyIgmpProfileVlanForkingMode(746),
			createIgmpSourceIpAddressEntry(747),
			deleteIgmpSourceIpAddressEntry(748),
			setIgmpTagMode(749),
			modifyMstpBaseStatus(750),
			modifyMstpBaseConfig(751),
			modifyMstpBaseConfIdVlanIdList(752),
			resetMstpTc(753),
			modifyMstpBridgeParamEntry(754),
			modifyMstpPortParamEntry(755),
			resetCistTc(756),
			modifyCistBridgeParameters(757),
			modifyCistPortParamEntry(758),
			setMstpPortBridgeGroupAddress(759),
			createIgmpBridgePortProviderEntry(763),
			modifyIgmpBridgePortProviderEntry(764),
			deleteIgmpBridgePortProviderEntry(765),
			modifyQueuePriorityMapping(775),
			modifyReducedQueuePriorityMapping(776),
			modifyQueueModeEntry(780),
			modifyQueueWeightEntry(781),
			configureCardQueueConfigurationEntry(790),
			deleteCardQueueConfigurationEntry(791),
			createShapingProfile(795),
			modifyShapingProfile(796),
			deleteShapingProfile(797),
			assignShapingProfile(798),
			deleteShapingProfileAssignment(799),
			modifyArpHandling(801),
			createArpFixedIpAddressEntry(802),
			modifyArpFixedIpAddressEntry(803),
			deleteArpFixedIpAddressEntry(804),
			modifyErpDomainTrafficVlan(825),
			modifyErpDomainEntry(826),
			activateErpDomain(827),
			operatorRequestErpDomain(828),
			modifyErpDomainGlobalGroup(829),
			clearQoSPmCounters(850),
			modifyArpVlanFlood(901),
			createCebsPortTableEntry(950),
			deleteCebsPotyTableEntry(951),
			createCebsStaticGatewayTableEntry(952),
			modifyCebsStaticGatewayTableEntry(953),
			deleteCebsStaticGatewayTableEntry(954),
			createCebsVirtualMacTableEntry(955),
			deleteCebsVirtualMacTableEntry(956),
			setExtResidentialMode(990)
			}

		SheBridgeControlReqResultType ::= INTEGER
			{
			none(0),
			noRequest(1),
			comExecStarted(30),
			paramFaulty(31),
			requestBusy(32),
			setDataFailed(34),
			aswTimeout(35),
			commandFailed(36),
			commandSucceeded(37),
			wrongPortVlanIndex(38),
			noMoreResources(40),
			parameterConflict(41),
			vlanServiceTypeConflict(42),
			featureNotSupportedYet(50),
			vlanInternalGeneralFailure(2101),
			vlanCreateFailOnInvalidVlanID(2102),
			vlanDeleteFailOnInvalidVlanID(2103),
			vlanModifyFailOnInvalidVlanID(2104),
			vlanModifyFailOnInvalidParameterRange(2105),
			vlanModifyFailOnInvalidParameter(2106),
			vlanInternalFailureOnIuCommunication(2107),
			vlanInternalFailureOnRestrictedVlanAccess(2108),
			vlanPortListModifyFailOnInvalidPortId(2109),
			vlanPortListModifyFail(2110),
			vlanPortListModifyFailOnOnlyUplinksForMgmtVlan(2111),
			vlanPortListModifyFailOnRestrictedPortListForCCMode(2112),
			vlanModifyFailOnWrongServiceTypeSelected(2113),
			vlanModifyFailOnRestrictedPortListForCCMode(2114),
			vlanModifyFailOnMaxNumberOfVlanRelationsReachedForPort(2115),
			vlanMatModifyFailOnDslamIdNotSet(2116),
			vlanVrBindingModifyFailOnRouterIdNotSet(2117)
			}

		SheBridgePortUsageType ::= INTEGER
			{
			notUsed(1),
			upLink(2),
			cascading(3),
			subscriber(4),
			aggregated(5),
			subcascading(6),
			bondingNotUsed(10),
			bondingSubscriber(11),
			bondedSubscriber(12),
			physbondedSubscriber(13),
			vccAggregatorNotUsed(20),
			vccAggregatorUsed(21),
			vccAggregated(22)
			}

		SheHostConfigurationProtocolType ::= INTEGER
			{
			none(0),
			useDHCP(1),
			usePPPoE(2),
			useDHCPandPPPoE(3)
			}

		SheBridgePortModeType ::= INTEGER
			{
			useIpoE(0),
			useIpoA(1),
			usePPPoA(2),
			useAuto(3)
			}

		SheBridgePortTaggingModeType ::= INTEGER
			{
			off(0),
			tagged(1),
			untagged(2)
			}

		SheBridgePortIgmpSubscriberAccessModeType ::= INTEGER
			{
			ipoe(0),
			pppoe(1)
			}

--  If a tag is added to an upstream user frame
-- set the .1p priority bits
-- dscp(1)
-- - according DSCP of IP header (use sheBridgePortPriorityMapProfile)
-- userTag(2)
-- - according user tag .1p
-- force(3)
-- - per port configured .1p (use sheBridgePortPriority)
		SheBridgePortPriorityOptionType ::= INTEGER
			{
			dscp(1),
			userTag(2),
			force(3)
			}

		SheVlanStatusType ::= INTEGER
			{
			static(1),
			dynamic(2)
			}

		SheVlanServiceType ::= INTEGER
			{
			doubleTagging(1),
			vlanStacking(2)
			}

		SheRuleType ::= INTEGER
			{
			globalSrcMacDeny(1),
			portFlowControl(2),
			meteringBridgePort(3),
			qosVlan(4),
			qosDscp(5),
			qosBridgePort(6),
			providerDoubleTagVlan01(7),
			qosDoubleTagPrio01(8),
			qosDoubleTagDscp01(9),
			providerDoubleTagVlan02(10),
			qosDoubleTagPrio02(11),
			qosDoubleTagDscp02(12),
			mirrorBridgePort(13),
			qosDscp02(14),
			portFlowControl02(15),
			providerSingleTagVlan01(16),
			providerSingleTagVlan02(17),
			portFlowControl03(18),
			cosTranslation(19),
			etherTypTranslation(20),
			vlanTranslation(21),
			dscpTranslation(22),
			meteringDot1P(25),
			meteringVlan(26),
			meteringDhcpOnIU(27),
			meteringDhcpOnPort(28),
			meteringArpOnIU(29),
			meteringArpOnPort(30),
			meteringIgmpOnIU(31),
			meteringIgmpOnPort(32),
			meteringDslPort(33),
			genericRule(50),
			genericAdminRule(51)
			}

--   
-- 
		SheRuleMatchType ::= INTEGER
			{
			ignore(1),
			exact(2),
			exclude(3)
			}

		SheRuleActionType ::= INTEGER
			{
			deny(1),
			allow(2),
			meter(3),
			changeInnerVlan(4),
			changeOuterVlan(5),
			changeInnerPriority(6),
			changeOuterPriority(7),
			changeTos(8),
			changeDscp(9),
			changeInnerVlanTag(10),
			changeOuterVlanTag(11),
			assignTC(12),
			mirror(13)
			}

		SheRuleFlowType ::= INTEGER
			{
			upstream(1),
			downstream(2),
			bidirectional(3)
			}

		SheRuleGenericActionType ::= BITS
			{
			deny(0),
			allow(1),
			meter(2),
			redirect(3),
			mirror(4),
			setDscp(5),
			setPriority(6),
			changeTagPriority(7),
			changeTagPriorityWithTos(8),
			setIpPrecedence(9),
			changeTosWithTagPriority(10),
			rateLimit(11),
			changeVlanId(12),
			copyToCpu(13),
			count(14),
			untag(15)
			}

		SheRuleActivationStateType ::= INTEGER
			{
			notActive(0),
			active(1)
			}

		SheFdbStatusType ::= INTEGER
			{
			other(1),
			invalid(2),
			learned(3),
			self(4),
			mgmt(5),
			static(6)
			}

		SheLagMethodType ::= INTEGER
			{
			srcmac(1),
			dstmac(2),
			xormac(3),
			srcip(4),
			dstip(5),
			xorip(6)
			}

		SheLagStateType ::= BITS
			{
			lacpActivity(0),
			lacpTimeout(1),
			lacpAggregation(2),
			lacpSynchronization(3),
			lacpCollecting(4),
			lacpDistribution(5),
			lacpDefaulted(6),
			lacpExpired(7)
			}

		SheDhcpRelayAgentOptionType ::= INTEGER
			{
			dhcpNone(0),
			dhcpOption82CircuitId(1),
			dhcpOption82RemoteId(2),
			dhcpOption82Both(3),
			pppoeNone(4),
			pppoeOptionCircuitId(5),
			pppoeOptionRemoteId(6),
			pppoeOptionBoth(7),
			simpDhcpNone(8),
			simpDhcpOption82CircuitId(9),
			simpDhcpOption82RemoteId(10),
			simpDhcpOption82Both(11),
			dhcpOption82LineProperty(12),
			dhcpOption82CircuitIdLineProperty(13),
			dhcpOption82RemoteIdLineProperty(14),
			dhcpOption82BothIdLineProperty(15),
			pppoeOptionLineProperty(16),
			pppoeOptionCircuitIdLineProperty(17),
			pppoeOptionRemoteIdLineProperty(18),
			pppoeOptionBothIdLineProperty(19),
			simpDhcpOption82LineProperty(20),
			simpDhcpOption82CircuitIdLineProperty(21),
			simpDhcpOption82RemoteIdLineProperty(22),
			simpDhcpOption82BothIdLineProperty(23)
			}

		SheIgmpModeType ::= INTEGER
			{
			noIgmp(1),
			snoopOnly(3),
			proxy(4)
			}

		SheIgmpProfileVlanForkingModeType ::= INTEGER
			{
			noForking(0),
			ipoeForking(1),
			pppoeForking(2)
			}

--   An Interval type identifier to select between the 15 minute
-- counters and the day counter.
		ShePmIntervalType ::= INTEGER
			{
			min15(1),
			day(2)
			}

--   A type identifier to estimate the validity of a PM event
-- counter.
		ShePmSuspectFlagType ::= INTEGER
			{
			undefined(0),
			reliable(1),
			suspect(2)
			}

		SheIgmpStatsBaseControlRequestType ::= INTEGER { clearIgmpStatsBase(741) }

		SheIgmpStatsBaseControlStatusType ::= INTEGER
			{
			requestIdle(1),
			requestBusy(2),
			requestPassed(3),
			requestFailed(4)
			}

		SheIgmpStatsBaseControlReqResultType ::= INTEGER
			{
			noRequest(1),
			comExecStarted(30),
			paramFaulty(31),
			requestBusy(32),
			setDataFailed(34),
			aswTimeout(35),
			commandFailed(36),
			commandSucceeded(37),
			wrongPortVlanIndex(38)
			}

		SheIgmpStatsPortControlRequestType ::= INTEGER { clearIgmpStatsPort(742) }

		SheIgmpStatsPortControlStatusType ::= INTEGER
			{
			requestIdle(1),
			requestBusy(2),
			requestPassed(3),
			requestFailed(4)
			}

		SheIgmpStatsPortControlReqResultType ::= INTEGER
			{
			noRequest(1),
			comExecStarted(30),
			paramFaulty(31),
			requestBusy(32),
			setDataFailed(34),
			aswTimeout(35),
			commandFailed(36),
			commandSucceeded(37),
			wrongPortVlanIndex(38)
			}

		SheIgmpStatsProviderControlRequestType ::= INTEGER { clearIgmpStatsProvider(743) }

		SheIgmpFloodVlanControlRequestType ::= INTEGER
			{
			createIgmpFloodVlan(743),
			deleteIgmpFloodVlan(744)
			}

		SheBridgeInterfaceType ::= INTEGER
			{
			uplink(1),
			downlink(2),
			cascading(3),
			subcascading(4)
			}

		SheQueueModeType ::= INTEGER
			{
			strict(0),
			weighted(1)
			}

--   The sheBridgePortIndex that is used to
-- differentiate between logical ports. The value -1 is
-- used to indicate that it is unassigned (Invalid).
		SheBridgePortIndexOrInvalid ::= INTEGER (-1 | 1..65535)

		SheErpDomainOperatorRequestType ::= INTEGER
			{
			manualToSecondary(1),
			clear(2)
			}

		SheErpNodeType ::= INTEGER
			{
			normalNode(1),
			rmNode(2)
			}

--   The virtual LAN identifier (VLAN ID) that may be used to
-- differentiate among traffic streams. The value -1 is
-- used to indicate that it is unassigned (Invalid).
		SheVlanIdOrInvalid ::= Integer32 (-1 | 1..4094)

		SheErpDomainNodeStatusType ::= INTEGER
			{
			rmIdle(1),
			primaryProtecting(2),
			protecting(3),
			idle(4),
			failedSecondary(5),
			failedPrimary(6),
			preForward(7),
			isolated(8),
			deactivated(9),
			backoff(10)
			}

		SheErpDomainRingStatusType ::= INTEGER
			{
			normal(1),
			protecting(2),
			unknown(3)
			}

		SheBcscTrafficType ::= INTEGER
			{
			broadcast(1),
			multicast(2),
			dlf(3)
			}

		SheBcscScopeType ::= INTEGER
			{
			port(1),
			vlan(2)
			}

		SheBcscThresholdType ::= INTEGER
			{
			packetPerSecond(1),
			bytesPerSecond(2)
			}

		SheMstpPortParamStateType ::= INTEGER
			{
			blocking(1),
			listening(2),
			learning(3),
			forwarding(4),
			disabled(5),
			discarding(6)
			}

		SheMstpPortParamPortRoleType ::= INTEGER
			{
			rootPort(1),
			designatedPort(2),
			alternatePort(3),
			backupPort(4),
			disabledPort(5),
			masterPort(6)
			}

		SheCistBridgeProtoParamForceVerType ::= INTEGER
			{
			stpCompatibility(0),
			normalOperation(2),
			mstpCompatibility(3)
			}

--   ForceTrue. The administrator requires the MAC to be
-- treated as if it is connected to a point-to-point LAN.
-- ForceFalse. The administrator requires the MAC to be
-- treated as connected to a non-point-to-point LAN.
-- Auto. The administrator requires the point-to-point
-- status of the MAC to be determined by specific MAC
-- procedures.
		SheCistAdminPTPMacType ::= INTEGER
			{
			forceTrue(1),
			forceFalse(2),
			auto(3)
			}

		SheMstpPortControlBridgeGroupAddress ::= INTEGER
			{
			bridgeGroupAddress(1),
			providerBridgeGroupAddress(2)
			}

		SheArpFixedIpAntiSpoofingStatusType ::= INTEGER
			{
			inactive(0),
			active(1)
			}

		SheIpAntiSpoofingStatusType ::= INTEGER
			{
			inactive(0),
			active(1)
			}

		SheArpVlanFloodType ::= INTEGER
			{
			enable(1),
			disable(2),
			default(3)
			}

--   UMAS(Uplink MAC AntiSpoofing)
-- 
		SheUmasControlRequestType ::= INTEGER
			{
			setUmasUseDhcpNextHop(101),
			addUmasStaticAddr(102),
			delUmasStaticAddr(103),
			setUmasUsePppoeNextHop(104),
			setUmasPppoeAgingTime(105),
			createUmasVlanEntry(110),
			deleteUmasVlanEntry(111)
			}

		SheUmasControlReqResultType ::= INTEGER
			{
			noRequest(1),
			comExecStarted(30),
			paramFaulty(31),
			requestBusy(32),
			setDataFailed(34),
			aswTimeout(35),
			commandFailed(36),
			commandSucceeded(37)
			}

--   MAT(MAC Address Translation)
-- 
		SheMatControlRequestType ::= INTEGER
			{
			setDslamId(100),
			setPortEnable(101),
			setMatTranslationMode(102),
			refreshMatTable(105)
			}

		SheBridgePortEtypeActionType ::= INTEGER
			{
			noAction(0),
			addTag(1),
			replaceOuterTag(2)
			}

	
--
-- Textual conventions
--
	
		SheMcastLeaveMode ::= TEXTUAL-CONVENTION
			STATUS current
			DESCRIPTION 
				"The leave mode of a bridgeport for mcast traffic."
			SYNTAX INTEGER
				{
				normal(0),
				fast(1),
				ehtMode(2)
				}

		SheBridgePortIpAsModeType ::= TEXTUAL-CONVENTION
			STATUS current
			DESCRIPTION 
				"The possible settings for bridgeport based IpAntispoofing."
			SYNTAX INTEGER
				{
				offIpAs(0),
				onIpAsNoVlanCheck(1),
				onIpAsInnerVlanCheck(2),
				onIpAsOuterVlanCheck(3),
				onIpAsBothVlanCheck(4)
				}

		SheBridgeIUProfileUsedMATBasisType ::= TEXTUAL-CONVENTION
			STATUS current
			DESCRIPTION 
				"Used type for selection of MAT basis per IU."
			SYNTAX INTEGER
				{
				useMATperVlan(1),
				useMATperBridgeport(2)
				}

		SheBridgePortACStatus ::= TEXTUAL-CONVENTION
			STATUS current
			DESCRIPTION 
				"Description."
			SYNTAX INTEGER
				{
				deny(0),
				accept(1)
				}

		SheVlanRoutedType ::= TEXTUAL-CONVENTION
			STATUS current
			DESCRIPTION 
				"ARP handling per vlan."
			SYNTAX INTEGER
				{
				switching(0),
				routing(1)
				}

		SheMeterProfileUseParametersType ::= TEXTUAL-CONVENTION
			STATUS current
			DESCRIPTION 
				"This type definition defines a bit-map for using the meterprofile parameter settings.
				If the corresponding bit is set to one the parameters should be used. "
			SYNTAX BITS
				{
				policingUS(0),
				policingDS(1)
				}

		SheDhcpRelayAdminStateType ::= TEXTUAL-CONVENTION
			STATUS current
			DESCRIPTION 
				"telegram handling for DHCP and PPPoE
				
				relay: valid telegrams are handled, invalid telegrams are dropped
				snoop: valid telegrams are forwarded, invalid telegrams are dropped
				bridge: valid telegrams are forwarded, invalid telegrams are forwarded
				
				handling explanation:
				dhcpPppoeRelayRelay -> dhcp and Pppoe use mode relay
				dhcpPppoeRelaySnoop -> dhcp use mode relay and Pppoe use mode snoop
				
				Attention:
				The value up(1) and down(2) are only valid for she R1.5, R2.0 and R2.3.
				Release R2.5 and later will only accept value's 4..12"
			SYNTAX INTEGER
				{
				up(1),
				down(2),
				testing(3),
				dhcpPppoeRelayRelay(4),
				dhcpPppoeRelaySnoop(5),
				dhcpPppoeRelayBridge(6),
				dhcpPppoeSnoopRelay(7),
				dhcpPppoeSnoopSnoop(8),
				dhcpPppoeSnoopBridge(9),
				dhcpPppoeBridgeRelay(10),
				dhcpPppoeBridgeSnoop(11),
				dhcpPppoeBridgeBridge(12)
				}

		SheDhcpUseTagForProtocolsType ::= TEXTUAL-CONVENTION
			STATUS current
			DESCRIPTION 
				"Used for configuration of global DHCP and PPPoE useTag settings."
			SYNTAX BITS
				{
				dhcpUseInnerTagTrue(0),
				pppoeUseInnerTagTrue(1)
				}

		SheIgmpVlanMode ::= TEXTUAL-CONVENTION
			STATUS current
			DESCRIPTION 
				"Configure VLAN mode for the system.
				This configuration is only functions when system is configured in 
				double tagging mode."
			SYNTAX INTEGER
				{
				inner(1),
				outer(2)
				}

		SheIgmpVersionType ::= TEXTUAL-CONVENTION
			STATUS current
			DESCRIPTION 
				"To configure the supported Igmp version on provider vlan base."
			SYNTAX INTEGER
				{
				iGMPv2(1),
				iGMPv3(2),
				iGMPv3Compatible(3)
				}

		SheIgmpProviderASM ::= TEXTUAL-CONVENTION
			STATUS current
			DESCRIPTION 
				"Description."
			SYNTAX INTEGER
				{
				enable(1),
				disable(2)
				}

		SheIgmpProviderVlanCxuSnoopingState ::= TEXTUAL-CONVENTION
			STATUS current
			DESCRIPTION 
				"Description."
			SYNTAX INTEGER
				{
				disable(0),
				enable(1)
				}

		SheIgmpPortGroupsFiltermodeType ::= TEXTUAL-CONVENTION
			STATUS current
			DESCRIPTION 
				"filter-mode may be either INCLUDE or EXCLUDE."
			SYNTAX INTEGER
				{
				include(1),
				exclude(2)
				}

		SheIgmpProviderACStatus ::= TEXTUAL-CONVENTION
			STATUS current
			DESCRIPTION 
				"Description."
			SYNTAX INTEGER
				{
				deny(0),
				accept(1)
				}

		SheQueueColourAwareType ::= TEXTUAL-CONVENTION
			STATUS current
			DESCRIPTION 
				"Description."
			SYNTAX INTEGER
				{
				none(0),
				dscp(2),
				providerBridge(4)
				}

		SheQueueDiscardPolicyType ::= TEXTUAL-CONVENTION
			STATUS current
			DESCRIPTION 
				"Description."
			SYNTAX INTEGER
				{
				tailDrop(1),
				wRed(2)
				}

		SheCardQueueModeType ::= TEXTUAL-CONVENTION
			STATUS current
			DESCRIPTION 
				"The possible queue modes a DSL IU can use."
			SYNTAX INTEGER
				{
				mode4QueueFlat(1),
				mode8QueueFlat(2),
				modeHQS(3)
				}

		SheMatTranslationModeType ::= TEXTUAL-CONVENTION
			STATUS current
			DESCRIPTION 
				"The attribute descripes, which format for MAC address translation will be used."
			SYNTAX INTEGER
				{
				world(1),
				ths(2),
				thsNoIndexOffset(3)
				}

		SheVlanProtocolHandlingType ::= TEXTUAL-CONVENTION
			STATUS current
			DESCRIPTION 
				"Protocol handling per Vlan. "
			SYNTAX INTEGER
				{
				off(0),
				deny(1),
				proxy(2)
				}

		SheBridgePortMCastAllowedVlanIdListType ::= TEXTUAL-CONVENTION
			STATUS current
			DESCRIPTION 
				"Description."
			SYNTAX BITS
				{
				wildCard(0),
				vlan1(1),
				vlan2(2),
				vlan3(3),
				vlan4(4),
				vlan5(5),
				vlan6(6),
				vlan7(7),
				vlan8(8),
				vlan9(9),
				vlan10(10),
				vlan11(11),
				vlan12(12),
				vlan13(13),
				vlan14(14),
				vlan15(15),
				vlan16(16),
				vlan17(17),
				vlan18(18),
				vlan19(19),
				vlan20(20),
				vlan21(21),
				vlan22(22),
				vlan23(23),
				vlan24(24),
				vlan25(25)
				}

		SheDhcpFloodingType ::= TEXTUAL-CONVENTION
			STATUS current
			DESCRIPTION 
				"To configure the flooding of DHCP and/or PPPoE packets per vlan."
			SYNTAX INTEGER
				{
				enableFloodingDhcpAndPppoE(1),
				disableFloodingDhcpAndPppoE(2),
				enableFloodingDhcpOnly(3),
				enableFloodingPppoEOnly(4)
				}

		SheBridgeMaxIpAddressType ::= TEXTUAL-CONVENTION
			STATUS current
			DESCRIPTION 
				"Used inside bridge configuration for maxIp support."
			SYNTAX Unsigned32 (1..64)

		SheBridgeIdType ::= TEXTUAL-CONVENTION
			STATUS current
			DESCRIPTION 
				"Used as type defintion for BridgeBase and BridgePort CircuitId and RemoteId configuration.
				The following predefined types are available:
				    %B -> portstring (like 'iuslot'/'iuport')
				    %M -> mac address
				    %N -> NodeId or Hostname (only if individuell NodeIdentifier not available)
				    %T -> (dsl) line type (adsl, vdsl, shdsl)
				    %S -> slot
				    %P -> port
				    %R -> subport/servicename or Vlan ID (only if subport/servicename not available)
				    %V -> unique vcc id
				    %b -> unique bridgeport id
				    %p -> vpi number
				    %c -> vci number
				    %E -> ethernet priority
				    %v -> vlan ID
				    %s -> slot number as printed on shelf
				    %t -> tc-layer type (atm, eth)
				
				Useful separation characters: space . , ; / - : *
				It is also allowed to place free text.
				Predefined types will be replaced by NE with the requested information.
				The maximum total length of a resulting Id string is still 63 byte (overlaps will be cut off)!"
			SYNTAX OCTET STRING (SIZE (0..63))

	
--
-- Node definitions
--
	
		sheBridge OBJECT IDENTIFIER ::= { sheBridgeMib 1 }

		
--    
-- 1.3.6.1.4.1.231.7.1.2.2.1.4.1.1
		sheBridgeBase OBJECT IDENTIFIER ::= { sheBridge 1 }

		
--   1.3.6.1.4.1.231.7.1.2.2.1.4.1.1.1
		sheBridgeBaseMode OBJECT-TYPE
			SYNTAX SheBridgeModeType
			MAX-ACCESS read-only
			STATUS current
			DESCRIPTION
				"The general operating mode of the bridge."
			::= { sheBridgeBase 1 }

		
--  1.3.6.1.4.1.231.7.1.2.2.1.4.1.1.2
		sheBridgeBaseTaggingMode OBJECT-TYPE
			SYNTAX SheBridgeTaggingModeType
			MAX-ACCESS read-only
			STATUS current
			DESCRIPTION
				"The general tagging mode of the bridge."
			::= { sheBridgeBase 2 }

		
--    
-- 1.3.6.1.4.1.231.7.1.2.2.1.4.1.1.3
		sheBridgeBaseMirrorPort OBJECT-TYPE
			SYNTAX Integer32
			MAX-ACCESS read-only
			STATUS current
			DESCRIPTION
				"The Mirror port of the system. That is a sheBridgePortIndex
				and it could only be used on ports with bridgePortUsage = uplink. 
				This value should be 0 if no mirror-port is configured in the system"
			DEFVAL { 0 }
			::= { sheBridgeBase 3 }

		
--   1.3.6.1.4.1.231.7.1.2.2.1.4.1.1.4
		sheBridgeBaseOuterPVID OBJECT-TYPE
			SYNTAX Integer32 (1..4093)
			MAX-ACCESS read-only
			STATUS current
			DESCRIPTION
				"The default PVID of the outer Vlan used by the switch fabric in case of doubleTag-Mode or
				if a frame with priority tag is received and no other rule to change the vlan tag will match."
			::= { sheBridgeBase 4 }

		
--   1.3.6.1.4.1.231.7.1.2.2.1.4.1.1.5
		sheBridgeBaseOuterPriority OBJECT-TYPE
			SYNTAX Integer32 (0..7)
			MAX-ACCESS read-only
			STATUS current
			DESCRIPTION
				"The default .1p-Priority of the outer vlan in case of doubleTag-Mode. "
			::= { sheBridgeBase 5 }

		
--   1.3.6.1.4.1.231.7.1.2.2.1.4.1.1.6
		sheBridgeBaseCircuitIdFormat OBJECT-TYPE
			SYNTAX SheBridgeIdType
			MAX-ACCESS read-only
			STATUS current
			DESCRIPTION
				"The default value should be: 
				'%N %t %S/%P:%p.%c'  -> when ATM/DSL is used
				'%N %t %S/%P:%v'     -> when Ethernet/DSL is used
				
				It is up to the customer, to select the needed informations from this list and
				use a meaningfull combination. Also a combination with free text is possible.
				The maximum total length of a resulting circuitId is still 63 byte (overlaps will be cut off)!"
			::= { sheBridgeBase 6 }

		
--   1.3.6.1.4.1.231.7.1.2.2.1.4.1.1.7
		sheBridgeBaseSharedVlanLearning OBJECT-TYPE
			SYNTAX SheBridgeSharedVlanLearningType
			MAX-ACCESS read-only
			STATUS current
			DESCRIPTION
				"Enable or disable the feature SharedVlanLearning in the NE."
			DEFVAL { 0 }
			::= { sheBridgeBase 7 }

		
--   1.3.6.1.4.1.231.7.1.2.2.1.4.1.1.8
		sheBridgeBaseRemoteIdFormat OBJECT-TYPE
			SYNTAX SheBridgeIdType
			MAX-ACCESS read-only
			STATUS current
			DESCRIPTION
				"The default value is: '%M'
				
				It is up to the custoumer, to select the needed informations from this list and
				use a meaningfull combination. Also a combination with free text is possible.
				The maximum total length of a resulting remoteId is still 63 byte (overlaps will be cut off)!"
			::= { sheBridgeBase 8 }

		
--   1.3.6.1.4.1.231.7.1.2.2.1.4.1.1.9
		sheBridgeBaseStagTPID OBJECT-TYPE
			SYNTAX Integer32 (0..65535)
			MAX-ACCESS read-only
			STATUS current
			DESCRIPTION
				"The TPID of the service tag if doubleTag is enabled."
			::= { sheBridgeBase 9 }

		
--   1.3.6.1.4.1.231.7.1.2.2.1.4.1.1.10
		sheBridgeBaseMacAntiSpoofing OBJECT-TYPE
			SYNTAX SheBridgeMacAntiSpoofingType
			MAX-ACCESS read-only
			STATUS current
			DESCRIPTION
				"Enable or disable the feature MacAntiSpoofing in the NE."
			::= { sheBridgeBase 10 }

		
--   1.3.6.1.4.1.231.7.1.2.2.1.4.1.1.11
		sheBridgeBaseRoutingMode OBJECT-TYPE
			SYNTAX SheBridgeRoutingModeType
			MAX-ACCESS read-only
			STATUS current
			DESCRIPTION
				"residential or unrestricted the feature Routing Mode of BridgeBase in the NE."
			::= { sheBridgeBase 11 }

		
--   1.3.6.1.4.1.231.7.1.2.2.1.4.1.1.12
		sheBridgeBaseMaxHostName OBJECT-TYPE
			SYNTAX Integer32 (1..64)
			MAX-ACCESS read-only
			STATUS current
			DESCRIPTION
				"the maximum length of hostname for circuit-id or remote-id."
			::= { sheBridgeBase 12 }

		
--   1.3.6.1.4.1.231.7.1.2.2.1.4.1.1.13
		sheBridgeBaseDlfFilter OBJECT-TYPE
			SYNTAX SheBridgeDlfFilterType
			MAX-ACCESS read-only
			STATUS current
			DESCRIPTION
				"The policy of DLF (destination lookup failur) unicast packets from uplink.
				Enable DLF filter -> destination-mac unknown unicast towards subscriber ports blocked
				Disable DLF filter -> destination-mac unknown unicast towards subscriber ports allowed
				default:enable
				"
			::= { sheBridgeBase 13 }

		
--   1.3.6.1.4.1.231.7.1.2.2.1.4.1.1.14
		sheBridgeBaseUnknownMuticastFilter OBJECT-TYPE
			SYNTAX SheBridgeUnknownMulticastFilterType
			MAX-ACCESS read-only
			STATUS current
			DESCRIPTION
				"The policy of unknown multicast packets from uplink. It can be set to enable when routing mode is residential
				default: enable in R2.0, disable in R2.3 / R2.5.x
				Possible values:
				disable(0),
				enable(1)    -> means enable both directions!
				enableDs(2)  -> enable only downstream direction
				enableUs(3)  -> enable only upstream direction
				"
			::= { sheBridgeBase 14 }

		
--   1.3.6.1.4.1.231.7.1.2.2.1.4.1.1.15
		sheBridgeBaseIpoaArpReqInterval OBJECT-TYPE
			SYNTAX Unsigned32
			UNITS "sec"
			MAX-ACCESS read-only
			STATUS current
			DESCRIPTION
				"The interval of ARP resolution for IPoA Bridgeport 
				Default: 0
				If the value is 0, it means NE does not send any arp request to an ipoa provider edge router after the router ip address is resolved.
				Thus, if the ipoa provider edge router's MAC address is changed, packet uses wrong MAC address, unused one, for ipoa provider edge router.
					"
			::= { sheBridgeBase 15 }

		
		sheBridgeBaseMaxIpUNI OBJECT-TYPE
			SYNTAX SheBridgeMaxIpAddressType
			MAX-ACCESS read-only
			STATUS current
			DESCRIPTION
				"This is the maximum number of possible IpAddresses (DHCP or fixed IP) per UNI Port.
				
				New parameter with SHE R2.8."
			DEFVAL { 64 }
			::= { sheBridgeBase 16 }

		
--   1.3.6.1.4.1.231.7.1.2.2.1.4.1.2
		sheBridgeBaseControl OBJECT IDENTIFIER ::= { sheBridge 2 }

		
--   1.3.6.1.4.1.231.7.1.2.2.1.4.1.2.1
		sheBridgeBaseControlRequest OBJECT-TYPE
			SYNTAX SheBridgeControlRequestType
			MAX-ACCESS read-write
			STATUS current
			DESCRIPTION
				"setBridgeMode:
				sheBridgeBaseControlMode
				
				setBridgeTaggingMode:
				sheBridgeBaseControlTaggingMode
				
				setBridgeMirrorPort:
				sheBridgeBaseControlMirrorPort
				
				setBridgeOuterVlanDefaults:
				sheBridgeBaseControlOuterPVID
				sheBridgeBaseControlOuterPriority
				
				setBridgeCircuitIdFormat:
				sheBridgeBaseControlCircuitIdFormat
				
				setBridgeSharedVlanLearning:
				sheBridgeBaseControlSharedVlanLearning
				
				setBridgeRemoteIdFormat:
				sheBridgeBaseControlRemoteIdFormat
				
				setBridgeStagTPID:
				sheBridgeBaseControlStagTPID
				
				setBridgeMacAntiSpoofing:
				sheBridgeBaseControlMacAntiSpoofing
				
				setBridgeRoutingMode:
				sheBridgeBaseControlRoutingMode
				
				setBridgeMaxHostName:
				sheBridgeBaseControlMaxHostName
				
				setBridgeDlfFilter:
				sheBridgeBaseControlDlfFilter
				
				setBridgeUnknownMulticastFilter:
				sheBridgeBaseControlUnknownMulticastFilter
				
				setBridgeIpoaArpReqInterval:
				sheBridgeBaseControlIpoaArpReqInterval"
			::= { sheBridgeBaseControl 1 }

		
--    
-- 1.3.6.1.4.1.231.7.1.2.2.1.4.1.2.2
		sheBridgeBaseControlStatus OBJECT-TYPE
			SYNTAX SheControlStatusType
			MAX-ACCESS read-only
			STATUS current
			DESCRIPTION
				"The status of a user command. 
				"
			::= { sheBridgeBaseControl 2 }

		
--   1.3.6.1.4.1.231.7.1.2.2.1.4.1.2.3
		sheBridgeBaseControlTimer OBJECT-TYPE
			SYNTAX Gauge32
			MAX-ACCESS read-only
			STATUS current
			DESCRIPTION
				"The maximum wait time for the manager for a long running user command."
			::= { sheBridgeBaseControl 3 }

		
--    
-- 1.3.6.1.4.1.231.7.1.2.2.1.4.1.2.4
		sheBridgeBaseControlReqResult OBJECT-TYPE
			SYNTAX SheBridgeControlReqResultType
			MAX-ACCESS read-only
			STATUS current
			DESCRIPTION
				"The result of the last user command."
			::= { sheBridgeBaseControl 4 }

		
--    
-- 1.3.6.1.4.1.231.7.1.2.2.1.4.1.2.5
		sheBridgeBaseControlTimeStamp OBJECT-TYPE
			SYNTAX Unsigned32
			UNITS "sec"
			MAX-ACCESS read-only
			STATUS current
			DESCRIPTION
				"The time stamp of the last command (end of command)."
			::= { sheBridgeBaseControl 5 }

		
--    
-- 1.3.6.1.4.1.231.7.1.2.2.1.4.1.2.6
		sheBridgeBaseControlMode OBJECT-TYPE
			SYNTAX SheBridgeModeType
			MAX-ACCESS read-write
			STATUS current
			DESCRIPTION
				"Set the basic bridge mode."
			::= { sheBridgeBaseControl 6 }

		
--   1.3.6.1.4.1.231.7.1.2.2.1.4.1.2.7
		sheBridgeBaseControlTaggingMode OBJECT-TYPE
			SYNTAX SheBridgeTaggingModeType
			MAX-ACCESS read-write
			STATUS current
			DESCRIPTION
				"Set the basic tagging mode."
			::= { sheBridgeBaseControl 7 }

		
--   1.3.6.1.4.1.231.7.1.2.2.1.4.1.2.8
		sheBridgeBaseControlMirrorPort OBJECT-TYPE
			SYNTAX Integer32
			MAX-ACCESS read-write
			STATUS current
			DESCRIPTION
				"Set the mirror port."
			::= { sheBridgeBaseControl 8 }

		
--   1.3.6.1.4.1.231.7.1.2.2.1.4.1.2.9
		sheBridgeBaseControlOuterPVID OBJECT-TYPE
			SYNTAX Integer32 (1..4093)
			MAX-ACCESS read-write
			STATUS current
			DESCRIPTION
				"The PVID of the outer Vlan in case of doubleTag-Mode."
			::= { sheBridgeBaseControl 9 }

		
--   1.3.6.1.4.1.231.7.1.2.2.1.4.1.2.10
		sheBridgeBaseControlOuterPriority OBJECT-TYPE
			SYNTAX Integer32 (0..7)
			MAX-ACCESS read-write
			STATUS current
			DESCRIPTION
				"The default .1p-Priority of the outer vlan in case of doubleTag-Mode. "
			::= { sheBridgeBaseControl 10 }

		
--   1.3.6.1.4.1.231.7.1.2.2.1.4.1.2.11
		sheBridgeBaseControlCircuitIdFormat OBJECT-TYPE
			SYNTAX SheBridgeIdType
			MAX-ACCESS read-write
			STATUS current
			DESCRIPTION
				"It is up to the customer, to select the needed informations from this list and
				use a meaningfull combination. Also a combination with free text is possible.
				The maximum total length of a resulting circuitId is still 63 byte (overlaps will be cut off)!"
			::= { sheBridgeBaseControl 11 }

		
--   1.3.6.1.4.1.231.7.1.2.2.1.4.1.2.12
		sheBridgeBaseControlSharedVlanLearning OBJECT-TYPE
			SYNTAX SheBridgeSharedVlanLearningType
			MAX-ACCESS read-write
			STATUS current
			DESCRIPTION
				"Enable or disable the feature SharedVlanLearning in the NE."
			::= { sheBridgeBaseControl 12 }

		
--   1.3.6.1.4.1.231.7.1.2.2.1.4.1.2.13
		sheBridgeBaseControlRemoteIdFormat OBJECT-TYPE
			SYNTAX SheBridgeIdType
			MAX-ACCESS read-write
			STATUS current
			DESCRIPTION
				"It is up to the customer, to select the needed informations from this list and
				use a meaningfull combination. Also a combination with free text is possible.
				The maximum total length of a resulting remoteId is still 63 byte (overlaps will be cut off)!"
			::= { sheBridgeBaseControl 13 }

		
--   1.3.6.1.4.1.231.7.1.2.2.1.4.1.2.14
		sheBridgeBaseControlStagTPID OBJECT-TYPE
			SYNTAX Integer32 (0..65535)
			MAX-ACCESS read-write
			STATUS current
			DESCRIPTION
				"The TPID of the service tag if doubleTag is enabled"
			::= { sheBridgeBaseControl 14 }

		
--   1.3.6.1.4.1.231.7.1.2.2.1.4.1.2.15
		sheBridgeBaseControlMacAntiSpoofing OBJECT-TYPE
			SYNTAX SheBridgeMacAntiSpoofingType
			MAX-ACCESS read-write
			STATUS current
			DESCRIPTION
				"Enable or disable the feature MacAntiSpoofing in the NE."
			::= { sheBridgeBaseControl 15 }

		
--   1.3.6.1.4.1.231.7.1.2.2.1.4.1.2.16
		sheBridgeBaseControlRoutingMode OBJECT-TYPE
			SYNTAX SheBridgeRoutingModeType
			MAX-ACCESS read-write
			STATUS current
			DESCRIPTION
				"residential or unrestricted the feature Routing Mode of BridgeBase in the NE."
			::= { sheBridgeBaseControl 16 }

		
--   1.3.6.1.4.1.231.7.1.2.2.1.4.1.2.17
		sheBridgeBaseControlMaxHostName OBJECT-TYPE
			SYNTAX Integer32 (1..64)
			MAX-ACCESS read-write
			STATUS current
			DESCRIPTION
				"the maximum length of hostname for circuit-id or remote-id."
			::= { sheBridgeBaseControl 17 }

		
--   1.3.6.1.4.1.231.7.1.2.2.1.4.1.2.18
		sheBridgeBaseControlDlfFilter OBJECT-TYPE
			SYNTAX SheBridgeDlfFilterType
			MAX-ACCESS read-write
			STATUS current
			DESCRIPTION
				"The policy of DLF unicast packets from uplink."
			::= { sheBridgeBaseControl 18 }

		
--   1.3.6.1.4.1.231.7.1.2.2.1.4.1.2.19
		sheBridgeBaseControlUnknownMulticastFilter OBJECT-TYPE
			SYNTAX SheBridgeUnknownMulticastFilterType
			MAX-ACCESS read-write
			STATUS current
			DESCRIPTION
				"The policy of unknown multicast packets from uplink. It can be set to enable when routing mode is residential
				default: enable in R2.0, disable in R2.3 / R2.5.x
				Possible values:
				disable(0),
				enable(1)    -> means enable both directions!
				enableDs(2)  -> enable only downstream direction
				enableUs(3)  -> enable only upstream direction
				
				"
			::= { sheBridgeBaseControl 19 }

		
--   1.3.6.1.4.1.231.7.1.2.2.1.4.1.2.20
		sheBridgeBaseControlIpoaArpReqInterval OBJECT-TYPE
			SYNTAX Unsigned32
			UNITS "sec"
			MAX-ACCESS read-write
			STATUS current
			DESCRIPTION
				"The interval of ARP resolution for IPoA Bridgeport 
				Default: 0
				If the value is 0, it means NE does not send any arp request to an ipoa provider edge router after the router ip address is resolved. 
				Thus, if the ipoa provider edge router's MAC address is changed, packet uses wrong MAC address, unused one, for ipoa provider edge router.
				"
			::= { sheBridgeBaseControl 20 }

		
		sheBridgeBaseControlMaxIpUNI OBJECT-TYPE
			SYNTAX SheBridgeMaxIpAddressType
			MAX-ACCESS read-write
			STATUS current
			DESCRIPTION
				"This is the maximum number of possible IpAddresses (DHCP or fixed IP) per UNI Port.
				
				New parameter with SHE R2.8.
				Not configurable with current release!"
			::= { sheBridgeBaseControl 21 }

		
--   1.3.6.1.4.1.231.7.1.2.2.1.4.1.3
		sheBridgePortTable OBJECT-TYPE
			SYNTAX SEQUENCE OF SheBridgePortEntry
			MAX-ACCESS not-accessible
			STATUS current
			DESCRIPTION
				"The bridgePort-Table."
			::= { sheBridge 3 }

		
--   1.3.6.1.4.1.231.7.1.2.2.1.4.1.3.1
		sheBridgePortEntry OBJECT-TYPE
			SYNTAX SheBridgePortEntry
			MAX-ACCESS not-accessible
			STATUS current
			DESCRIPTION
				"One entry for every bridgePort of the system."
			INDEX { sheBridgePortIndex }
			::= { sheBridgePortTable 1 }

		
		SheBridgePortEntry ::=
			SEQUENCE { 
				sheBridgePortIndex
					Unsigned32,
				sheSubLayerIndex
					InterfaceIndex,
				sheSubLayerCircuit
					Integer32,
				sheBridgePortPVID
					Integer32,
				sheBridgePortPriority
					Integer32,
				sheBridgePortUsage
					SheBridgePortUsageType,
				sheBridgePortHostConfigurationProtocol
					SheHostConfigurationProtocolType,
				sheBridgePortCircuitId
					OCTET STRING,
				sheBridgePortMaxLearnPermitCount
					Integer32,
				sheBridgePortMcastGroupPackageList
					OCTET STRING,
				sheBridgePortMode
					SheBridgePortModeType,
				sheBridgePortTaggingMode
					SheBridgePortTaggingModeType,
				sheBridgePortRemoteId
					OCTET STRING,
				sheBridgePortInnerPVID
					Integer32,
				sheBridgePortReplaceVlanTag
					Integer32,
				sheBridgePortInnerPriority
					Integer32,
				sheBridgePortIpoaProviderRouterIpAddress
					IpAddress,
				sheBridgePortPppoaSessionId
					Integer32,
				sheBridgePortMcastMaxJoinedGroup
					Unsigned32,
				sheBridgePortMcastLeaveMode
					SheMcastLeaveMode,
				sheBridgePortMcastEHTMode
					SheEnableType,
				sheBridgePortIgmpSubscriberAccessMode
					SheBridgePortIgmpSubscriberAccessModeType,
				sheBridgePortInnerPriorityOption
					SheBridgePortPriorityOptionType,
				sheBridgePortOuterPriorityOption
					SheBridgePortPriorityOptionType,
				sheBridgePortPriorityMapIndex
					Unsigned32,
				sheBridgePortIpAddressPermitCount
					SheBridgeMaxIpAddressType,
				sheBridgePortMatEnabled
					TruthValue,
				sheBridgePortIpAsMode
					SheBridgePortIpAsModeType,
				sheBridgePortEtypeVlanMapProfilePtr
					Unsigned32
			 }

--   1.3.6.1.4.1.231.7.1.2.2.1.4.1.3.1.1
		sheBridgePortIndex OBJECT-TYPE
			SYNTAX Unsigned32 (1..65535)
			MAX-ACCESS read-only
			STATUS current
			DESCRIPTION
				"A bridgePort-identifier."
			::= { sheBridgePortEntry 1 }

		
--   1.3.6.1.4.1.231.7.1.2.2.1.4.1.3.1.2
		sheSubLayerIndex OBJECT-TYPE
			SYNTAX InterfaceIndex
			MAX-ACCESS read-only
			STATUS current
			DESCRIPTION
				"IfIndex of the underlaying Interface in the interface-table, Also LAG-bridgePorts will 
				be modeled in the interface table. "
			::= { sheBridgePortEntry 2 }

		
--   1.3.6.1.4.1.231.7.1.2.2.1.4.1.3.1.3
		sheSubLayerCircuit OBJECT-TYPE
			SYNTAX Integer32
			MAX-ACCESS read-only
			STATUS current
			DESCRIPTION
				"Only used in case the bridgePort represents a PVC, otherwise equal 0. This value represent the 
				the index for sheAdslVccTpTable, sheXdslVccTpTable or sheShdslVccTpTable depending on ifType
				of underlaying physical interface. 
				
				This index was build by the following rule:
				index = (SubLayerIndex << 4) + Vcc-Number
				
				Lowest value for she is 0x0651 (ifIndex = 101 and Vcc-Number 1).
				Highest value for she is 0x6EC8 (ifIndex = 1772 and Vcc-Number 8).
				"
			::= { sheBridgePortEntry 3 }

		
--   1.3.6.1.4.1.231.7.1.2.2.1.4.1.3.1.4
		sheBridgePortPVID OBJECT-TYPE
			SYNTAX Integer32 (1..4093)
			MAX-ACCESS read-only
			STATUS current
			DESCRIPTION
				"The PVID of the port. Possible range is 1-4093 for subscriber ports. This value
				points to the corresponding vlanIndex of the sheVlanTable. 
				The default value for subscriber bridgePorts is the ifIndex of the underlaying
				physical interface (sublayerindex).
				Uplink and LAG bridgePorts use PVID 1 as default."
			::= { sheBridgePortEntry 4 }

		
--   1.3.6.1.4.1.231.7.1.2.2.1.4.1.3.1.5
		sheBridgePortPriority OBJECT-TYPE
			SYNTAX Integer32 (0..7)
			MAX-ACCESS read-only
			STATUS current
			DESCRIPTION
				"Default Priority of the bridgePort."
			DEFVAL { 0 }
			::= { sheBridgePortEntry 5 }

		
--   1.3.6.1.4.1.231.7.1.2.2.1.4.1.3.1.6
		sheBridgePortUsage OBJECT-TYPE
			SYNTAX SheBridgePortUsageType
			MAX-ACCESS read-only
			STATUS current
			DESCRIPTION
				"defaults:
				Dsl PVC : subscriber
				Adsl special: vccAggregatorNotUsed
				Uplink  : upLink
				Lag     : notUsed
				
				
				If upLink-Port is aggregated, the upLink state moves to aggregated and the Lag moves to uplink.
				
				If a physical bonding is used (Shdsl 4wire/6wire/8wire done over shdsl configuration, m-pair bonding),
				the master bridgeport changes his usage to physbondedSubscriber and all other members to notUsed.
				
				If a gbond bonding is used (via she-bonding-mib configuration), the master bridgeport-entry of the new
				bonding port changes  his usage to bondingSubscriber and all other members of bonding port to bondingNotUsed.
				
				For the feature singleMacMultipleVcc, it is possible to aggregate two or more single VCC's of one
				physical adsl-link to the vccAggregator. The usage of the single PVC - bridgeports (subscriber)
				could be set to vccAggregated and the special bridgeport change his usage 
				from vccAggregatorNotUsed to ..Used in that case.
				It is also possible to set this special bridgeport usage directly and in that case all
				bridgeports with identical sublayerindex will change her usage to vccAggregated.
				This configuration has additional restrictions for PVID and priority configuration. 
				Check MSC for detailes."
			::= { sheBridgePortEntry 6 }

		
--   1.3.6.1.4.1.231.7.1.2.2.1.4.1.3.1.7
		sheBridgePortHostConfigurationProtocol OBJECT-TYPE
			SYNTAX SheHostConfigurationProtocolType
			MAX-ACCESS read-only
			STATUS current
			DESCRIPTION
				"Used host configuration protocol. Valid values could 	
				none(0),
				useDHCP(1),
				usePPPoE(2).
				useDHCPandPPPoE(3)."
			::= { sheBridgePortEntry 7 }

		
--   1.3.6.1.4.1.231.7.1.2.2.1.4.1.3.1.8
		sheBridgePortCircuitId OBJECT-TYPE
			SYNTAX OCTET STRING (SIZE (0..63))
			MAX-ACCESS read-only
			STATUS current
			DESCRIPTION
				"Needed for special Options in DHCP or PPPoE.
				If not configured the default format string from sheBridgeBaseCircuitIdFormat
				will be used."
			::= { sheBridgePortEntry 8 }

		
--   1.3.6.1.4.1.231.7.1.2.2.1.4.1.3.1.9
		sheBridgePortMaxLearnPermitCount OBJECT-TYPE
			SYNTAX Integer32 (-1 | 0 | 1..2147483647)
			MAX-ACCESS read-only
			STATUS current
			DESCRIPTION
				"Number of dynamic learned Mac addresses per port.
				
				The valid configuration range for dynamic MacAddress learning is 1..2147483647 (0x7fffffff). 
				A value of -1 disable the MacAddress limitation (default for uplink) -> 'No Limit'.
				A value of 0 disable the dynamic MacAddress learning -> 'Disabled'. Static FdbTable entrys possible. 
				
				Additional limitations depending on the used CXU or IU type are possible.
				The default setting for subscriber ports is 16.
				
				Note:
				Syntax modified with R2.8 BFR 2.0. "
			::= { sheBridgePortEntry 9 }

		
--   1.3.6.1.4.1.231.7.1.2.2.1.4.1.3.1.10
		sheBridgePortMcastGroupPackageList OBJECT-TYPE
			SYNTAX OCTET STRING (SIZE (0..20))
			MAX-ACCESS read-only
			STATUS current
			DESCRIPTION
				"That is a list of allowed corresponding indices of the 
				sheIgmpMcastGroupPackageTable for this subscriber.
				Each index has 16 bit. 
				If no packet is assigned, the string has 0 length.
				"
			::= { sheBridgePortEntry 10 }

		
--   1.3.6.1.4.1.231.7.1.2.2.1.4.1.3.1.11
		sheBridgePortMode OBJECT-TYPE
			SYNTAX SheBridgePortModeType
			MAX-ACCESS read-only
			STATUS current
			DESCRIPTION
				"Mode of this bridgeport useIpoE, useIpoA, usePPPoA or useAuto. 
				
				useIpoE is the default setting. This mode will also support PPPoE.
				
				useIPoA is only possible for IU_ADSL or IU_SHDSL boards.
				If no MacAddress is configured in the corresponding MacProfileTable-entry, the NE 
				will autogenerate a own value.
				
				In case of usePPPoA, the IU will translate the PPPoA protocol to PPPoE.
				This configuration is only valid for bridgeports with SubLayerIndex placed on 
				IU_ADSL72 with IFX chipset! A SrcMac-address in sheBridgeIUProfileTable has to
				be configured for the IU where these port is placed on.
				
				The configuration useAuto forces the IU to start a autodetection mode for supporting PPPoA or
				PPPoE. "
			DEFVAL { 0 }
			::= { sheBridgePortEntry 11 }

		
--   1.3.6.1.4.1.231.7.1.2.2.1.4.1.3.1.12
		sheBridgePortTaggingMode OBJECT-TYPE
			SYNTAX SheBridgePortTaggingModeType
			MAX-ACCESS read-only
			STATUS current
			DESCRIPTION
				"Tagging modes for bridgePort's. This modes are only valid for received frames.
				Tagging of transmitted frames depends on the bridgeBase-tagging mode and on the
				vlan-membership.
				
				off(0)
				Untagged frames are tagged with PVID and forwarded. Tagged frames are
				forwarded unchanged.
				That is the default value for uplink port's and should not be changed.
				
				tagged(1)
				Frames tagged with the configured VIDs are forwarded unchanged. Untagged
				frames and frames with unknown VIDs are dropped. Check sheBridgePortReplaceTag
				value if a received tag should be replaced by PVID.
				
				untagged(2)
				Untagged frames are tagged with PVID and forwarded. Tagged frames are dropped.
				That is the default value for subscriber port's.
				 	
				NOTE:
				SHE releases older then R2.5 will only support modes (0) and (1).
				"
			::= { sheBridgePortEntry 12 }

		
--   1.3.6.1.4.1.231.7.1.2.2.1.4.1.3.1.13
		sheBridgePortRemoteId OBJECT-TYPE
			SYNTAX OCTET STRING (SIZE (0..63))
			MAX-ACCESS read-only
			STATUS current
			DESCRIPTION
				"Needed for special Options in DHCP or PPPoE.
				If not configured the default format string from sheBridgeBaseRemoteIdFormat
				will be used."
			::= { sheBridgePortEntry 13 }

		
--   1.3.6.1.4.1.231.7.1.2.2.1.4.1.3.1.14
		sheBridgePortInnerPVID OBJECT-TYPE
			SYNTAX Integer32 (1..4093)
			MAX-ACCESS read-only
			STATUS current
			DESCRIPTION
				"The Inner PVID of this bridgePort. Taken if no other rule given for VLAN association. 
				The default Value is 1."
			::= { sheBridgePortEntry 14 }

		
--   1.3.6.1.4.1.231.7.1.2.2.1.4.1.3.1.15
		sheBridgePortReplaceVlanTag OBJECT-TYPE
			SYNTAX Integer32 (0..4093)
			MAX-ACCESS read-only
			STATUS current
			DESCRIPTION
				"If configured unequal 0, the configured vlan-tag could be received and will be
				replaced by PVID before forwarding the frame. A zero will disable this feature.
				Only valid if the Bridgeport is running tagged(1) mode - otherwise must be zero.
				
				NOTE:
				Modified with R2.8.
				CG based IU's could only support one vlan tag per IU. This configuration is now used
				for enable/disable the feature on bridgeport-base. For enable, only the configured value
				from the IU global configuration will be accepted!
				"
			DEFVAL { 0 }
			::= { sheBridgePortEntry 15 }

		
--   1.3.6.1.4.1.231.7.1.2.2.1.4.1.3.1.16
		sheBridgePortInnerPriority OBJECT-TYPE
			SYNTAX Integer32 (0..7)
			MAX-ACCESS read-only
			STATUS current
			DESCRIPTION
				"The inner priority of this bridgePort. Taken if no other rule given for VLAN association. 
				The default value is 0."
			DEFVAL { 0 }
			::= { sheBridgePortEntry 16 }

		
--   1.3.6.1.4.1.231.7.1.2.2.1.4.1.3.1.17
		sheBridgePortIpoaProviderRouterIpAddress OBJECT-TYPE
			SYNTAX IpAddress
			MAX-ACCESS read-only
			STATUS current
			DESCRIPTION
				"The IPoA provider edge router's ip address for this bridgePort.
				0.0.0.0 is also a valid setting and force the NE together with a similar entry in
				sheArpFixedIpAddressTable to retrieve the needed information automatically."
			::= { sheBridgePortEntry 17 }

		
--   1.3.6.1.4.1.231.7.1.2.2.1.4.1.3.1.18
		sheBridgePortPppoaSessionId OBJECT-TYPE
			SYNTAX Integer32
			MAX-ACCESS read-only
			STATUS current
			DESCRIPTION
				"The session id from a PPP server is for the PPPoA session."
			::= { sheBridgePortEntry 18 }

		
		sheBridgePortMcastMaxJoinedGroup OBJECT-TYPE
			SYNTAX Unsigned32 (0 | 1..32 | 255)
			MAX-ACCESS read-only
			STATUS current
			DESCRIPTION
				"The maximum number of multicast group's (channels) that this subscriber can join.
				0 is a special value and means 'no' access.
				255 is a special value and means 'unlimited' access.
				
				This configuration is only valid for bridgeports with usage 'subscriber'."
			DEFVAL { 10 }
			::= { sheBridgePortEntry 19 }

		
		sheBridgePortMcastLeaveMode OBJECT-TYPE
			SYNTAX SheMcastLeaveMode
			MAX-ACCESS read-only
			STATUS current
			DESCRIPTION
				"If normal leave is enabled and the client sends a leave message, the switch sends
				a query message to the client. When there is no response from the client,
				it is deleted from the multicast group.
				If fast leave is enabled, the client is deleted from the multicast group when the switch receives the leave message.
				
				New with R2.8:
				If ehtMode ('explicit host tracking') is enabled, the multicaststream will only be deleted from FDB if all
				members of this stream has send her leave."
			DEFVAL { ethMode }
			::= { sheBridgePortEntry 20 }

		
		sheBridgePortMcastEHTMode OBJECT-TYPE
			SYNTAX SheEnableType
			MAX-ACCESS read-only
			STATUS obsolete
			DESCRIPTION
				"Enables or disables the 'explicit host tracking' function. 
				If enabled and fastleave-mode is also running, the multicaststream will only be
				deleted from FDB if all members of this stream has send her leave.
				
				Note:
				Functionality bundled in McastLeaveMode with SHE R2.8."
			DEFVAL { enable }
			::= { sheBridgePortEntry 21 }

		
		sheBridgePortIgmpSubscriberAccessMode OBJECT-TYPE
			SYNTAX SheBridgePortIgmpSubscriberAccessModeType
			MAX-ACCESS read-only
			STATUS obsolete
			DESCRIPTION
				"When sheBridgePortIgmpSubscriberAccessMode is set to 0, 
				it means the access mode is IPoE, when set to 1, it means 
				the access mode is PPPoE. 
				
				Note:
				Merged parameter for SHE R2.4. 
				R2.8 will not use this configuration and ignore any modification."
			::= { sheBridgePortEntry 22 }

		
		sheBridgePortInnerPriorityOption OBJECT-TYPE
			SYNTAX SheBridgePortPriorityOptionType
			MAX-ACCESS read-only
			STATUS current
			DESCRIPTION
				"This parameter configures the handling of the inner vlan tag in the doubleTagged scenario.
				In singleTagged Mode, this parameter definition is not used.
				If tagged frames are received set the .1p priority bits of this tag.
				
				        dscp(1) -> according DSCP of IP header (use sheBridgePortPriorityMapIndex
					                                        or sheBridgeIUDscpPriorityMapIndex)
				        userTag(2) -> no change of the received .1p priority 
				        force(3) -> per port configured .1p (sheBridgePortInnerPriority)
				
				If a tag is added to an upstream user frame, because untagged frames are received
				set the .1p priority bits of the added tag.
				
				        dscp(1) -> according DSCP of IP header (use sheBridgePortPriorityMapIndex
					                                        or sheBridgeIUDscpPriorityMapIndex)
				        userTag(2) -> per port configured .1p (sheBridgePortInnerPriority, same as force(3))
				        force(3) -> per port configured .1p (sheBridgePortInnerPriority)
				
				New parameters with SHE R2.7
				Expanded with R2.8."
			DEFVAL { userTag }
			::= { sheBridgePortEntry 23 }

		
		sheBridgePortOuterPriorityOption OBJECT-TYPE
			SYNTAX SheBridgePortPriorityOptionType
			MAX-ACCESS read-only
			STATUS current
			DESCRIPTION
				"This parameter configures the handling of the outer vlan tag in the doubleTagged
				and singleTagged scenario.
				
				doubleTagged Scenario: 
				   If tagged frames are received set the .1p priority bits of the added outer tag.
					
				        dscp(1) -> according DSCP of IP header (use sheBridgePortPriorityMapIndex
					                                        or sheBridgeIUDscpPriorityMapIndex)
					
				        userTag(2) -> copy .1p priority from the assigned inner .1p priority (inner to outer)
					
				        force(3) -> per port configured .1p (sheBridgePortPriority)
							
				   If two tag's are added to an upstream user frame, because untagged frames are received
				   set the .1p priority bits of the added outer tag.
							
				        dscp(1) -> according DSCP of IP header (use sheBridgePortPriorityMapIndex
					                                        or sheBridgeIUDscpPriorityMapIndex)
				        userTag(2) -> per port configured .1p (sheBridgePortPriority, same as force(3))
				
				        force(3) -> per port configured .1p (sheBridgePortPriority)
				
				singleTagged Scenario: 
				   If tagged frames are received set the .1p priority bits of the tag.
							
				        dscp(1) -> according DSCP of IP header (use sheBridgePortPriorityMapIndex
					                                        or sheBridgeIUDscpPriorityMapIndex)
				
				        userTag(2) -> no change of the received .1p priority 
				
				        force(3) -> per port configured .1p (sheBridgePortPriority)
							
				   If untagged frames are received set the .1p priority bits of the added tag.
							
				        dscp(1) -> according DSCP of IP header (use sheBridgePortPriorityMapIndex
					                                        or sheBridgeIUDscpPriorityMapIndex)
				
				        userTag(2) -> per port configured .1p (sheBridgePortPriority, same as force(3))
				
				        force(3) -> per port configured .1p (sheBridgePortPriority)
							
				New parameters with SHE R2.7
				Expanded with R2.8.
				"
			DEFVAL { force }
			::= { sheBridgePortEntry 24 }

		
		sheBridgePortPriorityMapIndex OBJECT-TYPE
			SYNTAX Unsigned32 (0 | 1..16)
			MAX-ACCESS read-only
			STATUS current
			DESCRIPTION
				"This is a pointer to a mapping entry DSCP to .1p.
				Value 0 (default) means there is no mapping in use or the IU specific assignment
				via sheBridgeIUDscpPriorityMapIndex will be used.
				
				One of these two pointer's (port specific or IU global) must be valid
				if sheBridgePortPriorityOption is dscp(1) and sheBridgePortUsage is subscriber(4).
				Used if a tag is added to an upstream user frame and sheBridgePortPriorityOption
				is dscp to set .1p bits. Used if an upstream user frame is tagged and
				sheBridgePortPriorityOption is dscp for .1p range check.
				
				NOTE:
				Convergate based IU's could only support ONE profile for all port's were these
				mapping should be used!!
				
				New parameter with SHE R2.8."
			DEFVAL { 0 }
			::= { sheBridgePortEntry 25 }

		
		sheBridgePortIpAddressPermitCount OBJECT-TYPE
			SYNTAX SheBridgeMaxIpAddressType
			MAX-ACCESS read-only
			STATUS current
			DESCRIPTION
				"Maximum number of possible IpAddresses per BridgePort. 
				The assignment could be done via DHCP or fixedIpAddress configuration.
				
				Note:
				There is an additional restriction of possible IpAddresses per UNI port which
				could never exceeded. Remark this if more then one bridgePort is used on a single UNI port. 
				Additional restrictions could be possible in case of using IpAntispoofing feature.
				
				New parameter with SHE R2.8."
			DEFVAL { 8 }
			::= { sheBridgePortEntry 26 }

		
		sheBridgePortMatEnabled OBJECT-TYPE
			SYNTAX TruthValue
			MAX-ACCESS read-only
			STATUS current
			DESCRIPTION
				"Enable or disable the MAC address translation feature on bridgePort base.
				
				New parameter with SHE R2.8."
			DEFVAL { false }
			::= { sheBridgePortEntry 27 }

		
		sheBridgePortIpAsMode OBJECT-TYPE
			SYNTAX SheBridgePortIpAsModeType
			MAX-ACCESS read-only
			STATUS current
			DESCRIPTION
				"This configuration enable/disable the feature IpAntispoofing on bridgePort base.
				Depending on the used mode, the IU could made the following checks:
				
				offIpAs(0)              -> IpAs disabled
				onIpAsNoVlanCheck(1)    -> IpAs enabled, Only frames with configured Ip will be forwarded.
				onIpAsInnerVlanCheck(2) -> IpAs enabled, Only frames with configured couple Ip-InnerTag will be forwarded.
				onIpAsOuterVlanCheck(3) -> IpAs enabled, Only frames with configured couple Ip-OuterTag will be forwarded.
				onIpAsBothVlanCheck(4)  -> IpAs enabled, Only frames with configured triple Ip-InnerTag-OuterTag will be forwarded.
				
				All other frames will be discarded. 
				Bridgeports on IU cards with wintegra chipset will not check any Vlan dependencies, don't care which
				onIpAsxxx - mode was selected. Only cards with convergate chipset will made the requested differentiation.
				There is an additional global switch for IpAs available (sheIpAntiSpoofingEnable),
				which will outvote this configuration if set to 'enable'.
				
				The configuration of the valid triple Ip-InnerTag-OuterTag will be done via
				DHCP or StaticIpAddress configuration.
				
				New parameter with SHE R2.8. "
			DEFVAL { offIpAs }
			::= { sheBridgePortEntry 28 }

		
		sheBridgePortEtypeVlanMapProfilePtr OBJECT-TYPE
			SYNTAX Unsigned32 (0 | 1..100)
			MAX-ACCESS read-only
			STATUS current
			DESCRIPTION
				"Ethertype-VLAN mapping profile pointer to sheBridgePortEtypeVlanMapTable
				(sheBridgePortEtypeVlanMapProfIndex).
				This attribute is optional and the pointer is null when it is not assigned.
				
				Note:
				The bridgeport has to be untagged member of the mapped vlan, assigned via these
				profile.
				
				New parameter with SHE R2.8."
			DEFVAL { 0 }
			::= { sheBridgePortEntry 29 }

		
--   1.3.6.1.4.1.231.7.1.2.2.1.4.1.4
		sheBridgePortControl OBJECT IDENTIFIER ::= { sheBridge 4 }

		
--   1.3.6.1.4.1.231.7.1.2.2.1.4.1.4.1
		sheBridgePortControlRequest OBJECT-TYPE
			SYNTAX SheBridgeControlRequestType
			MAX-ACCESS read-write
			STATUS current
			DESCRIPTION
				"setBridgePortVLANDefaults: 
				sheBridgePortControlIndex
				sheBridgePortControlPVID
				sheBridgePortControlPriority
				
				setBridgePortUsage:
				sheBridgePortControlIndex
				sheBridgePortControlUsage
				
				setBridgePortHostConfigurationProtocol:
				sheBridgePortControlIndex
				sheBridgePortControlHostConfigurationProtocol
				sheBridgePortControlCircuitId
				
				setBridgePortMaxLearnPermitCount:
				sheBridgePortControlIndex
				sheBridgePortControlMaxLearnPermitCount
				
				setBridgePortMcastGroupPackageList: 
				sheBridgePortControlIndex
				sheBridgePortControlMcastGroupPackageList
				
				setBridgePortFeature:
				sheBridgePortControlIndex
				sheBridgePortControlMode
				sheBridgePortControlTaggingMode
				sheBridgePortControlReplaceTag 
				
				setBridgePortCircuitId:
				sheBridgePortControlIndex
				sheBridgePortControlCircuitId
				
				setBridgePortRemoteId:
				sheBridgePortControlIndex
				sheBridgePortControlRemoteId
				
				clearBridgePortCircuitId:
				sheBridgePortControlIndex
				
				clearBridgePortRemoteId:
				sheBridgePortControlIndex
				
				setBridgePortInnerPVID:
				sheBridgePortControlIndex
				sheBridgePortControlInnerPVID
				
				setBridgePortInnerPriority:
				sheBridgePortControlIndex
				sheBridgePortControlInnerPriority
				
				setBridgePortIpoaProviderRouterIpAddress:
				sheBridgePortControlIndex
				sheBridgePortControlIpoaProviderRouterIpAddress
				
				setBridgePortMcastParameter:  
				sheBridgePortControlIndex
				sheBridgePortControlMcastMaxJoinedGroup
				sheBridgePortControlMcastLeaveMode
				sheBridgePortControlMcastEHTMode   (obsolete with R2.8)
				
				setBridgePortIgmpSubscriberAccessMode
				sheBridgePortControlIndex
				sheBridgePortControlIgmpSubscriberAccessMode
				
				New with R2.7:
				setBridgePortPriorityOptions
				sheBridgePortControlIndex
				sheBridgePortControlInnerPriorityOption
				sheBridgePortControlOuterPriorityOption
				sheBridgePortControlPriorityMapIndex (new with R2.8)
				
				New with R2.8:
				setBridgePortMatEnabled
				sheBridgePortControlIndex
				sheBridgePortControlMatEnabled
				
				setBridgePortIpAddressPermitCount
				sheBridgePortControlIndex
				sheBridgePortControlIpAddressPermitCount
				
				setBridgePortIpAsMode (165)
				 sheBridgePortControlIndex
				 sheBridgePortControlIpAsMode
				->sheBridgePortIpAsModeModified
				
				setBridgePortEtypeVlanMapping (166)
				 sheBridgePortControlIndex
				 sheBridgePortControlEtypeVlanMapProfilePtr
				->sheBridgePortEtypeVlanMappingModified"
			::= { sheBridgePortControl 1 }

		
--   1.3.6.1.4.1.231.7.1.2.2.1.4.1.4.2
		sheBridgePortControlIndex OBJECT-TYPE
			SYNTAX Integer32
			MAX-ACCESS read-write
			STATUS current
			DESCRIPTION
				"The index of the bridgePort to be configured."
			::= { sheBridgePortControl 2 }

		
--   1.3.6.1.4.1.231.7.1.2.2.1.4.1.4.3
		sheBridgePortControlStatus OBJECT-TYPE
			SYNTAX SheControlStatusType
			MAX-ACCESS read-only
			STATUS current
			DESCRIPTION
				"The status of a user command. 
				"
			::= { sheBridgePortControl 3 }

		
--   1.3.6.1.4.1.231.7.1.2.2.1.4.1.4.4
		sheBridgePortControlTimer OBJECT-TYPE
			SYNTAX Gauge32
			MAX-ACCESS read-only
			STATUS current
			DESCRIPTION
				"The maximum wait time for the manager for a long running user command. 
				"
			::= { sheBridgePortControl 4 }

		
--   1.3.6.1.4.1.231.7.1.2.2.1.4.1.4.5
		sheBridgePortControlReqResult OBJECT-TYPE
			SYNTAX SheBridgeControlReqResultType
			MAX-ACCESS read-only
			STATUS current
			DESCRIPTION
				"The result of the last user command."
			::= { sheBridgePortControl 5 }

		
--   1.3.6.1.4.1.231.7.1.2.2.1.4.1.4.6
		sheBridgePortControlTimeStamp OBJECT-TYPE
			SYNTAX Unsigned32
			UNITS "sec"
			MAX-ACCESS read-only
			STATUS current
			DESCRIPTION
				"The time stamp of the last command (end of command)."
			::= { sheBridgePortControl 6 }

		
--   1.3.6.1.4.1.231.7.1.2.2.1.4.1.4.7
		sheBridgePortControlPVID OBJECT-TYPE
			SYNTAX Integer32 (1..4093)
			MAX-ACCESS read-write
			STATUS current
			DESCRIPTION
				"The PVID for that port."
			::= { sheBridgePortControl 7 }

		
--   1.3.6.1.4.1.231.7.1.2.2.1.4.1.4.8
		sheBridgePortControlPriority OBJECT-TYPE
			SYNTAX Integer32 (0..7)
			MAX-ACCESS read-write
			STATUS current
			DESCRIPTION
				"Set the default port priority."
			::= { sheBridgePortControl 8 }

		
--   1.3.6.1.4.1.231.7.1.2.2.1.4.1.4.9
		sheBridgePortControlUsage OBJECT-TYPE
			SYNTAX SheBridgePortUsageType
			MAX-ACCESS read-write
			STATUS current
			DESCRIPTION
				"Only the values uplink, cascading, and subcascading could be interchanged.
				
				For the feature singleMacMultipleVcc, it is possible to aggregate two or more single VCC's of one
				physical adsl-link to the vccAggregator. The usage of the single PVC - bridgeports (subscriber)
				could be set to vccAggregated and the special bridgeport change his usage 
				from vccAggregatorNotUsed to ..Used in that case.
				It is also possible to set this special bridgeport usage directly and in that case all
				bridgeports with identical sublayerindex will change her usage to vccAggregated.
				This configuration has additional restrictions for PVID and priority configuration. 
				Check MSC for detailes.
				
				All other changes will be done by NE automatically based on other configurations."
			::= { sheBridgePortControl 9 }

		
--   1.3.6.1.4.1.231.7.1.2.2.1.4.1.4.10
		sheBridgePortControlHostConfigurationProtocol OBJECT-TYPE
			SYNTAX SheHostConfigurationProtocolType
			MAX-ACCESS read-write
			STATUS current
			DESCRIPTION
				"Used host configuration protocol. Valid values could 	
				none(0),
				useDHCP(1),
				usePPPoE(2).
				"
			::= { sheBridgePortControl 10 }

		
--   1.3.6.1.4.1.231.7.1.2.2.1.4.1.4.11
		sheBridgePortControlMaxLearnPermitCount OBJECT-TYPE
			SYNTAX Integer32 (-1 | 0 | 1..2147483647)
			MAX-ACCESS read-write
			STATUS current
			DESCRIPTION
				"look at table.
				
				Note:
				Syntax modified with R2.8 BFR 2.0. "
			::= { sheBridgePortControl 11 }

		
--   1.3.6.1.4.1.231.7.1.2.2.1.4.1.4.12
		sheBridgePortControlMcastGroupPackageList OBJECT-TYPE
			SYNTAX OCTET STRING (SIZE (0..20))
			MAX-ACCESS read-write
			STATUS current
			DESCRIPTION
				"This bridgePort is user of this MCastGroup-Package.
				"
			::= { sheBridgePortControl 12 }

		
--   1.3.6.1.4.1.231.7.1.2.2.1.4.1.4.13
		sheBridgePortControlCircuitId OBJECT-TYPE
			SYNTAX OCTET STRING (SIZE (0..63))
			MAX-ACCESS read-write
			STATUS current
			DESCRIPTION
				"Look at table."
			::= { sheBridgePortControl 13 }

		
--   1.3.6.1.4.1.231.7.1.2.2.1.4.1.4.14
		sheBridgePortControlMode OBJECT-TYPE
			SYNTAX SheBridgePortModeType
			MAX-ACCESS read-write
			STATUS current
			DESCRIPTION
				"Look at table."
			::= { sheBridgePortControl 14 }

		
--   1.3.6.1.4.1.231.7.1.2.2.1.4.1.4.15
		sheBridgePortControlTaggingMode OBJECT-TYPE
			SYNTAX SheBridgePortTaggingModeType
			MAX-ACCESS read-write
			STATUS current
			DESCRIPTION
				"Look at table."
			::= { sheBridgePortControl 15 }

		
--   1.3.6.1.4.1.231.7.1.2.2.1.4.1.4.16
		sheBridgePortControlRemoteId OBJECT-TYPE
			SYNTAX OCTET STRING (SIZE (0..63))
			MAX-ACCESS read-write
			STATUS current
			DESCRIPTION
				"Look at table."
			::= { sheBridgePortControl 16 }

		
--   1.3.6.1.4.1.231.7.1.2.2.1.4.1.4.17
		sheBridgePortControlInnerPVID OBJECT-TYPE
			SYNTAX Integer32
			MAX-ACCESS read-write
			STATUS current
			DESCRIPTION
				"The Inner PVID of this bridgePort. Taken if no other rule given for VLAN association. The default Value is the bridgePortIndex +1."
			::= { sheBridgePortControl 17 }

		
--   1.3.6.1.4.1.231.7.1.2.2.1.4.1.4.18			
		sheBridgePortControlReplaceVlanTag OBJECT-TYPE
			SYNTAX Integer32 (0..4093)
			MAX-ACCESS read-write
			STATUS current
			DESCRIPTION
				"Configure a Vlan-Tag which should be replaced by PVID.
				Check table entry for details.
				
				NOTE:
				Modified with R2.8.
				CG based IU's could only support one vlan tag per IU. This configuration is now used
				for enable/disable the feature on bridgeport-base. For enable, only the configured value
				from the IU global configuration will be accepted!"
			::= { sheBridgePortControl 18 }

		
--   1.3.6.1.4.1.231.7.1.2.2.1.4.1.4.19
		sheBridgePortControlInnerPriority OBJECT-TYPE
			SYNTAX Integer32 (0..7)
			MAX-ACCESS read-write
			STATUS current
			DESCRIPTION
				"The inner priority of this bridgePort. Taken if no other rule given for VLAN association. The default value is the '0'."
			::= { sheBridgePortControl 19 }

		
--   1.3.6.1.4.1.231.7.1.2.2.1.4.1.4.20
		sheBridgePortControlIpoaProviderRouterIpAddress OBJECT-TYPE
			SYNTAX IpAddress
			MAX-ACCESS read-write
			STATUS current
			DESCRIPTION
				"look at table"
			::= { sheBridgePortControl 20 }

		
		sheBridgePortControlMcastMaxJoinedGroup OBJECT-TYPE
			SYNTAX Unsigned32 (0 | 1..32 | 255)
			MAX-ACCESS read-write
			STATUS current
			DESCRIPTION
				"The maximum number of multicast group's that this subscriber can join.
				0 is a special value and means 'no' access.
				255 is a special value and means 'unlimited' access.
				"
			::= { sheBridgePortControl 21 }

		
		sheBridgePortControlMcastLeaveMode OBJECT-TYPE
			SYNTAX SheMcastLeaveMode
			MAX-ACCESS read-write
			STATUS current
			DESCRIPTION
				"Modify subscriber leave mode."
			::= { sheBridgePortControl 22 }

		
		sheBridgePortControlMcastEHTMode OBJECT-TYPE
			SYNTAX SheEnableType
			MAX-ACCESS read-write
			STATUS current
			DESCRIPTION
				"Enables or disables the 'explicit host tracking' function.
				
				NOTE:
				Functionality bundled in McastLeaveMode with SHE R2.8. Will not longer used by R2.8."
			::= { sheBridgePortControl 23 }

		
		sheBridgePortControlIgmpSubscriberAccessMode OBJECT-TYPE
			SYNTAX SheBridgePortIgmpSubscriberAccessModeType
			MAX-ACCESS read-write
			STATUS obsolete
			DESCRIPTION
				"When sheBridgePortIgmpSubscriberAccessMode is set to 0, 
				it means the access mode is IPoE, when set to 1, it means 
				the access mode is PPPoE. 
				
				Note:
				Merged parameter for SHE R2.4. 
				R2.8 will not use this configuration and ignore any modification."
			::= { sheBridgePortControl 24 }

		
		sheBridgePortControlInnerPriorityOption OBJECT-TYPE
			SYNTAX SheBridgePortPriorityOptionType
			MAX-ACCESS read-write
			STATUS current
			DESCRIPTION
				"look at table."
			::= { sheBridgePortControl 25 }

		
		sheBridgePortControlOuterPriorityOption OBJECT-TYPE
			SYNTAX SheBridgePortPriorityOptionType
			MAX-ACCESS read-write
			STATUS current
			DESCRIPTION
				"look at table."
			::= { sheBridgePortControl 26 }

		
		sheBridgePortControlPriorityMapIndex OBJECT-TYPE
			SYNTAX Unsigned32 (0 | 1..16)
			MAX-ACCESS read-write
			STATUS current
			DESCRIPTION
				"look at table"
			::= { sheBridgePortControl 27 }

		
		sheBridgePortControlIpAddressPermitCount OBJECT-TYPE
			SYNTAX SheBridgeMaxIpAddressType
			MAX-ACCESS read-write
			STATUS current
			DESCRIPTION
				"look at table description."
			::= { sheBridgePortControl 28 }

		
		sheBridgePortControlMatEnabled OBJECT-TYPE
			SYNTAX TruthValue
			MAX-ACCESS read-write
			STATUS current
			DESCRIPTION
				"Enable or disable the MAC address translation feature on bridgePort base."
			::= { sheBridgePortControl 29 }

		
		sheBridgePortControlIpAsMode OBJECT-TYPE
			SYNTAX SheBridgePortIpAsModeType
			MAX-ACCESS read-write
			STATUS current
			DESCRIPTION
				"This configuration enable/disable the feature IpAntispoofing on bridgePort base.
				Depending on the used mode, the IU could made the following checks:
				
				offIpAs(0)              -> IpAs disabled
				onIpAsNoVlanCheck(1)    -> IpAs enabled, Only frames with configured Ip will be forwarded.
				onIpAsInnerVlanCheck(2) -> IpAs enabled, Only frames with configured couple Ip-InnerTag will be forwarded.
				onIpAsOuterVlanCheck(3) -> IpAs enabled, Only frames with configured couple Ip-OuterTag will be forwarded.
				onIpAsBothVlanCheck(4)  -> IpAs enabled, Only frames with configured triple Ip-InnerTag-OuterTag will be forwarded.
				
				All other frames will be discarded.
				Bridgeports on IU cards with wintegra chipset will not check any Vlan dependencies, don't care which
				onIpAsxxx - mode was selected. Only cards with convergate chipset will made the requested differentiation.
				There is an additional global switch for IpAs available (sheIpAntiSpoofingEnable),
				which will outvote this configuration if set to 'enable'. 
				
				The configuration of the valid triple Ip-InnerTag-OuterTag will be done via
				DHCP or StaticIpAddress configuration.
				
				New parameter with SHE R2.8."
			::= { sheBridgePortControl 30 }

		
		sheBridgePortControlEtypeVlanMapProfilePtr OBJECT-TYPE
			SYNTAX Unsigned32 (0 | 1..100)
			MAX-ACCESS read-write
			STATUS current
			DESCRIPTION
				"Ethertype-VLAN mapping profile pointer to sheBridgePortEtypeVlanMapTable
				(sheBridgePortEtypeVlanMapProfIndex).
				This attribute is optional and the pointer is null when it is not assigned.
				
				New parameter with SHE R2.8."
			::= { sheBridgePortControl 31 }

		
--   1.3.6.1.4.1.231.7.1.2.2.1.4.1.5
		sheBridgePortNotifications OBJECT IDENTIFIER ::= { sheBridge 5 }

		
--   1.3.6.1.4.1.231.7.1.2.2.1.4.1.5.1
		sheBridgeBaseParamModified NOTIFICATION-TYPE
			OBJECTS { sheBridgeBaseCircuitIdFormat, sheBridgeBaseControlTimeStamp, sheBridgeBaseMode, sheBridgeBaseTaggingMode, sheBridgeBaseMirrorPort, 
				sheBridgeBaseOuterPVID, sheBridgeBaseOuterPriority, sheBridgeBaseSharedVlanLearning, sheBridgeBaseRemoteIdFormat, sheBridgeBaseStagTPID, 
				sheBridgeBaseRoutingMode, sheBridgeBaseMacAntiSpoofing, sheBridgeBaseMaxHostName, sheBridgeBaseDlfFilter, sheBridgeBaseUnknownMuticastFilter, 
				sheBridgeBaseIpoaArpReqInterval }
			STATUS current
			DESCRIPTION 
				"Configuration notification."
			::= { sheBridgePortNotifications 1 }

		
--   1.3.6.1.4.1.231.7.1.2.2.1.4.1.5.2
		sheBridgePortCreated NOTIFICATION-TYPE
			OBJECTS { sheBridgePortControlTimeStamp, sheSubLayerIndex, sheSubLayerCircuit, sheBridgePortPVID, sheBridgePortPriority, 
				sheBridgePortUsage, sheBridgePortHostConfigurationProtocol, sheBridgePortCircuitId, sheBridgePortMaxLearnPermitCount, sheBridgePortMode, 
				sheBridgePortTaggingMode }
			STATUS current
			DESCRIPTION 
				"A new bridgePort was created."
			::= { sheBridgePortNotifications 2 }

		
--   1.3.6.1.4.1.231.7.1.2.2.1.4.1.5.3
		sheBridgePortDeleted NOTIFICATION-TYPE
			OBJECTS { sheBridgePortControlIndex, sheBridgePortControlTimeStamp }
			STATUS current
			DESCRIPTION 
				"A bridgePort was deleted."
			::= { sheBridgePortNotifications 3 }

		
--   1.3.6.1.4.1.231.7.1.2.2.1.4.1.5.4
		sheBridgePortVlanDefaultsModified NOTIFICATION-TYPE
			OBJECTS { sheBridgePortControlIndex, sheBridgePortControlTimeStamp, sheBridgePortControlPVID, sheBridgePortControlPriority }
			STATUS current
			DESCRIPTION 
				"Configuration notification."
			::= { sheBridgePortNotifications 4 }

		
--   1.3.6.1.4.1.231.7.1.2.2.1.4.1.5.5
		sheBridgePortUsageModified NOTIFICATION-TYPE
			OBJECTS { sheBridgePortControlIndex, sheBridgePortControlTimeStamp, sheBridgePortControlUsage }
			STATUS current
			DESCRIPTION 
				"BridgePort usage modified."
			::= { sheBridgePortNotifications 5 }

		
--   1.3.6.1.4.1.231.7.1.2.2.1.4.1.5.6
		sheBridgePortHostConfigurationProtocolModified NOTIFICATION-TYPE
			OBJECTS { sheBridgePortControlIndex, sheBridgePortControlTimeStamp, sheBridgePortControlHostConfigurationProtocol, sheBridgePortControlCircuitId }
			STATUS current
			DESCRIPTION 
				"Configuration notification."
			::= { sheBridgePortNotifications 6 }

		
--   1.3.6.1.4.1.231.7.1.2.2.1.4.1.5.7
		sheBridgePortMaxLearnPermitCountModified NOTIFICATION-TYPE
			OBJECTS { sheBridgePortControlIndex, sheBridgePortControlTimeStamp, sheBridgePortControlMaxLearnPermitCount }
			STATUS current
			DESCRIPTION 
				"Configuration notification."
			::= { sheBridgePortNotifications 7 }

		
--   1.3.6.1.4.1.231.7.1.2.2.1.4.1.5.8
		sheBridgePortMcastGroupPackageListModified NOTIFICATION-TYPE
			OBJECTS { sheBridgePortControlIndex, sheBridgePortControlTimeStamp, sheBridgePortControlMcastGroupPackageList }
			STATUS current
			DESCRIPTION 
				"Configuration notification."
			::= { sheBridgePortNotifications 8 }

		
--   1.3.6.1.4.1.231.7.1.2.2.1.4.1.5.9
		sheBridgePortFeatureModified NOTIFICATION-TYPE
			OBJECTS { sheBridgePortControlIndex, sheBridgePortControlTimeStamp, sheBridgePortControlMode, sheBridgePortControlTaggingMode, sheBridgePortControlReplaceVlanTag
				 }
			STATUS current
			DESCRIPTION 
				"Configuration notification."
			::= { sheBridgePortNotifications 9 }

		
--   1.3.6.1.4.1.231.7.1.2.2.1.4.1.5.10
		sheBridgeMacProfileSrcMacAddressModified NOTIFICATION-TYPE
			OBJECTS { sheBridgeMacProfileControlIndex, sheBridgeMacProfileControlTimeStamp, sheBridgeMacProfileControlSrcMacAddress }
			STATUS current
			DESCRIPTION 
				"Configuration notification."
			::= { sheBridgePortNotifications 10 }

		
--   1.3.6.1.4.1.231.7.1.2.2.1.4.1.5.11
		sheBridgePortCircuitIdModified NOTIFICATION-TYPE
			OBJECTS { sheBridgePortControlIndex, sheBridgePortControlCircuitId }
			STATUS current
			DESCRIPTION 
				"send trap when bridgeport circuitid is set."
			::= { sheBridgePortNotifications 11 }

		
--   1.3.6.1.4.1.231.7.1.2.2.1.4.1.5.12
		sheBridgePortRemoteIdModified NOTIFICATION-TYPE
			OBJECTS { sheBridgePortControlIndex, sheBridgePortControlRemoteId }
			STATUS current
			DESCRIPTION 
				"send trap when bridgeport remoteid is set."
			::= { sheBridgePortNotifications 12 }

		
--   1.3.6.1.4.1.231.7.1.2.2.1.4.1.5.13
		sheBridgePortCircuitIdCleared NOTIFICATION-TYPE
			OBJECTS { sheBridgePortControlIndex }
			STATUS current
			DESCRIPTION 
				"send trap when bridgeport circuitid is cleared."
			::= { sheBridgePortNotifications 13 }

		
--   1.3.6.1.4.1.231.7.1.2.2.1.4.1.5.14
		sheBridgePortRemoteIdCleared NOTIFICATION-TYPE
			OBJECTS { sheBridgePortControlIndex }
			STATUS current
			DESCRIPTION 
				"send trap when bridgeport remoteid is cleared."
			::= { sheBridgePortNotifications 14 }

		
--   1.3.6.1.4.1.231.7.1.2.2.1.4.1.5.15
		sheBridgePortInnerPVIDModified NOTIFICATION-TYPE
			OBJECTS { sheBridgePortControlIndex, sheBridgePortControlTimeStamp, sheBridgePortControlInnerPVID }
			STATUS current
			DESCRIPTION 
				"send trap when bridgeport inner PVID is set."
			::= { sheBridgePortNotifications 15 }

		
--   1.3.6.1.4.1.231.7.1.2.2.1.4.1.5.16
		sheBridgePortInnerPriorityModified NOTIFICATION-TYPE
			OBJECTS { sheBridgePortControlIndex, sheBridgePortControlTimeStamp, sheBridgePortControlInnerPriority }
			STATUS current
			DESCRIPTION 
				"send trap when bridgeport inner priority is set."
			::= { sheBridgePortNotifications 16 }

		
--   1.3.6.1.4.1.231.7.1.2.2.1.4.1.5.17
		sheBridgePortIpoaProviderRouterIpAddressModified NOTIFICATION-TYPE
			OBJECTS { sheBridgePortControlIndex, sheBridgePortControlTimeStamp, sheBridgePortControlIpoaProviderRouterIpAddress }
			STATUS current
			DESCRIPTION 
				"send trap when bridgeport IPoA provider edge router's ip address is set."
			::= { sheBridgePortNotifications 17 }

		
--   1.3.6.1.4.1.231.7.1.2.2.1.4.1.5.18
		sheBridgePortMcastParameterModified NOTIFICATION-TYPE
			OBJECTS { sheBridgePortControlIndex, sheBridgePortControlTimeStamp, sheBridgePortControlMcastMaxJoinedGroup, sheBridgePortControlMcastLeaveMode, sheBridgePortControlMcastEHTMode
				 }
			STATUS current
			DESCRIPTION 
				"send trap when bridgeport mcast parameter is set."
			::= { sheBridgePortNotifications 18 }

		
--    1.3.6.1.4.1.231.7.1.2.2.1.4.1.5.19
		sheBridgePortIgmpSubscriberAccessModeModified NOTIFICATION-TYPE
			OBJECTS { sheBridgePortControlIndex, sheBridgePortControlTimeStamp, sheBridgePortControlIgmpSubscriberAccessMode }
			STATUS obsolete
			DESCRIPTION 
				"send trap when bridgeport igmp subscriber Access mode is set."
			::= { sheBridgePortNotifications 19 }

		
		setBridgePortPriorityOptionsModified NOTIFICATION-TYPE
			OBJECTS { sheBridgePortControlIndex, sheBridgePortControlTimeStamp, sheBridgePortControlPriorityMapIndex, sheBridgePortControlInnerPriorityOption, sheBridgePortControlOuterPriorityOption
				 }
			STATUS current
			DESCRIPTION 
				"send trap when configuration of PriorityOptions parameters was modified"
			::= { sheBridgePortNotifications 20 }

		
		sheBridgePortMatEnabledModified NOTIFICATION-TYPE
			OBJECTS { sheBridgePortControlIndex, sheBridgePortControlTimeStamp, sheBridgePortControlMatEnabled }
			STATUS current
			DESCRIPTION 
				"send trap when configuration of MatEnabled on BridgePort base was modified"
			::= { sheBridgePortNotifications 21 }

		
		sheBridgePortIpAddressPermitCountModified NOTIFICATION-TYPE
			OBJECTS { sheBridgePortControlIndex, sheBridgePortControlTimeStamp, sheBridgePortControlIpAddressPermitCount }
			STATUS current
			DESCRIPTION 
				"send trap when configuration of permit count for DHCP was modified"
			::= { sheBridgePortNotifications 22 }

		
		sheBridgePortPrioMapEntryCreated NOTIFICATION-TYPE
			OBJECTS { sheBridgePortPrioMapControlIndex, sheBridgePortPrioMapControlTimeStamp }
			STATUS current
			DESCRIPTION 
				"a complete entry (64 dscp entries) with a default mapping is created"
			::= { sheBridgePortNotifications 23 }

		
		sheBridgePortPrioMapEntryDeleted NOTIFICATION-TYPE
			OBJECTS { sheBridgePortPrioMapControlIndex, sheBridgePortPrioMapControlTimeStamp }
			STATUS current
			DESCRIPTION 
				"a complete entry (64 dscp entries) is deleted"
			::= { sheBridgePortNotifications 24 }

		
		sheBridgePortPrioMapEntryModified NOTIFICATION-TYPE
			OBJECTS { sheBridgePortPrioMapControlIndex, sheBridgePortPrioMapControlTimeStamp, sheBridgePortPrioMapControlDscp, sheBridgePortPrioMapControlPrio }
			STATUS current
			DESCRIPTION 
				"a single dscp entry is modified"
			::= { sheBridgePortNotifications 25 }

		
		sheBridgePortExtMCastParameterModified NOTIFICATION-TYPE
			OBJECTS { sheBridgePortMCastControlIndex, sheBridgePortMCastControlTimeStamp, sheBridgePortMCastControlBandwithLimit, sheBridgePortMCastControlMinUCBandwithLimit, sheBridgePortMCastControlMaxJoinedNonPremiumGroup
				 }
			STATUS current
			DESCRIPTION 
				"send trap when bridgeport R2.8 mcast parameter are set."
			::= { sheBridgePortNotifications 28 }

		
		sheEtypeVlanMapProfEntryCreated NOTIFICATION-TYPE
			OBJECTS { sheBridgePortEtypeVlanMapControlTimeStamp, sheBridgePortEtypeVlanMapCtrlProfIndex, sheBridgePortEtypeVlanMapCtrlEthertype, sheBridgePortEtypeVlanMapCtrlVlanId, sheBridgePortEtypeVlanMapCtrlPriority
				 }
			STATUS current
			DESCRIPTION 
				"A new sheBridgePortEtypeVlanMapProfile was created in the NE.
				New with SHE R2.8."
			::= { sheBridgePortNotifications 29 }

		
		sheEtypeVlanMapProfEntryModified NOTIFICATION-TYPE
			OBJECTS { sheBridgePortEtypeVlanMapControlTimeStamp, sheBridgePortEtypeVlanMapCtrlProfIndex, sheBridgePortEtypeVlanMapCtrlEthertype, sheBridgePortEtypeVlanMapCtrlVlanId, sheBridgePortEtypeVlanMapCtrlPriority
				 }
			STATUS current
			DESCRIPTION 
				"A sheBridgePortEtypeVlanMapProfile was modified in the NE.
				New with SHE R2.8."
			::= { sheBridgePortNotifications 30 }

		
		sheEtypeVlanMapProfEntryDeleted NOTIFICATION-TYPE
			OBJECTS { sheBridgePortEtypeVlanMapControlTimeStamp, sheBridgePortEtypeVlanMapCtrlProfIndex }
			STATUS current
			DESCRIPTION 
				"A sheBridgePortEtypeVlanMapProfile was deleted in the NE.
				New with SHE R2.8."
			::= { sheBridgePortNotifications 31 }

		
		sheBridgePortIpAsModeModified NOTIFICATION-TYPE
			OBJECTS { sheBridgePortControlIndex, sheBridgePortControlTimeStamp, sheBridgePortControlIpAsMode }
			STATUS current
			DESCRIPTION 
				"The bridgePort specific IpAs mode was modified."
			::= { sheBridgePortNotifications 32 }

		
		sheBridgePortEtypeVlanMappingModified NOTIFICATION-TYPE
			OBJECTS { sheBridgePortControlIndex, sheBridgePortControlTimeStamp, sheBridgePortControlEtypeVlanMapProfilePtr }
			STATUS current
			DESCRIPTION 
				"The bridgePort specific EthertypeVlanMapping profile assignment was modified."
			::= { sheBridgePortNotifications 33 }

		
		sheBridgeExtResidentialModeModified NOTIFICATION-TYPE
			OBJECTS { sheBridgeExtResidentialControlPortIndex, sheBridgeExtResidentialControlTimeStamp, sheBridgeExtResidentialControlMode }
			STATUS current
			DESCRIPTION 
				"The port specific ext-residential mode was modified."
			::= { sheBridgePortNotifications 40 }

		
--   1.3.6.1.4.1.231.7.1.2.2.1.4.1.6
		sheBridgeMacProfileTable OBJECT-TYPE
			SYNTAX SEQUENCE OF SheBridgeMacProfileEntry
			MAX-ACCESS not-accessible
			STATUS current
			DESCRIPTION
				"Description."
			::= { sheBridge 6 }

		
--   1.3.6.1.4.1.231.7.1.2.2.1.4.1.6.1
		sheBridgeMacProfileEntry OBJECT-TYPE
			SYNTAX SheBridgeMacProfileEntry
			MAX-ACCESS not-accessible
			STATUS current
			DESCRIPTION
				"Needed for feature IpoA. Configure the used Mac-Address if this bridgeport is running
				in IpoA-Mode."
			INDEX { sheBridgePortIndex }
			::= { sheBridgeMacProfileTable 1 }

		
		SheBridgeMacProfileEntry ::=
			SEQUENCE { 
				sheBridgeMacProfileSrcMacAddress
					OCTET STRING
			 }

--   1.3.6.1.4.1.231.7.1.2.2.1.4.1.6.1.1
		sheBridgeMacProfileSrcMacAddress OBJECT-TYPE
			SYNTAX OCTET STRING (SIZE (6))
			MAX-ACCESS read-only
			STATUS current
			DESCRIPTION
				"The used Src-MacAddress if this port is running in IpoA - mode.
				If address 000000 is set, the NE will autogenerate a valid mac-address."
			::= { sheBridgeMacProfileEntry 1 }

		
--   1.3.6.1.4.1.231.7.1.2.2.1.4.1.7
		sheBridgeMacProfileControl OBJECT IDENTIFIER ::= { sheBridge 7 }

		
--   1.3.6.1.4.1.231.7.1.2.2.1.4.1.7.1
		sheBridgeMacProfileControlRequest OBJECT-TYPE
			SYNTAX SheBridgeControlRequestType
			MAX-ACCESS read-write
			STATUS current
			DESCRIPTION
				"setBridgeMacProfileSrcMacAddress:
				sheBridgeMacProfileControlIndex
				sheBridgeMacProfileControlSrcMacAddress"
			::= { sheBridgeMacProfileControl 1 }

		
--   1.3.6.1.4.1.231.7.1.2.2.1.4.1.7.2
		sheBridgeMacProfileControlIndex OBJECT-TYPE
			SYNTAX Integer32
			MAX-ACCESS read-write
			STATUS current
			DESCRIPTION
				"The index of the bridgePort to be configured."
			::= { sheBridgeMacProfileControl 2 }

		
--    
-- 1.3.6.1.4.1.231.7.1.2.2.1.4.1.7.3
		sheBridgeMacProfileControlStatus OBJECT-TYPE
			SYNTAX SheControlStatusType
			MAX-ACCESS read-only
			STATUS current
			DESCRIPTION
				"The status of a user command. 
				"
			::= { sheBridgeMacProfileControl 3 }

		
--   1.3.6.1.4.1.231.7.1.2.2.1.4.1.7.4
		sheBridgeMacProfileControlTimer OBJECT-TYPE
			SYNTAX Gauge32
			MAX-ACCESS read-only
			STATUS current
			DESCRIPTION
				"The maximum wait time for the manager for a long running user command. 
				"
			::= { sheBridgeMacProfileControl 4 }

		
--    
-- 1.3.6.1.4.1.231.7.1.2.2.1.4.1.7.5
		sheBridgeMacProfileControlReqResult OBJECT-TYPE
			SYNTAX SheBridgeControlReqResultType
			MAX-ACCESS read-only
			STATUS current
			DESCRIPTION
				"The result of the last user command."
			::= { sheBridgeMacProfileControl 5 }

		
--    
-- 1.3.6.1.4.1.231.7.1.2.2.1.4.1.7.6
		sheBridgeMacProfileControlTimeStamp OBJECT-TYPE
			SYNTAX Unsigned32
			UNITS "sec"
			MAX-ACCESS read-only
			STATUS current
			DESCRIPTION
				"The time stamp of the last command (end of command)."
			::= { sheBridgeMacProfileControl 6 }

		
--   1.3.6.1.4.1.231.7.1.2.2.1.4.1.7.7
		sheBridgeMacProfileControlSrcMacAddress OBJECT-TYPE
			SYNTAX OCTET STRING (SIZE (6))
			MAX-ACCESS read-write
			STATUS current
			DESCRIPTION
				"look at table."
			::= { sheBridgeMacProfileControl 7 }

		
--  Contain needed bridge specific IU configurations.
		sheBridgeIUConfig OBJECT IDENTIFIER ::= { sheBridge 8 }

		
--   1.3.6.1.4.1.231.7.1.2.2.1.4.1.6
		sheBridgeIUProfileTable OBJECT-TYPE
			SYNTAX SEQUENCE OF SheBridgeIUProfileEntry
			MAX-ACCESS not-accessible
			STATUS current
			DESCRIPTION
				"Description."
			::= { sheBridgeIUConfig 1 }

		
--   1.3.6.1.4.1.231.7.1.2.2.1.4.1.6.1
		sheBridgeIUProfileEntry OBJECT-TYPE
			SYNTAX SheBridgeIUProfileEntry
			MAX-ACCESS not-accessible
			STATUS current
			DESCRIPTION
				"Needed to configure some IU specific settings.
				Index should be the entPhysicalIndex of the IU."
			INDEX { entPhysicalIndex }
			::= { sheBridgeIUProfileTable 1 }

		
		SheBridgeIUProfileEntry ::=
			SEQUENCE { 
				sheBridgeIUPPPoASrcMacAddress
					OCTET STRING,
				sheBridgeIUProfileUsedMATBasis
					SheBridgeIUProfileUsedMATBasisType,
				sheBridgeIUReplaceVlanTag
					Integer32,
				sheBridgeIUDscpPriorityMapIndex
					Unsigned32
			 }

--  1.3.6.1.4.1.231.7.1.2.2.1.4.1.8.1.1.1
		sheBridgeIUPPPoASrcMacAddress OBJECT-TYPE
			SYNTAX OCTET STRING (SIZE (6))
			MAX-ACCESS read-only
			STATUS current
			DESCRIPTION
				"The used Src-MacAddress for this IU if one of her port's is running in
				PPPoA - mode. The PPPoA session is translated to PPPoE. This configuration
				should be made before a port could be switched to PPPoA - mode."
			::= { sheBridgeIUProfileEntry 1 }

		
--  1.3.6.1.4.1.231.7.1.2.2.1.4.1.8.1.1.2
		sheBridgeIUProfileUsedMATBasis OBJECT-TYPE
			SYNTAX SheBridgeIUProfileUsedMATBasisType
			MAX-ACCESS read-only
			STATUS current
			DESCRIPTION
				"This parameter select the basis for MAT on these IU. This will NOT enable the MAT feature
				himself, but select the valid configuration for this IU. 
				If useMATperVlan (default) is selected, the settings of sheBridgePortMatEnabled will be ignored.
				Only settings of sheVlanMatEnable are valid, if the VLAN is used on this IU.
				If useMATperBridgeport is selected, the handling will be done in an opposite way.
				
				If the used basis should be changed, a reboot of the corresponding IU may be needed to come operational.
				
				New parameter with R2.8."
			DEFVAL { useMATperVlan }
			::= { sheBridgeIUProfileEntry 2 }

		
--   1.3.6.1.4.1.231.7.1.2.2.1.4.1.3.1.15
		sheBridgeIUReplaceVlanTag OBJECT-TYPE
			SYNTAX Integer32 (0 | 1..4093)
			MAX-ACCESS read-only
			STATUS current
			DESCRIPTION
				"If configured unequal 0, the configured vlan-tag could be received and will be
				replaced by PVID before forwarding the frame. A zero will disable this feature for this IU.
				Only valid for IU Bridgeport's which are running tagged(1) mode and only if the NE 
				global tagging mode is singleTag.
				
				NOTE:
				New with R2.8. Configuration was moved from sheBridgePortTable. 
				The corresponding entry in the bridgeport table enable/disable the feature per bridgeport."
			DEFVAL { 0 }
			::= { sheBridgeIUProfileEntry 3 }

		
		sheBridgeIUDscpPriorityMapIndex OBJECT-TYPE
			SYNTAX Unsigned32 (0 | 1..16)
			MAX-ACCESS read-only
			STATUS current
			DESCRIPTION
				"This is a pointer to a mapping entry DSCP to .1p.
				Value 0 (default) means there is no mapping in use or the port specific assignment
				via sheBridgePortPriorityMapIndex will be used.
				
				One of these two pointer's (port specific or IU global) must be valid
				if sheBridgePortPriorityOption is dscp(1) and sheBridgePortUsage is subscriber(4).
				Used if a tag is added to an upstream user frame and sheBridgePortPriorityOption
				is dscp to set .1p bits. Used if an upstream user frame is tagged and
				sheBridgePortPriorityOption is dscp for .1p range check.
				
				NOTE:
				Convergate based IU's could only support ONE profile for all port's were these
				mapping should be used!!
				
				New parameter with SHE R2.8."
			DEFVAL { 0 }
			::= { sheBridgeIUProfileEntry 4 }

		
--   1.3.6.1.4.1.231.7.1.2.2.1.4.1.7
		sheBridgeIUProfileControl OBJECT IDENTIFIER ::= { sheBridgeIUConfig 2 }

		
--  1.3.6.1.4.1.231.7.1.2.2.1.4.1.8.2.1
		sheBridgeIUProfileControlRequest OBJECT-TYPE
			SYNTAX SheBridgeControlRequestType
			MAX-ACCESS read-write
			STATUS current
			DESCRIPTION
				"setBridgeIUProfilePPPoASrcMacAddress (131):
				sheBridgeIUProfileControlIndex
				sheBridgeIUProfileControlPPPoASrcMacAddress
				
				New with R2.8:
				setBridgeIUProfileUsedMATBasis (132):
				sheBridgeIUProfileControlIndex
				sheBridgeIUProfileControlUsedMATBasis
				
				setBridgeIUProfileReplaceVlanTag (133):
				sheBridgeIUProfileControlIndex
				sheBridgeIUProfileControlReplaceVlanTag
				
				setBridgeIUProfileDscpPriorityMapProfileIndex (134):
				sheBridgeIUProfileControlIndex
				sheBridgeIUProfileControlDscpPriorityMapIndex"
			::= { sheBridgeIUProfileControl 1 }

		
--  1.3.6.1.4.1.231.7.1.2.2.1.4.1.8.2.2
		sheBridgeIUProfileControlIndex OBJECT-TYPE
			SYNTAX PhysicalIndex
			MAX-ACCESS read-write
			STATUS current
			DESCRIPTION
				"The index of the IU to be configured."
			::= { sheBridgeIUProfileControl 2 }

		
--  1.3.6.1.4.1.231.7.1.2.2.1.4.1.8.2.3
		sheBridgeIUProfileControlStatus OBJECT-TYPE
			SYNTAX SheControlStatusType
			MAX-ACCESS read-only
			STATUS current
			DESCRIPTION
				"The status of a user command. 
				"
			::= { sheBridgeIUProfileControl 3 }

		
--  1.3.6.1.4.1.231.7.1.2.2.1.4.1.8.2.4
		sheBridgeIUProfileControlTimer OBJECT-TYPE
			SYNTAX Gauge32
			MAX-ACCESS read-only
			STATUS current
			DESCRIPTION
				"The maximum wait time for the manager for a long running user command. 
				"
			::= { sheBridgeIUProfileControl 4 }

		
--  1.3.6.1.4.1.231.7.1.2.2.1.4.1.8.2.5
		sheBridgeIUProfileControlReqResult OBJECT-TYPE
			SYNTAX SheBridgeControlReqResultType
			MAX-ACCESS read-only
			STATUS current
			DESCRIPTION
				"The result of the last user command."
			::= { sheBridgeIUProfileControl 5 }

		
--  1.3.6.1.4.1.231.7.1.2.2.1.4.1.8.2.6
		sheBridgeIUProfileControlTimeStamp OBJECT-TYPE
			SYNTAX Unsigned32
			UNITS "sec"
			MAX-ACCESS read-only
			STATUS current
			DESCRIPTION
				"The time stamp of the last command (end of command)."
			::= { sheBridgeIUProfileControl 6 }

		
--  1.3.6.1.4.1.231.7.1.2.2.1.4.1.8.2.7
		sheBridgeIUProfileControlPPPoASrcMacAddress OBJECT-TYPE
			SYNTAX OCTET STRING (SIZE (6))
			MAX-ACCESS read-write
			STATUS current
			DESCRIPTION
				"look at table."
			::= { sheBridgeIUProfileControl 7 }

		
--  1.3.6.1.4.1.231.7.1.2.2.1.4.1.8.2.8
		sheBridgeIUProfileControlUsedMATBasis OBJECT-TYPE
			SYNTAX SheBridgeIUProfileUsedMATBasisType
			MAX-ACCESS read-write
			STATUS current
			DESCRIPTION
				"This parameter select the basis for MAT on these IU. This will NOT enable the MAT feature
				himself, but select the valid configuration for this IU. 
				If useMATperVlan (default) is selected, the settings of sheBridgePortMatEnabled will be ignored.
				Only settings of sheVlanMatEnable are valid, if the VLAN is used on this IU.
				If useMATperBridgeport is selected, the handling will be done in an opposite way.
				
				If the used basis should be changed, a reboot of the corresponding IU may be needed to come operational.
				
				New parameter with R2.8."
			::= { sheBridgeIUProfileControl 8 }

		
--   1.3.6.1.4.1.231.7.1.2.2.1.4.1.4.18			
		sheBridgeIUProfileControlReplaceVlanTag OBJECT-TYPE
			SYNTAX Integer32 (0 | 1..4093)
			MAX-ACCESS read-write
			STATUS current
			DESCRIPTION
				"If configured unequal 0, the configured vlan-tag could be received and will be
				replaced by PVID before forwarding the frame. A zero will disable this feature for this IU.
				Only valid for IU Bridgeport's which are running tagged(1) mode and only if the NE 
				global tagging mode is singleTag.
				
				NOTE:
				New with R2.8. Configuration was moved from sheBridgePortTable. 
				The corresponding entry in the bridgeport table enable/disable the feature per bridgeport."
			::= { sheBridgeIUProfileControl 9 }

		
		sheBridgeIUProfileControlDscpPriorityMapIndex OBJECT-TYPE
			SYNTAX Unsigned32 (0 | 1..16)
			MAX-ACCESS read-write
			STATUS current
			DESCRIPTION
				"look at table"
			::= { sheBridgeIUProfileControl 10 }

		
--   1.3.6.1.4.1.231.7.1.2.2.1.4.1.10
		sheBridgeIUNotifications OBJECT IDENTIFIER ::= { sheBridgeIUConfig 3 }

		
--  1.3.6.1.4.1.231.7.1.2.2.1.4.1.8.3.2
		sheBridgeIUProfilePPPoASrcMacAddressModified NOTIFICATION-TYPE
			OBJECTS { sheBridgeIUProfileControlIndex, sheBridgeIUProfileControlTimeStamp, sheBridgeIUProfileControlPPPoASrcMacAddress }
			STATUS current
			DESCRIPTION 
				"Configuration notification."
			::= { sheBridgeIUNotifications 1 }

		
--  1.3.6.1.4.1.231.7.1.2.2.1.4.1.8.3.2
		sheBridgeIUProfileUsedMATBasisModified NOTIFICATION-TYPE
			OBJECTS { sheBridgeIUProfileControlIndex, sheBridgeIUProfileControlTimeStamp, sheBridgeIUProfileControlUsedMATBasis }
			STATUS current
			DESCRIPTION 
				"Configuration notification."
			::= { sheBridgeIUNotifications 2 }

		
--  1.3.6.1.4.1.231.7.1.2.2.1.4.1.8.3.2
		sheBridgeIUProfileReplaceVlanTagModified NOTIFICATION-TYPE
			OBJECTS { sheBridgeIUProfileControlIndex, sheBridgeIUProfileControlTimeStamp, sheBridgeIUProfileControlReplaceVlanTag }
			STATUS current
			DESCRIPTION 
				"Configuration notification."
			::= { sheBridgeIUNotifications 3 }

		
--  1.3.6.1.4.1.231.7.1.2.2.1.4.1.8.3.2
		sheBridgeIUProfileDscpPriorityMapProfileIndexModified NOTIFICATION-TYPE
			OBJECTS { sheBridgeIUProfileControlIndex, sheBridgeIUProfileControlTimeStamp, sheBridgeIUProfileControlDscpPriorityMapIndex }
			STATUS current
			DESCRIPTION 
				"Configuration notification."
			::= { sheBridgeIUNotifications 4 }

		
--  New with SHE R2.8.
		sheBridgePortPriorityMapConfig OBJECT IDENTIFIER ::= { sheBridge 9 }

		
		sheBridgePortPriorityMapTable OBJECT-TYPE
			SYNTAX SEQUENCE OF SheBridgePortPriorityMapEntry
			MAX-ACCESS not-accessible
			STATUS current
			DESCRIPTION
				"A mapping profile DSCP to .1p.
				Used if a tag is added to an upstream user frame (when sheBridgePortTaggingMode
				is untagged or tagged) and sheBridgePortPriorityOption is dscp.
				The first table index is the profile number. The second table index and
				the mapping key is the DSCP field.
				One default profile with index 1 always exist and can't be deleted but modified.
				"
			::= { sheBridgePortPriorityMapConfig 1 }

		
		sheBridgePortPriorityMapEntry OBJECT-TYPE
			SYNTAX SheBridgePortPriorityMapEntry
			MAX-ACCESS not-accessible
			STATUS current
			DESCRIPTION
				"A mapping entry DSCP to .1p.
				Used if a tag is added to an upstream user frame (when sheBridgePortTaggingMode
				is untagged or tagged) and sheBridgePortPriorityOption is dscp.
				The first table index is the entry index. The second table index and the
				mapping key is the DSCP field.
				One default mapping entry with index 1 always exist and can't be deleted but modified."
			INDEX { sheBridgePortPriorityMapEntryIndex, sheBridgePortPriorityMapDscp }
			::= { sheBridgePortPriorityMapTable 1 }

		
		SheBridgePortPriorityMapEntry ::=
			SEQUENCE { 
				sheBridgePortPriorityMapEntryIndex
					Unsigned32,
				sheBridgePortPriorityMapDscp
					Unsigned32,
				sheBridgePortPriorityMapPrio
					Unsigned32
			 }

		sheBridgePortPriorityMapEntryIndex OBJECT-TYPE
			SYNTAX Unsigned32 (1..16)
			MAX-ACCESS read-only
			STATUS current
			DESCRIPTION
				"The number of the mapping profile is the first table index."
			::= { sheBridgePortPriorityMapEntry 1 }

		
		sheBridgePortPriorityMapDscp OBJECT-TYPE
			SYNTAX Unsigned32 (1..64)
			MAX-ACCESS read-only
			STATUS current
			DESCRIPTION
				"Bits 2-7 of TOS field of IP header are called DSCP.
				DSCP 000000 is the lowest priority (best effort).
				
				This is the second table index and the mapping key.
				Since zero is not allowed as table index, this value is increased by 1 (range is 1..64)."
			::= { sheBridgePortPriorityMapEntry 2 }

		
		sheBridgePortPriorityMapPrio OBJECT-TYPE
			SYNTAX Unsigned32 (0..7)
			MAX-ACCESS read-only
			STATUS current
			DESCRIPTION
				"The .1p priority bits in the VLAN tag is the mapping value."
			::= { sheBridgePortPriorityMapEntry 3 }

		
		sheBridgePortPriorityMapControl OBJECT IDENTIFIER ::= { sheBridgePortPriorityMapConfig 2 }

		
		sheBridgePortPrioMapControlRequest OBJECT-TYPE
			SYNTAX SheBridgeControlRequestType
			MAX-ACCESS read-write
			STATUS current
			DESCRIPTION
				"One default mapping entry with index 1 always exist and can't be deleted but modified.
				
				createBridgePortPrioMapEntry
				- a complete profile (64 entries) with a default mapping is created
				
				deleteBridgePortPrioMapEntry
				 sheBridgePortPrioMapControlIndex
				- a complete profile (64 entries) is deleted
				
				modifyBridgePortPrioMapEntry
				 sheBridgePortPrioMapControlIndex
				 sheBridgePortPrioMapControlDscp
				 sheBridgePortPrioMapControlPrio
				- a single entry of a profile is modified"
			::= { sheBridgePortPriorityMapControl 1 }

		
		sheBridgePortPrioMapControlIndex OBJECT-TYPE
			SYNTAX Unsigned32 (1..16)
			MAX-ACCESS read-write
			STATUS current
			DESCRIPTION
				"The number of the mapping entry is the first table index."
			::= { sheBridgePortPriorityMapControl 2 }

		
		sheBridgePortPrioMapControlStatus OBJECT-TYPE
			SYNTAX SheControlStatusType
			MAX-ACCESS read-only
			STATUS current
			DESCRIPTION
				"The status of a user command. "
			::= { sheBridgePortPriorityMapControl 3 }

		
		sheBridgePortPrioMapControlTimer OBJECT-TYPE
			SYNTAX Gauge32
			MAX-ACCESS read-only
			STATUS current
			DESCRIPTION
				"The maximum wait time for the manager for a long running user command."
			::= { sheBridgePortPriorityMapControl 4 }

		
		sheBridgePortPrioMapControlReqResult OBJECT-TYPE
			SYNTAX SheBridgeControlReqResultType
			MAX-ACCESS read-only
			STATUS current
			DESCRIPTION
				"The result of the last user command."
			::= { sheBridgePortPriorityMapControl 5 }

		
		sheBridgePortPrioMapControlTimeStamp OBJECT-TYPE
			SYNTAX Unsigned32
			UNITS "sec"
			MAX-ACCESS read-only
			STATUS current
			DESCRIPTION
				"The time stamp of the last command (end of command)."
			::= { sheBridgePortPriorityMapControl 6 }

		
		sheBridgePortPrioMapControlDscp OBJECT-TYPE
			SYNTAX Unsigned32 (1..64)
			MAX-ACCESS read-write
			STATUS current
			DESCRIPTION
				"Bits 2-7 of TOS field of IP header are called DSCP.
				DSCP 000000 is the lowest priority (best effort).
				
				This is the second table index and the mapping key.
				Since zero is not allowed as table index, this value is increased
				by 1 (range is 1..64)."
			::= { sheBridgePortPriorityMapControl 7 }

		
		sheBridgePortPrioMapControlPrio OBJECT-TYPE
			SYNTAX Unsigned32 (0..7)
			MAX-ACCESS read-write
			STATUS current
			DESCRIPTION
				"The .1p priority bits in the VLAN tag is the mapping value."
			::= { sheBridgePortPriorityMapControl 8 }

		
		sheBridgePortMCastConfig OBJECT IDENTIFIER ::= { sheBridge 10 }

		
		sheBridgePortMCastConfigTable OBJECT-TYPE
			SYNTAX SEQUENCE OF SheBridgePortMCastConfigEntry
			MAX-ACCESS not-accessible
			STATUS current
			DESCRIPTION
				"This table contain all new defined bridgePort specific multicast configurations.
				New supported with SHE R2.8!"
			::= { sheBridgePortMCastConfig 1 }

		
		sheBridgePortMCastConfigEntry OBJECT-TYPE
			SYNTAX SheBridgePortMCastConfigEntry
			MAX-ACCESS not-accessible
			STATUS current
			DESCRIPTION
				"The MCast configuration settiongs per BridgePort."
			INDEX { sheBridgePortIndex }
			::= { sheBridgePortMCastConfigTable 1 }

		
		SheBridgePortMCastConfigEntry ::=
			SEQUENCE { 
				sheBridgePortMCastBandwithLimit
					Unsigned32,
				sheBridgePortMCastMinUCBandwithLimit
					Unsigned32,
				sheBridgePortMCastMaxJoinedNonPremiumGroup
					Unsigned32,
				sheBridgePortMCastRemainBandwith
					Unsigned32,
				sheBridgePortMCastACStatus
					SheBridgePortACStatus
			 }

		sheBridgePortMCastBandwithLimit OBJECT-TYPE
			SYNTAX Unsigned32 (0..500 | 65535)
			UNITS "100 kbps"
			MAX-ACCESS read-only
			STATUS current
			DESCRIPTION
				"This is the configured multicast bandwith limitation per bridgePort.
				0 kbps indicates that no multicast traffic is allowed for the bport.
				The value 65535 (0xFFFF) is a special value and means unlimited access for this bridgeport
				(switch off feature AC - admission control - default).
				
				New parameter with SHE R2.8."
			DEFVAL { 65535 }
			::= { sheBridgePortMCastConfigEntry 1 }

		
		sheBridgePortMCastMinUCBandwithLimit OBJECT-TYPE
			SYNTAX Unsigned32 (0..500)
			UNITS "100 kbps"
			MAX-ACCESS read-only
			STATUS current
			DESCRIPTION
				"This is the minimum bandwidth of sustainable unicast traffic for a bridge port.
				M/C admission control shall include this minimum bandwidth of sustainable unicast
				traffic within the calculation to reserve a minimum bandwidth for VoD services.
				
				New parameter with SHE R2.8."
			DEFVAL { 0 }
			::= { sheBridgePortMCastConfigEntry 2 }

		
		sheBridgePortMCastMaxJoinedNonPremiumGroup OBJECT-TYPE
			SYNTAX Unsigned32 (0 | 1..32 | 255)
			MAX-ACCESS read-only
			STATUS current
			DESCRIPTION
				"The maximum number of non-premium multicast group's (channels) that this subscriber can join.
				0 is a special value and means 'no' access.
				255 is a special value and means 'unlimited' access.
				
				New parameter with SHE R2.8."
			DEFVAL { 10 }
			::= { sheBridgePortMCastConfigEntry 3 }

		
		sheBridgePortMCastRemainBandwith OBJECT-TYPE
			SYNTAX Unsigned32 (0..500)
			UNITS "100 kbps"
			MAX-ACCESS read-only
			STATUS current
			DESCRIPTION
				"It is the remaining multicast bandwidth of a bridge port.
				New parameter with SHE R2.8."
			::= { sheBridgePortMCastConfigEntry 4 }

		
		sheBridgePortMCastACStatus OBJECT-TYPE
			SYNTAX SheBridgePortACStatus
			MAX-ACCESS read-only
			STATUS current
			DESCRIPTION
				"It indicates the AC (admission control) status of a bridgeport, 
				It can be accept or deny.
				When it is accepted, it indicates the bridgeport still has enough bandwidth for multicast access.
				When it is denied, it indicates the bridgeport is short of bandwidth for multicast access. 
				1 means accept, 0 means deny.
				New parameter with SHE R2.8."
			::= { sheBridgePortMCastConfigEntry 5 }

		
		sheBridgePortMCastControl OBJECT IDENTIFIER ::= { sheBridgePortMCastConfig 2 }

		
		sheBridgePortMCastControlRequest OBJECT-TYPE
			SYNTAX SheBridgeControlRequestType
			MAX-ACCESS read-write
			STATUS current
			DESCRIPTION
				"setBridgePortExtMCastParameter(162):
				sheBridgePortMCastControlIndex
				sheBridgePortMCastControlBandwithLimit
				sheBridgePortMCastControlMinUCBandwithLimit 
				sheBridgePortMCastControlMaxJoinedNonPremiumGroup "
			::= { sheBridgePortMCastControl 1 }

		
		sheBridgePortMCastControlIndex OBJECT-TYPE
			SYNTAX Integer32
			MAX-ACCESS read-write
			STATUS current
			DESCRIPTION
				"The index of the bridgePort to be configured."
			::= { sheBridgePortMCastControl 2 }

		
		sheBridgePortMCastControlStatus OBJECT-TYPE
			SYNTAX SheControlStatusType
			MAX-ACCESS read-only
			STATUS current
			DESCRIPTION
				"The status of a user command. 
				"
			::= { sheBridgePortMCastControl 3 }

		
		sheBridgePortMCastControlTimer OBJECT-TYPE
			SYNTAX Gauge32
			MAX-ACCESS read-only
			STATUS current
			DESCRIPTION
				"The maximum wait time for the manager for a long running user command. 
				"
			::= { sheBridgePortMCastControl 4 }

		
		sheBridgePortMCastControlReqResult OBJECT-TYPE
			SYNTAX SheBridgeControlReqResultType
			MAX-ACCESS read-only
			STATUS current
			DESCRIPTION
				"The result of the last user command."
			::= { sheBridgePortMCastControl 5 }

		
		sheBridgePortMCastControlTimeStamp OBJECT-TYPE
			SYNTAX Unsigned32
			UNITS "sec"
			MAX-ACCESS read-only
			STATUS current
			DESCRIPTION
				"The time stamp of the last command (end of command)."
			::= { sheBridgePortMCastControl 6 }

		
		sheBridgePortMCastControlBandwithLimit OBJECT-TYPE
			SYNTAX Unsigned32 (0..500 | 65535)
			UNITS "100 kbps"
			MAX-ACCESS read-write
			STATUS current
			DESCRIPTION
				"This is the configured multicast bandwith limitation per bridgePort.
				0 kbps indicates that no multicast traffic is allowed for the bport.
				The value 655353 (0xFFFF) is a special value and means unlimited access for this bridgeport
				(switch off feature AC - admission control).
				New parameter with SHE R2.8.
				"
			::= { sheBridgePortMCastControl 11 }

		
		sheBridgePortMCastControlMinUCBandwithLimit OBJECT-TYPE
			SYNTAX Unsigned32 (0..500)
			UNITS "100 kbps"
			MAX-ACCESS read-write
			STATUS current
			DESCRIPTION
				"This is the minimum bandwidth of sustainable unicast traffic for a bridge port.
				M/C admission control shall include this minimum bandwidth of sustainable unicast
				traffic within the calculation to reserve a minimum bandwidth for VoD services.
				
				New parameter with SHE R2.8.
				"
			::= { sheBridgePortMCastControl 12 }

		
		sheBridgePortMCastControlMaxJoinedNonPremiumGroup OBJECT-TYPE
			SYNTAX Unsigned32 (0 | 1..32 | 255)
			MAX-ACCESS read-write
			STATUS current
			DESCRIPTION
				"The maximum number of non-premium multicast group's that this subscriber can join.
				0 is a special value and means 'no' access.
				255 is a special value and means 'unlimited' access.
				
				New parameter with SHE R2.8."
			::= { sheBridgePortMCastControl 13 }

		
--  New with SHR R2.8.
		sheBridgePortEtherTypeConfig OBJECT IDENTIFIER ::= { sheBridge 11 }

		
		sheBridgePortEtypeVlanMapTable OBJECT-TYPE
			SYNTAX SEQUENCE OF SheBridgePortEtypeVlanMapEntry
			MAX-ACCESS not-accessible
			STATUS current
			DESCRIPTION
				"This table is used with SHE R2.8.
				
				Ethertype-VLAN mapping profiles. Index is the profile index."
			::= { sheBridgePortEtherTypeConfig 1 }

		
		sheBridgePortEtypeVlanMapEntry OBJECT-TYPE
			SYNTAX SheBridgePortEtypeVlanMapEntry
			MAX-ACCESS not-accessible
			STATUS current
			DESCRIPTION
				"This table is used with SHE R2.8.
				
				Ethertype-VLAN mapping profiles. Index is the profile index."
			INDEX { sheBridgePortEtypeVlanMapProfIndex }
			::= { sheBridgePortEtypeVlanMapTable 1 }

		
		SheBridgePortEtypeVlanMapEntry ::=
			SEQUENCE { 
				sheBridgePortEtypeVlanMapProfIndex
					Unsigned32,
				sheBridgePortEtypeVlanMapEthertype
					OCTET STRING,
				sheBridgePortEtypeVlanMapVlanId
					Unsigned32,
				sheBridgePortEtypeVlanMapPriority
					Unsigned32
			 }

		sheBridgePortEtypeVlanMapProfIndex OBJECT-TYPE
			SYNTAX Unsigned32 (1..100)
			MAX-ACCESS read-only
			STATUS current
			DESCRIPTION
				"The Ethertype-VLAN mapping profile index."
			::= { sheBridgePortEtypeVlanMapEntry 1 }

		
--   1.3.6.1.4.1.231.7.1.2.2.2.4.1.20.1.2
		sheBridgePortEtypeVlanMapEthertype OBJECT-TYPE
			SYNTAX OCTET STRING (SIZE (0..16))
			MAX-ACCESS read-only
			STATUS current
			DESCRIPTION
				"That is a list of possible 16bit protocol type field's of the ethernet frames.
				The octet string is a list of two octet entries each identifying an ethertyp value
				The least significant byte is the second octet.
				The octet string has a variable length of up to 16 octets (max. 8 ethertypes in the list).
				
				examples:
				0x0800 IP Internet Protocol (IPv4) 
				0x0806 Address Resolution Protocol (ARP) 
				0x8100 VLAN Tag (VLAN) 
				0x8863 PPPoE Discovery
				0x8864 PPPoE Session
				
				The VlanMapping is applied to upstream frames matching this Ethertype's.
				Other frames are forwarded unchanged."
			::= { sheBridgePortEtypeVlanMapEntry 2 }

		
		sheBridgePortEtypeVlanMapVlanId OBJECT-TYPE
			SYNTAX Unsigned32 (1..4093)
			MAX-ACCESS read-only
			STATUS current
			DESCRIPTION
				"A VLAN identifier mapped to the Ethertype's."
			::= { sheBridgePortEtypeVlanMapEntry 3 }

		
		sheBridgePortEtypeVlanMapPriority OBJECT-TYPE
			SYNTAX Unsigned32 (0..7)
			MAX-ACCESS read-only
			STATUS current
			DESCRIPTION
				"The priority part of the VLAN tag mapped to the Ethertype's."
			::= { sheBridgePortEtypeVlanMapEntry 4 }

		
--  New supported with SHE R2.8.
		sheBridgePortEtypeVlanMapControl OBJECT IDENTIFIER ::= { sheBridgePortEtherTypeConfig 2 }

		
		sheBridgePortEtypeVlanMapControlRequest OBJECT-TYPE
			SYNTAX SheBridgeControlRequestType
			MAX-ACCESS read-write
			STATUS current
			DESCRIPTION
				"the command to be executed
				
				createEtypeVlanMapProfEntry (171)
				 sheBridgePortEtypeVlanMapCtrlEthertype
				 sheBridgePortEtypeVlanMapCtrlVlanId
				 sheBridgePortEtypeVlanMapCtrlPriority
				->sheEtypeVlanMapProfEntryCreated
				
				modifyEtypeVlanMapProfEntry (172)
				 sheBridgePortEtypeVlanMapCtrlProfIndex
				 sheBridgePortEtypeVlanMapCtrlEthertype
				 sheBridgePortEtypeVlanMapCtrlVlanId
				 sheBridgePortEtypeVlanMapCtrlPriority
				->sheEtypeVlanMapProfEntryModified
				
				deleteEtypeVlanMapProfEnty (173)
				 sheBridgePortEtypeVlanMapCtrlProfIndex
				->sheEtypeVlanMapProfEntryDeleted"
			::= { sheBridgePortEtypeVlanMapControl 1 }

		
		sheBridgePortEtypeVlanMapControlStatus OBJECT-TYPE
			SYNTAX SheControlStatusType
			MAX-ACCESS read-only
			STATUS current
			DESCRIPTION
				"The status of a user command."
			::= { sheBridgePortEtypeVlanMapControl 2 }

		
		sheBridgePortEtypeVlanMapControlTimer OBJECT-TYPE
			SYNTAX Unsigned32
			MAX-ACCESS read-only
			STATUS current
			DESCRIPTION
				"The maximum wait time for the manager for a long running 
				user command. "
			::= { sheBridgePortEtypeVlanMapControl 3 }

		
		sheBridgePortEtypeVlanMapControlReqResult OBJECT-TYPE
			SYNTAX SheBridgeControlReqResultType
			MAX-ACCESS read-only
			STATUS current
			DESCRIPTION
				"The result of the last user command."
			::= { sheBridgePortEtypeVlanMapControl 4 }

		
		sheBridgePortEtypeVlanMapControlTimeStamp OBJECT-TYPE
			SYNTAX Unsigned32
			UNITS "sec"
			MAX-ACCESS read-only
			STATUS current
			DESCRIPTION
				"The time stamp of the last command (end of command). "
			::= { sheBridgePortEtypeVlanMapControl 5 }

		
		sheBridgePortEtypeVlanMapCtrlProfIndex OBJECT-TYPE
			SYNTAX Unsigned32 (1..100)
			MAX-ACCESS read-write
			STATUS current
			DESCRIPTION
				"The Ethertype-VLAN mapping profile index (first index)."
			::= { sheBridgePortEtypeVlanMapControl 6 }

		
		sheBridgePortEtypeVlanMapCtrlEthertype OBJECT-TYPE
			SYNTAX OCTET STRING (SIZE (0..16))
			MAX-ACCESS read-write
			STATUS current
			DESCRIPTION
				"That is a list of possible 16bit protocol type field's of the ethernet frames.
				The octet string is a list of two octet entries each identifying an ethertyp value.
				The least significant byte is the second octet.
				The octet string has a variable length of up to 16 octets (max. 8 ethertypes in the list).
				
				examples:
				0x0800 IP Internet Protocol (IPv4) 
				0x0806 Address Resolution Protocol (ARP) 
				0x8100 VLAN Tag (VLAN) 
				0x8863 PPPoE Discovery
				0x8864 PPPoE Session
				
				The VlanMapping is applied to upstream frames matching this Ethertype's.
				Other frames are forwarded unchanged."
			::= { sheBridgePortEtypeVlanMapControl 7 }

		
		sheBridgePortEtypeVlanMapCtrlVlanId OBJECT-TYPE
			SYNTAX Unsigned32 (1..4093)
			MAX-ACCESS read-write
			STATUS current
			DESCRIPTION
				"A VLAN identifier mapped to the Ethertype's."
			::= { sheBridgePortEtypeVlanMapControl 8 }

		
		sheBridgePortEtypeVlanMapCtrlPriority OBJECT-TYPE
			SYNTAX Unsigned32 (0..7)
			MAX-ACCESS read-write
			STATUS current
			DESCRIPTION
				"The priority part of the VLAN tag mapped to the Ethertype's."
			::= { sheBridgePortEtypeVlanMapControl 9 }

		
--  1.3.6.1.4.1.231.7.1.2.2.1.4.1.99
-- Only supported by SHE hiX5608 !!
		sheBridgeExtResidentialConfig OBJECT IDENTIFIER ::= { sheBridge 99 }

		
--  1.3.6.1.4.1.231.7.1.2.2.1.4.1.99.1
		sheBridgeExtResidentialTable OBJECT-TYPE
			SYNTAX SEQUENCE OF SheBridgeExtResidentialEntry
			MAX-ACCESS not-accessible
			STATUS current
			DESCRIPTION
				"Only supported by SHE hiX5608 !!
				
				Table index is the ifIndex of uplink or trunk interfaces."
			::= { sheBridgeExtResidentialConfig 1 }

		
--  1.3.6.1.4.1.231.7.1.2.2.1.4.1.99.1.1
		sheBridgeExtResidentialEntry OBJECT-TYPE
			SYNTAX SheBridgeExtResidentialEntry
			MAX-ACCESS not-accessible
			STATUS current
			DESCRIPTION
				"Description."
			INDEX { ifIndex }
			::= { sheBridgeExtResidentialTable 1 }

		
		SheBridgeExtResidentialEntry ::=
			SEQUENCE { 
				sheBridgeExtResidentialMode
					SheEnableType,
				sheBridgeExtResidentialState
					SheBridgePortUsageType
			 }

--  1.3.6.1.4.1.231.7.1.2.2.1.4.1.99.1.1.2
		sheBridgeExtResidentialMode OBJECT-TYPE
			SYNTAX SheEnableType (0..1)
			MAX-ACCESS read-only
			STATUS current
			DESCRIPTION
				"A ext-residential mode: enable/disable"
			DEFVAL { disable }
			::= { sheBridgeExtResidentialEntry 1 }

		
--  1.3.6.1.4.1.231.7.1.2.2.1.4.1.99.1.1.3
		sheBridgeExtResidentialState OBJECT-TYPE
			SYNTAX SheBridgePortUsageType
			MAX-ACCESS read-only
			STATUS current
			DESCRIPTION
				"Operative role of the port. (uplink,cascading,aggregated,notUsed, ...)"
			::= { sheBridgeExtResidentialEntry 2 }

		
--  1.3.6.1.4.1.231.7.1.2.2.1.4.1.99.2
		sheBridgeExtResidentialControl OBJECT IDENTIFIER ::= { sheBridgeExtResidentialConfig 2 }

		
--  1.3.6.1.4.1.231.7.1.2.2.1.4.1.99.2.1
		sheBridgeExtResidentialControlRequest OBJECT-TYPE
			SYNTAX SheBridgeControlRequestType
			MAX-ACCESS read-write
			STATUS current
			DESCRIPTION
				"New with R2.8 - Only supported by SHE hiX5608 !!:
				setExtResidentialMode (990):
				sheBridgeExtResidentialControlPortIndex
				sheBridgeExtResidentialControlMode
				->sheBridgeExtResidentialModeModified
				"
			::= { sheBridgeExtResidentialControl 1 }

		
--  1.3.6.1.4.1.231.7.1.2.2.1.4.1.99.2.2
		sheBridgeExtResidentialControlStatus OBJECT-TYPE
			SYNTAX SheControlStatusType
			MAX-ACCESS read-only
			STATUS current
			DESCRIPTION
				"The status of a user command. 
				"
			::= { sheBridgeExtResidentialControl 2 }

		
--  1.3.6.1.4.1.231.7.1.2.2.1.4.1.99.2.3
		sheBridgeExtResidentialControlTimer OBJECT-TYPE
			SYNTAX Gauge32
			MAX-ACCESS read-only
			STATUS current
			DESCRIPTION
				"The maximum wait time for the manager for a long running user command."
			::= { sheBridgeExtResidentialControl 3 }

		
--  1.3.6.1.4.1.231.7.1.2.2.1.4.1.99.2.4
		sheBridgeExtResidentialControlReqResult OBJECT-TYPE
			SYNTAX SheBridgeControlReqResultType
			MAX-ACCESS read-only
			STATUS current
			DESCRIPTION
				"The result of the last user command."
			::= { sheBridgeExtResidentialControl 4 }

		
--  1.3.6.1.4.1.231.7.1.2.2.1.4.1.99.2.5
		sheBridgeExtResidentialControlTimeStamp OBJECT-TYPE
			SYNTAX Unsigned32
			UNITS "sec"
			MAX-ACCESS read-only
			STATUS current
			DESCRIPTION
				"The time stamp of the last command (end of command)."
			::= { sheBridgeExtResidentialControl 5 }

		
--  1.3.6.1.4.1.231.7.1.2.2.1.4.1.99.2.6
		sheBridgeExtResidentialControlPortIndex OBJECT-TYPE
			SYNTAX InterfaceIndex
			MAX-ACCESS read-write
			STATUS current
			DESCRIPTION
				"Set the port index."
			::= { sheBridgeExtResidentialControl 6 }

		
--  1.3.6.1.4.1.231.7.1.2.2.1.4.1.99.2.7
		sheBridgeExtResidentialControlMode OBJECT-TYPE
			SYNTAX SheEnableType
			MAX-ACCESS read-write
			STATUS current
			DESCRIPTION
				"Set the ext-residential mode."
			::= { sheBridgeExtResidentialControl 7 }

		
--   1.3.6.1.4.1.231.7.1.2.2.1.4.1.100
		sheBridgeConformance OBJECT IDENTIFIER ::= { sheBridge 100 }

		
--   1.3.6.1.4.1.231.7.1.2.2.1.4.1.100.1
		sheBridgeCompliances OBJECT IDENTIFIER ::= { sheBridgeConformance 1 }

		
--   1.3.6.1.4.1.231.7.1.2.2.1.4.1.100.1.1
-- this module
-- this module
		sheBridgeCompliance MODULE-COMPLIANCE
			STATUS current
			DESCRIPTION 
				"Description."
			MODULE -- this module
				MANDATORY-GROUPS { sheBridgeBaseGroup, sheBridgeBaseControlGroup, sheBridgePortGroup, sheBridgePortControlGroup, sheBridgeNotificationsGroup, 
					sheBridgeMacProfileGroup, sheBridgeIUProfileGroup, sheBridgeIUNotificationGroup, sheBridgePortPriorityMapGroup, sheBridgePortObsoleteGroup, 
					sheBridgePortEtypeGroup }
			::= { sheBridgeCompliances 1 }

		
--   1.3.6.1.4.1.231.7.1.2.2.1.4.1.100.2
		sheBridgeGroups OBJECT IDENTIFIER ::= { sheBridgeConformance 2 }

		
--   1.3.6.1.4.1.231.7.1.2.2.1.4.1.100.2.1
		sheBridgeBaseGroup OBJECT-GROUP
			OBJECTS { sheBridgeBaseMode, sheBridgeBaseOuterPVID, sheBridgeBaseSharedVlanLearning, sheBridgeBaseRemoteIdFormat, sheBridgeBaseStagTPID, 
				sheBridgeBaseMacAntiSpoofing, sheBridgeBaseRoutingMode, sheBridgeBaseMaxHostName, sheBridgeBaseDlfFilter, sheBridgeBaseUnknownMuticastFilter, 
				sheBridgeBaseIpoaArpReqInterval, sheBridgeBaseMaxIpUNI, sheBridgeBaseMirrorPort, sheBridgeBaseTaggingMode, sheBridgeBaseOuterPriority, 
				sheBridgeBaseCircuitIdFormat }
			STATUS current
			DESCRIPTION 
				"Description."
			::= { sheBridgeGroups 1 }

		
--   1.3.6.1.4.1.231.7.1.2.2.1.4.1.100.2.2
		sheBridgeBaseControlGroup OBJECT-GROUP
			OBJECTS { sheBridgeBaseControlRequest, sheBridgeBaseControlStatus, sheBridgeBaseControlMode, sheBridgeBaseControlTaggingMode, sheBridgeBaseControlTimeStamp, 
				sheBridgeBaseControlOuterPVID, sheBridgeBaseControlSharedVlanLearning, sheBridgeBaseControlStagTPID, sheBridgeBaseControlMacAntiSpoofing, sheBridgeBaseControlRoutingMode, 
				sheBridgeBaseControlMaxHostName, sheBridgeBaseControlDlfFilter, sheBridgeBaseControlUnknownMulticastFilter, sheBridgeBaseControlIpoaArpReqInterval, sheBridgeBaseControlMirrorPort, 
				sheBridgeBaseControlTimer, sheBridgeBaseControlReqResult, sheBridgeBaseControlOuterPriority, sheBridgeBaseControlCircuitIdFormat, sheBridgeBaseControlRemoteIdFormat, 
				sheBridgeBaseControlMaxIpUNI }
			STATUS current
			DESCRIPTION 
				"Description."
			::= { sheBridgeGroups 2 }

		
--   1.3.6.1.4.1.231.7.1.2.2.1.4.1.100.2.3
		sheBridgePortGroup OBJECT-GROUP
			OBJECTS { sheSubLayerIndex, sheSubLayerCircuit, sheBridgePortPVID, sheBridgePortPriority, sheBridgePortUsage, 
				sheBridgePortMaxLearnPermitCount, sheBridgePortIndex, sheBridgePortMode, sheBridgePortTaggingMode, sheBridgePortReplaceVlanTag, 
				sheBridgePortRemoteId, sheBridgePortInnerPVID, sheBridgePortInnerPriority, sheBridgePortIpoaProviderRouterIpAddress, sheBridgePortPppoaSessionId, 
				sheBridgePortMatEnabled, sheBridgePortHostConfigurationProtocol, sheBridgePortCircuitId, sheBridgePortIpAddressPermitCount, sheBridgePortPriorityMapIndex, 
				sheBridgePortMcastGroupPackageList, sheBridgePortMcastMaxJoinedGroup, sheBridgePortMcastLeaveMode, sheBridgePortOuterPriorityOption, sheBridgePortInnerPriorityOption, 
				sheBridgePortIpAsMode, sheBridgePortEtypeVlanMapProfilePtr }
			STATUS current
			DESCRIPTION 
				"Description."
			::= { sheBridgeGroups 3 }

		
--   1.3.6.1.4.1.231.7.1.2.2.1.4.1.100.2.4
		sheBridgePortControlGroup OBJECT-GROUP
			OBJECTS { sheBridgePortControlRequest, sheBridgePortControlIndex, sheBridgePortControlStatus, sheBridgePortControlPVID, sheBridgePortControlPriority, 
				sheBridgePortControlUsage, sheBridgePortControlTimeStamp, sheBridgePortControlMaxLearnPermitCount, sheBridgePortControlTimer, sheBridgePortControlReqResult, 
				sheBridgePortControlCircuitId, sheBridgePortControlMode, sheBridgePortControlTaggingMode, sheBridgePortControlReplaceVlanTag, sheBridgePortControlRemoteId, 
				sheBridgePortControlInnerPVID, sheBridgePortControlInnerPriority, sheBridgePortControlIpoaProviderRouterIpAddress, sheBridgePortControlMatEnabled, sheBridgePortControlHostConfigurationProtocol, 
				sheBridgePortControlIpAddressPermitCount, sheBridgePortControlPriorityMapIndex, sheBridgePortControlMcastGroupPackageList, sheBridgePortControlMcastMaxJoinedGroup, sheBridgePortControlMcastLeaveMode, 
				sheBridgePortControlOuterPriorityOption, sheBridgePortControlInnerPriorityOption, sheBridgePortControlIpAsMode, sheBridgePortControlEtypeVlanMapProfilePtr }
			STATUS current
			DESCRIPTION 
				"Description."
			::= { sheBridgeGroups 4 }

		
--   1.3.6.1.4.1.231.7.1.2.2.1.4.1.100.2.5
		sheBridgeNotificationsGroup NOTIFICATION-GROUP
			NOTIFICATIONS { sheBridgeBaseParamModified, sheBridgePortCreated, sheBridgePortDeleted, sheBridgePortVlanDefaultsModified, sheBridgePortUsageModified, 
				sheBridgePortMaxLearnPermitCountModified, sheBridgePortFeatureModified, sheBridgeMacProfileSrcMacAddressModified, sheBridgePortCircuitIdModified, sheBridgePortRemoteIdModified, 
				sheBridgePortCircuitIdCleared, sheBridgePortRemoteIdCleared, sheBridgePortInnerPVIDModified, sheBridgePortInnerPriorityModified, sheBridgePortIpoaProviderRouterIpAddressModified, 
				sheBridgeIUProfilePPPoASrcMacAddressModified, setBridgePortPriorityOptionsModified, sheBridgePortMatEnabledModified, sheBridgePortPrioMapEntryModified, sheBridgePortMcastGroupPackageListModified, 
				sheBridgePortMcastParameterModified, sheEtypeVlanMapProfEntryCreated, sheEtypeVlanMapProfEntryDeleted, sheBridgePortHostConfigurationProtocolModified, sheBridgePortIpAddressPermitCountModified, 
				sheBridgePortPrioMapEntryCreated, sheEtypeVlanMapProfEntryModified, sheBridgePortPrioMapEntryDeleted, sheBridgePortIpAsModeModified, sheBridgeExtResidentialModeModified, 
				sheBridgePortEtypeVlanMappingModified, sheBridgePortExtMCastParameterModified }
			STATUS current
			DESCRIPTION 
				"Description."
			::= { sheBridgeGroups 5 }

		
--   1.3.6.1.4.1.231.7.1.2.2.1.4.1.100.2.6
		sheBridgeMacProfileGroup OBJECT-GROUP
			OBJECTS { sheBridgeMacProfileSrcMacAddress, sheBridgeMacProfileControlRequest, sheBridgeMacProfileControlIndex, sheBridgeMacProfileControlStatus, sheBridgeMacProfileControlTimer, 
				sheBridgeMacProfileControlReqResult, sheBridgeMacProfileControlTimeStamp, sheBridgeMacProfileControlSrcMacAddress }
			STATUS current
			DESCRIPTION 
				"Description."
			::= { sheBridgeGroups 6 }

		
--   1.3.6.1.4.1.231.7.1.2.2.1.4.1.100.2.7
		sheBridgeIUProfileGroup OBJECT-GROUP
			OBJECTS { sheBridgeIUPPPoASrcMacAddress, sheBridgeIUProfileControlRequest, sheBridgeIUProfileControlIndex, sheBridgeIUProfileControlStatus, sheBridgeIUProfileControlTimer, 
				sheBridgeIUProfileControlReqResult, sheBridgeIUProfileControlTimeStamp, sheBridgeIUProfileControlPPPoASrcMacAddress, sheBridgeIUProfileUsedMATBasis, sheBridgeIUProfileControlUsedMATBasis, 
				sheBridgeIUReplaceVlanTag, sheBridgeIUProfileControlReplaceVlanTag, sheBridgeIUDscpPriorityMapIndex, sheBridgeIUProfileControlDscpPriorityMapIndex }
			STATUS current
			DESCRIPTION 
				"Description."
			::= { sheBridgeGroups 7 }

		
--   1.3.6.1.4.1.231.7.1.2.2.1.4.1.100.2.8
		sheBridgeIUNotificationGroup NOTIFICATION-GROUP
			NOTIFICATIONS { sheBridgeIUProfilePPPoASrcMacAddressModified, sheBridgeIUProfileUsedMATBasisModified, sheBridgeIUProfileReplaceVlanTagModified, sheBridgeIUProfileDscpPriorityMapProfileIndexModified }
			STATUS current
			DESCRIPTION 
				"Description."
			::= { sheBridgeGroups 8 }

		
		sheBridgePortPriorityMapGroup OBJECT-GROUP
			OBJECTS { sheBridgePortPriorityMapDscp, sheBridgePortPriorityMapPrio, sheBridgePortPrioMapControlRequest, sheBridgePortPrioMapControlIndex, sheBridgePortPrioMapControlStatus, 
				sheBridgePortPrioMapControlTimer, sheBridgePortPrioMapControlReqResult, sheBridgePortPrioMapControlTimeStamp, sheBridgePortPrioMapControlDscp, sheBridgePortPrioMapControlPrio, 
				sheBridgePortPriorityMapEntryIndex }
			STATUS current
			DESCRIPTION 
				"Description."
			::= { sheBridgeGroups 9 }

		
		sheBridgePortMCastGroup OBJECT-GROUP
			OBJECTS { sheBridgePortMCastBandwithLimit, sheBridgePortMCastMaxJoinedNonPremiumGroup, sheBridgePortMCastRemainBandwith, sheBridgePortMCastMinUCBandwithLimit, sheBridgePortMCastACStatus, 
				sheBridgePortMCastControlRequest, sheBridgePortMCastControlIndex, sheBridgePortMCastControlStatus, sheBridgePortMCastControlTimer, sheBridgePortMCastControlReqResult, 
				sheBridgePortMCastControlTimeStamp, sheBridgePortMCastControlBandwithLimit, sheBridgePortMCastControlMaxJoinedNonPremiumGroup, sheBridgePortMCastControlMinUCBandwithLimit }
			STATUS current
			DESCRIPTION 
				"Description."
			::= { sheBridgeGroups 10 }

		
		sheBridgePortMCastNotificationGroup NOTIFICATION-GROUP
			NOTIFICATIONS { sheBridgePortExtMCastParameterModified }
			STATUS current
			DESCRIPTION 
				"Description."
			::= { sheBridgeGroups 11 }

		
		sheBridgePortObsoleteGroup OBJECT-GROUP
			OBJECTS { sheBridgePortMcastEHTMode, sheBridgePortControlMcastEHTMode, sheBridgePortIgmpSubscriberAccessMode, sheBridgePortControlIgmpSubscriberAccessMode }
			STATUS obsolete
			DESCRIPTION 
				"Description."
			::= { sheBridgeGroups 12 }

		
		sheBridgePortEtypeGroup OBJECT-GROUP
			OBJECTS { sheBridgePortEtypeVlanMapProfIndex, sheBridgePortEtypeVlanMapEthertype, sheBridgePortEtypeVlanMapVlanId, sheBridgePortEtypeVlanMapPriority, sheBridgePortEtypeVlanMapControlRequest, 
				sheBridgePortEtypeVlanMapControlStatus, sheBridgePortEtypeVlanMapControlTimer, sheBridgePortEtypeVlanMapControlReqResult, sheBridgePortEtypeVlanMapControlTimeStamp, sheBridgePortEtypeVlanMapCtrlProfIndex, 
				sheBridgePortEtypeVlanMapCtrlEthertype, sheBridgePortEtypeVlanMapCtrlVlanId, sheBridgePortEtypeVlanMapCtrlPriority }
			STATUS current
			DESCRIPTION 
				"Description."
			::= { sheBridgeGroups 14 }

		
		sheBridgeObsoleteNotificationsGroup NOTIFICATION-GROUP
			NOTIFICATIONS { sheBridgePortIgmpSubscriberAccessModeModified }
			STATUS obsolete
			DESCRIPTION 
				"Description."
			::= { sheBridgeGroups 15 }

		
		sheBridgeExtResidentialGroup OBJECT-GROUP
			OBJECTS { sheBridgeExtResidentialMode, sheBridgeExtResidentialState, sheBridgeExtResidentialControlRequest, sheBridgeExtResidentialControlStatus, sheBridgeExtResidentialControlTimer, 
				sheBridgeExtResidentialControlReqResult, sheBridgeExtResidentialControlTimeStamp, sheBridgeExtResidentialControlPortIndex, sheBridgeExtResidentialControlMode }
			STATUS current
			DESCRIPTION 
				"Description."
			::= { sheBridgeGroups 16 }

		
--   1.3.6.1.4.1.231.7.1.2.2.1.4.2
		sheVlan OBJECT IDENTIFIER ::= { sheBridgeMib 2 }

		
--   1.3.6.1.4.1.231.7.1.2.2.1.4.2.1
		sheVlanTable OBJECT-TYPE
			SYNTAX SEQUENCE OF SheVlanEntry
			MAX-ACCESS not-accessible
			STATUS current
			DESCRIPTION
				"The vlanTable."
			::= { sheVlan 1 }

		
--   1.3.6.1.4.1.231.7.1.2.2.1.4.2.1.1
		sheVlanEntry OBJECT-TYPE
			SYNTAX SheVlanEntry
			MAX-ACCESS not-accessible
			STATUS current
			DESCRIPTION
				"One entry for every existing vlan in the system."
			INDEX { sheVlanIndex }
			::= { sheVlanTable 1 }

		
		SheVlanEntry ::=
			SEQUENCE { 
				sheVlanIndex
					Integer32,
				sheVlanName
					OCTET STRING,
				sheVlanStatus
					SheVlanStatusType,
				sheVlanEgressPorts
					OCTET STRING,
				sheVlanUnTaggedPorts
					OCTET STRING,
				sheVlanFdbId
					Unsigned32,
				sheVlanCreationTime
					TimeTicks,
				sheVlanMulticastPermission
					ShePermissionType,
				sheVlanDhcpProviderIndex
					Unsigned32,
				sheVlanDefaultGateway
					OCTET STRING,
				sheVlanPPPoEProviderIndex
					Unsigned32,
				sheVlanMgmtVlan
					INTEGER,
				sheVlanServiceTagOnly
					TruthValue,
				sheVlanAgeingTime
					Unsigned32,
				sheVlanRoutingMode
					SheBridgeRoutingModeType,
				sheVlanTunnelingL2Protocol
					TruthValue,
				sheVlanServiceType
					SheVlanServiceType,
				sheVlanDlfFlood
					TruthValue,
				sheVlanDlfFloodCard
					PhysicalIndex,
				sheVlanCCMode
					TruthValue,
				sheVlanRouted
					SheVlanRoutedType,
				sheVlanMcastFlood
					TruthValue,
				sheVlanMatEnable
					TruthValue,
				sheVlanSubportServiceName
					OCTET STRING,
				sheVlanUplinkTranslationVlan
					Integer32
			 }

--   1.3.6.1.4.1.231.7.1.2.2.1.4.2.1.1.1
		sheVlanIndex OBJECT-TYPE
			SYNTAX Integer32 (1..4093)
			MAX-ACCESS read-only
			STATUS current
			DESCRIPTION
				"A vlan-identifier."
			::= { sheVlanEntry 1 }

		
--   1.3.6.1.4.1.231.7.1.2.2.1.4.2.1.1.2
		sheVlanName OBJECT-TYPE
			SYNTAX OCTET STRING (SIZE (0..255))
			MAX-ACCESS read-only
			STATUS current
			DESCRIPTION
				"A descriptional name for that vlan.
				Spaces and other special characters (: o) are not allowed!! "
			::= { sheVlanEntry 2 }

		
--   1.3.6.1.4.1.231.7.1.2.2.1.4.2.1.1.3
		sheVlanStatus OBJECT-TYPE
			SYNTAX SheVlanStatusType
			MAX-ACCESS read-only
			STATUS current
			DESCRIPTION
				"static, in future gvrp
				values:		static(1),
						dynamic(2)
				"
			::= { sheVlanEntry 3 }

		
--   1.3.6.1.4.1.231.7.1.2.2.1.4.2.1.1.4
		sheVlanEgressPorts OBJECT-TYPE
			SYNTAX OCTET STRING (SIZE (0..65535))
			MAX-ACCESS read-only
			STATUS current
			DESCRIPTION
				"Portlist for all member of this VLAN, they will send tagged or untagged frames.
				The octet string is a list of pairs of octets each identify
				an sheBridgePortIndex. The least significant byte is the
				second octet."
			::= { sheVlanEntry 4 }

		
--   1.3.6.1.4.1.231.7.1.2.2.1.4.2.1.1.5
		sheVlanUnTaggedPorts OBJECT-TYPE
			SYNTAX OCTET STRING (SIZE (0..65535))
			MAX-ACCESS read-only
			STATUS current
			DESCRIPTION
				"Portlist for members of this Vlan they will send only untagged frames.
				The octet string is a list of pairs of octets each identify
				an sheBridgePortIndex. The least significant byte is the second
				octet."
			::= { sheVlanEntry 5 }

		
--   1.3.6.1.4.1.231.7.1.2.2.1.4.2.1.1.6
		sheVlanFdbId OBJECT-TYPE
			SYNTAX Unsigned32
			MAX-ACCESS read-only
			STATUS current
			DESCRIPTION
				"First index of the used Filtering Table. The value would be in current 
				implementation identical to the VlanIndex."
			::= { sheVlanEntry 6 }

		
--   1.3.6.1.4.1.231.7.1.2.2.1.4.2.1.1.7
		sheVlanCreationTime OBJECT-TYPE
			SYNTAX TimeTicks
			MAX-ACCESS read-only
			STATUS current
			DESCRIPTION
				"Only useful in case of gvrp."
			::= { sheVlanEntry 7 }

		
--   1.3.6.1.4.1.231.7.1.2.2.1.4.2.1.1.8
		sheVlanMulticastPermission OBJECT-TYPE
			SYNTAX ShePermissionType
			MAX-ACCESS read-only
			STATUS current
			DESCRIPTION
				"Permission to transmit multicast-traffic. If a vlan has this permission,
				it could transmit multicast-traffic or igmp-request's.
				Transmission of non MC traffic is always possible.
				
				NOTE: SHE R2.6 will not longer support this configuration.
				A McastPermission per Vlan is not needed anymore and each existing Vlan is able to transport mcast traffic.
				"
			DEFVAL { permit }
			::= { sheVlanEntry 8 }

		
--   1.3.6.1.4.1.231.7.1.2.2.1.4.2.1.1.9
		sheVlanDhcpProviderIndex OBJECT-TYPE
			SYNTAX Unsigned32
			MAX-ACCESS read-only
			STATUS current
			DESCRIPTION
				"Points to the Vlan associated Dhcp-Provider entry in the
				DhcpProvider-Table. Default 0 -> DHCP Relay for this Vlan is deactivated.
				This value should also be 0 if this vlan will be used as a DHCP or PPPoE 
				provider vlan (sheDhcpVlanId)."
			DEFVAL { 0 }
			::= { sheVlanEntry 9 }

		
--   1.3.6.1.4.1.231.7.1.2.2.1.4.2.1.1.10
		sheVlanDefaultGateway OBJECT-TYPE
			SYNTAX OCTET STRING (SIZE (4))
			MAX-ACCESS read-only
			STATUS current
			DESCRIPTION
				"Only needed if this VLAN is used as subscriber Vlan (PVID for a bridgeport) and the 
				corresponding bridgeport use IpoA mode. Otherwise don't care.
				
				NOTE:
				Configuration not longer needed with R2.8.
				Funcionality replaced by bridgePort configuration of sheBridgePortIpoaProviderRouterIpAddress."
			::= { sheVlanEntry 10 }

		
--   1.3.6.1.4.1.231.7.1.2.2.1.4.2.1.1.11
		sheVlanPPPoEProviderIndex OBJECT-TYPE
			SYNTAX Unsigned32
			MAX-ACCESS read-only
			STATUS current
			DESCRIPTION
				"Points to the Vlan associated PPPoE-Provider entry in the
				DhcpProvider-Table. Default 0 -> PPPoE Relay for this Vlan is deactivated.
				This value should also be 0 if this vlan will be used as a PPPoE or DHCP
				provider vlan (sheDhcpVlanId)."
			DEFVAL { 0 }
			::= { sheVlanEntry 11 }

		
--   1.3.6.1.4.1.231.7.1.2.2.1.4.2.1.1.12
		sheVlanMgmtVlan OBJECT-TYPE
			SYNTAX INTEGER
				{
				off(0),
				on(1)
				}
			MAX-ACCESS read-only
			STATUS current
			DESCRIPTION
				"Specify the VLAN that doesn't allows for subscriber ports to be joined."
			DEFVAL { 0 }
			::= { sheVlanEntry 12 }

		
--   1.3.6.1.4.1.231.7.1.2.2.1.4.2.1.1.13
		sheVlanServiceTagOnly OBJECT-TYPE
			SYNTAX TruthValue
			MAX-ACCESS read-only
			STATUS current
			DESCRIPTION
				"A customer tag is not expected for the VLAN in the double tagging mode.
				
				Note: 
				This configuration is not longer supported with SHE R2.6."
			::= { sheVlanEntry 13 }

		
--   1.3.6.1.4.1.231.7.1.2.2.1.4.2.1.1.14
		sheVlanAgeingTime OBJECT-TYPE
			SYNTAX Unsigned32 (0..100000)
			MAX-ACCESS read-only
			STATUS current
			DESCRIPTION
				"MAC aging time for the VLAN. If the value is '0', it means that aging time 
				for the VLAN follows global agiang time which is defined as 'sheFdbBaseAgeingTime'."
			DEFVAL { 0 }
			::= { sheVlanEntry 14 }

		
--   1.3.6.1.4.1.231.7.1.2.2.1.4.2.1.1.15
		sheVlanRoutingMode OBJECT-TYPE
			SYNTAX SheBridgeRoutingModeType
			MAX-ACCESS read-only
			STATUS current
			DESCRIPTION
				"Generally, the default routing mode is residential; all packets cannot be forwarded between subscribers on the same VLAN. 
				But if this mode is true, the communication between subscribers becomes available. (Default: false)."
			::= { sheVlanEntry 15 }

		
--   1.3.6.1.4.1.231.7.1.2.2.1.4.2.1.1.16
		sheVlanTunnelingL2Protocol OBJECT-TYPE
			SYNTAX TruthValue
			MAX-ACCESS read-only
			STATUS current
			DESCRIPTION
				"If L2VPN is supported, all L2 protocol packets should be set as flood or drop. 
				The value of this attribute is true, all L2 protocol packets is flooded to customers networks. (Default: false).
				
				Note: 
				This configuration is not longer supported with SHE R2.8."
			::= { sheVlanEntry 16 }

		
--   1.3.6.1.4.1.231.7.1.2.2.1.4.2.1.1.17
		sheVlanServiceType OBJECT-TYPE
			SYNTAX SheVlanServiceType
			MAX-ACCESS read-only
			STATUS current
			DESCRIPTION
				"Define a tagging/stripping method in NE DT mode.
				1 - It is a DoubleTagging mode for a VLAN. It strips both C-tag and S-tag in DSLAM.
				2 - It is a VlanStacking mode for a VLAN. It strips an S-tag in DSLAM.
				"
			DEFVAL { 2 }
			::= { sheVlanEntry 17 }

		
--   1.3.6.1.4.1.231.7.1.2.2.1.4.2.1.1.18
		sheVlanDlfFlood OBJECT-TYPE
			SYNTAX TruthValue
			MAX-ACCESS read-only
			STATUS current
			DESCRIPTION
				"If it is enabled, DLF packets should be flooded to the line card which is set to sheVlanDlfFloodCard regardless of BridgeBase DLF state.
				In case it is disabled, handling of DLF packets comply with BridgeBase DLF state. 
				The maxium number of vlan which is set to enable is 50. (Default:false)"
			DEFVAL { false }
			::= { sheVlanEntry 18 }

		
--   1.3.6.1.4.1.231.7.1.2.2.1.4.2.1.1.19
		sheVlanDlfFloodCard OBJECT-TYPE
			SYNTAX PhysicalIndex
			MAX-ACCESS read-only
			STATUS current
			DESCRIPTION
				"The entPhysicalIndex of the line card where to flood DLF packets from uplink"
			::= { sheVlanEntry 19 }

		
--   1.3.6.1.4.1.231.7.1.2.2.1.4.2.1.1.21
		sheVlanCCMode OBJECT-TYPE
			SYNTAX TruthValue
			MAX-ACCESS read-only
			STATUS current
			DESCRIPTION
				"This parameter describes the handling of broadcast (bc), unknown multicast (umc)
				and unknown unicast (uuc) traffic for this vlan. If cross connect mode is True 
				all these packets are flooded in the VLAN otherwise they are droped.
				
				Supported by R2.5.1 and higher.
				"
			DEFVAL { false }
			::= { sheVlanEntry 21 }

		
--   1.3.6.1.4.1.231.7.1.2.2.1.4.2.1.1.22
		sheVlanRouted OBJECT-TYPE
			SYNTAX SheVlanRoutedType
			MAX-ACCESS read-only
			STATUS current
			DESCRIPTION
				"Configure the handling of ARP request's in the NE for this vlan.
				Valid values:
				switching - A ARP request from Network side will be answered with CPE mac address.
				routing   - A ARP request from Network side will be answered with DSLAM mac address.
				
				Supported by R2.5.1 and higher.
				"
			::= { sheVlanEntry 22 }

		
--   1.3.6.1.4.1.231.7.1.2.2.1.4.2.1.1.23
		sheVlanMcastFlood OBJECT-TYPE
			SYNTAX TruthValue
			MAX-ACCESS read-only
			STATUS current
			DESCRIPTION
				"If it is enabled, all mcast packets should be flooded in this vlan."
			DEFVAL { false }
			::= { sheVlanEntry 23 }

		
--  1.3.6.1.4.1.231.7.1.2.2.1.4.2.1.1.24
		sheVlanMatEnable OBJECT-TYPE
			SYNTAX TruthValue
			MAX-ACCESS read-only
			STATUS current
			DESCRIPTION
				"Enable or disable the MAC address translation feature on Vlan base.
				
				The feature will use the ingress vlan to decide if the mac address of 
				a member bridgePort should be translated. For bridgePorts they receive only
				untagged frames, the feature could be enabled via the PVID vlan.
				"
			DEFVAL { false }
			::= { sheVlanEntry 24 }

		
		sheVlanSubportServiceName OBJECT-TYPE
			SYNTAX OCTET STRING (SIZE (0..64))
			MAX-ACCESS read-only
			STATUS current
			DESCRIPTION
				"The format identifier %R in sheBridgeBaseCircuitIdFormat, sheBridgePortCircuitId,
				sheBridgeBaseRemoteIdFormat and sheBridgePortRemoteId is replaced by this string.
				If the string is empty, %R is replaced by the VLAN ID.
				
				New parameter with SHE R2.8."
			DEFVAL { "" }
			::= { sheVlanEntry 26 }

		
--   1.3.6.1.4.1.231.7.1.2.2.1.4.2.1.1.27
		sheVlanUplinkTranslationVlan OBJECT-TYPE
			SYNTAX Integer32 (0 | 1..4093 | 65535)
			MAX-ACCESS read-only
			STATUS current
			DESCRIPTION
				"This parameter enable a bidirectional vlanTranslation on Uplink side.
				The Vlan, identified by sheVlanIndex of this table-entry (subscriber side)
				will be translated to the vlan configured with this parameter.
				
				0  - disabled -> is the default value and will disable the vlan translation.
				65535 - usedAsTranslationVlan  -> this vlan is already in use as an Translation-Vlan and could not be translated
						
				This configuration will only be valid for protocolframes, which are routed via hostprocessor.
				SharedVlanLearning has to be enabled (bridgeBase parameter)!
				For translation of usertraffic, additional rules has to be configured!
				"
			::= { sheVlanEntry 27 }

		
--   1.3.6.1.4.1.231.7.1.2.2.1.4.2.2
		sheVlanControl OBJECT IDENTIFIER ::= { sheVlan 2 }

		
--   1.3.6.1.4.1.231.7.1.2.2.1.4.2.2.1
		sheVlanControlRequest OBJECT-TYPE
			SYNTAX SheBridgeControlRequestType
			MAX-ACCESS read-write
			STATUS current
			DESCRIPTION
				"createVlan:
				sheVlanControlIndex
				sheVlanControlName
				sheVlanControlEgressPorts
				sheVlanControlUntaggedPorts
				sheVlanControlMulticastPermision (obsolete)
				sheVlanControlDhcpProviderIndex
				sheVlanControlPPPoEProviderIndex
				
				
				deleteVlan:
				sheVlanControlIndex
				
				setVlanName:
				sheVlanControlIndex
				sheVlanControlName
				
				setVlanPorts:         - change complete Portlist
				sheVlanControlIndex
				sheVlanControlEgressPorts
				sheVlanControlUnTaggedPorts
				
				setVlanMulticastPermission (will not longer supported with R2.6)
				sheVlanControlIndex
				sheVlanControlMulticastPermission
				
				setVlanDhcpProviderIndex:
				sheVlanControlIndex
				sheVlanControlDhcpProviderIndex
				
				setVlanDefaultGateway:
				sheVlanControlIndex
				sheVlanControlDefaultGateway
				
				setVlanPppoeProviderIndex:
				sheVlanControlIndex
				sheVlanControlPPPoEProviderIndex  
				
				setVlanMgmtVlan:
				sheVlanControlIndex
				sheVlanControlMgmtVlan
				
				setVlanServiceTagOnly:(not longer supported with R2.6)
				sheVlanControlIndex
				sheVlanControlServiceTagOnly
				
				setVlanAgeingTime:
				sheVlanControlIndex
				sheVlanControlAgeingTime
				
				setVlanRoutingMode:
				sheVlanControlIndex
				sheVlanControlRoutingMode
				
				setVlanTunnelingL2Protocol:
				sheVlanControlIndex
				sheVlanControlTunnelingL2Protocol
				
				setVlanServiceType:
				sheVlanControlIndex
				sheVlanControlServiceType
				
				addVlanPorts:         - add Ports to Portlist
				sheVlanControlIndex
				sheVlanControlEgressPorts
				sheVlanControlUnTaggedPorts
				
				deleteVlanPorts:      - delete Ports from Portlist
				sheVlanControlIndex
				sheVlanControlEgressPorts
				
				setVlanDlfFlood:
				sheVlanControlIndex
				sheVlanControlDlfFlood
				sheVlanControlDlfFloodCard
				
				setVlanCCMode(230),
				sheVlanControlIndex
				sheVlanControlCCMode
				
				setVlanRouted(231),
				sheVlanControlIndex
				sheVlanControlRouted
				
				setVlanMcastFlood(232),
				sheVlanControlIndex
				sheVlanControlMcastFlood
				
				setVlanMatEnable(233),
				sheVlanControlIndex
				sheVlanControlMatEnable
				
				setVlanTranslation(235)
				sheVlanControlIndex
				sheVlanControlUplinkTranslationVlan
				
				modifySubportServiceName (242)
				sheVlanControlIndex
				sheVlanControlSubportServiceName"
			::= { sheVlanControl 1 }

		
--   1.3.6.1.4.1.231.7.1.2.2.1.4.2.2.2
		sheVlanControlIndex OBJECT-TYPE
			SYNTAX Integer32 (1..4093)
			MAX-ACCESS read-write
			STATUS current
			DESCRIPTION
				"Index of the table entry to be configured."
			::= { sheVlanControl 2 }

		
--   1.3.6.1.4.1.231.7.1.2.2.1.4.2.2.3
		sheVlanControlStatus OBJECT-TYPE
			SYNTAX SheControlStatusType
			MAX-ACCESS read-only
			STATUS current
			DESCRIPTION
				"The status of a user command. 
				"
			::= { sheVlanControl 3 }

		
--   1.3.6.1.4.1.231.7.1.2.2.1.4.2.2.4
		sheVlanControlTimer OBJECT-TYPE
			SYNTAX Gauge32
			MAX-ACCESS read-only
			STATUS current
			DESCRIPTION
				"The maximum wait time for the manager for a long running user command. 
				"
			::= { sheVlanControl 4 }

		
--   1.3.6.1.4.1.231.7.1.2.2.1.4.2.2.5
		sheVlanControlReqResult OBJECT-TYPE
			SYNTAX SheBridgeControlReqResultType
			MAX-ACCESS read-only
			STATUS current
			DESCRIPTION
				"The result of the last user command."
			::= { sheVlanControl 5 }

		
--   1.3.6.1.4.1.231.7.1.2.2.1.4.2.2.6
		sheVlanControlTimeStamp OBJECT-TYPE
			SYNTAX Unsigned32
			UNITS "sec"
			MAX-ACCESS read-only
			STATUS current
			DESCRIPTION
				"The time stamp of the last command (end of command)."
			::= { sheVlanControl 6 }

		
--   1.3.6.1.4.1.231.7.1.2.2.1.4.2.2.7
		sheVlanControlName OBJECT-TYPE
			SYNTAX OCTET STRING (SIZE (0..255))
			MAX-ACCESS read-write
			STATUS current
			DESCRIPTION
				"A descriptional name for that vlan.
				Spaces and other special characters (: o) are not allowed!! "
			::= { sheVlanControl 7 }

		
--   1.3.6.1.4.1.231.7.1.2.2.1.4.2.2.8
		sheVlanControlEgressPorts OBJECT-TYPE
			SYNTAX OCTET STRING (SIZE (0..65535))
			MAX-ACCESS read-write
			STATUS current
			DESCRIPTION
				"Portlist for all member of this VLAN, they will send tagged or untagged frames.
				The octet string is a list of pairs of octets each identify
				an sheBridgePortIndex. The least significant byte is the
				second octet."
			::= { sheVlanControl 8 }

		
--   1.3.6.1.4.1.231.7.1.2.2.1.4.2.2.9
		sheVlanControlUnTaggedPorts OBJECT-TYPE
			SYNTAX OCTET STRING (SIZE (0..65535))
			MAX-ACCESS read-write
			STATUS current
			DESCRIPTION
				"Portlist for members of this Vlan they will send only untagged frames.
				The octet string is a list of pairs of octets each identify
				an sheBridgePortIndex. The least significant byte is the second
				octet."
			::= { sheVlanControl 9 }

		
--   1.3.6.1.4.1.231.7.1.2.2.1.4.2.2.10
		sheVlanControlMulticastPermission OBJECT-TYPE
			SYNTAX ShePermissionType
			MAX-ACCESS read-write
			STATUS current
			DESCRIPTION
				"Permission to transmit multicast-traffic. If a vlan has this permission,
				it could transmit multicast-traffic or igmp-request's.
				Transmission of non MC traffic is always possible.
				
				NOTE: SHE R2.6 will not longer support this configuration.
				A McastPermission per Vlan is not needed anymore and each existing Vlan is able to transport mcast traffic."
			::= { sheVlanControl 10 }

		
--   1.3.6.1.4.1.231.7.1.2.2.1.4.2.2.11
		sheVlanControlDhcpProviderIndex OBJECT-TYPE
			SYNTAX Unsigned32
			MAX-ACCESS read-write
			STATUS current
			DESCRIPTION
				"Points to the Vlan associated Dhcp-Provider entry in the
				DhcpProvider-Table. Default 0 -> DHCP Relay for this Vlan is deactivated."
			::= { sheVlanControl 11 }

		
--   1.3.6.1.4.1.231.7.1.2.2.1.4.2.2.12
		sheVlanControlDefaultGateway OBJECT-TYPE
			SYNTAX OCTET STRING (SIZE (4))
			MAX-ACCESS read-write
			STATUS current
			DESCRIPTION
				"Look at table."
			::= { sheVlanControl 12 }

		
--   1.3.6.1.4.1.231.7.1.2.2.1.4.2.2.13
		sheVlanControlPPPoEProviderIndex OBJECT-TYPE
			SYNTAX Unsigned32
			MAX-ACCESS read-write
			STATUS current
			DESCRIPTION
				"Points to the Vlan associated PPPoE-Provider entry in the
				DhcpProvider-Table. Default 0 -> PPPoE Relay for this Vlan is deactivated."
			::= { sheVlanControl 13 }

		
--    1.3.6.1.4.1.231.7.1.2.2.1.4.2.2.14
		sheVlanControlMgmtVlan OBJECT-TYPE
			SYNTAX INTEGER
				{
				off(0),
				on(1)
				}
			MAX-ACCESS read-write
			STATUS current
			DESCRIPTION
				"Specify the VLAN that doesn't allow subscribers to join."
			::= { sheVlanControl 14 }

		
--    1.3.6.1.4.1.231.7.1.2.2.1.4.2.2.15
		sheVlanControlServiceTagOnly OBJECT-TYPE
			SYNTAX TruthValue
			MAX-ACCESS read-write
			STATUS current
			DESCRIPTION
				"A customer tag is not expected for the VLAN in the double tagging mode.
				
				Note: 
				This configuration is not longer supported with SHE R2.6."
			::= { sheVlanControl 15 }

		
--   1.3.6.1.4.1.231.7.1.2.2.1.4.2.2.16
		sheVlanControlAgeingTime OBJECT-TYPE
			SYNTAX Unsigned32 (0..100000)
			MAX-ACCESS read-write
			STATUS current
			DESCRIPTION
				"MAC aging time for the VLAN. If the value is '0', it means that aging time 
				for the VLAN follows global agiang time which is defined as 'sheFdbBaseAgeingTime'."
			::= { sheVlanControl 16 }

		
--   1.3.6.1.4.1.231.7.1.2.2.1.4.2.2.17
		sheVlanControlRoutingMode OBJECT-TYPE
			SYNTAX SheBridgeRoutingModeType
			MAX-ACCESS read-write
			STATUS current
			DESCRIPTION
				"Generally, the default routing mode is residential; all packets cannot be forwarded between subscribers on the same VLAN. 
				But if this mode is true, the communication between subscribers becomes available. (Default: false)."
			::= { sheVlanControl 17 }

		
--   1.3.6.1.4.1.231.7.1.2.2.1.4.2.2.18
		sheVlanControlTunnelingL2Protocol OBJECT-TYPE
			SYNTAX TruthValue
			MAX-ACCESS read-write
			STATUS current
			DESCRIPTION
				"look at table."
			::= { sheVlanControl 18 }

		
--   1.3.6.1.4.1.231.7.1.2.2.1.4.2.2.19
		sheVlanControlServiceType OBJECT-TYPE
			SYNTAX SheVlanServiceType
			MAX-ACCESS read-write
			STATUS current
			DESCRIPTION
				"Set a tagging/stripping method in NE DT mode."
			::= { sheVlanControl 19 }

		
--   1.3.6.1.4.1.231.7.1.2.2.1.4.2.2.20
		sheVlanControlDlfFlood OBJECT-TYPE
			SYNTAX TruthValue
			MAX-ACCESS read-write
			STATUS current
			DESCRIPTION
				"If it is enabled, DLF packets should be flooded to the line card which is set to sheVlanDlfFloodCard regardless of BridgeBase DLF state.
				In case it is disabled, handling of DLF packets comply with BridgeBase DLF state. 
				The maxium number of vlan which is set to enable is 50. (Default:false)"
			::= { sheVlanControl 20 }

		
--   1.3.6.1.4.1.231.7.1.2.2.1.4.2.2.21
		sheVlanControlDlfFloodCard OBJECT-TYPE
			SYNTAX PhysicalIndex
			MAX-ACCESS read-write
			STATUS current
			DESCRIPTION
				"The entPhysicalIndex of the line card where to flood DLF packets from uplink"
			::= { sheVlanControl 21 }

		
--   1.3.6.1.4.1.231.7.1.2.2.1.4.2.2.22
		sheVlanControlCCMode OBJECT-TYPE
			SYNTAX TruthValue
			MAX-ACCESS read-write
			STATUS current
			DESCRIPTION
				"look at table"
			::= { sheVlanControl 22 }

		
--   1.3.6.1.4.1.231.7.1.2.2.1.4.2.2.23
		sheVlanControlRouted OBJECT-TYPE
			SYNTAX SheVlanRoutedType
			MAX-ACCESS read-write
			STATUS current
			DESCRIPTION
				"look at table"
			::= { sheVlanControl 23 }

		
--   1.3.6.1.4.1.231.7.1.2.2.1.4.2.2.24
		sheVlanControlMcastFlood OBJECT-TYPE
			SYNTAX TruthValue
			MAX-ACCESS read-write
			STATUS current
			DESCRIPTION
				"If it is enabled, all mcast packets should be flooded in this vlan."
			::= { sheVlanControl 24 }

		
		sheVlanControlMatEnable OBJECT-TYPE
			SYNTAX TruthValue
			MAX-ACCESS read-write
			STATUS current
			DESCRIPTION
				"Enable or disable the MAC address translation feature on Vlan base.
				
				The feature will use the ingress vlan to decide if the mac address of 
				a member bridgePort should be translated. For bridgePorts they receive only
				untagged frames, the feature could be enabled via the PVID vlan."
			::= { sheVlanControl 25 }

		
--   1.3.6.1.4.1.231.7.1.2.2.1.4.2.2.27
		sheVlanControlSubportServiceName OBJECT-TYPE
			SYNTAX OCTET STRING (SIZE (0..64))
			MAX-ACCESS read-write
			STATUS current
			DESCRIPTION
				"The format identifier %R in sheBridgeBaseCircuitIdFormat, sheBridgePortCircuitId,
				sheBridgeBaseRemoteIdFormat and sheBridgePortRemoteId is replaced by this string.
				If the string is empty, %R is replaced by the VLAN ID."
			::= { sheVlanControl 27 }

		
--   1.3.6.1.4.1.231.7.1.2.2.1.4.2.2.28
		sheVlanControlUplinkTranslationVlan OBJECT-TYPE
			SYNTAX Integer32 (0 | 1..4093)
			MAX-ACCESS read-write
			STATUS current
			DESCRIPTION
				"look at table"
			::= { sheVlanControl 28 }

		
--   1.3.6.1.4.1.231.7.1.2.2.1.4.2.3
		sheVlanNotifications OBJECT IDENTIFIER ::= { sheVlan 3 }

		
--    
-- 1.3.6.1.4.1.231.7.1.2.2.1.4.2.3.1
		sheVlanCreated NOTIFICATION-TYPE
			OBJECTS { sheVlanControlIndex, sheVlanControlTimeStamp, sheVlanControlName, sheVlanControlEgressPorts, sheVlanControlUnTaggedPorts, 
				sheVlanControlMulticastPermission, sheVlanControlDhcpProviderIndex, sheVlanControlPPPoEProviderIndex }
			STATUS current
			DESCRIPTION 
				"A new vlan was created."
			::= { sheVlanNotifications 1 }

		
--    
-- 1.3.6.1.4.1.231.7.1.2.2.1.4.2.3.2
		sheVlanModified NOTIFICATION-TYPE
			OBJECTS { sheVlanControlIndex, sheVlanControlTimeStamp, sheVlanName, sheVlanEgressPorts, sheVlanUnTaggedPorts, 
				sheVlanMulticastPermission, sheVlanDhcpProviderIndex, sheVlanDefaultGateway, sheVlanPPPoEProviderIndex }
			STATUS current
			DESCRIPTION 
				"A vlan was modified."
			::= { sheVlanNotifications 2 }

		
--    
-- 1.3.6.1.4.1.231.7.1.2.2.1.4.2.3.3
		sheVlanDeleted NOTIFICATION-TYPE
			OBJECTS { sheVlanControlIndex, sheVlanControlTimeStamp }
			STATUS current
			DESCRIPTION 
				"A vlan was deleted."
			::= { sheVlanNotifications 3 }

		
--    
-- 1.3.6.1.4.1.231.7.1.2.2.1.4.2.3.4
		sheVlanPortsModified NOTIFICATION-TYPE
			OBJECTS { sheVlanControlIndex, sheVlanControlTimeStamp, sheVlanControlEgressPorts, sheVlanControlUnTaggedPorts, sheVlanControlName
				 }
			STATUS current
			DESCRIPTION 
				"A vlan portlist was modified by command setVlanPorts."
			::= { sheVlanNotifications 4 }

		
--   1.3.6.1.4.1.231.7.1.2.2.1.4.2.3.5
		sheVlanMgmtVlanChanged NOTIFICATION-TYPE
			OBJECTS { sheVlanControlIndex, sheVlanControlTimeStamp, sheVlanControlName, sheVlanControlMgmtVlan }
			STATUS current
			DESCRIPTION 
				"A vlan is assigned as Mgmt-Vlan."
			::= { sheVlanNotifications 5 }

		
--   1.3.6.1.4.1.231.7.1.2.2.1.4.2.3.6
		sheVlanServiceTagOnlyChanged NOTIFICATION-TYPE
			OBJECTS { sheVlanControlIndex, sheVlanControlTimeStamp, sheVlanControlServiceTagOnly }
			STATUS current
			DESCRIPTION 
				"A customer tagging policy for a VLAN has been changed."
			::= { sheVlanNotifications 6 }

		
--   1.3.6.1.4.1.231.7.1.2.2.1.4.2.3.7
		sheVlanAgeingTimeChanged NOTIFICATION-TYPE
			OBJECTS { sheVlanControlIndex, sheVlanControlTimeStamp, sheVlanControlAgeingTime }
			STATUS current
			DESCRIPTION 
				"MAC ageing time for a VLAN has been changed."
			::= { sheVlanNotifications 7 }

		
--   1.3.6.1.4.1.231.7.1.2.2.1.4.2.3.8
		sheVlanRoutingModeChanged NOTIFICATION-TYPE
			OBJECTS { sheVlanControlIndex, sheVlanControlTimeStamp, sheVlanControlRoutingMode }
			STATUS current
			DESCRIPTION 
				"Local switching for a VLAN has been changed."
			::= { sheVlanNotifications 8 }

		
--   1.3.6.1.4.1.231.7.1.2.2.1.4.2.3.9
		sheVlanTunnelingL2ProtocolChanged NOTIFICATION-TYPE
			OBJECTS { sheVlanControlIndex, sheVlanControlTimeStamp, sheVlanControlTunnelingL2Protocol }
			STATUS current
			DESCRIPTION 
				"L2 protocol for a VLAN has been changed."
			::= { sheVlanNotifications 9 }

		
--   1.3.6.1.4.1.231.7.1.2.2.1.4.2.3.10
		sheVlanServiceTypeChanged NOTIFICATION-TYPE
			OBJECTS { sheVlanControlIndex, sheVlanControlTimeStamp, sheVlanControlServiceType }
			STATUS current
			DESCRIPTION 
				"Vlan service type for a VLAN has been changed."
			::= { sheVlanNotifications 10 }

		
--   1.3.6.1.4.1.231.7.1.2.2.1.4.2.3.11
		sheVlanDlfFloodChanged NOTIFICATION-TYPE
			OBJECTS { sheVlanControlIndex, sheVlanControlTimeStamp, sheVlanControlDlfFlood, sheVlanControlDlfFloodCard }
			STATUS current
			DESCRIPTION 
				"A policy for handling Dlf packets has been changed."
			::= { sheVlanNotifications 11 }

		
--   1.3.6.1.4.1.231.7.1.2.2.1.4.2.3.11
		sheVlanPortslistModified NOTIFICATION-TYPE
			OBJECTS { sheVlanControlIndex, sheVlanControlStatus, sheVlanControlReqResult, sheVlanControlTimeStamp, sheVlanEgressPorts, 
				sheVlanUnTaggedPorts }
			STATUS current
			DESCRIPTION 
				"Configuration trap after changing the current vlan portlist's by using 
				the commands addVlanPorts or deleteVlanPorts. "
			::= { sheVlanNotifications 12 }

		
		sheVlanCCModeChanged NOTIFICATION-TYPE
			OBJECTS { sheVlanControlIndex, sheVlanControlTimeStamp, sheVlanControlCCMode }
			STATUS current
			DESCRIPTION 
				"configuration trap"
			::= { sheVlanNotifications 13 }

		
		sheVlanRoutedChanged NOTIFICATION-TYPE
			OBJECTS { sheVlanControlIndex, sheVlanControlTimeStamp, sheVlanControlRouted }
			STATUS current
			DESCRIPTION 
				"configuration trap"
			::= { sheVlanNotifications 14 }

		
		sheVlanMcastFloodChanged NOTIFICATION-TYPE
			OBJECTS { sheVlanControlIndex, sheVlanControlTimeStamp, sheVlanControlMcastFlood }
			STATUS current
			DESCRIPTION 
				"configuration trap"
			::= { sheVlanNotifications 15 }

		
		sheVlanMatEnableChanged NOTIFICATION-TYPE
			OBJECTS { sheVlanControlIndex, sheVlanControlTimeStamp, sheVlanControlMatEnable }
			STATUS current
			DESCRIPTION 
				"MAC address translation feature on Vlan base changed."
			::= { sheVlanNotifications 16 }

		
		sheVlanSubportServiceNameModified NOTIFICATION-TYPE
			OBJECTS { sheVlanControlIndex, sheVlanControlTimeStamp, sheVlanControlSubportServiceName }
			STATUS current
			DESCRIPTION 
				"configuration trap"
			::= { sheVlanNotifications 18 }

		
		sheVlanUplinkTranslationChanged NOTIFICATION-TYPE
			OBJECTS { sheVlanControlIndex, sheVlanControlTimeStamp, sheVlanControlUplinkTranslationVlan }
			STATUS current
			DESCRIPTION 
				"Configuration modified."
			::= { sheVlanNotifications 19 }

		
--  1.3.6.1.4.1.231.7.1.2.2.1.4.2.4
		sheVlanConformance OBJECT IDENTIFIER ::= { sheVlan 100 }

		
--    
-- 1.3.6.1.4.1.231.7.1.2.2.1.4.2.4.1
		sheVlanCompliances OBJECT IDENTIFIER ::= { sheVlanConformance 1 }

		
--    
-- 1.3.6.1.4.1.231.7.1.2.2.1.4.2.4.1.1
-- this module
-- this module
		sheVlanCompliance MODULE-COMPLIANCE
			STATUS current
			DESCRIPTION 
				"Description."
			MODULE -- this module
				MANDATORY-GROUPS { sheVlanGroup, sheVlanControlGroup, sheVlanNotificationGroup }
			::= { sheVlanCompliances 1 }

		
--    
-- 1.3.6.1.4.1.231.7.1.2.2.1.4.2.4.2
		sheVlanGroups OBJECT IDENTIFIER ::= { sheVlanConformance 2 }

		
--    
-- 1.3.6.1.4.1.231.7.1.2.2.1.4.2.4.2.1
		sheVlanGroup OBJECT-GROUP
			OBJECTS { sheVlanName, sheVlanStatus, sheVlanEgressPorts, sheVlanUnTaggedPorts, sheVlanFdbId, 
				sheVlanCreationTime, sheVlanDlfFlood, sheVlanDlfFloodCard, sheVlanCCMode, sheVlanRouted, 
				sheVlanMatEnable, sheVlanMulticastPermission, sheVlanUplinkTranslationVlan, sheVlanMcastFlood, sheVlanIndex, 
				sheVlanDhcpProviderIndex, sheVlanDefaultGateway, sheVlanPPPoEProviderIndex, sheVlanMgmtVlan, sheVlanServiceTagOnly, 
				sheVlanAgeingTime, sheVlanRoutingMode, sheVlanTunnelingL2Protocol, sheVlanServiceType, sheVlanSubportServiceName
				 }
			STATUS current
			DESCRIPTION 
				"Description."
			::= { sheVlanGroups 1 }

		
--   1.3.6.1.4.1.231.7.1.2.2.1.4.2.4.2.2
		sheVlanControlGroup OBJECT-GROUP
			OBJECTS { sheVlanControlRequest, sheVlanControlIndex, sheVlanControlStatus, sheVlanControlName, sheVlanControlEgressPorts, 
				sheVlanControlUnTaggedPorts, sheVlanControlMulticastPermission, sheVlanControlDlfFlood, sheVlanControlDlfFloodCard, sheVlanControlCCMode, 
				sheVlanControlRouted, sheVlanControlMcastFlood, sheVlanControlMatEnable, sheVlanControlUplinkTranslationVlan, sheVlanControlTimeStamp, 
				sheVlanControlTimer, sheVlanControlReqResult, sheVlanControlDhcpProviderIndex, sheVlanControlDefaultGateway, sheVlanControlPPPoEProviderIndex, 
				sheVlanControlMgmtVlan, sheVlanControlServiceTagOnly, sheVlanControlAgeingTime, sheVlanControlRoutingMode, sheVlanControlTunnelingL2Protocol, 
				sheVlanControlServiceType, sheVlanControlSubportServiceName }
			STATUS current
			DESCRIPTION 
				"Description."
			::= { sheVlanGroups 2 }

		
--    
-- 1.3.6.1.4.1.231.7.1.2.2.1.4.2.4.2.3
		sheVlanNotificationGroup NOTIFICATION-GROUP
			NOTIFICATIONS { sheVlanCreated, sheVlanModified, sheVlanDeleted, sheVlanPortsModified, sheVlanMgmtVlanChanged, 
				sheVlanServiceTagOnlyChanged, sheVlanAgeingTimeChanged, sheVlanRoutingModeChanged, sheVlanTunnelingL2ProtocolChanged, sheVlanServiceTypeChanged, 
				sheVlanCCModeChanged, sheVlanRoutedChanged, sheVlanMcastFloodChanged, sheVlanMatEnableChanged, sheVlanUplinkTranslationChanged, 
				sheVlanPortslistModified, sheVlanDlfFloodChanged, sheVlanSubportServiceNameModified }
			STATUS current
			DESCRIPTION 
				"Description."
			::= { sheVlanGroups 3 }

		
--   1.3.6.1.4.1.231.7.1.2.2.1.4.3
		sheRulesAndMetering OBJECT IDENTIFIER ::= { sheBridgeMib 3 }

		
--   1.3.6.1.4.1.231.7.1.2.2.1.4.3.1
		sheRuleTable OBJECT-TYPE
			SYNTAX SEQUENCE OF SheRuleEntry
			MAX-ACCESS not-accessible
			STATUS current
			DESCRIPTION
				"The she rule table."
			::= { sheRulesAndMetering 1 }

		
--   1.3.6.1.4.1.231.7.1.2.2.1.4.3.1.1
		sheRuleEntry OBJECT-TYPE
			SYNTAX SheRuleEntry
			MAX-ACCESS not-accessible
			STATUS current
			DESCRIPTION
				"Define pattern, matches and action's for Rule Controls."
			INDEX { sheRuleIndex }
			::= { sheRuleTable 1 }

		
		SheRuleEntry ::=
			SEQUENCE { 
				sheRuleIndex
					Unsigned32,
				sheRuleType
					SheRuleType,
				sheRuleName
					OCTET STRING,
				sheRulePriority
					Integer32,
				sheRuleBridgePortPattern
					Integer32,
				sheRuleBridgePortMatch
					SheRuleMatchType,
				sheRuleSourceMacPattern
					OCTET STRING,
				sheRuleSourceMacMatch
					SheRuleMatchType,
				sheRuleSourceMacStartPattern
					OCTET STRING,
				sheRuleSourceMacStopPattern
					OCTET STRING,
				sheRuleSourceMacRangeMatch
					SheRuleMatchType,
				sheRuleDestinationMacPattern
					OCTET STRING,
				sheRuleDestinationMacMatch
					SheRuleMatchType,
				sheRuleDestinationMacStartPattern
					OCTET STRING,
				sheRuleDestinationMacStopPattern
					OCTET STRING,
				sheRuleDestinationMacRangeMatch
					SheRuleMatchType,
				sheRuleVlanIdPattern
					Integer32,
				sheRuleVlanIdMatch
					SheRuleMatchType,
				sheRulePriorityPattern
					INTEGER,
				sheRulePriorityMatch
					SheRuleMatchType,
				sheRuleTosPattern
					INTEGER,
				sheRuleTosMatch
					SheRuleMatchType,
				sheRuleDscpPattern
					INTEGER,
				sheRuleDscpMatch
					SheRuleMatchType,
				sheRuleEtherTypePattern
					OCTET STRING,
				sheRuleEtherTypeMatch
					SheRuleMatchType,
				sheRuleSourceIpAddressPattern
					OCTET STRING,
				sheRuleSourceIpAddressMatch
					SheRuleMatchType,
				sheRuleSourceIpSubnetMaskPattern
					OCTET STRING,
				sheRuleSourceIpSubnetMaskMatch
					SheRuleMatchType,
				sheRuleDestinationIpAddressPattern
					OCTET STRING,
				sheRuleDestinationIpAddressMatch
					SheRuleMatchType,
				sheRuleDestinationIpSubnetMaskPattern
					OCTET STRING,
				sheRuleDestinationIpSubnetMaskMatch
					SheRuleMatchType,
				sheRuleSourcePortPattern
					Integer32,
				sheRuleSourcePortMatch
					SheRuleMatchType,
				sheRuleDestinationPortPattern
					Integer32,
				sheRuleDestinationPortMatch
					SheRuleMatchType,
				sheRuleAction
					SheRuleActionType,
				sheRuleActionParameter01
					Integer32,
				sheRuleActionParameter02
					Integer32,
				sheRuleFlowPattern
					SheRuleFlowType,
				sheRuleFlowMatch
					SheRuleMatchType,
				sheRuleIpProtocolPattern
					Unsigned32,
				sheRuleIpProtocolMatch
					SheRuleMatchType,
				sheRuleIpPrecedencePattern
					Unsigned32,
				sheRuleIpPrecedenceMatch
					SheRuleMatchType,
				sheRuleSourceMacMaskPattern
					OCTET STRING,
				sheRuleSourceMacMaskMatch
					SheRuleMatchType,
				sheRuleDestinationMacMaskPattern
					OCTET STRING,
				sheRuleDestinationMacMaskMatch
					SheRuleMatchType,
				sheRuleMessageTypePattern
					Integer32,
				sheRuleMessageTypeMatch
					SheRuleMatchType,
				sheRuleMessageCodePattern
					Integer32,
				sheRuleMessageCodeMatch
					SheRuleMatchType,
				sheRuleGenericMatchAction
					SheRuleGenericActionType,
				sheRuleGenericNoMatchAction
					SheRuleGenericActionType,
				sheRuleGenericMatchActionParameterMeterIndex
					Unsigned32,
				sheRuleGenericMatchActionParameterRedirPort
					Unsigned32,
				sheRuleGenericMatchActionParameterDscp
					Unsigned32,
				sheRuleGenericMatchActionParameterPriority
					Unsigned32,
				sheRuleGenericMatchActionParameterTagPriority
					Unsigned32,
				sheRuleGenericMatchActionParameterIpPrecedence
					Unsigned32,
				sheRuleGenericMatchActionParameterRate
					Unsigned32,
				sheRuleGenericMatchActionParameterVlanId
					Unsigned32,
				sheRuleGenericNoMatchActionParameterMeterIndex
					Unsigned32,
				sheRuleGenericNoMatchActionParameterRedirPort
					Unsigned32,
				sheRuleGenericNoMatchActionParameterDscp
					Unsigned32,
				sheRuleGenericNoMatchActionParameterPriority
					Unsigned32,
				sheRuleGenericNoMatchActionParameterTagPriority
					Unsigned32,
				sheRuleGenericNoMatchActionParameterIpPrecedence
					Unsigned32,
				sheRuleGenericNoMatchActionParameterRate
					Unsigned32,
				sheRuleGenericNoMatchActionParameterVlanId
					Unsigned32,
				sheRuleMatchCounter
					Integer32,
				sheRuleActivationState
					SheRuleActivationStateType,
				sheRuleInnerVlanIdPattern
					Integer32,
				sheRuleInnerVlanIdMatch
					SheRuleMatchType,
				sheRuleInnerPriorityPattern
					Integer32,
				sheRuleInnerPriorityMatch
					SheRuleMatchType,
				sheRuleIUPhysIndexPattern
					PhysicalIndex,
				sheRuleIUPhysIndexMatch
					SheRuleMatchType,
				sheRulePortIfIndexPattern
					InterfaceIndex,
				sheRulePortIfIndexMatch
					SheRuleMatchType
			 }

--   1.3.6.1.4.1.231.7.1.2.2.1.4.3.1.1.1
		sheRuleIndex OBJECT-TYPE
			SYNTAX Unsigned32 (1..65535)
			MAX-ACCESS read-only
			STATUS current
			DESCRIPTION
				"A userflow-identifier."
			::= { sheRuleEntry 1 }

		
--   1.3.6.1.4.1.231.7.1.2.2.1.4.3.1.1.2
		sheRuleType OBJECT-TYPE
			SYNTAX SheRuleType
			MAX-ACCESS read-only
			STATUS current
			DESCRIPTION
				"This type defines the set of used pattern and actions for a rule of type.
				Inside one rule all used match-values have to be exact or exclude. Ignore is don't care.
				
				globalSrcMacDeny(1)
				Type = 1
				Name = 
				SourceMacPattern = 
				SourceMacMatch = exact
				Action = Deny
				
				portFlowControl(2)
				Type = 2
				Name = 
				BridgePortPattern =
				BridgePortMatch = exact
				SourceMacPattern =
				SourceMacMatch = exact
				Action = Allow
				
				meteringBridgePort(3)
				Type = 3
				Name = 
				Priority =
				BridgePortPattern =
				BridgePortMatch = exact
				Action = Meter
				ActionParameter01 = Profile
				
				qosVlan(4)
				Type = 4
				Name = 
				Priority = 
				VlanIdPattern =
				VlanIdMatch = exact
				Action = ChangeInnerPriority
				ActionParameter01 = newPriority
				
				qosDscp(5)
				Type = 5
				Name = 
				Priority = 
				DscpPattern =
				DscpMatch = exact
				Action = ChangeInnerPriority
				ActionParameter01 = newPriority
				
				qosBridgePort(6)
				Type = 6
				Name = 
				Priority = 
				BridgePortPattern =
				BridgePortMatch = exact
				Action = ChangeInnerPriority
				ActionParameter01 = newPriority
				
				providerDoubleTagVlan01(7)
				Type = 7
				Name = 
				Priority = 
				VlanIdPattern =
				VlanIdMatch = exact
				Action = ChangeOuterVlan
				ActionParameter01 = newVlanId
				
				qosDoubleTagPriority01(8)
				type = 8
				Name = 
				Priority = 
				PriorityPattern =
				PriorityMatch = exact
				Action = ChangeOuterVlan
				ActionParameter01 = newVlanId
				
				qosDoubleTagDscp01(9)
				type = 9
				Name = 
				Priority = 
				DscpPattern =
				DscpMatch = exact
				Action = ChangeOuterVlan
				ActionParameter01 = newVlanId
				
				providerDoubleTagVlan02(10)
				Type = 10
				Name = 
				Priority = 
				VlanIdPattern =
				VlanIdMatch = exact
				Action = ChangeOuterVlanTag
				ActionParameter01 = newVlanId
				ActionParameter02 = new Priority
				
				qosDoubleTagPriority02(11)
				type = 11
				Name = 
				Priority = 
				PriorityPattern =
				PriorityMatch = exact
				Action = ChangeOuterVlanTag
				ActionParameter01 = newVlanId
				ActionParameter02 = new Priority
				
				qosDoubleTagDscp(12)
				type = 12
				Name = 
				Priority = 
				DscpPattern =
				DscpMatch = exact
				Action = ChangeOuterVlanTag
				ActionParameter01 = newVlanId
				ActionParameter02 = new Priority
				
				mirrorBridgePort(13)
				Type = 13
				Name = 
				Priority = 
				VlanIdPattern =
				VlanIdMatch = exact
				Action = mirror
				
				qosDscp02(14)
				type = 14
				Name = 
				Priority = 
				DscpPattern =
				DscpMatch = exact
				Action = ChangeInnerVlanTag
				ActionParameter01 = newVlanId
				ActionParameter02 = new Priority
				
				portFlowControl02(15)
				Type = 15
				Name = 
				Priority = 
				DscpPattern =
				DscpMatch = exact
				BridgePortPattern =
				BridgePortMatch = exact
				Action = deny
				
				providerSingleTagVlan01(16)
				sheRuleControlType= 16
				sheRuleControlName = 
				sheRuleControlPriority = 
				sheRuleControlVlanIdPattern = 
				sheRuleControlVlanIdMatch = exact
				sheRuleControlAction = changeInnerVlan
				sheRuleControlActionParameter01 = new VlanId
				
				
				providerSingleTagVlan02(17)
				sheRuleControlType= 17
				sheRuleControlName = 
				sheRuleControlPriority = 
				sheRuleControlVlanIdPattern = 
				sheRuleControlVlanIdMatch = exact
				sheRuleControlAction = changeInnerVlanTag
				sheRuleControlActionParameter01 = newVlanId
				sheRuleControlActionParameter02 = new Priority
				
				portFlowControl03(18)
				sheRuleControlType= 18
				sheRuleControlName = portEtherTypVlan
				sheRuleControlPriority = 
				sheRuleControlEtherTypPattern = xx
				sheRuleControlEtherTypMatch = exact
				sheRuleControlBridgePortPattern = yy
				sheRuleControlBridgePortMatch = exact
				sheRuleControlAction = changeInnerVlan
				sheRuleControlActionParameter01 = new  PVID 
				
				cosTranslation(19)
				sheRuleControlType= 19
				sheRuleControlName = cosTranslation
				sheRuleControlPriority = 
				sheRuleControlPriorityPattern = xx
				sheRuleControlPriorityMatch = exact
				sheRuleControlFlowPattern = yy
				sheRuleControlFlowMatch = exact
				sheRuleControlAction = changeOuterVlan | changeOuterPriority | changeOuterTag
				sheRuleControlActionParameter01 = new VlanID | new Priority
				sheRuleControlActionParameter02 = new Priority | empty
				
				etherTypTranslation(20)
				sheRuleControlType= 20
				sheRuleControlName = etherTypTranslation
				sheRuleControlPriority = 
				sheRuleControlEtherTypPattern = xx
				sheRuleControlEtherTypMatch = exact
				sheRuleControlFlowPattern = yy
				sheRuleControlFlowMatch = exact
				sheRuleControlAction = changeOuterVlan | changeOuterPriority | changeOuterTag
				sheRuleControlActionParameter01 = new VlanID | new Priority
				sheRuleControlActionParameter02 = new Priority | empty
				
				vlanTranslation(21)
				sheRuleControlType= 21
				sheRuleControlName = vlanTranslation
				sheRuleControlPriority = 
				sheRuleControlVlanIdPattern = xx
				sheRuleControlVlanIdMatch = exact
				sheRuleControlFlowPattern = yy
				sheRuleControlFlowMatch = exact
				sheRuleControlAction = changeOuterVlan | changeOuterPriority | changeOuterTag
				sheRuleControlActionParameter01 = new VlanID | new Priority
				sheRuleControlActionParameter02 = new Priority | empty
				
				dscpTranslation(22)
				sheRuleControlType= 22
				sheRuleControlName = dscpTranslation
				sheRuleControlPriority = 
				sheRuleControlDscpPattern = xx
				sheRuleControlDscpMatch = exact
				sheRuleControlFlowPattern = yy
				sheRuleControlFlowMatch = exact
				sheRuleControlAction = changeOuterVlan | changeOuterPriority | changeOuterTag
				sheRuleControlActionParameter01 = new VlanID | new Priority
				sheRuleControlActionParameter02 = new Priority | empty
				
				New with SHE R2.7:
				
				meteringDot1P(25)
				Type = 25
				Name = 
				Priority =
				BridgePortPattern =
				BridgePortMatch = exact
				PriorityPattern =
				PriorityMatch = exact
				Action = Meter
				ActionParameter01 = MeterProfile
				
				New with SHE R2.8:
				
				meteringVlan(26) (currently support only by WIN/CNX IU)
				Type = 26
				Name = 
				Priority =
				VlanIdPattern =
				VlanIdMatch = exact
				IUPhysIndexPattern =
				IUPhysIndexMatch = exact
				Action = Meter
				ActionParameter01 = MeterProfile
				
				meteringDhcpOnIU(27) (currently support only by WIN/CNX IU's)
				Type = 27
				Name = 
				Priority =
				IUPhysIndexPattern =
				IUPhysIndexMatch = exact
				Action = Meter
				ActionParameter01 = MeterProfile
				
				meteringDhcpOnPort(28) (currently support only by CG IU's)
				Type = 28
				Name = 
				Priority =
				PortIfIndexPattern =
				PortIfIndexMatch = exact
				Action = Meter
				ActionParameter01 = MeterProfile
				
				meteringArpOnIU(29) (currently support only by WIN/CNX IU's)
				Type = 29
				Name = 
				Priority =
				IUPhysIndexPattern =
				IUPhysIndexMatch = exact
				Action = Meter
				ActionParameter01 = MeterProfile
				
				meteringArpOnPort(30) (currently support only by CG IU's)
				Type = 30
				Name = 
				Priority =
				PortIfIndexPattern =
				PortIfIndexMatch = exact
				Action = Meter
				ActionParameter01 = MeterProfile
				
				meteringIgmpOnIU(31) (currently support only by WIN/CNX IU's)
				Type = 31
				Name = 
				Priority =
				IUPhysIndexPattern =
				IUPhysIndexMatch = exact
				Action = Meter
				ActionParameter01 = MeterProfile
				
				meteringIgmpOnPort(32) (currently support only by CG IU's)
				Type = 32
				Name = 
				Priority =
				PortIfIndexPattern =
				PortIfIndexMatch = exact
				Action = Meter
				ActionParameter01 = MeterProfile
				
				meteringDslPort(33) (currently support only by CG IU's)
				Type = 33
				Name = 
				Priority =
				PortIfIndexPattern =
				PortIfIndexMatch = exact
				Action = Meter
				ActionParameter01 = MeterProfile
				
				
				########
				
				
				genericRule(50)
				sheRuleControlType= 50
				In case of using the genericRule-Type the set of used pattern matches and action are not fixed.
				The NE has to parse the complete control-group and the managment system must send the complete
				control-group, but only pattern with a match-value unequal ignore will be evaluated.
				Be careful!!
				
				genericAdminRule(51)
				sheRuleControlType= 51
				In case of using the genericAdminRule-Type the set of used pattern matches and action are not fixed.
				The NE has to parse the complete control-group and the managment system must send the complete
				control-group, but only pattern with a match-value unequal ignore will be evaluated.
				Be careful!!
				The only difference to rule-type 50, genericRule, is, that the AdminRule will complete handled by CXU-Software,
				without support of switching fabric!!
				"
			::= { sheRuleEntry 2 }

		
--   1.3.6.1.4.1.231.7.1.2.2.1.4.3.1.1.3
		sheRuleName OBJECT-TYPE
			SYNTAX OCTET STRING (SIZE (0..63))
			MAX-ACCESS read-only
			STATUS current
			DESCRIPTION
				"A descriptional userflow-name. The name should be unique. 
				Spaces and other special characters (: o) are not allowed!! "
			::= { sheRuleEntry 3 }

		
--   1.3.6.1.4.1.231.7.1.2.2.1.4.3.1.1.4
		sheRulePriority OBJECT-TYPE
			SYNTAX Integer32 (0..7)
			MAX-ACCESS read-only
			STATUS current
			DESCRIPTION
				"The priority of the rule. Usefull in case of multiple matches."
			::= { sheRuleEntry 4 }

		
--   1.3.6.1.4.1.231.7.1.2.2.1.4.3.1.1.5
		sheRuleBridgePortPattern OBJECT-TYPE
			SYNTAX Integer32
			MAX-ACCESS read-only
			STATUS current
			DESCRIPTION
				"A sheBridgePortIndex."
			::= { sheRuleEntry 5 }

		
--   1.3.6.1.4.1.231.7.1.2.2.1.4.3.1.1.6
		sheRuleBridgePortMatch OBJECT-TYPE
			SYNTAX SheRuleMatchType
			MAX-ACCESS read-only
			STATUS current
			DESCRIPTION
				"Defines the usage of the corresponding pattern-value.
				ignore(1),
				exact(2),
				exclude(3)
				"
			DEFVAL { ignore }
			::= { sheRuleEntry 6 }

		
--   1.3.6.1.4.1.231.7.1.2.2.1.4.3.1.1.7
		sheRuleSourceMacPattern OBJECT-TYPE
			SYNTAX OCTET STRING (SIZE (6))
			MAX-ACCESS read-only
			STATUS current
			DESCRIPTION
				"A single source mac-address."
			::= { sheRuleEntry 7 }

		
--   1.3.6.1.4.1.231.7.1.2.2.1.4.3.1.1.8
		sheRuleSourceMacMatch OBJECT-TYPE
			SYNTAX SheRuleMatchType
			MAX-ACCESS read-only
			STATUS current
			DESCRIPTION
				"Defines the usage of the corresponding pattern-value.
				ignore(1),
				exact(2),
				exclude(3)
				"
			DEFVAL { ignore }
			::= { sheRuleEntry 8 }

		
--    
-- 1.3.6.1.4.1.231.7.1.2.2.1.4.3.1.1.9
		sheRuleSourceMacStartPattern OBJECT-TYPE
			SYNTAX OCTET STRING (SIZE (6))
			MAX-ACCESS read-only
			STATUS current
			DESCRIPTION
				"A source mac-address to define the start point of a address range."
			::= { sheRuleEntry 9 }

		
--   1.3.6.1.4.1.231.7.1.2.2.1.4.3.1.1.10
		sheRuleSourceMacStopPattern OBJECT-TYPE
			SYNTAX OCTET STRING (SIZE (6))
			MAX-ACCESS read-only
			STATUS current
			DESCRIPTION
				"A source mac-address to define the end point of a address range."
			::= { sheRuleEntry 10 }

		
--   1.3.6.1.4.1.231.7.1.2.2.1.4.3.1.1.11
		sheRuleSourceMacRangeMatch OBJECT-TYPE
			SYNTAX SheRuleMatchType
			MAX-ACCESS read-only
			STATUS current
			DESCRIPTION
				"Defines the usage of the corresponding pattern-value.
				ignore(1),
				exact(2),
				exclude(3)
				"
			DEFVAL { ignore }
			::= { sheRuleEntry 11 }

		
--    
-- 1.3.6.1.4.1.231.7.1.2.2.1.4.3.1.1.12
		sheRuleDestinationMacPattern OBJECT-TYPE
			SYNTAX OCTET STRING (SIZE (6))
			MAX-ACCESS read-only
			STATUS current
			DESCRIPTION
				"A single destination mac-address."
			::= { sheRuleEntry 12 }

		
--    
-- 1.3.6.1.4.1.231.7.1.2.2.1.4.3.1.1.13
		sheRuleDestinationMacMatch OBJECT-TYPE
			SYNTAX SheRuleMatchType
			MAX-ACCESS read-only
			STATUS current
			DESCRIPTION
				"Defines the usage of the corresponding pattern-value.
				ignore(1),
				exact(2),
				exclude(3)
				"
			DEFVAL { ignore }
			::= { sheRuleEntry 13 }

		
--   1.3.6.1.4.1.231.7.1.2.2.1.4.3.1.1.14
		sheRuleDestinationMacStartPattern OBJECT-TYPE
			SYNTAX OCTET STRING (SIZE (6))
			MAX-ACCESS read-only
			STATUS current
			DESCRIPTION
				"A destination mac-address to define the start point of a address range."
			::= { sheRuleEntry 14 }

		
--   1.3.6.1.4.1.231.7.1.2.2.1.4.3.1.1.15
		sheRuleDestinationMacStopPattern OBJECT-TYPE
			SYNTAX OCTET STRING (SIZE (6))
			MAX-ACCESS read-only
			STATUS current
			DESCRIPTION
				"A destination mac-address to define the end point of a address range."
			::= { sheRuleEntry 15 }

		
--   1.3.6.1.4.1.231.7.1.2.2.1.4.3.1.1.16
		sheRuleDestinationMacRangeMatch OBJECT-TYPE
			SYNTAX SheRuleMatchType
			MAX-ACCESS read-only
			STATUS current
			DESCRIPTION
				"Defines the usage of the corresponding pattern-value.
				ignore(1),
				exact(2),
				exclude(3)
				"
			::= { sheRuleEntry 16 }

		
--   1.3.6.1.4.1.231.7.1.2.2.1.4.3.1.1.17
		sheRuleVlanIdPattern OBJECT-TYPE
			SYNTAX Integer32 (1..4093)
			MAX-ACCESS read-only
			STATUS current
			DESCRIPTION
				"A sheVlanIndex."
			::= { sheRuleEntry 17 }

		
--   1.3.6.1.4.1.231.7.1.2.2.1.4.3.1.1.18
		sheRuleVlanIdMatch OBJECT-TYPE
			SYNTAX SheRuleMatchType
			MAX-ACCESS read-only
			STATUS current
			DESCRIPTION
				"Defines the usage of the corresponding pattern-value.
				ignore(1),
				exact(2),
				exclude(3)
				"
			DEFVAL { ignore }
			::= { sheRuleEntry 18 }

		
--   1.3.6.1.4.1.231.7.1.2.2.1.4.3.1.1.19
		sheRulePriorityPattern OBJECT-TYPE
			SYNTAX INTEGER (0..7)
			MAX-ACCESS read-only
			STATUS current
			DESCRIPTION
				"A .1p priority value. Range is 0-7."
			::= { sheRuleEntry 19 }

		
--   1.3.6.1.4.1.231.7.1.2.2.1.4.3.1.1.20
		sheRulePriorityMatch OBJECT-TYPE
			SYNTAX SheRuleMatchType
			MAX-ACCESS read-only
			STATUS current
			DESCRIPTION
				"Defines the usage of the corresponding pattern-value.
				ignore(1),
				exact(2),
				exclude(3)
				"
			DEFVAL { ignore }
			::= { sheRuleEntry 20 }

		
--   1.3.6.1.4.1.231.7.1.2.2.1.4.3.1.1.21
		sheRuleTosPattern OBJECT-TYPE
			SYNTAX INTEGER (0..255)
			MAX-ACCESS read-only
			STATUS current
			DESCRIPTION
				"A tos value. Range is 0..255.
				Inside one rule only one of three could be used: Tos or Dscp or IpPrecedence."
			::= { sheRuleEntry 21 }

		
--   1.3.6.1.4.1.231.7.1.2.2.1.4.3.1.1.22
		sheRuleTosMatch OBJECT-TYPE
			SYNTAX SheRuleMatchType
			MAX-ACCESS read-only
			STATUS current
			DESCRIPTION
				"Defines the usage of the corresponding pattern-value.
				ignore(1),
				exact(2),
				exclude(3)
				"
			DEFVAL { ignore }
			::= { sheRuleEntry 22 }

		
--   1.3.6.1.4.1.231.7.1.2.2.1.4.3.1.1.23
		sheRuleDscpPattern OBJECT-TYPE
			SYNTAX INTEGER (0..63)
			MAX-ACCESS read-only
			STATUS current
			DESCRIPTION
				"A dscp value. Range is 0-63.
				Inside one rule only one of three could be used: Tos or Dscp or IpPrecedence."
			::= { sheRuleEntry 23 }

		
--    
-- 1.3.6.1.4.1.231.7.1.2.2.1.4.3.1.1.24
		sheRuleDscpMatch OBJECT-TYPE
			SYNTAX SheRuleMatchType
			MAX-ACCESS read-only
			STATUS current
			DESCRIPTION
				"Defines the usage of the corresponding pattern-value.
				ignore(1),
				exact(2),
				exclude(3)
				"
			DEFVAL { ignore }
			::= { sheRuleEntry 24 }

		
--   1.3.6.1.4.1.231.7.1.2.2.1.4.3.1.1.25
		sheRuleEtherTypePattern OBJECT-TYPE
			SYNTAX OCTET STRING (SIZE (2))
			MAX-ACCESS read-only
			STATUS current
			DESCRIPTION
				"A ethertype pattern match."
			::= { sheRuleEntry 25 }

		
--   1.3.6.1.4.1.231.7.1.2.2.1.4.3.1.1.26
		sheRuleEtherTypeMatch OBJECT-TYPE
			SYNTAX SheRuleMatchType
			MAX-ACCESS read-only
			STATUS current
			DESCRIPTION
				"Defines the usage of the corresponding pattern-value.
				ignore(1),
				exact(2),
				exclude(3)
				"
			DEFVAL { ignore }
			::= { sheRuleEntry 26 }

		
--   1.3.6.1.4.1.231.7.1.2.2.1.4.3.1.1.27
		sheRuleSourceIpAddressPattern OBJECT-TYPE
			SYNTAX OCTET STRING (SIZE (4))
			MAX-ACCESS read-only
			STATUS current
			DESCRIPTION
				"A single source ip-address."
			::= { sheRuleEntry 27 }

		
--   1.3.6.1.4.1.231.7.1.2.2.1.4.3.1.1.28
		sheRuleSourceIpAddressMatch OBJECT-TYPE
			SYNTAX SheRuleMatchType
			MAX-ACCESS read-only
			STATUS current
			DESCRIPTION
				"Defines the usage of the corresponding pattern-value.
				ignore(1),
				exact(2),
				exclude(3)
				"
			DEFVAL { ignore }
			::= { sheRuleEntry 28 }

		
--   1.3.6.1.4.1.231.7.1.2.2.1.4.3.1.1.29
		sheRuleSourceIpSubnetMaskPattern OBJECT-TYPE
			SYNTAX OCTET STRING (SIZE (4))
			MAX-ACCESS read-only
			STATUS current
			DESCRIPTION
				"A source ip-address subnet mask."
			::= { sheRuleEntry 29 }

		
--   1.3.6.1.4.1.231.7.1.2.2.1.4.3.1.1.30
		sheRuleSourceIpSubnetMaskMatch OBJECT-TYPE
			SYNTAX SheRuleMatchType
			MAX-ACCESS read-only
			STATUS current
			DESCRIPTION
				"Defines the usage of the corresponding pattern-value.
				ignore(1),
				exact(2),
				exclude(3)
				"
			DEFVAL { ignore }
			::= { sheRuleEntry 30 }

		
--   1.3.6.1.4.1.231.7.1.2.2.1.4.3.1.1.31
		sheRuleDestinationIpAddressPattern OBJECT-TYPE
			SYNTAX OCTET STRING (SIZE (4))
			MAX-ACCESS read-only
			STATUS current
			DESCRIPTION
				"A single destination ip-address."
			::= { sheRuleEntry 31 }

		
--   1.3.6.1.4.1.231.7.1.2.2.1.4.3.1.1.32
		sheRuleDestinationIpAddressMatch OBJECT-TYPE
			SYNTAX SheRuleMatchType
			MAX-ACCESS read-only
			STATUS current
			DESCRIPTION
				"Defines the usage of the corresponding pattern-value.
				ignore(1),
				exact(2),
				exclude(3)
				"
			DEFVAL { ignore }
			::= { sheRuleEntry 32 }

		
--   1.3.6.1.4.1.231.7.1.2.2.1.4.3.1.1.33
		sheRuleDestinationIpSubnetMaskPattern OBJECT-TYPE
			SYNTAX OCTET STRING (SIZE (4))
			MAX-ACCESS read-only
			STATUS current
			DESCRIPTION
				"A destination ip-address subnet mask."
			::= { sheRuleEntry 33 }

		
--   1.3.6.1.4.1.231.7.1.2.2.1.4.3.1.1.34
		sheRuleDestinationIpSubnetMaskMatch OBJECT-TYPE
			SYNTAX SheRuleMatchType
			MAX-ACCESS read-only
			STATUS current
			DESCRIPTION
				"Defines the usage of the corresponding pattern-value.
				ignore(1),
				exact(2),
				exclude(3)
				"
			DEFVAL { ignore }
			::= { sheRuleEntry 34 }

		
--   1.3.6.1.4.1.231.7.1.2.2.1.4.3.1.1.35
		sheRuleSourcePortPattern OBJECT-TYPE
			SYNTAX Integer32
			MAX-ACCESS read-only
			STATUS current
			DESCRIPTION
				"TCP/UDP Port.
				Source- or DestinationPort will only be evaluated if a IpProtocolPattern equal Udp or Tcp is given."
			::= { sheRuleEntry 35 }

		
--   1.3.6.1.4.1.231.7.1.2.2.1.4.3.1.1.36
		sheRuleSourcePortMatch OBJECT-TYPE
			SYNTAX SheRuleMatchType
			MAX-ACCESS read-only
			STATUS current
			DESCRIPTION
				"Defines the usage of the corresponding pattern-value.
				ignore(1),
				exact(2),
				exclude(3)
				"
			DEFVAL { ignore }
			::= { sheRuleEntry 36 }

		
--   1.3.6.1.4.1.231.7.1.2.2.1.4.3.1.1.37
		sheRuleDestinationPortPattern OBJECT-TYPE
			SYNTAX Integer32
			MAX-ACCESS read-only
			STATUS current
			DESCRIPTION
				"TCP/UDP Port.
				Source- or DestinationPort will only be evaluated if a IpProtocolPattern equal Udp or Tcp is given."
			::= { sheRuleEntry 37 }

		
--   1.3.6.1.4.1.231.7.1.2.2.1.4.3.1.1.38
		sheRuleDestinationPortMatch OBJECT-TYPE
			SYNTAX SheRuleMatchType
			MAX-ACCESS read-only
			STATUS current
			DESCRIPTION
				"Defines the usage of the corresponding pattern-value.
				ignore(1),
				exact(2),
				exclude(3)
				"
			DEFVAL { ignore }
			::= { sheRuleEntry 38 }

		
--   1.3.6.1.4.1.231.7.1.2.2.1.4.3.1.1.39
		sheRuleAction OBJECT-TYPE
			SYNTAX SheRuleActionType
			MAX-ACCESS read-only
			STATUS current
			DESCRIPTION
				"Gives the action for the defined userflow.
				deny(1),
				allow(2),
				meter(3),
				changeInnerVlan(4),
				changeOuterVlan(5),
				changeInnerPriority(6),
				changeOuterPriority(7),
				changeTos(8),
				changeDscp(9),
				changeInnerVlanTag(10),
				changeOuterVlanTag(11),
				assignTC(12)
				mirror(13),"
			DEFVAL { deny }
			::= { sheRuleEntry 39 }

		
--   1.3.6.1.4.1.231.7.1.2.2.1.4.3.1.1.40
		sheRuleActionParameter01 OBJECT-TYPE
			SYNTAX Integer32
			MAX-ACCESS read-only
			STATUS current
			DESCRIPTION
				"Define an additional parameter depence on the used action.
				
				deny,allow,mirror: not used
				
				changeTos: new Tos value
				
				changeDscp: new Dscp value
				
				changeInnerVlan: new Vlan Id
				changeOuterVlan: new Vlan Id
				
				meter: meterProfileIndex
				
				changeInnerPriority: new Priority (1p)
				changeOuterPriority: new Priority (1p)
				
				assignTC: Traffic class values 0-7
				
				changeInnerVlanTag: new Vlan Id
				changeOuterVlanTag: new Vlan Id
				"
			::= { sheRuleEntry 40 }

		
--   1.3.6.1.4.1.231.7.1.2.2.1.4.3.1.1.41
		sheRuleActionParameter02 OBJECT-TYPE
			SYNTAX Integer32
			MAX-ACCESS read-only
			STATUS current
			DESCRIPTION
				"Define an additional parameter depence on the used action.
				
				deny,allow,mirror,changeTos, changeDscp, changeInnerVlan,
				changeOuterVlan, meter, changeInnerPriority, changeOuterPriority,
				assignTC, mirror: not used
				
				changeInnerVlanTag: new Priority (1p)
				changeOuterVlanTag: new Priority (1p)"
			::= { sheRuleEntry 41 }

		
--   1.3.6.1.4.1.231.7.1.2.2.1.4.3.1.1.42
		sheRuleFlowPattern OBJECT-TYPE
			SYNTAX SheRuleFlowType
			MAX-ACCESS read-only
			STATUS current
			DESCRIPTION
				"The flow-direction for which this rule should work.
				1 - upstream
				2 - downstream
				3 - bidirectional"
			::= { sheRuleEntry 42 }

		
--   1.3.6.1.4.1.231.7.1.2.2.1.4.3.1.1.43
		sheRuleFlowMatch OBJECT-TYPE
			SYNTAX SheRuleMatchType
			MAX-ACCESS read-only
			STATUS current
			DESCRIPTION
				"Defines the usage of the corresponding pattern-value.
				ignore(1),
				exact(2),
				exclude(3)
				"
			DEFVAL { ignore }
			::= { sheRuleEntry 43 }

		
--   1.3.6.1.4.1.231.7.1.2.2.1.4.3.1.1.44
		sheRuleIpProtocolPattern OBJECT-TYPE
			SYNTAX Unsigned32 (0..255)
			MAX-ACCESS read-only
			STATUS current
			DESCRIPTION
				"Used L4-ProtocolType. Needed to evaluate the correct 
				Ip-PortPattern (look at RFC791)."
			::= { sheRuleEntry 44 }

		
--   1.3.6.1.4.1.231.7.1.2.2.1.4.3.1.1.45
		sheRuleIpProtocolMatch OBJECT-TYPE
			SYNTAX SheRuleMatchType
			MAX-ACCESS read-only
			STATUS current
			DESCRIPTION
				"Defines the usage of the corresponding pattern-value.
				ignore(1),
				exact(2),
				exclude(3)
				                            "
			DEFVAL { ignore }
			::= { sheRuleEntry 45 }

		
--   1.3.6.1.4.1.231.7.1.2.2.1.4.3.1.1.46
		sheRuleIpPrecedencePattern OBJECT-TYPE
			SYNTAX Unsigned32 (0..7)
			MAX-ACCESS read-only
			STATUS current
			DESCRIPTION
				"A Ip precedence value 0-7.
				Inside one rule only one of three could be used: Tos or Dscp or IpPrecedence."
			::= { sheRuleEntry 46 }

		
--   1.3.6.1.4.1.231.7.1.2.2.1.4.3.1.1.47
		sheRuleIpPrecedenceMatch OBJECT-TYPE
			SYNTAX SheRuleMatchType
			MAX-ACCESS read-only
			STATUS current
			DESCRIPTION
				"Defines the usage of the corresponding pattern-value.
				ignore(1),
				exact(2),
				exclude(3)
				                            "
			DEFVAL { ignore }
			::= { sheRuleEntry 47 }

		
--   1.3.6.1.4.1.231.7.1.2.2.1.4.3.1.1.48
		sheRuleSourceMacMaskPattern OBJECT-TYPE
			SYNTAX OCTET STRING (SIZE (1..6))
			MAX-ACCESS read-only
			STATUS current
			DESCRIPTION
				"Bit mask for sheRuleSourceMacPattern.
				Will be evaluated by NE only if sheRuleSourceMacPattern is given.
				The NE assumes #ffffffffffff as default if no mask is present.
				"
			::= { sheRuleEntry 48 }

		
--   1.3.6.1.4.1.231.7.1.2.2.1.4.3.1.1.49
		sheRuleSourceMacMaskMatch OBJECT-TYPE
			SYNTAX SheRuleMatchType
			MAX-ACCESS read-only
			STATUS current
			DESCRIPTION
				"Defines the usage of the corresponding pattern-value.
				ignore(1),
				exact(2),
				exclude(3)
				                            "
			DEFVAL { ignore }
			::= { sheRuleEntry 49 }

		
--   1.3.6.1.4.1.231.7.1.2.2.1.4.3.1.1.50
		sheRuleDestinationMacMaskPattern OBJECT-TYPE
			SYNTAX OCTET STRING (SIZE (1..6))
			MAX-ACCESS read-only
			STATUS current
			DESCRIPTION
				"Bit mask for sheRuleDestinationMacPattern.
				Will be evaluated by NE only if sheRuleDestinationMacPattern is given.
				The NE assumes #ffffffffffff as default if no mask is present.
				"
			::= { sheRuleEntry 50 }

		
--   1.3.6.1.4.1.231.7.1.2.2.1.4.3.1.1.51
		sheRuleDestinationMacMaskMatch OBJECT-TYPE
			SYNTAX SheRuleMatchType
			MAX-ACCESS read-only
			STATUS current
			DESCRIPTION
				"Defines the usage of the corresponding pattern-value.
				ignore(1),
				exact(2),
				exclude(3)
				                            "
			DEFVAL { ignore }
			::= { sheRuleEntry 51 }

		
--   1.3.6.1.4.1.231.7.1.2.2.1.4.3.1.1.52
		sheRuleMessageTypePattern OBJECT-TYPE
			SYNTAX Integer32
			MAX-ACCESS read-only
			STATUS current
			DESCRIPTION
				"Message Type.
				Currently used only if IP Protocol pattern is set to 
				ICMP (RFC950).
				Otherwise ignored.
				"
			::= { sheRuleEntry 52 }

		
--   1.3.6.1.4.1.231.7.1.2.2.1.4.3.1.1.53
		sheRuleMessageTypeMatch OBJECT-TYPE
			SYNTAX SheRuleMatchType
			MAX-ACCESS read-only
			STATUS current
			DESCRIPTION
				"Defines the usage of the corresponding pattern-value.
				ignore(1),
				exact(2),
				exclude(3)
				                            "
			DEFVAL { ignore }
			::= { sheRuleEntry 53 }

		
--   1.3.6.1.4.1.231.7.1.2.2.1.4.3.1.1.54
		sheRuleMessageCodePattern OBJECT-TYPE
			SYNTAX Integer32
			MAX-ACCESS read-only
			STATUS current
			DESCRIPTION
				"CodeType.
				Currently used only if IP Protocol pattern is set to 
				ICMP and a MessageType Pattern is given (RFC950).
				Otherwise ignored.
				                            "
			::= { sheRuleEntry 54 }

		
--   1.3.6.1.4.1.231.7.1.2.2.1.4.3.1.1.55
		sheRuleMessageCodeMatch OBJECT-TYPE
			SYNTAX SheRuleMatchType
			MAX-ACCESS read-only
			STATUS current
			DESCRIPTION
				"Defines the usage of the corresponding pattern-value.
				ignore(1),
				exact(2),
				exclude(3)
				                            "
			DEFVAL { ignore }
			::= { sheRuleEntry 55 }

		
--   1.3.6.1.4.1.231.7.1.2.2.1.4.3.1.1.56
		sheRuleGenericMatchAction OBJECT-TYPE
			SYNTAX SheRuleGenericActionType
			MAX-ACCESS read-only
			STATUS current
			DESCRIPTION
				"Handle packet as follows if rule match.
				- deny(0)
					Drops matching packets.
					Action parameter: none
				
				- allow(1)
					Permits matching packets.
					Action parameter: none
				
				- meter(2)
					Maps an rate limiting profile.
					Action parameter: sheRuleGenericMatchActionMeterIndex
				
				- redirect(3)
					Redirects matching packets to given bridge port
					(uplink interface).
					Action parameter: sheRuleGenericMatchActionRedirPort
				
				- mirror(4)
					Copies matching packets to mirror monitor port.
					Action parameter: none
				
				- setDscp(5)
					Sets DSCP value in matching packets.
					Action parameter: sheRuleGenericMatchActionDscp
				
				- setPriority(6)
					Schedules matching frames (queue mapping)
					according given priority value.
					Action parameter: sheRuleGenericMatchActionSetPrio
				
				- changeTagPriority(7)
					Changes .1p priority value in VLAN tag.
					Action parameter: sheRuleGenericMatchActionSetTagPrio
				
				- changeTagPriorityWithTos(8)
					Copies IP Precedence Bits of TOS field into .1p
					priority of VLAN tag.
					Action parameter: none
				
				- setIpPrecedence(9)
					Sets IP Precedence bits in TOS field.
					Action parameter: sheRuleGenericMatchActionIpPrecedence
				
				- changeTosWithTagPrio(10)
					Action parameter: none
				
				- rateLimit(11)
					Applies rate limiting for matching packets.
					Action parameter: sheRuleGenericMatchActionRate
				
				- changeVlanId(12)
					Changes Vlan-ID in VLAN-Tag of matching frames.
					Action parameter: sheRuleActionVlan
				
				- copyToCpu(13)
					Copies matching frames to CPU port.
					Action parameter: none
				
				- count(14)
					Initiates counting of matching packets.
					The NE supports only a limited number of counters at
					the same time and may reject this rule if the number of
					timers is exceeded.
					
				- untag (15)
				        untag the frame
				"
			::= { sheRuleEntry 56 }

		
--   1.3.6.1.4.1.231.7.1.2.2.1.4.3.1.1.57
		sheRuleGenericNoMatchAction OBJECT-TYPE
			SYNTAX SheRuleGenericActionType
			MAX-ACCESS read-only
			STATUS current
			DESCRIPTION
				"Handle packet as follows if rule not match.
				- deny(0)
					Drops matching packets.
					Action parameter: none
				
				- allow(1)
					Permits matching packets.
					Action parameter: none
				
				- meter(2)
					Maps an rate limiting profile.
					Action parameter: sheRuleGenericNoMatchActionMeterIndex
				
				- redirect(3)
					Redirects matching packets to given bridge port
					(uplink interface).
					Action parameter: sheRuleGenericNoMatchActionRedirPort
				
				- mirror(4)
					Copies matching packets to mirror monitor port.
					Action parameter: none
				
				- setDscp(5)
					Sets DSCP value in matching packets.
					Action parameter: sheRuleGenericNoMatchActionDscp
				
				- setPriority(6)
					Schedules matching frames (queue mapping)
					according given priority value.
					Action parameter: sheRuleActionSetPrio
				
				- changeTagPriority(7)
					Changes .1p priority value in VLAN tag.
					Action parameter: sheRuleGenericNoMatchActionSetTagPrio
				
				- changeTagPriorityWithTos(8)
					Copies IP Precedence Bits of TOS field into .1p
					priority of VLAN tag.
					Action parameter: none
				
				- setIpPrecedence(9)
					Sets IP Precedence bits in TOS field.
					Action parameter: sheRuleGenericNoMatchActionIpPrecedence
				
				- changeTosWithTagPrio(10)
					Action parameter: none
				
				- rateLimit(11)
					Applies rate limiting for matching packets.
					Action parameter: sheRuleGenericNoMatchActionRate
				
				- changeVlanId(12)
					Changes Vlan-ID in VLAN-Tag of matching frames.
					Action parameter: sheRuleGenericNoMatchActionVlan
				
				- copyToCpu(13)
					Copies matching frames to CPU port.
					Action parameter: none
				
				- count(14)
					Initiates counting of matching packets.
					The NE supports only a limited number of counters at
					the same time and may reject this rule if the number of
					timers is exceeded.
					
				- untag (15)
				        untag the frame
				"
			::= { sheRuleEntry 57 }

		
--   1.3.6.1.4.1.231.7.1.2.2.1.4.3.1.1.58
		sheRuleGenericMatchActionParameterMeterIndex OBJECT-TYPE
			SYNTAX Unsigned32
			MAX-ACCESS read-only
			STATUS current
			DESCRIPTION
				"Metering Profile Index used by genericrule action:  
				meter(2)"
			::= { sheRuleEntry 58 }

		
--   1.3.6.1.4.1.231.7.1.2.2.1.4.3.1.1.59
		sheRuleGenericMatchActionParameterRedirPort OBJECT-TYPE
			SYNTAX Unsigned32
			MAX-ACCESS read-only
			STATUS current
			DESCRIPTION
				"BridgePort Index used by rule action: redirect(3)
				"
			::= { sheRuleEntry 59 }

		
--   1.3.6.1.4.1.231.7.1.2.2.1.4.3.1.1.60
		sheRuleGenericMatchActionParameterDscp OBJECT-TYPE
			SYNTAX Unsigned32 (0..63)
			MAX-ACCESS read-only
			STATUS current
			DESCRIPTION
				"DSCP value used by rule action: setDscp(5)
				"
			::= { sheRuleEntry 60 }

		
--   1.3.6.1.4.1.231.7.1.2.2.1.4.3.1.1.61
		sheRuleGenericMatchActionParameterPriority OBJECT-TYPE
			SYNTAX Unsigned32 (0..7)
			MAX-ACCESS read-only
			STATUS current
			DESCRIPTION
				"Priority value used by rule action: setPriority(6)
				"
			::= { sheRuleEntry 61 }

		
--   1.3.6.1.4.1.231.7.1.2.2.1.4.3.1.1.62
		sheRuleGenericMatchActionParameterTagPriority OBJECT-TYPE
			SYNTAX Unsigned32 (0..7)
			MAX-ACCESS read-only
			STATUS current
			DESCRIPTION
				"Priority value used by rule action: changeTagPriority(7)
				"
			::= { sheRuleEntry 62 }

		
--   1.3.6.1.4.1.231.7.1.2.2.1.4.3.1.1.63
		sheRuleGenericMatchActionParameterIpPrecedence OBJECT-TYPE
			SYNTAX Unsigned32
			MAX-ACCESS read-only
			STATUS current
			DESCRIPTION
				"IP Precedence value used by rule action:  setIpPrecedence(9)
				
				"
			::= { sheRuleEntry 63 }

		
--   1.3.6.1.4.1.231.7.1.2.2.1.4.3.1.1.64
		sheRuleGenericMatchActionParameterRate OBJECT-TYPE
			SYNTAX Unsigned32
			UNITS "MBit/s"
			MAX-ACCESS read-only
			STATUS current
			DESCRIPTION
				"Rate limit value (MBit per second) used by rule action:	rateLimit(11)
				
				"
			::= { sheRuleEntry 64 }

		
--   1.3.6.1.4.1.231.7.1.2.2.1.4.3.1.1.65
		sheRuleGenericMatchActionParameterVlanId OBJECT-TYPE
			SYNTAX Unsigned32 (1..4093)
			MAX-ACCESS read-only
			STATUS current
			DESCRIPTION
				"Vlan ID used by rule action: changeVlanId(12)
				"
			::= { sheRuleEntry 65 }

		
--   1.3.6.1.4.1.231.7.1.2.2.1.4.3.1.1.66
		sheRuleGenericNoMatchActionParameterMeterIndex OBJECT-TYPE
			SYNTAX Unsigned32
			MAX-ACCESS read-only
			STATUS current
			DESCRIPTION
				"Metering Profile Index used by rule action:  
				---"
			::= { sheRuleEntry 66 }

		
--   1.3.6.1.4.1.231.7.1.2.2.1.4.3.1.1.67
		sheRuleGenericNoMatchActionParameterRedirPort OBJECT-TYPE
			SYNTAX Unsigned32
			MAX-ACCESS read-only
			STATUS current
			DESCRIPTION
				"BridgePort Index used by rule action: redirect(3)
				"
			::= { sheRuleEntry 67 }

		
--   1.3.6.1.4.1.231.7.1.2.2.1.4.3.1.1.68
		sheRuleGenericNoMatchActionParameterDscp OBJECT-TYPE
			SYNTAX Unsigned32 (0..63)
			MAX-ACCESS read-only
			STATUS current
			DESCRIPTION
				"DSCP value used by rule action: setDscp(5)
				"
			::= { sheRuleEntry 68 }

		
--   1.3.6.1.4.1.231.7.1.2.2.1.4.3.1.1.69
		sheRuleGenericNoMatchActionParameterPriority OBJECT-TYPE
			SYNTAX Unsigned32 (0..7)
			MAX-ACCESS read-only
			STATUS current
			DESCRIPTION
				"Priority value used by rule action: setPriority(6)
				"
			::= { sheRuleEntry 69 }

		
--   1.3.6.1.4.1.231.7.1.2.2.1.4.3.1.1.70
		sheRuleGenericNoMatchActionParameterTagPriority OBJECT-TYPE
			SYNTAX Unsigned32 (0..7)
			MAX-ACCESS read-only
			STATUS current
			DESCRIPTION
				"Priority value used by rule action: changeTagPriority(7)
				"
			::= { sheRuleEntry 70 }

		
--   1.3.6.1.4.1.231.7.1.2.2.1.4.3.1.1.71
		sheRuleGenericNoMatchActionParameterIpPrecedence OBJECT-TYPE
			SYNTAX Unsigned32
			MAX-ACCESS read-only
			STATUS current
			DESCRIPTION
				"IP Precedence value used by rule action:  setIpPrecedence(9)
				"
			::= { sheRuleEntry 71 }

		
--   1.3.6.1.4.1.231.7.1.2.2.1.4.3.1.1.72
		sheRuleGenericNoMatchActionParameterRate OBJECT-TYPE
			SYNTAX Unsigned32
			UNITS "MBit/s"
			MAX-ACCESS read-only
			STATUS current
			DESCRIPTION
				"Rate limit value (MBit per second) used by rule action:	rateLimit(11)
				
				"
			::= { sheRuleEntry 72 }

		
--   1.3.6.1.4.1.231.7.1.2.2.1.4.3.1.1.73
		sheRuleGenericNoMatchActionParameterVlanId OBJECT-TYPE
			SYNTAX Unsigned32 (1..4093)
			MAX-ACCESS read-only
			STATUS current
			DESCRIPTION
				"Vlan ID used by rule action: changeVlanId(12)
				"
			::= { sheRuleEntry 73 }

		
--   1.3.6.1.4.1.231.7.1.2.2.1.4.3.1.1.74
		sheRuleMatchCounter OBJECT-TYPE
			SYNTAX Integer32 (-1..2147483647)
			MAX-ACCESS read-only
			STATUS current
			DESCRIPTION
				"Number of matches (how often the rule has been matched).
				Note: Not all rules types support counters. The NE
				responds the value -1 if there is no counter available.
				"
			DEFVAL { -1 }
			::= { sheRuleEntry 74 }

		
--   1.3.6.1.4.1.231.7.1.2.2.1.4.3.1.1.75
		sheRuleActivationState OBJECT-TYPE
			SYNTAX SheRuleActivationStateType
			MAX-ACCESS read-only
			STATUS current
			DESCRIPTION
				"Show the activation state of a rule. A change of this value will not be notified by trap.
				"
			DEFVAL { 0 }
			::= { sheRuleEntry 75 }

		
--   1.3.6.1.4.1.231.7.1.2.2.1.4.3.1.1.76
		sheRuleInnerVlanIdPattern OBJECT-TYPE
			SYNTAX Integer32 (1..4093)
			MAX-ACCESS read-only
			STATUS current
			DESCRIPTION
				"Match the inner vlanid under double-tag mode."
			::= { sheRuleEntry 76 }

		
--   1.3.6.1.4.1.231.7.1.2.2.1.4.3.1.1.77
		sheRuleInnerVlanIdMatch OBJECT-TYPE
			SYNTAX SheRuleMatchType
			MAX-ACCESS read-only
			STATUS current
			DESCRIPTION
				"Defines the usage of the corresponding pattern-value.
				ignore(1),
				exact(2),
				exclude(3)
				"
			::= { sheRuleEntry 77 }

		
--   1.3.6.1.4.1.231.7.1.2.2.1.4.3.1.1.78
		sheRuleInnerPriorityPattern OBJECT-TYPE
			SYNTAX Integer32 (0..7)
			MAX-ACCESS read-only
			STATUS current
			DESCRIPTION
				"Match the inner .1p priority under double-tag mode."
			::= { sheRuleEntry 78 }

		
--   1.3.6.1.4.1.231.7.1.2.2.1.4.3.1.1.79
		sheRuleInnerPriorityMatch OBJECT-TYPE
			SYNTAX SheRuleMatchType
			MAX-ACCESS read-only
			STATUS current
			DESCRIPTION
				"Defines the usage of the corresponding pattern-value.
				ignore(1),
				exact(2),
				exclude(3)
				"
			::= { sheRuleEntry 79 }

		
--   1.3.6.1.4.1.231.7.1.2.2.1.4.3.1.1.82
		sheRuleIUPhysIndexPattern OBJECT-TYPE
			SYNTAX PhysicalIndex
			MAX-ACCESS read-only
			STATUS current
			DESCRIPTION
				"Match the IU entPhysIndex from entPhysicalTable."
			::= { sheRuleEntry 82 }

		
--   1.3.6.1.4.1.231.7.1.2.2.1.4.3.1.1.83
		sheRuleIUPhysIndexMatch OBJECT-TYPE
			SYNTAX SheRuleMatchType
			MAX-ACCESS read-only
			STATUS current
			DESCRIPTION
				"Defines the usage of the corresponding pattern-value.
				ignore(1),
				exact(2),
				exclude(3)
				"
			::= { sheRuleEntry 83 }

		
--   1.3.6.1.4.1.231.7.1.2.2.1.4.3.1.1.84
		sheRulePortIfIndexPattern OBJECT-TYPE
			SYNTAX InterfaceIndex
			MAX-ACCESS read-only
			STATUS current
			DESCRIPTION
				"Match the DSL port ifIndex from ifTable."
			::= { sheRuleEntry 84 }

		
--   1.3.6.1.4.1.231.7.1.2.2.1.4.3.1.1.85
		sheRulePortIfIndexMatch OBJECT-TYPE
			SYNTAX SheRuleMatchType
			MAX-ACCESS read-only
			STATUS current
			DESCRIPTION
				"Defines the usage of the corresponding pattern-value.
				ignore(1),
				exact(2),
				exclude(3)
				"
			::= { sheRuleEntry 85 }

		
--   1.3.6.1.4.1.231.7.1.2.2.1.4.3.2
		sheRuleControl OBJECT IDENTIFIER ::= { sheRulesAndMetering 2 }

		
--   1.3.6.1.4.1.231.7.1.2.2.1.4.3.2.1
		sheRuleControlRequest OBJECT-TYPE
			SYNTAX SheBridgeControlRequestType
			MAX-ACCESS read-write
			STATUS current
			DESCRIPTION
				"createRule:
				sheRuleControlName
				...
				minimum of one pair of pattern-match-combination with a match-value unequal to ignore
				...
				sheRuleControlAction
				sheRuleControlActionParameter01
				...
				
				deleteRule:
				sheRuleControlIndex
				
				clearRuleMatchCounter:
				sheRuleControlIndex
				"
			::= { sheRuleControl 1 }

		
--   1.3.6.1.4.1.231.7.1.2.2.1.4.3.2.2
		sheRuleControlIndex OBJECT-TYPE
			SYNTAX Unsigned32
			MAX-ACCESS read-write
			STATUS current
			DESCRIPTION
				"The index of the deleted rule."
			::= { sheRuleControl 2 }

		
--   1.3.6.1.4.1.231.7.1.2.2.1.4.3.2.3
		sheRuleControlStatus OBJECT-TYPE
			SYNTAX SheControlStatusType
			MAX-ACCESS read-only
			STATUS current
			DESCRIPTION
				"The status of a user command. 
				"
			::= { sheRuleControl 3 }

		
--   1.3.6.1.4.1.231.7.1.2.2.1.4.3.2.4
		sheRuleControlTimer OBJECT-TYPE
			SYNTAX Gauge32
			MAX-ACCESS read-only
			STATUS current
			DESCRIPTION
				"The maximum wait time for the manager for a long running user command. 
				"
			::= { sheRuleControl 4 }

		
--    
-- 1.3.6.1.4.1.231.7.1.2.2.1.4.3.2.5
		sheRuleControlReqResult OBJECT-TYPE
			SYNTAX SheBridgeControlReqResultType
			MAX-ACCESS read-only
			STATUS current
			DESCRIPTION
				"The result of the last user command."
			::= { sheRuleControl 5 }

		
--   1.3.6.1.4.1.231.7.1.2.2.1.4.3.2.6
		sheRuleControlTimeStamp OBJECT-TYPE
			SYNTAX Unsigned32
			UNITS "sec"
			MAX-ACCESS read-only
			STATUS current
			DESCRIPTION
				"The time stamp of the last command (end of command)."
			::= { sheRuleControl 6 }

		
--   1.3.6.1.4.1.231.7.1.2.2.1.4.3.2.7
		sheRuleControlType OBJECT-TYPE
			SYNTAX SheRuleType
			MAX-ACCESS read-write
			STATUS current
			DESCRIPTION
				"This type defines the set of used pattern and actions for this rule:
				look at rule-table."
			::= { sheRuleControl 7 }

		
--   1.3.6.1.4.1.231.7.1.2.2.1.4.3.2.8
		sheRuleControlName OBJECT-TYPE
			SYNTAX OCTET STRING (SIZE (0..63))
			MAX-ACCESS read-write
			STATUS current
			DESCRIPTION
				"A descriptional userflow-name. The name should be unique, but there is a exception:
				In case of using a expand-Ruletype, the name of the expanding rule must be equal to the original rule,
				which should be expanded. 
				Spaces and other special characters (: o) are not allowed!! "
			::= { sheRuleControl 8 }

		
--   1.3.6.1.4.1.231.7.1.2.2.1.4.3.2.9
		sheRuleControlPriority OBJECT-TYPE
			SYNTAX Integer32 (0..7)
			MAX-ACCESS read-write
			STATUS current
			DESCRIPTION
				"The priority of the rule. Usefull in case of multiple matches."
			::= { sheRuleControl 9 }

		
--   1.3.6.1.4.1.231.7.1.2.2.1.4.3.2.10
		sheRuleControlBridgePortPattern OBJECT-TYPE
			SYNTAX Integer32
			MAX-ACCESS read-write
			STATUS current
			DESCRIPTION
				"look at rule table..."
			::= { sheRuleControl 10 }

		
--   1.3.6.1.4.1.231.7.1.2.2.1.4.3.2.11
		sheRuleControlBridgePortMatch OBJECT-TYPE
			SYNTAX SheRuleMatchType
			MAX-ACCESS read-write
			STATUS current
			DESCRIPTION
				"look at rule table..."
			::= { sheRuleControl 11 }

		
--   1.3.6.1.4.1.231.7.1.2.2.1.4.3.2.12
		sheRuleControlSourceMacPattern OBJECT-TYPE
			SYNTAX OCTET STRING (SIZE (6))
			MAX-ACCESS read-write
			STATUS current
			DESCRIPTION
				"look at rule table..."
			::= { sheRuleControl 12 }

		
--   1.3.6.1.4.1.231.7.1.2.2.1.4.3.2.13
		sheRuleControlSourceMacMatch OBJECT-TYPE
			SYNTAX SheRuleMatchType
			MAX-ACCESS read-write
			STATUS current
			DESCRIPTION
				"look at rule table..."
			::= { sheRuleControl 13 }

		
--   1.3.6.1.4.1.231.7.1.2.2.1.4.3.2.14
		sheRuleControlSourceMacStartPattern OBJECT-TYPE
			SYNTAX OCTET STRING (SIZE (6))
			MAX-ACCESS read-write
			STATUS current
			DESCRIPTION
				"look at rule table..."
			::= { sheRuleControl 14 }

		
--   1.3.6.1.4.1.231.7.1.2.2.1.4.3.2.15
		sheRuleControlSourceMacStopPattern OBJECT-TYPE
			SYNTAX OCTET STRING (SIZE (6))
			MAX-ACCESS read-write
			STATUS current
			DESCRIPTION
				"look at rule table..."
			::= { sheRuleControl 15 }

		
--   1.3.6.1.4.1.231.7.1.2.2.1.4.3.2.16
		sheRuleControlSourceMacRangeMatch OBJECT-TYPE
			SYNTAX SheRuleMatchType
			MAX-ACCESS read-write
			STATUS current
			DESCRIPTION
				"look at rule table..."
			::= { sheRuleControl 16 }

		
--    
-- 1.3.6.1.4.1.231.7.1.2.2.1.4.3.2.17
		sheRuleControlDestinationMacPattern OBJECT-TYPE
			SYNTAX OCTET STRING (SIZE (6))
			MAX-ACCESS read-write
			STATUS current
			DESCRIPTION
				"look at rule table..."
			::= { sheRuleControl 17 }

		
--   1.3.6.1.4.1.231.7.1.2.2.1.4.3.2.18
		sheRuleControlDestinationMacMatch OBJECT-TYPE
			SYNTAX SheRuleMatchType
			MAX-ACCESS read-write
			STATUS current
			DESCRIPTION
				"look at rule table..."
			::= { sheRuleControl 18 }

		
--   1.3.6.1.4.1.231.7.1.2.2.1.4.3.2.19
		sheRuleControlDestinationMacStartPattern OBJECT-TYPE
			SYNTAX OCTET STRING (SIZE (6))
			MAX-ACCESS read-write
			STATUS current
			DESCRIPTION
				"look at rule table..."
			::= { sheRuleControl 19 }

		
--   1.3.6.1.4.1.231.7.1.2.2.1.4.3.2.20
		sheRuleControlDestinationMacStopPattern OBJECT-TYPE
			SYNTAX OCTET STRING (SIZE (6))
			MAX-ACCESS read-write
			STATUS current
			DESCRIPTION
				"look at rule table..."
			::= { sheRuleControl 20 }

		
--   1.3.6.1.4.1.231.7.1.2.2.1.4.3.2.21
		sheRuleControlDestinationMacRangeMatch OBJECT-TYPE
			SYNTAX SheRuleMatchType
			MAX-ACCESS read-write
			STATUS current
			DESCRIPTION
				"look at rule table..."
			::= { sheRuleControl 21 }

		
--   1.3.6.1.4.1.231.7.1.2.2.1.4.3.2.22
		sheRuleControlVlanIdPattern OBJECT-TYPE
			SYNTAX Integer32 (1..4093)
			MAX-ACCESS read-write
			STATUS current
			DESCRIPTION
				"look at rule table..."
			::= { sheRuleControl 22 }

		
--   1.3.6.1.4.1.231.7.1.2.2.1.4.3.2.23
		sheRuleControlVlanIdMatch OBJECT-TYPE
			SYNTAX SheRuleMatchType
			MAX-ACCESS read-write
			STATUS current
			DESCRIPTION
				"look at rule table..."
			::= { sheRuleControl 23 }

		
--   1.3.6.1.4.1.231.7.1.2.2.1.4.3.2.24
		sheRuleControlPriorityPattern OBJECT-TYPE
			SYNTAX INTEGER (0..7)
			MAX-ACCESS read-write
			STATUS current
			DESCRIPTION
				"look at rule table..."
			::= { sheRuleControl 24 }

		
--   1.3.6.1.4.1.231.7.1.2.2.1.4.3.2.25
		sheRuleControlPriorityMatch OBJECT-TYPE
			SYNTAX SheRuleMatchType
			MAX-ACCESS read-write
			STATUS current
			DESCRIPTION
				"look at rule table..."
			::= { sheRuleControl 25 }

		
--   1.3.6.1.4.1.231.7.1.2.2.1.4.3.2.26
		sheRuleControlTosPattern OBJECT-TYPE
			SYNTAX INTEGER (0..255)
			MAX-ACCESS read-write
			STATUS current
			DESCRIPTION
				"look at rule table..."
			::= { sheRuleControl 26 }

		
--   1.3.6.1.4.1.231.7.1.2.2.1.4.3.2.27
		sheRuleControlTosMatch OBJECT-TYPE
			SYNTAX SheRuleMatchType
			MAX-ACCESS read-write
			STATUS current
			DESCRIPTION
				"look at rule table..."
			::= { sheRuleControl 27 }

		
--   1.3.6.1.4.1.231.7.1.2.2.1.4.3.2.28
		sheRuleControlDscpPattern OBJECT-TYPE
			SYNTAX INTEGER (0..63)
			MAX-ACCESS read-write
			STATUS current
			DESCRIPTION
				"look at rule table..."
			::= { sheRuleControl 28 }

		
--   1.3.6.1.4.1.231.7.1.2.2.1.4.3.2.29
		sheRuleControlDscpMatch OBJECT-TYPE
			SYNTAX SheRuleMatchType
			MAX-ACCESS read-write
			STATUS current
			DESCRIPTION
				"look at rule table..."
			::= { sheRuleControl 29 }

		
--   1.3.6.1.4.1.231.7.1.2.2.1.4.3.2.30
		sheRuleControlEtherTypePattern OBJECT-TYPE
			SYNTAX OCTET STRING (SIZE (2))
			MAX-ACCESS read-write
			STATUS current
			DESCRIPTION
				"look at rule table..."
			::= { sheRuleControl 30 }

		
--   1.3.6.1.4.1.231.7.1.2.2.1.4.3.2.31
		sheRuleControlEtherTypeMatch OBJECT-TYPE
			SYNTAX SheRuleMatchType
			MAX-ACCESS read-write
			STATUS current
			DESCRIPTION
				"look at rule table..."
			::= { sheRuleControl 31 }

		
--   1.3.6.1.4.1.231.7.1.2.2.1.4.3.2.32
		sheRuleControlSourceIpAddressPattern OBJECT-TYPE
			SYNTAX OCTET STRING (SIZE (4))
			MAX-ACCESS read-write
			STATUS current
			DESCRIPTION
				"look at rule table..."
			::= { sheRuleControl 32 }

		
--   1.3.6.1.4.1.231.7.1.2.2.1.4.3.2.33
		sheRuleControlSourceIpAddressMatch OBJECT-TYPE
			SYNTAX SheRuleMatchType
			MAX-ACCESS read-write
			STATUS current
			DESCRIPTION
				"look at rule table..."
			::= { sheRuleControl 33 }

		
--   1.3.6.1.4.1.231.7.1.2.2.1.4.3.2.34
		sheRuleControlSourceIpSubnetMaskPattern OBJECT-TYPE
			SYNTAX OCTET STRING (SIZE (4))
			MAX-ACCESS read-write
			STATUS current
			DESCRIPTION
				"look at rule table..."
			::= { sheRuleControl 34 }

		
--   1.3.6.1.4.1.231.7.1.2.2.1.4.3.2.35
		sheRuleControlSourceIpSubnetMaskMatch OBJECT-TYPE
			SYNTAX SheRuleMatchType
			MAX-ACCESS read-write
			STATUS current
			DESCRIPTION
				"look at rule table..."
			::= { sheRuleControl 35 }

		
--   1.3.6.1.4.1.231.7.1.2.2.1.4.3.2.36
		sheRuleControlDestinationIpAddressPattern OBJECT-TYPE
			SYNTAX OCTET STRING (SIZE (4))
			MAX-ACCESS read-write
			STATUS current
			DESCRIPTION
				"look at rule table..."
			::= { sheRuleControl 36 }

		
--   1.3.6.1.4.1.231.7.1.2.2.1.4.3.2.37
		sheRuleControlDestinationIpAddressMatch OBJECT-TYPE
			SYNTAX SheRuleMatchType
			MAX-ACCESS read-write
			STATUS current
			DESCRIPTION
				"look at rule table..."
			::= { sheRuleControl 37 }

		
--   1.3.6.1.4.1.231.7.1.2.2.1.4.3.2.38
		sheRuleControlDestinationIpSubnetMaskPattern OBJECT-TYPE
			SYNTAX OCTET STRING (SIZE (4))
			MAX-ACCESS read-write
			STATUS current
			DESCRIPTION
				"look at rule table..."
			::= { sheRuleControl 38 }

		
--   1.3.6.1.4.1.231.7.1.2.2.1.4.3.2.39
		sheRuleControlDestinationIpSubnetMaskMatch OBJECT-TYPE
			SYNTAX SheRuleMatchType
			MAX-ACCESS read-write
			STATUS current
			DESCRIPTION
				"look at rule table..."
			::= { sheRuleControl 39 }

		
--   1.3.6.1.4.1.231.7.1.2.2.1.4.3.2.40
		sheRuleControlSourcePortPattern OBJECT-TYPE
			SYNTAX Integer32
			MAX-ACCESS read-write
			STATUS current
			DESCRIPTION
				"look at rule table..."
			::= { sheRuleControl 40 }

		
--   1.3.6.1.4.1.231.7.1.2.2.1.4.3.2.41
		sheRuleControlSourcePortMatch OBJECT-TYPE
			SYNTAX SheRuleMatchType
			MAX-ACCESS read-write
			STATUS current
			DESCRIPTION
				"look at rule table..."
			::= { sheRuleControl 41 }

		
--   1.3.6.1.4.1.231.7.1.2.2.1.4.3.2.42
		sheRuleControlDestinationPortPattern OBJECT-TYPE
			SYNTAX Integer32
			MAX-ACCESS read-write
			STATUS current
			DESCRIPTION
				"look at rule table..."
			::= { sheRuleControl 42 }

		
--   1.3.6.1.4.1.231.7.1.2.2.1.4.3.2.43
		sheRuleControlDestinationPortMatch OBJECT-TYPE
			SYNTAX SheRuleMatchType
			MAX-ACCESS read-write
			STATUS current
			DESCRIPTION
				"look at rule table..."
			::= { sheRuleControl 43 }

		
--   1.3.6.1.4.1.231.7.1.2.2.1.4.3.2.44
		sheRuleControlAction OBJECT-TYPE
			SYNTAX SheRuleActionType
			MAX-ACCESS read-write
			STATUS current
			DESCRIPTION
				"look at rule table..."
			::= { sheRuleControl 44 }

		
--   1.3.6.1.4.1.231.7.1.2.2.1.4.3.2.45
		sheRuleControlActionParameter01 OBJECT-TYPE
			SYNTAX Integer32
			MAX-ACCESS read-write
			STATUS current
			DESCRIPTION
				"look at rule table..."
			::= { sheRuleControl 45 }

		
--   1.3.6.1.4.1.231.7.1.2.2.1.4.3.2.46
		sheRuleControlActionParameter02 OBJECT-TYPE
			SYNTAX Integer32
			MAX-ACCESS read-write
			STATUS current
			DESCRIPTION
				"look at rule table..."
			::= { sheRuleControl 46 }

		
--   1.3.6.1.4.1.231.7.1.2.2.1.4.3.2.47
		sheRuleControlFlowPattern OBJECT-TYPE
			SYNTAX SheRuleFlowType
			MAX-ACCESS read-write
			STATUS current
			DESCRIPTION
				"look at rule table..."
			::= { sheRuleControl 47 }

		
--   1.3.6.1.4.1.231.7.1.2.2.1.4.3.2.48
		sheRuleControlFlowMatch OBJECT-TYPE
			SYNTAX SheRuleMatchType
			MAX-ACCESS read-write
			STATUS current
			DESCRIPTION
				"look at rule table..."
			::= { sheRuleControl 48 }

		
--   1.3.6.1.4.1.231.7.1.2.2.1.4.3.2.49
		sheRuleControlIpProtocolPattern OBJECT-TYPE
			SYNTAX Unsigned32 (0..255)
			MAX-ACCESS read-write
			STATUS current
			DESCRIPTION
				"look at table"
			::= { sheRuleControl 49 }

		
--   1.3.6.1.4.1.231.7.1.2.2.1.4.3.2.50
		sheRuleControlIpProtocolMatch OBJECT-TYPE
			SYNTAX SheRuleMatchType
			MAX-ACCESS read-write
			STATUS current
			DESCRIPTION
				"look at table"
			::= { sheRuleControl 50 }

		
--   1.3.6.1.4.1.231.7.1.2.2.1.4.3.2.51
		sheRuleControlIpPrecedencePattern OBJECT-TYPE
			SYNTAX Unsigned32 (0..7)
			MAX-ACCESS read-write
			STATUS current
			DESCRIPTION
				"look at table"
			::= { sheRuleControl 51 }

		
--   1.3.6.1.4.1.231.7.1.2.2.1.4.3.2.52
		sheRuleControlIpPrecedenceMatch OBJECT-TYPE
			SYNTAX SheRuleMatchType
			MAX-ACCESS read-write
			STATUS current
			DESCRIPTION
				"look at table"
			::= { sheRuleControl 52 }

		
--   1.3.6.1.4.1.231.7.1.2.2.1.4.3.2.53
		sheRuleControlSourceMacMaskPattern OBJECT-TYPE
			SYNTAX OCTET STRING (SIZE (1..6))
			MAX-ACCESS read-write
			STATUS current
			DESCRIPTION
				"look at table"
			::= { sheRuleControl 53 }

		
--   1.3.6.1.4.1.231.7.1.2.2.1.4.3.2.54
		sheRuleControlSourceMacMaskMatch OBJECT-TYPE
			SYNTAX SheRuleMatchType
			MAX-ACCESS read-write
			STATUS current
			DESCRIPTION
				"look at table"
			::= { sheRuleControl 54 }

		
--   1.3.6.1.4.1.231.7.1.2.2.1.4.3.2.55
		sheRuleControlDestinationMacMaskPattern OBJECT-TYPE
			SYNTAX OCTET STRING (SIZE (1..6))
			MAX-ACCESS read-write
			STATUS current
			DESCRIPTION
				"look at table"
			::= { sheRuleControl 55 }

		
--   1.3.6.1.4.1.231.7.1.2.2.1.4.3.2.56
		sheRuleControlDestinationMacMaskMatch OBJECT-TYPE
			SYNTAX SheRuleMatchType
			MAX-ACCESS read-write
			STATUS current
			DESCRIPTION
				"look at table"
			::= { sheRuleControl 56 }

		
--   1.3.6.1.4.1.231.7.1.2.2.1.4.3.2.57
		sheRuleControlMessageTypePattern OBJECT-TYPE
			SYNTAX Integer32
			MAX-ACCESS read-write
			STATUS current
			DESCRIPTION
				"look at table"
			::= { sheRuleControl 57 }

		
--   1.3.6.1.4.1.231.7.1.2.2.1.4.3.2.58
		sheRuleControlMessageTypeMatch OBJECT-TYPE
			SYNTAX SheRuleMatchType
			MAX-ACCESS read-write
			STATUS current
			DESCRIPTION
				"look at table"
			::= { sheRuleControl 58 }

		
--   1.3.6.1.4.1.231.7.1.2.2.1.4.3.2.59
		sheRuleControlMessageCodePattern OBJECT-TYPE
			SYNTAX Integer32
			MAX-ACCESS read-write
			STATUS current
			DESCRIPTION
				"look at table"
			::= { sheRuleControl 59 }

		
--   1.3.6.1.4.1.231.7.1.2.2.1.4.3.2.60
		sheRuleControlMessageCodeMatch OBJECT-TYPE
			SYNTAX SheRuleMatchType
			MAX-ACCESS read-write
			STATUS current
			DESCRIPTION
				"look at table"
			::= { sheRuleControl 60 }

		
--   1.3.6.1.4.1.231.7.1.2.2.1.4.3.2.61
		sheRuleControlGenericMatchAction OBJECT-TYPE
			SYNTAX SheRuleGenericActionType
			MAX-ACCESS read-write
			STATUS current
			DESCRIPTION
				"look at rule table..."
			::= { sheRuleControl 61 }

		
--   1.3.6.1.4.1.231.7.1.2.2.1.4.3.2.62
		sheRuleControlGenericNoMatchAction OBJECT-TYPE
			SYNTAX SheRuleGenericActionType
			MAX-ACCESS read-write
			STATUS current
			DESCRIPTION
				"look at rule table..."
			::= { sheRuleControl 62 }

		
--   1.3.6.1.4.1.231.7.1.2.2.1.4.3.2.63
		sheRuleControlGenericMatchActionParameterMeterIndex OBJECT-TYPE
			SYNTAX Unsigned32
			MAX-ACCESS read-write
			STATUS current
			DESCRIPTION
				"look at table"
			::= { sheRuleControl 63 }

		
--   1.3.6.1.4.1.231.7.1.2.2.1.4.3.2.64
		sheRuleControlGenericMatchActionParameterRedirPort OBJECT-TYPE
			SYNTAX Unsigned32
			MAX-ACCESS read-write
			STATUS current
			DESCRIPTION
				"look at table"
			::= { sheRuleControl 64 }

		
--   1.3.6.1.4.1.231.7.1.2.2.1.4.3.2.65
		sheRuleControlGenericMatchActionParameterDscp OBJECT-TYPE
			SYNTAX Unsigned32 (0..63)
			MAX-ACCESS read-write
			STATUS current
			DESCRIPTION
				"look at table"
			::= { sheRuleControl 65 }

		
--   1.3.6.1.4.1.231.7.1.2.2.1.4.3.2.66
		sheRuleControlGenericMatchActionParameterPriority OBJECT-TYPE
			SYNTAX Unsigned32 (0..7)
			MAX-ACCESS read-write
			STATUS current
			DESCRIPTION
				"look at table"
			::= { sheRuleControl 66 }

		
--   1.3.6.1.4.1.231.7.1.2.2.1.4.3.2.67
		sheRuleControlGenericMatchActionParameterTagPriority OBJECT-TYPE
			SYNTAX Unsigned32 (0..7)
			MAX-ACCESS read-write
			STATUS current
			DESCRIPTION
				"look at table"
			::= { sheRuleControl 67 }

		
--   1.3.6.1.4.1.231.7.1.2.2.1.4.3.2.68
		sheRuleControlGenericMatchActionParameterIpPrecedence OBJECT-TYPE
			SYNTAX Unsigned32
			MAX-ACCESS read-write
			STATUS current
			DESCRIPTION
				"look at table"
			::= { sheRuleControl 68 }

		
--   1.3.6.1.4.1.231.7.1.2.2.1.4.3.2.69
		sheRuleControlGenericMatchActionParameterRate OBJECT-TYPE
			SYNTAX Unsigned32
			UNITS "MBit/s"
			MAX-ACCESS read-write
			STATUS current
			DESCRIPTION
				"look at table"
			::= { sheRuleControl 69 }

		
--   1.3.6.1.4.1.231.7.1.2.2.1.4.3.2.70
		sheRuleControlGenericMatchActionParameterVlanId OBJECT-TYPE
			SYNTAX Unsigned32 (1..4093)
			MAX-ACCESS read-write
			STATUS current
			DESCRIPTION
				"look at table"
			::= { sheRuleControl 70 }

		
--   1.3.6.1.4.1.231.7.1.2.2.1.4.3.2.71
		sheRuleControlGenericNoMatchActionParameterMeterIndex OBJECT-TYPE
			SYNTAX Unsigned32
			MAX-ACCESS read-write
			STATUS current
			DESCRIPTION
				"look at table"
			::= { sheRuleControl 71 }

		
--   1.3.6.1.4.1.231.7.1.2.2.1.4.3.2.72
		sheRuleControlGenericNoMatchActionParameterRedirPort OBJECT-TYPE
			SYNTAX Unsigned32
			MAX-ACCESS read-write
			STATUS current
			DESCRIPTION
				"look at table"
			::= { sheRuleControl 72 }

		
--   1.3.6.1.4.1.231.7.1.2.2.1.4.3.2.73
		sheRuleControlGenericNoMatchActionParameterDscp OBJECT-TYPE
			SYNTAX Unsigned32 (0..63)
			MAX-ACCESS read-write
			STATUS current
			DESCRIPTION
				"look at table"
			::= { sheRuleControl 73 }

		
--   1.3.6.1.4.1.231.7.1.2.2.1.4.3.2.74
		sheRuleControlGenericNoMatchActionParameterPriority OBJECT-TYPE
			SYNTAX Unsigned32 (0..7)
			MAX-ACCESS read-write
			STATUS current
			DESCRIPTION
				"look at table"
			::= { sheRuleControl 74 }

		
--   1.3.6.1.4.1.231.7.1.2.2.1.4.3.2.75
		sheRuleControlGenericNoMatchActionParameterTagPriority OBJECT-TYPE
			SYNTAX Unsigned32 (0..7)
			MAX-ACCESS read-write
			STATUS current
			DESCRIPTION
				"look at table"
			::= { sheRuleControl 75 }

		
--   1.3.6.1.4.1.231.7.1.2.2.1.4.3.2.76
		sheRuleControlGenericNoMatchActionParameterIpPrecedence OBJECT-TYPE
			SYNTAX Unsigned32
			MAX-ACCESS read-write
			STATUS current
			DESCRIPTION
				"look at table"
			::= { sheRuleControl 76 }

		
--   1.3.6.1.4.1.231.7.1.2.2.1.4.3.2.77
		sheRuleControlGenericNoMatchActionParameterRate OBJECT-TYPE
			SYNTAX Unsigned32
			UNITS "MBit/s"
			MAX-ACCESS read-write
			STATUS current
			DESCRIPTION
				"look at table"
			::= { sheRuleControl 77 }

		
--   1.3.6.1.4.1.231.7.1.2.2.1.4.3.2.78
		sheRuleControlGenericNoMatchActionParameterVlanId OBJECT-TYPE
			SYNTAX Unsigned32 (1..4093)
			MAX-ACCESS read-write
			STATUS current
			DESCRIPTION
				"look at table"
			::= { sheRuleControl 78 }

		
--   1.3.6.1.4.1.231.7.1.2.2.1.4.3.2.79
		sheRuleControlInnerVlanIdPattern OBJECT-TYPE
			SYNTAX Integer32 (1..4093)
			MAX-ACCESS read-write
			STATUS current
			DESCRIPTION
				"Match the inner vlanid under double-tag mode."
			::= { sheRuleControl 79 }

		
--   1.3.6.1.4.1.231.7.1.2.2.1.4.3.2.80
		sheRuleControlInnerVlanIdMatch OBJECT-TYPE
			SYNTAX SheRuleMatchType
			MAX-ACCESS read-write
			STATUS current
			DESCRIPTION
				"look at table"
			::= { sheRuleControl 80 }

		
--   1.3.6.1.4.1.231.7.1.2.2.1.4.3.2.81
		sheRuleControlInnerPriorityPattern OBJECT-TYPE
			SYNTAX Integer32 (0..7)
			MAX-ACCESS read-write
			STATUS current
			DESCRIPTION
				"look at table"
			::= { sheRuleControl 81 }

		
--   1.3.6.1.4.1.231.7.1.2.2.1.4.3.2.82
		sheRuleControlInnerPriorityMatch OBJECT-TYPE
			SYNTAX SheRuleMatchType
			MAX-ACCESS read-write
			STATUS current
			DESCRIPTION
				"look at table"
			::= { sheRuleControl 82 }

		
--   1.3.6.1.4.1.231.7.1.2.2.1.4.3.2.85
		sheRuleControlIUPhysIndexPattern OBJECT-TYPE
			SYNTAX PhysicalIndex
			MAX-ACCESS read-write
			STATUS current
			DESCRIPTION
				"look at rule table..."
			::= { sheRuleControl 85 }

		
--   1.3.6.1.4.1.231.7.1.2.2.1.4.3.2.86
		sheRuleControlIUPhysIndexMatch OBJECT-TYPE
			SYNTAX SheRuleMatchType
			MAX-ACCESS read-write
			STATUS current
			DESCRIPTION
				"look at rule table..."
			::= { sheRuleControl 86 }

		
--   1.3.6.1.4.1.231.7.1.2.2.1.4.3.2.87
		sheRuleControlPortIfIndexPattern OBJECT-TYPE
			SYNTAX InterfaceIndex
			MAX-ACCESS read-write
			STATUS current
			DESCRIPTION
				"look at rule table..."
			::= { sheRuleControl 87 }

		
--   1.3.6.1.4.1.231.7.1.2.2.1.4.3.2.88
		sheRuleControlPortIfIndexMatch OBJECT-TYPE
			SYNTAX SheRuleMatchType
			MAX-ACCESS read-write
			STATUS current
			DESCRIPTION
				"look at rule table..."
			::= { sheRuleControl 88 }

		
--   1.3.6.1.4.1.231.7.1.2.2.1.4.3.3
		sheRuleNotifications OBJECT IDENTIFIER ::= { sheRulesAndMetering 3 }

		
--   1.3.6.1.4.1.231.7.1.2.2.1.4.3.3.1
		sheRuleCreated NOTIFICATION-TYPE
			OBJECTS { sheRuleControlIndex, sheRuleControlTimeStamp, sheRuleControlName, sheRuleControlType }
			STATUS current
			DESCRIPTION 
				"Configuration notification."
			::= { sheRuleNotifications 1 }

		
--   1.3.6.1.4.1.231.7.1.2.2.1.4.3.3.2
		sheRuleDeleted NOTIFICATION-TYPE
			OBJECTS { sheRuleControlIndex, sheRuleControlTimeStamp, sheRuleControlName }
			STATUS current
			DESCRIPTION 
				"Configuration notification."
			::= { sheRuleNotifications 2 }

		
--   1.3.6.1.4.1.231.7.1.2.2.1.4.3.3.3
		sheRuleModified NOTIFICATION-TYPE
			OBJECTS { sheRuleControlIndex, sheRuleControlTimeStamp, sheRuleControlType, sheRuleControlName }
			STATUS current
			DESCRIPTION 
				"Configuration notification."
			::= { sheRuleNotifications 3 }

		
--   1.3.6.1.4.1.231.7.1.2.2.1.4.3.4
		sheMeterProfileTable OBJECT-TYPE
			SYNTAX SEQUENCE OF SheMeterProfileEntry
			MAX-ACCESS not-accessible
			STATUS current
			DESCRIPTION
				"The meter profile table."
			::= { sheRulesAndMetering 4 }

		
--   1.3.6.1.4.1.231.7.1.2.2.1.4.3.4.1
		sheMeterProfileEntry OBJECT-TYPE
			SYNTAX SheMeterProfileEntry
			MAX-ACCESS not-accessible
			STATUS current
			DESCRIPTION
				"One entry for each metering profile. Selection of the used profile will
				be done via rule-configuration.
				
				Note:
				DS policing will currently not supported by the NE (information stand R2.8)!"
			INDEX { sheMeterProfileIndex }
			::= { sheMeterProfileTable 1 }

		
		SheMeterProfileEntry ::=
			SEQUENCE { 
				sheMeterProfileIndex
					Unsigned32,
				sheMeterProfileName
					OCTET STRING,
				sheMeterProfileCir
					Integer32,
				sheMeterProfileCbs
					Integer32,
				sheMeterProfilePir
					Integer32,
				sheMeterProfilePbs
					Integer32,
				sheMeterProfileDsCir
					Integer32,
				sheMeterProfileDsCbs
					Integer32,
				sheMeterProfileDsPir
					Integer32,
				sheMeterProfileDsPbs
					Integer32,
				sheMeterProfileUseParameters
					SheMeterProfileUseParametersType
			 }

--   1.3.6.1.4.1.231.7.1.2.2.1.4.3.4.1.1
		sheMeterProfileIndex OBJECT-TYPE
			SYNTAX Unsigned32 (1..65535)
			MAX-ACCESS read-only
			STATUS current
			DESCRIPTION
				"A profile-table index."
			::= { sheMeterProfileEntry 1 }

		
--   1.3.6.1.4.1.231.7.1.2.2.1.4.3.4.1.2
		sheMeterProfileName OBJECT-TYPE
			SYNTAX OCTET STRING (SIZE (0..255))
			MAX-ACCESS read-only
			STATUS current
			DESCRIPTION
				"A descriptional name for this metering profile.
				Spaces and other special characters (: o) are not allowed!! "
			::= { sheMeterProfileEntry 2 }

		
--   1.3.6.1.4.1.231.7.1.2.2.1.4.3.4.1.3
		sheMeterProfileCir OBJECT-TYPE
			SYNTAX Integer32 (0..100000)
			UNITS "kBit/s"
			MAX-ACCESS read-only
			STATUS current
			DESCRIPTION
				"The Committed Information Rate for upstream policing. 
				ATTENTION: CIR smaller or equal PIR"
			::= { sheMeterProfileEntry 3 }

		
--   1.3.6.1.4.1.231.7.1.2.2.1.4.3.4.1.4
		sheMeterProfileCbs OBJECT-TYPE
			SYNTAX Integer32 (96..10000)
			UNITS "Bytes"
			MAX-ACCESS read-only
			STATUS current
			DESCRIPTION
				"The Committed Burst Size for upstream policing. 
				ATTENTION: CBS smaller or equal PBS (MBS)"
			::= { sheMeterProfileEntry 4 }

		
--   1.3.6.1.4.1.231.7.1.2.2.1.4.3.4.1.5
		sheMeterProfilePir OBJECT-TYPE
			SYNTAX Integer32 (0..100000)
			UNITS "kBit/s"
			MAX-ACCESS read-only
			STATUS current
			DESCRIPTION
				"The peak information rate for upstream policing. 
				ATTENTION: CIR smaller or equal PIR"
			::= { sheMeterProfileEntry 5 }

		
--   1.3.6.1.4.1.231.7.1.2.2.1.4.3.4.1.6
		sheMeterProfilePbs OBJECT-TYPE
			SYNTAX Integer32 (96..15000)
			UNITS "Bytes"
			MAX-ACCESS read-only
			STATUS current
			DESCRIPTION
				"The peak burst size (or maximum burst size MBS) for upstream policing.
				ATTENTION: CBS smaller or equal PBS (MBS)"
			::= { sheMeterProfileEntry 6 }

		
--   1.3.6.1.4.1.231.7.1.2.2.1.4.3.4.1.7
		sheMeterProfileDsCir OBJECT-TYPE
			SYNTAX Integer32 (0..100000)
			UNITS "kBit/s"
			MAX-ACCESS read-only
			STATUS current
			DESCRIPTION
				"The Committed Information Rate for downstream policing. 
				ATTENTION: DsCIR smaller or equal DsPIR"
			::= { sheMeterProfileEntry 7 }

		
--   1.3.6.1.4.1.231.7.1.2.2.1.4.3.4.1.8
		sheMeterProfileDsCbs OBJECT-TYPE
			SYNTAX Integer32 (96..10000)
			UNITS "Bytes"
			MAX-ACCESS read-only
			STATUS current
			DESCRIPTION
				"The Committed Burst Size for downstream policing.
				ATTENTION: DsCBS smaller or equal DsPBS (MBS)"
			::= { sheMeterProfileEntry 8 }

		
--   1.3.6.1.4.1.231.7.1.2.2.1.4.3.4.1.9
		sheMeterProfileDsPir OBJECT-TYPE
			SYNTAX Integer32 (0..100000)
			UNITS "kBit/s"
			MAX-ACCESS read-only
			STATUS current
			DESCRIPTION
				"The peak information rate for downstream policing.
				ATTENTION: DsCIR smaller or equal DsPIR"
			::= { sheMeterProfileEntry 9 }

		
--   1.3.6.1.4.1.231.7.1.2.2.1.4.3.4.1.10
		sheMeterProfileDsPbs OBJECT-TYPE
			SYNTAX Integer32 (96..15000)
			UNITS "Bytes"
			MAX-ACCESS read-only
			STATUS current
			DESCRIPTION
				"The peak burst size (or maximum burst size MBS) for downstream policing.
				ATTENTION: DsCBS smaller or equal DsPBS (MBS)"
			::= { sheMeterProfileEntry 10 }

		
--   1.3.6.1.4.1.231.7.1.2.2.1.4.3.4.1.13
		sheMeterProfileUseParameters OBJECT-TYPE
			SYNTAX SheMeterProfileUseParametersType
			MAX-ACCESS read-only
			STATUS current
			DESCRIPTION
				"This defines a bit-map for using the meterprofile parameter settings.
				If the corresponding bit is set to one the parameters should be used.
				
				 - policingUS(0)
				 - policingDS(1)
				
				Note:
				DS policing will currently not supported by the NE (information stand R2.8)!"
			::= { sheMeterProfileEntry 13 }

		
--   1.3.6.1.4.1.231.7.1.2.2.1.4.3.5
		sheMeterControl OBJECT IDENTIFIER ::= { sheRulesAndMetering 5 }

		
--   1.3.6.1.4.1.231.7.1.2.2.1.4.3.5.1
		sheMeterControlRequest OBJECT-TYPE
			SYNTAX SheBridgeControlRequestType
			MAX-ACCESS read-write
			STATUS current
			DESCRIPTION
				"createMeterProfile:
				sheMeterControlProfileName
				sheMeterControlProfileCir
				sheMeterControlProfileCbs
				sheMeterControlProfilePir
				sheMeterControlProfilePbs
				sheMeterControlProfileDsCir
				sheMeterControlProfileDsCbs
				sheMeterControlProfileDsPir
				sheMeterControlProfileDsPbs
				sheMeterControlProfileDsShapingCir
				sheMeterControlProfileDsShapingCbs
				sheMeterControlProfileUseParameters
				
				deleteMeterProfile:
				sheMeterControlIndex
				
				modifyMeterProfile:
				sheMeterControlIndex
				sheMeterControlProfileName
				sheMeterControlProfileCir
				sheMeterControlProfileCbs
				sheMeterControlProfilePir
				sheMeterControlProfilePbs
				sheMeterControlProfileDsCir
				sheMeterControlProfileDsCbs
				sheMeterControlProfileDsPir
				sheMeterControlProfileDsPbs
				sheMeterControlProfileDsShapingCir
				sheMeterControlProfileDsShapingCbs
				sheMeterControlProfileUseParameters
				"
			::= { sheMeterControl 1 }

		
--   1.3.6.1.4.1.231.7.1.2.2.1.4.3.5.2
		sheMeterControlIndex OBJECT-TYPE
			SYNTAX Unsigned32
			MAX-ACCESS read-write
			STATUS current
			DESCRIPTION
				"Index of the configured table entry. Needed for modify or delete."
			::= { sheMeterControl 2 }

		
--   1.3.6.1.4.1.231.7.1.2.2.1.4.3.5.3
		sheMeterControlStatus OBJECT-TYPE
			SYNTAX SheControlStatusType
			MAX-ACCESS read-only
			STATUS current
			DESCRIPTION
				"The status of a user command. 
				"
			::= { sheMeterControl 3 }

		
--   1.3.6.1.4.1.231.7.1.2.2.1.4.3.5.4
		sheMeterControlTimer OBJECT-TYPE
			SYNTAX Gauge32
			MAX-ACCESS read-only
			STATUS current
			DESCRIPTION
				"The maximum wait time for the manager for a long running user command. 
				"
			::= { sheMeterControl 4 }

		
--    
-- 1.3.6.1.4.1.231.7.1.2.2.1.4.3.5.5
		sheMeterControlReqResult OBJECT-TYPE
			SYNTAX SheBridgeControlReqResultType
			MAX-ACCESS read-only
			STATUS current
			DESCRIPTION
				"The result of the last user command."
			::= { sheMeterControl 5 }

		
--   1.3.6.1.4.1.231.7.1.2.2.1.4.3.5.6
		sheMeterControlTimeStamp OBJECT-TYPE
			SYNTAX Unsigned32
			UNITS "sec"
			MAX-ACCESS read-only
			STATUS current
			DESCRIPTION
				"The time stamp of the last command (end of command)."
			::= { sheMeterControl 6 }

		
--   1.3.6.1.4.1.231.7.1.2.2.1.4.3.5.7
		sheMeterControlProfileName OBJECT-TYPE
			SYNTAX OCTET STRING (SIZE (0..255))
			MAX-ACCESS read-write
			STATUS current
			DESCRIPTION
				"look at meterProfileTable...
				Spaces and other special characters (: o) are not allowed!! "
			::= { sheMeterControl 7 }

		
--   1.3.6.1.4.1.231.7.1.2.2.1.4.3.5.8
		sheMeterControlProfileCir OBJECT-TYPE
			SYNTAX Integer32 (0..100000)
			UNITS "kBit/s"
			MAX-ACCESS read-write
			STATUS current
			DESCRIPTION
				"look at meterProfileTable..."
			::= { sheMeterControl 8 }

		
--   1.3.6.1.4.1.231.7.1.2.2.1.4.3.5.9
		sheMeterControlProfileCbs OBJECT-TYPE
			SYNTAX Integer32 (96..10000)
			UNITS "Bytes"
			MAX-ACCESS read-write
			STATUS current
			DESCRIPTION
				"look at meterProfileTable..."
			::= { sheMeterControl 9 }

		
--   1.3.6.1.4.1.231.7.1.2.2.1.4.3.5.10
		sheMeterControlProfilePir OBJECT-TYPE
			SYNTAX Integer32 (0..100000)
			UNITS "kBit/s"
			MAX-ACCESS read-write
			STATUS current
			DESCRIPTION
				"look at meterProfileTable..."
			::= { sheMeterControl 10 }

		
--   1.3.6.1.4.1.231.7.1.2.2.1.4.3.5.11
		sheMeterControlProfilePbs OBJECT-TYPE
			SYNTAX Integer32 (96..15000)
			UNITS "Bytes"
			MAX-ACCESS read-write
			STATUS current
			DESCRIPTION
				"look at meterProfileTable..."
			::= { sheMeterControl 11 }

		
--   1.3.6.1.4.1.231.7.1.2.2.1.4.3.5.12
		sheMeterControlProfileDsCir OBJECT-TYPE
			SYNTAX Integer32 (0..100000)
			UNITS "kBit/s"
			MAX-ACCESS read-write
			STATUS current
			DESCRIPTION
				"look at meterProfileTable..."
			::= { sheMeterControl 12 }

		
--   1.3.6.1.4.1.231.7.1.2.2.1.4.3.5.13
		sheMeterControlProfileDsCbs OBJECT-TYPE
			SYNTAX Integer32 (96..10000)
			UNITS "Bytes"
			MAX-ACCESS read-write
			STATUS current
			DESCRIPTION
				"look at meterProfileTable..."
			::= { sheMeterControl 13 }

		
--   1.3.6.1.4.1.231.7.1.2.2.1.4.3.5.14
		sheMeterControlProfileDsPir OBJECT-TYPE
			SYNTAX Integer32 (0..100000)
			UNITS "kBit/s"
			MAX-ACCESS read-write
			STATUS current
			DESCRIPTION
				"look at meterProfileTable..."
			::= { sheMeterControl 14 }

		
--   1.3.6.1.4.1.231.7.1.2.2.1.4.3.5.15
		sheMeterControlProfileDsPbs OBJECT-TYPE
			SYNTAX Integer32 (96..15000)
			UNITS "Bytes"
			MAX-ACCESS read-write
			STATUS current
			DESCRIPTION
				"look at meterProfileTable..."
			::= { sheMeterControl 15 }

		
--   1.3.6.1.4.1.231.7.1.2.2.1.4.3.5.18
		sheMeterControlProfileUseParameters OBJECT-TYPE
			SYNTAX SheMeterProfileUseParametersType
			MAX-ACCESS read-write
			STATUS current
			DESCRIPTION
				"look at table"
			::= { sheMeterControl 18 }

		
--   1.3.6.1.4.1.231.7.1.2.2.1.4.3.6
		sheMeteringNotifications OBJECT IDENTIFIER ::= { sheRulesAndMetering 6 }

		
--   1.3.6.1.4.1.231.7.1.2.2.1.4.3.6.1
		sheMeteringProfileCreated NOTIFICATION-TYPE
			OBJECTS { sheMeterControlIndex, sheMeterControlTimeStamp, sheMeterControlProfileName, sheMeterControlProfileCir, sheMeterControlProfileCbs, 
				sheMeterControlProfilePir, sheMeterControlProfilePbs, sheMeterControlProfileDsCir, sheMeterControlProfileDsCbs, sheMeterControlProfileDsPir, 
				sheMeterControlProfileDsPbs, sheMeterControlProfileUseParameters }
			STATUS current
			DESCRIPTION 
				"Configuration notification."
			::= { sheMeteringNotifications 1 }

		
--    
-- 1.3.6.1.4.1.231.7.1.2.2.1.4.3.6.2
		sheMeteringProfileModified NOTIFICATION-TYPE
			OBJECTS { sheMeterControlIndex, sheMeterControlTimeStamp, sheMeterControlProfileName, sheMeterControlProfileCir, sheMeterControlProfileCbs, 
				sheMeterControlProfilePir, sheMeterControlProfilePbs, sheMeterControlProfileDsCir, sheMeterControlProfileDsCbs, sheMeterControlProfileDsPir, 
				sheMeterControlProfileDsPbs, sheMeterControlProfileUseParameters }
			STATUS current
			DESCRIPTION 
				"Configuration notification."
			::= { sheMeteringNotifications 2 }

		
--   1.3.6.1.4.1.231.7.1.2.2.1.4.3.6.3
		sheMeteringProfileDeleted NOTIFICATION-TYPE
			OBJECTS { sheMeterControlIndex, sheMeterControlTimeStamp, sheMeterControlProfileName }
			STATUS current
			DESCRIPTION 
				"Configuration notification."
			::= { sheMeteringNotifications 3 }

		
--   1.3.6.1.4.1.231.7.1.2.2.1.4.3.7
		sheRuleAndMeteringConformance OBJECT IDENTIFIER ::= { sheRulesAndMetering 100 }

		
--   1.3.6.1.4.1.231.7.1.2.2.1.4.3.7.1
		sheUserFlowAndMeteringCompliances OBJECT IDENTIFIER ::= { sheRuleAndMeteringConformance 1 }

		
--   1.3.6.1.4.1.231.7.1.2.2.1.4.3.7.1.1
-- this module
-- this module
		sheUserFlowAndMeteringCompliance MODULE-COMPLIANCE
			STATUS current
			DESCRIPTION 
				"Description."
			MODULE -- this module
				MANDATORY-GROUPS { sheRuleGroup, sheMeteringGroup, sheRuleControlGroup, sheMeteringControlGroup, sheRuleAndMeteringNotificationGroup
					 }
			::= { sheUserFlowAndMeteringCompliances 1 }

		
--   1.3.6.1.4.1.231.7.1.2.2.1.4.3.7.2
		sheUserFlowAndMeteringGroups OBJECT IDENTIFIER ::= { sheRuleAndMeteringConformance 2 }

		
--   1.3.6.1.4.1.231.7.1.2.2.1.4.3.7.2.1
		sheRuleGroup OBJECT-GROUP
			OBJECTS { sheRuleIndex, sheRuleName, sheRulePriority, sheRuleBridgePortPattern, sheRuleBridgePortMatch, 
				sheRuleSourceMacPattern, sheRuleSourceMacMatch, sheRuleSourceMacStartPattern, sheRuleSourceMacStopPattern, sheRuleSourceMacRangeMatch, 
				sheRuleDestinationMacPattern, sheRuleDestinationMacMatch, sheRuleDestinationMacStartPattern, sheRuleDestinationMacStopPattern, sheRuleDestinationMacRangeMatch, 
				sheRuleVlanIdPattern, sheRuleVlanIdMatch, sheRulePriorityPattern, sheRulePriorityMatch, sheRuleTosPattern, 
				sheRuleTosMatch, sheRuleDscpPattern, sheRuleDscpMatch, sheRuleEtherTypePattern, sheRuleEtherTypeMatch, 
				sheRuleSourceIpAddressPattern, sheRuleSourceIpAddressMatch, sheRuleSourceIpSubnetMaskPattern, sheRuleSourceIpSubnetMaskMatch, sheRuleDestinationIpAddressPattern, 
				sheRuleDestinationIpAddressMatch, sheRuleDestinationIpSubnetMaskPattern, sheRuleDestinationIpSubnetMaskMatch, sheRuleSourcePortPattern, sheRuleSourcePortMatch, 
				sheRuleDestinationPortPattern, sheRuleDestinationPortMatch, sheRuleFlowPattern, sheRuleFlowMatch, sheRuleIpProtocolPattern, 
				sheRuleIpPrecedencePattern, sheRuleIpPrecedenceMatch, sheRuleActivationState, sheRuleSourceMacMaskPattern, sheRuleSourceMacMaskMatch, 
				sheRuleDestinationMacMaskPattern, sheRuleDestinationMacMaskMatch, sheRuleMessageTypePattern, sheRuleMessageTypeMatch, sheRuleMessageCodePattern, 
				sheRuleMessageCodeMatch, sheRuleGenericMatchAction, sheRuleGenericNoMatchAction, sheRuleGenericMatchActionParameterMeterIndex, sheRuleGenericMatchActionParameterRedirPort, 
				sheRuleGenericMatchActionParameterDscp, sheRuleGenericMatchActionParameterPriority, sheRuleGenericMatchActionParameterTagPriority, sheRuleGenericMatchActionParameterIpPrecedence, sheRuleGenericMatchActionParameterRate, 
				sheRuleGenericMatchActionParameterVlanId, sheRuleGenericNoMatchActionParameterMeterIndex, sheRuleGenericNoMatchActionParameterRedirPort, sheRuleGenericNoMatchActionParameterDscp, sheRuleGenericNoMatchActionParameterPriority, 
				sheRuleGenericNoMatchActionParameterTagPriority, sheRuleGenericNoMatchActionParameterIpPrecedence, sheRuleGenericNoMatchActionParameterRate, sheRuleGenericNoMatchActionParameterVlanId, sheRuleMatchCounter, 
				sheRuleIUPhysIndexPattern, sheRuleIUPhysIndexMatch, sheRulePortIfIndexPattern, sheRulePortIfIndexMatch, sheRuleAction, 
				sheRuleType, sheRuleActionParameter01, sheRuleActionParameter02, sheRuleIpProtocolMatch, sheRuleInnerVlanIdPattern, 
				sheRuleInnerVlanIdMatch, sheRuleInnerPriorityPattern, sheRuleInnerPriorityMatch }
			STATUS current
			DESCRIPTION 
				"Description."
			::= { sheUserFlowAndMeteringGroups 1 }

		
--   1.3.6.1.4.1.231.7.1.2.2.1.4.3.7.2.2
		sheMeteringGroup OBJECT-GROUP
			OBJECTS { sheMeterProfileCir, sheMeterProfileCbs, sheMeterProfilePir, sheMeterProfileDsCir, sheMeterProfileDsCbs, 
				sheMeterProfileDsPir, sheMeterProfileDsPbs, sheMeterProfileUseParameters, sheMeterProfileName, sheMeterProfileIndex, 
				sheMeterProfilePbs }
			STATUS current
			DESCRIPTION 
				"Description."
			::= { sheUserFlowAndMeteringGroups 2 }

		
--   1.3.6.1.4.1.231.7.1.2.2.1.4.3.7.2.3
		sheRuleControlGroup OBJECT-GROUP
			OBJECTS { sheRuleControlRequest, sheRuleControlIndex, sheRuleControlStatus, sheRuleControlTimer, sheRuleControlReqResult, 
				sheRuleControlTimeStamp, sheRuleControlName, sheRuleControlBridgePortPattern, sheRuleControlBridgePortMatch, sheRuleControlSourceMacPattern, 
				sheRuleControlSourceMacMatch, sheRuleControlSourceMacStartPattern, sheRuleControlSourceMacStopPattern, sheRuleControlSourceMacRangeMatch, sheRuleControlDestinationMacPattern, 
				sheRuleControlDestinationMacMatch, sheRuleControlDestinationMacStartPattern, sheRuleControlDestinationMacStopPattern, sheRuleControlDestinationMacRangeMatch, sheRuleControlVlanIdPattern, 
				sheRuleControlVlanIdMatch, sheRuleControlPriorityPattern, sheRuleControlPriorityMatch, sheRuleControlTosPattern, sheRuleControlTosMatch, 
				sheRuleControlDscpPattern, sheRuleControlDscpMatch, sheRuleControlEtherTypePattern, sheRuleControlEtherTypeMatch, sheRuleControlSourceIpAddressPattern, 
				sheRuleControlSourceIpAddressMatch, sheRuleControlSourceIpSubnetMaskPattern, sheRuleControlSourceIpSubnetMaskMatch, sheRuleControlDestinationIpAddressPattern, sheRuleControlDestinationIpAddressMatch, 
				sheRuleControlDestinationIpSubnetMaskPattern, sheRuleControlDestinationIpSubnetMaskMatch, sheRuleControlSourcePortPattern, sheRuleControlSourcePortMatch, sheRuleControlDestinationPortPattern, 
				sheRuleControlDestinationPortMatch, sheRuleControlFlowPattern, sheRuleControlFlowMatch, sheRuleControlIpProtocolPattern, sheRuleControlIpProtocolMatch, 
				sheRuleControlIpPrecedencePattern, sheRuleControlIpPrecedenceMatch, sheRuleControlSourceMacMaskPattern, sheRuleControlSourceMacMaskMatch, sheRuleControlDestinationMacMaskPattern, 
				sheRuleControlDestinationMacMaskMatch, sheRuleControlMessageTypePattern, sheRuleControlMessageTypeMatch, sheRuleControlMessageCodePattern, sheRuleControlMessageCodeMatch, 
				sheRuleControlGenericMatchAction, sheRuleControlGenericNoMatchAction, sheRuleControlGenericMatchActionParameterMeterIndex, sheRuleControlGenericMatchActionParameterRedirPort, sheRuleControlGenericMatchActionParameterDscp, 
				sheRuleControlGenericMatchActionParameterPriority, sheRuleControlGenericMatchActionParameterTagPriority, sheRuleControlGenericMatchActionParameterIpPrecedence, sheRuleControlGenericMatchActionParameterRate, sheRuleControlGenericMatchActionParameterVlanId, 
				sheRuleControlGenericNoMatchActionParameterMeterIndex, sheRuleControlGenericNoMatchActionParameterRedirPort, sheRuleControlGenericNoMatchActionParameterDscp, sheRuleControlGenericNoMatchActionParameterPriority, sheRuleControlGenericNoMatchActionParameterTagPriority, 
				sheRuleControlGenericNoMatchActionParameterIpPrecedence, sheRuleControlGenericNoMatchActionParameterRate, sheRuleControlGenericNoMatchActionParameterVlanId, sheRuleControlIUPhysIndexPattern, sheRuleControlIUPhysIndexMatch, 
				sheRuleControlPortIfIndexPattern, sheRuleControlPortIfIndexMatch, sheRuleControlAction, sheRuleControlType, sheRuleControlPriority, 
				sheRuleControlActionParameter01, sheRuleControlActionParameter02, sheRuleControlInnerVlanIdPattern, sheRuleControlInnerVlanIdMatch, sheRuleControlInnerPriorityPattern, 
				sheRuleControlInnerPriorityMatch }
			STATUS current
			DESCRIPTION 
				"Description."
			::= { sheUserFlowAndMeteringGroups 3 }

		
--   1.3.6.1.4.1.231.7.1.2.2.1.4.3.7.2.4
		sheMeteringControlGroup OBJECT-GROUP
			OBJECTS { sheMeterControlRequest, sheMeterControlIndex, sheMeterControlStatus, sheMeterControlTimer, sheMeterControlReqResult, 
				sheMeterControlTimeStamp, sheMeterControlProfileName, sheMeterControlProfileCir, sheMeterControlProfileCbs, sheMeterControlProfilePir, 
				sheMeterControlProfilePbs, sheMeterControlProfileDsCir, sheMeterControlProfileDsCbs, sheMeterControlProfileDsPir, sheMeterControlProfileDsPbs, 
				sheMeterControlProfileUseParameters }
			STATUS current
			DESCRIPTION 
				"Description."
			::= { sheUserFlowAndMeteringGroups 4 }

		
--   1.3.6.1.4.1.231.7.1.2.2.1.4.3.7.2.5
		sheRuleAndMeteringNotificationGroup NOTIFICATION-GROUP
			NOTIFICATIONS { sheMeteringProfileCreated, sheMeteringProfileDeleted, sheRuleModified, sheMeteringProfileModified, sheRuleCreated, 
				sheRuleDeleted }
			STATUS current
			DESCRIPTION 
				"Description."
			::= { sheUserFlowAndMeteringGroups 5 }

		
--   1.3.6.1.4.1.231.7.1.2.2.1.4.4
		sheFdb OBJECT IDENTIFIER ::= { sheBridgeMib 4 }

		
--   1.3.6.1.4.1.231.7.1.2.2.1.4.4.1
		sheFdbBase OBJECT IDENTIFIER ::= { sheFdb 1 }

		
--   1.3.6.1.4.1.231.7.1.2.2.1.4.4.1.1
		sheFdbBaseAgeingTime OBJECT-TYPE
			SYNTAX Unsigned32 (1..100000)
			UNITS "seconds"
			MAX-ACCESS read-only
			STATUS current
			DESCRIPTION
				"The general ageing time for learned Mac-addresses."
			::= { sheFdbBase 1 }

		
--   1.3.6.1.4.1.231.7.1.2.2.1.4.4.1.2
		sheFdbBaseLearningUplink OBJECT-TYPE
			SYNTAX TruthValue
			MAX-ACCESS read-only
			STATUS current
			DESCRIPTION
				"The global value that indicates whether to use a mac learning function for uplink."
			::= { sheFdbBase 2 }

		
--   1.3.6.1.4.1.231.7.1.2.2.1.4.4.2
		sheFdbTable OBJECT-TYPE
			SYNTAX SEQUENCE OF SheFdbEntry
			MAX-ACCESS not-accessible
			STATUS current
			DESCRIPTION
				"The forwarding data base table.
				
				New with R2.8 maintenance:
				This release introduces a new ControlRequest command for refresh of this table. 
				Without calling this command, the table content will be static and not longer automatically updated.
				The refresh command could be used together with the vlanIndex, which is the first table index here.
				If a valid vlanIndex value was used, only the tableEntries with this vlanIndex as first key will be
				refreshed. 
				If the vlanIndex is 0 or unknown the full table will be refreshed."
			::= { sheFdb 2 }

		
--   1.3.6.1.4.1.231.7.1.2.2.1.4.4.2.1
		sheFdbEntry OBJECT-TYPE
			SYNTAX SheFdbEntry
			MAX-ACCESS not-accessible
			STATUS current
			DESCRIPTION
				"One entry per learned mac-address per vlan. First key is the VlanIndex."
			INDEX { sheVlanFdbId, sheFdbIndex }
			::= { sheFdbTable 1 }

		
		SheFdbEntry ::=
			SEQUENCE { 
				sheFdbIndex
					Unsigned32,
				sheFdbMacAddress
					OCTET STRING,
				sheFdbPort
					INTEGER,
				sheFdbAge
					Unsigned32,
				sheFdbStatus
					SheFdbStatusType,
				sheFdbCpuPermit
					ShePermissionType,
				sheFdbPortPermit
					ShePermissionType
			 }

--   1.3.6.1.4.1.231.7.1.2.2.1.4.4.2.1.1
		sheFdbIndex OBJECT-TYPE
			SYNTAX Unsigned32 (1..65535)
			MAX-ACCESS read-only
			STATUS current
			DESCRIPTION
				"Second key for fdb-table. 
				Number of valid entrys is equal to number of current learned Mac-Addresses
				for vlan indeced by key 1."
			::= { sheFdbEntry 1 }

		
--   1.3.6.1.4.1.231.7.1.2.2.1.4.4.2.1.2
		sheFdbMacAddress OBJECT-TYPE
			SYNTAX OCTET STRING (SIZE (6))
			MAX-ACCESS read-only
			STATUS current
			DESCRIPTION
				"The learned mac-address."
			::= { sheFdbEntry 2 }

		
--   1.3.6.1.4.1.231.7.1.2.2.1.4.4.2.1.3
		sheFdbPort OBJECT-TYPE
			SYNTAX INTEGER (1..65535)
			MAX-ACCESS read-only
			STATUS current
			DESCRIPTION
				"That is the sheBridgePortIndex of the destination port."
			::= { sheFdbEntry 3 }

		
--   1.3.6.1.4.1.231.7.1.2.2.1.4.4.2.1.4
		sheFdbAge OBJECT-TYPE
			SYNTAX Unsigned32
			UNITS "second"
			MAX-ACCESS read-only
			STATUS current
			DESCRIPTION
				"Time this mac-address was learned."
			::= { sheFdbEntry 4 }

		
--   1.3.6.1.4.1.231.7.1.2.2.1.4.4.2.1.5
		sheFdbStatus OBJECT-TYPE
			SYNTAX SheFdbStatusType
			MAX-ACCESS read-only
			STATUS current
			DESCRIPTION
				"The status of this entry.  The meanings of the
				values are:
				
				  other(1)   : none of the following.
				  invalid(2) : this entry is not longer valid
				               (e.g., it was learned but has since
				               aged-out), but has not yet been
				               flushed from the table.
				
				  learned(3) : the value was learned, and is being used.
				
				  self(4)    : the value of the corresponding
				               instance of FdbAclAddress
				               represents one of the bridge's
				               addresses.
				
				  mgmt(5)    : 
				
				  static(6) : the value was not learned but fixed configured by operator
				"
			::= { sheFdbEntry 5 }

		
--   1.3.6.1.4.1.231.7.1.2.2.1.4.4.2.1.6
		sheFdbCpuPermit OBJECT-TYPE
			SYNTAX ShePermissionType
			MAX-ACCESS read-only
			STATUS current
			DESCRIPTION
				"Frames have the permission to be send to control plane."
			::= { sheFdbEntry 6 }

		
--   1.3.6.1.4.1.231.7.1.2.2.1.4.4.2.1.7
		sheFdbPortPermit OBJECT-TYPE
			SYNTAX ShePermissionType
			MAX-ACCESS read-only
			STATUS current
			DESCRIPTION
				"Frames have the permission to be send to data plane."
			::= { sheFdbEntry 7 }

		
--   1.3.6.1.4.1.231.7.1.2.2.1.4.4.3
		sheFdbControl OBJECT IDENTIFIER ::= { sheFdb 3 }

		
--   1.3.6.1.4.1.231.7.1.2.2.1.4.4.3.1
		sheFdbControlRequest OBJECT-TYPE
			SYNTAX SheBridgeControlRequestType
			MAX-ACCESS read-write
			STATUS current
			DESCRIPTION
				"setFdbBaseAgeingTime (401):
				sheFdbControlBaseAgeingTime
				
				setFdbBaseLearningUplink (402):
				sheFdbControlBaseLearningUplink
				                            
				
				New with R2.8 maintenance:
				refreshFdbTable (403):
				sheFdbControlIndex    -> define the vlan for which the Fdb should be updated,
				
				Only supported by hiX5608 R1.3!!
				createFdbStaticEntry(404):
				sheFdbControlIndex   -> define the vlan for which the FdbEntry should be created
				sheFdbControlPort    -> define the bridgePort-Index for which the FdbEntry should be created
				sheFdbControlMacAddress   -> define the used MacAddress 
				"
			::= { sheFdbControl 1 }

		
--   1.3.6.1.4.1.231.7.1.2.2.1.4.4.3.2
		sheFdbControlIndex OBJECT-TYPE
			SYNTAX Integer32
			MAX-ACCESS read-write
			STATUS current
			DESCRIPTION
				"Value depends on the used ControlRequest.
				"
			::= { sheFdbControl 2 }

		
--   1.3.6.1.4.1.231.7.1.2.2.1.4.4.3.3
		sheFdbControlStatus OBJECT-TYPE
			SYNTAX SheControlStatusType
			MAX-ACCESS read-only
			STATUS current
			DESCRIPTION
				"The status of a user command. 
				."
			::= { sheFdbControl 3 }

		
--   1.3.6.1.4.1.231.7.1.2.2.1.4.4.3.4
		sheFdbControlTimer OBJECT-TYPE
			SYNTAX Gauge32
			MAX-ACCESS read-only
			STATUS current
			DESCRIPTION
				"The maximum wait time for the manager for a long running user command. 
				"
			::= { sheFdbControl 4 }

		
--   1.3.6.1.4.1.231.7.1.2.2.1.4.4.3.5
		sheFdbControlReqResult OBJECT-TYPE
			SYNTAX SheBridgeControlReqResultType
			MAX-ACCESS read-only
			STATUS current
			DESCRIPTION
				"The result of the last user command."
			::= { sheFdbControl 5 }

		
--   1.3.6.1.4.1.231.7.1.2.2.1.4.4.3.6
		sheFdbControlTimeStamp OBJECT-TYPE
			SYNTAX Unsigned32
			UNITS "sec"
			MAX-ACCESS read-only
			STATUS current
			DESCRIPTION
				"The time stamp of the last command (end of command)."
			::= { sheFdbControl 6 }

		
--   1.3.6.1.4.1.231.7.1.2.2.1.4.4.3.7
		sheFdbControlBaseAgeingTime OBJECT-TYPE
			SYNTAX Unsigned32 (1..100000)
			UNITS "seconds"
			MAX-ACCESS read-write
			STATUS current
			DESCRIPTION
				"The values to be configured."
			::= { sheFdbControl 7 }

		
--   1.3.6.1.4.1.231.7.1.2.2.1.4.4.3.8
		sheFdbControlBaseLearningUplink OBJECT-TYPE
			SYNTAX TruthValue
			MAX-ACCESS read-write
			STATUS current
			DESCRIPTION
				"The values to be configured.
				True : enable mac learning for uplink
				False : disable mac learning for uplink
				"
			::= { sheFdbControl 8 }

		
		sheFdbControlPort OBJECT-TYPE
			SYNTAX Integer32 (0 | 1..65535)
			MAX-ACCESS read-write
			STATUS current
			DESCRIPTION
				"Define the bridgePort-Index for which the FdbEntry should be created/deleted.
				Value depends on the used ControlRequest.
				0 used as wildcard for 'ALL'
				
				NOTE:
				No support by BFR2.0 of R2.8 56xx!!
				Only supported by 5608 R1.3!!"
			::= { sheFdbControl 9 }

		
		sheFdbControlMacAddress OBJECT-TYPE
			SYNTAX OCTET STRING (SIZE (6))
			MAX-ACCESS read-write
			STATUS current
			DESCRIPTION
				"Define the MacAddress for configuration or delete.
				Value depends on the used ControlRequest.
				
				NOTE:
				No support by BFR2.0 of R2.8 56xx!!
				Only supported by 5608 R1.3!!"
			::= { sheFdbControl 10 }

		
--   1.3.6.1.4.1.231.7.1.2.2.1.4.4.4
		sheFdbNotifications OBJECT IDENTIFIER ::= { sheFdb 4 }

		
--   1.3.6.1.4.1.231.7.1.2.2.1.4.4.4.1
		sheFdbBaseAgeingTimeChanged NOTIFICATION-TYPE
			OBJECTS { sheFdbControlTimeStamp, sheFdbControlBaseAgeingTime }
			STATUS current
			DESCRIPTION 
				"Configuration Notification"
			::= { sheFdbNotifications 1 }

		
--   1.3.6.1.4.1.231.7.1.2.2.1.4.4.4.2
		sheFdbBaseLearningUplinkChanged NOTIFICATION-TYPE
			OBJECTS { sheFdbControlTimeStamp, sheFdbControlBaseLearningUplink }
			STATUS current
			DESCRIPTION 
				"Configuration Notification"
			::= { sheFdbNotifications 2 }

		
--   1.3.6.1.4.1.231.7.1.2.2.1.4.4.4.3
		sheFdbTableUpdated NOTIFICATION-TYPE
			OBJECTS { sheFdbControlTimeStamp, sheFdbControlIndex, sheFdbControlReqResult }
			STATUS current
			DESCRIPTION 
				"FDB table update finished."
			::= { sheFdbNotifications 3 }

		
--     1.3.6.1.4.1.231.7.1.2.2.1.4.4.4.4
		sheFdbStaticMacCreated NOTIFICATION-TYPE
			OBJECTS { sheFdbControlTimeStamp, sheFdbControlIndex, sheFdbControlPort, sheFdbControlMacAddress }
			STATUS current
			DESCRIPTION 
				"static FDB table entry created"
			::= { sheFdbNotifications 4 }

		
--   1.3.6.1.4.1.231.7.1.2.2.1.4.4.5
		sheFdbConformance OBJECT IDENTIFIER ::= { sheFdb 100 }

		
--   1.3.6.1.4.1.231.7.1.2.2.1.4.4.5.1
		sheFdbCompliances OBJECT IDENTIFIER ::= { sheFdbConformance 1 }

		
--   1.3.6.1.4.1.231.7.1.2.2.1.4.4.5.1.1
-- this module
-- this module
		sheFdbCompliance MODULE-COMPLIANCE
			STATUS current
			DESCRIPTION 
				"Description."
			MODULE -- this module
				MANDATORY-GROUPS { sheFdbBaseGroup, sheFdbGroup, sheFdbControlGroup, sheFdbNotificationGroup }
			::= { sheFdbCompliances 1 }

		
--   1.3.6.1.4.1.231.7.1.2.2.1.4.4.5.2
		sheFdbGroups OBJECT IDENTIFIER ::= { sheFdbConformance 2 }

		
--   1.3.6.1.4.1.231.7.1.2.2.1.4.4.5.2.1
		sheFdbBaseGroup OBJECT-GROUP
			OBJECTS { sheFdbBaseAgeingTime, sheFdbBaseLearningUplink }
			STATUS current
			DESCRIPTION 
				"Description."
			::= { sheFdbGroups 1 }

		
--   1.3.6.1.4.1.231.7.1.2.2.1.4.4.5.2.2
		sheFdbGroup OBJECT-GROUP
			OBJECTS { sheFdbIndex, sheFdbMacAddress, sheFdbPort, sheFdbAge, sheFdbStatus, 
				sheFdbCpuPermit, sheFdbPortPermit }
			STATUS current
			DESCRIPTION 
				"Description."
			::= { sheFdbGroups 2 }

		
--   1.3.6.1.4.1.231.7.1.2.2.1.4.4.5.2.3
		sheFdbControlGroup OBJECT-GROUP
			OBJECTS { sheFdbControlRequest, sheFdbControlIndex, sheFdbControlStatus, sheFdbControlBaseAgeingTime, sheFdbControlBaseLearningUplink, 
				sheFdbControlPort, sheFdbControlMacAddress, sheFdbControlTimeStamp, sheFdbControlTimer, sheFdbControlReqResult
				 }
			STATUS current
			DESCRIPTION 
				"Description."
			::= { sheFdbGroups 3 }

		
--   1.3.6.1.4.1.231.7.1.2.2.1.4.4.5.2.4
		sheFdbNotificationGroup NOTIFICATION-GROUP
			NOTIFICATIONS { sheFdbBaseAgeingTimeChanged, sheFdbBaseLearningUplinkChanged, sheFdbTableUpdated, sheFdbStaticMacCreated }
			STATUS current
			DESCRIPTION 
				"Description."
			::= { sheFdbGroups 4 }

		
--   1.3.6.1.4.1.231.7.1.2.2.1.4.5
		sheLag OBJECT IDENTIFIER ::= { sheBridgeMib 5 }

		
--   1.3.6.1.4.1.231.7.1.2.2.1.4.5.1
		sheLagGroupTable OBJECT-TYPE
			SYNTAX SEQUENCE OF SheLagGroupEntry
			MAX-ACCESS not-accessible
			STATUS current
			DESCRIPTION
				"Contain allways two entrys for possible available Lag-Groups."
			::= { sheLag 1 }

		
--   1.3.6.1.4.1.231.7.1.2.2.1.4.5.1.1
		sheLagGroupEntry OBJECT-TYPE
			SYNTAX SheLagGroupEntry
			MAX-ACCESS not-accessible
			STATUS current
			DESCRIPTION
				"One entry for each possible lag-group."
			INDEX { ifIndex }
			::= { sheLagGroupTable 1 }

		
		SheLagGroupEntry ::=
			SEQUENCE { 
				sheLagGroupMacAddress
					OCTET STRING,
				sheLagGroupActorSystemPriority
					Unsigned32,
				sheLagGroupActorSystemId
					OCTET STRING,
				sheLagGroupAggregateOrIndividual
					TruthValue,
				sheLagGroupActorAdminKey
					Integer32,
				sheLagGroupActorOperKey
					Integer32,
				sheLagGroupPartnerSystemId
					OCTET STRING,
				sheLagGroupPartnerSystemPriority
					Integer32,
				sheLagGroupPartnerOperKey
					Integer32,
				sheLagGroupCollectorMaxDelay
					Integer32,
				sheLagGroupLacpActivity
					TruthValue,
				sheLagGroupMethod
					SheLagMethodType,
				sheLagGroupPortList
					OCTET STRING,
				sheLagGroupEntPhysicalIndex
					PhysicalIndex
			 }

--   1.3.6.1.4.1.231.7.1.2.2.1.4.5.1.1.1
		sheLagGroupMacAddress OBJECT-TYPE
			SYNTAX OCTET STRING (SIZE (6))
			MAX-ACCESS read-only
			STATUS current
			DESCRIPTION
				"A 6-octet read-only value carrying the individual
				MAC address assigned to the Aggregator."
			REFERENCE
				"IEEE 802.3 Section 30.7.1.1.9"
			::= { sheLagGroupEntry 1 }

		
--   1.3.6.1.4.1.231.7.1.2.2.1.4.5.1.1.2
		sheLagGroupActorSystemPriority OBJECT-TYPE
			SYNTAX Unsigned32 (1..65535)
			MAX-ACCESS read-only
			STATUS current
			DESCRIPTION
				"A 2-octet value indicating the priority value
				associated with the Actor's System ID."
			REFERENCE
				"IEEE 802.3 Section 30.7.1.1.5"
			::= { sheLagGroupEntry 2 }

		
--   1.3.6.1.4.1.231.7.1.2.2.1.4.5.1.1.3
		sheLagGroupActorSystemId OBJECT-TYPE
			SYNTAX OCTET STRING (SIZE (6))
			MAX-ACCESS read-only
			STATUS current
			DESCRIPTION
				"A 6-octet read-write MAC address value used as a unique
				identifier for the System that contains this Aggregator."
			REFERENCE
				"IEEE 802.3 Section 30.7.1.1.4"
			::= { sheLagGroupEntry 3 }

		
--   1.3.6.1.4.1.231.7.1.2.2.1.4.5.1.1.4
		sheLagGroupAggregateOrIndividual OBJECT-TYPE
			SYNTAX TruthValue
			MAX-ACCESS read-only
			STATUS current
			DESCRIPTION
				"A read-only Boolean value indicating whether the
				Aggregator represents an Aggregate ('TRUE') or
				an Individual link ('FALSE')."
			REFERENCE
				"IEEE 802.3 Section 30.7.1.1.6"
			::= { sheLagGroupEntry 4 }

		
--   1.3.6.1.4.1.231.7.1.2.2.1.4.5.1.1.5
		sheLagGroupActorAdminKey OBJECT-TYPE
			SYNTAX Integer32 (0..15)
			MAX-ACCESS read-only
			STATUS current
			DESCRIPTION
				"The current administrative value of the Key for the Aggregator.
				The administrative Key value may differ from the operational
				Key value for the reasons discussed in 43.6.2. 
				The meaning of particular Key values is of local significance."
			REFERENCE
				"IEEE 802.3 Section 30.7.1.1.7"
			::= { sheLagGroupEntry 5 }

		
--   1.3.6.1.4.1.231.7.1.2.2.1.4.5.1.1.6
		sheLagGroupActorOperKey OBJECT-TYPE
			SYNTAX Integer32 (0..65535)
			MAX-ACCESS read-only
			STATUS current
			DESCRIPTION
				"The current operational value of the Key for the Aggregator.
				The administrative Key value may differ from the operational
				Key value for the reasons discussed in 43.6.2.
				This is a 16-bit, read-only value. The meaning of particular Key
				values is of local significance."
			REFERENCE
				"IEEE 802.3 Section 30.7.1.1.8"
			::= { sheLagGroupEntry 6 }

		
--   1.3.6.1.4.1.231.7.1.2.2.1.4.5.1.1.7
		sheLagGroupPartnerSystemId OBJECT-TYPE
			SYNTAX OCTET STRING (SIZE (6))
			MAX-ACCESS read-only
			STATUS current
			DESCRIPTION
				"A 6-octet read-only MAC address value consisting
				of the unique identifier for the current protocol Partner of
				this Aggregator. A value of zero indicates that there is no
				known Partner. If the aggregation is manually configured, this
				System ID value will be a value assigned by the local System."
			REFERENCE
				"IEEE 802.3 Section 30.7.1.1.10"
			::= { sheLagGroupEntry 7 }

		
--   1.3.6.1.4.1.231.7.1.2.2.1.4.5.1.1.8
		sheLagGroupPartnerSystemPriority OBJECT-TYPE
			SYNTAX Integer32 (1..65535)
			MAX-ACCESS read-only
			STATUS current
			DESCRIPTION
				"A 2-octet read-only value that indicates the priority
				value associated with the Partner's System ID. If the
				aggregation is manually configured, this System Priority value
				will be a value assigned by the local System."
			REFERENCE
				"IEEE 802.3 Section 30.7.1.1.11"
			::= { sheLagGroupEntry 8 }

		
--   1.3.6.1.4.1.231.7.1.2.2.1.4.5.1.1.9
		sheLagGroupPartnerOperKey OBJECT-TYPE
			SYNTAX Integer32
			MAX-ACCESS read-only
			STATUS current
			DESCRIPTION
				"The current operational value of the Key for the
				Aggregator's current protocol Partner. This is
				a 16-bit, read-only value. If the aggregation is manually
				configured, this Key value will be a value assigned by the
				local System."
			REFERENCE
				"IEEE 802.3 Section 30.7.1.1.12"
			::= { sheLagGroupEntry 9 }

		
--   1.3.6.1.4.1.231.7.1.2.2.1.4.5.1.1.10
		sheLagGroupCollectorMaxDelay OBJECT-TYPE
			SYNTAX Integer32 (0..65535)
			MAX-ACCESS read-only
			STATUS current
			DESCRIPTION
				"The value of this 16-bit attribute defines the maximum delay, in tens of microseconds,
				that may be imposed by the Frame Collector between receiving a frame from an
				Aggregator Parser and either delivering the frame to its MAC Client or discarding
				the frame (see 43.2.3.1.1).
				
				Note:
				R2.8 will not longer accept any modification of this parameter and use always NE internal value."
			REFERENCE
				"IEEE 802.3 Section 30.7.1.1.31"
			::= { sheLagGroupEntry 10 }

		
--   1.3.6.1.4.1.231.7.1.2.2.1.4.5.1.1.11
		sheLagGroupLacpActivity OBJECT-TYPE
			SYNTAX TruthValue
			MAX-ACCESS read-only
			STATUS current
			DESCRIPTION
				"This attribute will enable or disable LACP-Activity for this Lag-Group."
			DEFVAL { false }
			::= { sheLagGroupEntry 11 }

		
--   1.3.6.1.4.1.231.7.1.2.2.1.4.5.1.1.12
		sheLagGroupMethod OBJECT-TYPE
			SYNTAX SheLagMethodType
			MAX-ACCESS read-only
			STATUS current
			DESCRIPTION
				"Possible values:
				srcmac(1),
				dstmac(2),
				xormac(3),
				srcip(4),
				dstip(5),
				xorip(6)"
			::= { sheLagGroupEntry 12 }

		
--   1.3.6.1.4.1.231.7.1.2.2.1.4.5.1.1.13
		sheLagGroupPortList OBJECT-TYPE
			SYNTAX OCTET STRING (SIZE (0..65535))
			MAX-ACCESS read-only
			STATUS current
			DESCRIPTION
				"Portlist for all member's of this LAG.
				The octet string is a list of pairs of octets each identify
				an sheBridgePortIndex. The least significant byte is the
				second octet."
			REFERENCE
				"IEEE 802.3 Section 30.7.1.1.30"
			::= { sheLagGroupEntry 13 }

		
		sheLagGroupEntPhysicalIndex OBJECT-TYPE
			SYNTAX PhysicalIndex
			MAX-ACCESS read-only
			STATUS current
			DESCRIPTION
				"This attribute describes the entPhysicalIndex of the card, where this LAG group
				is placed. Only LagPorts with identical entPhysicalIndex for the card could be
				added to a group. 
				This information is given via:
				sheLagGroupPortList -> sheLagPortEntry -> sheBridgePortIndex -> sheSublayerIndex
				-> ifIndex -> shePhysPortEntPhysicalIndex"
			::= { sheLagGroupEntry 14 }

		
--   1.3.6.1.4.1.231.7.1.2.2.1.4.5.2
		sheLagPortTable OBJECT-TYPE
			SYNTAX SEQUENCE OF SheLagPortEntry
			MAX-ACCESS not-accessible
			STATUS current
			DESCRIPTION
				"A table that contains Link Aggregation Control
				configuration information about every
				Aggregation Port associated with this device.
				A row appears in this table for each physical port. 
				
				For she, this table will contain allways 4 entrys."
			::= { sheLag 2 }

		
--   1.3.6.1.4.1.231.7.1.2.2.1.4.5.2.1
		sheLagPortEntry OBJECT-TYPE
			SYNTAX SheLagPortEntry
			MAX-ACCESS not-accessible
			STATUS current
			DESCRIPTION
				"A list of Link Aggregation Control configuration
				parameters for each Aggregation Port on this device."
			INDEX { sheBridgePortIndex }
			::= { sheLagPortTable 1 }

		
		SheLagPortEntry ::=
			SEQUENCE { 
				sheLagPortActorSystemPriority
					Integer32,
				sheLagPortActorSystemId
					OCTET STRING,
				sheLagPortActorAdminKey
					Integer32,
				sheLagPortActorOperKey
					Integer32,
				sheLagPortPartnerAdminSystemPriority
					Integer32,
				sheLagPortPartnerOperSystemPriority
					Integer32,
				sheLagPortPartnerAdminSystemId
					OCTET STRING,
				sheLagPortPartnerOperSystemId
					OCTET STRING,
				sheLagPortPartnerAdminKey
					Integer32,
				sheLagPortPartnerOperKey
					Integer32,
				sheLagPortSelectedAggId
					Integer32,
				sheLagPortAttachedAggId
					Integer32,
				sheLagPortActorPort
					Integer32,
				sheLagPortActorPortPriority
					Integer32,
				sheLagPortPartnerAdminPort
					Integer32,
				sheLagPortPartnerOperPort
					Integer32,
				sheLagPortPartnerAdminPortPriority
					Integer32,
				sheLagPortPartnerOperPortPriority
					Integer32,
				sheLagPortActorAdminState
					SheLagStateType,
				sheLagPortActorOperState
					SheLagStateType,
				sheLagPortPartnerAdminState
					SheLagStateType,
				sheLagPortPartnerOperState
					SheLagStateType,
				sheLagPortAggregateOrIndividual
					TruthValue,
				sheLagPortLacpAvailability
					TruthValue
			 }

--   1.3.6.1.4.1.231.7.1.2.2.1.4.5.2.1.1
		sheLagPortActorSystemPriority OBJECT-TYPE
			SYNTAX Integer32 (0..65535)
			MAX-ACCESS read-only
			STATUS current
			DESCRIPTION
				"A 2-octet value used to define the priority
				value associated with the Actor's System ID."
			::= { sheLagPortEntry 1 }

		
--   1.3.6.1.4.1.231.7.1.2.2.1.4.5.2.1.2
		sheLagPortActorSystemId OBJECT-TYPE
			SYNTAX OCTET STRING (SIZE (6))
			MAX-ACCESS read-only
			STATUS current
			DESCRIPTION
				"A 6-octet read-only MAC address value that defines
				the value of the System ID for the System that contains this
				Aggregation Port."
			::= { sheLagPortEntry 2 }

		
--   1.3.6.1.4.1.231.7.1.2.2.1.4.5.2.1.3
		sheLagPortActorAdminKey OBJECT-TYPE
			SYNTAX Integer32
			MAX-ACCESS read-only
			STATUS current
			DESCRIPTION
				"The current administrative value of the Key for the
				Aggregation Port. This is a 16-bit, read-write value.
				The meaning of particular Key values is of local significance."
			::= { sheLagPortEntry 3 }

		
--   1.3.6.1.4.1.231.7.1.2.2.1.4.5.2.1.4
		sheLagPortActorOperKey OBJECT-TYPE
			SYNTAX Integer32
			MAX-ACCESS read-only
			STATUS current
			DESCRIPTION
				"The current operational value of the Key for the
				Aggregation Port. This is a 16-bit, read-only value.
				The meaning of particular Key values is of local significance."
			::= { sheLagPortEntry 4 }

		
--   1.3.6.1.4.1.231.7.1.2.2.1.4.5.2.1.5
		sheLagPortPartnerAdminSystemPriority OBJECT-TYPE
			SYNTAX Integer32 (0..65535)
			MAX-ACCESS read-only
			STATUS current
			DESCRIPTION
				"A 2-octet value used to define the administrative
				value of priority associated with the Partner's System ID. The
				assigned value is used, along with the value of
				PortPartnerAdminSystemID, PortPartnerAdminKey,
				PortPartnerAdminPort, and PortPartnerAdminPortPriority,
				in order to achieve manually configured aggregation."
			::= { sheLagPortEntry 5 }

		
--   1.3.6.1.4.1.231.7.1.2.2.1.4.5.2.1.6
		sheLagPortPartnerOperSystemPriority OBJECT-TYPE
			SYNTAX Integer32 (0..65535)
			MAX-ACCESS read-only
			STATUS current
			DESCRIPTION
				"A 2-octet read-only value indicating the operational value
				of priority associated with the Partner's System ID. The
				value of this attribute may contain the manually configured value
				carried in PortPartnerAdminSystemPriority
				if there is no protocol Partner."
			::= { sheLagPortEntry 6 }

		
--   1.3.6.1.4.1.231.7.1.2.2.1.4.5.2.1.7
		sheLagPortPartnerAdminSystemId OBJECT-TYPE
			SYNTAX OCTET STRING (SIZE (6))
			MAX-ACCESS read-only
			STATUS current
			DESCRIPTION
				"A 6-octet MACAddress value representing
				the administrative value of the Aggregation Port's protocol
				Partner's System ID. The assigned value is used, along with
				the value of PortPartnerAdminSystemPriority,
				PortPartnerAdminKey, PortPartnerAdminPort,
				and PortPartnerAdminPortPriority, in order to
				achieve manually configured aggregation."
			::= { sheLagPortEntry 7 }

		
--   1.3.6.1.4.1.231.7.1.2.2.1.4.5.2.1.8
		sheLagPortPartnerOperSystemId OBJECT-TYPE
			SYNTAX OCTET STRING (SIZE (6))
			MAX-ACCESS read-only
			STATUS current
			DESCRIPTION
				"A 6-octet read-only MACAddress value representing
				the current value of the Aggregation Port's protocol Partner's
				System ID. A value of zero indicates that there is no known
				protocol Partner. The value of this attribute may contain the
				manually configured value carried in
				PortPartnerAdminSystemID if there is no protocol Partner."
			::= { sheLagPortEntry 8 }

		
--   1.3.6.1.4.1.231.7.1.2.2.1.4.5.2.1.9
		sheLagPortPartnerAdminKey OBJECT-TYPE
			SYNTAX Integer32
			MAX-ACCESS read-only
			STATUS current
			DESCRIPTION
				"The current administrative value of the Key for the
				protocol Partner. This is a 16-bit, read-write value.
				The assigned value is used, along with the value of
				PortPartnerAdminSystemPriority, PortPartnerAdminSystemID,
				PortPartnerAdminPort, and PortPartnerAdminPortPriority,
				in order to achieve manually configured aggregation."
			::= { sheLagPortEntry 9 }

		
--   1.3.6.1.4.1.231.7.1.2.2.1.4.5.2.1.10
		sheLagPortPartnerOperKey OBJECT-TYPE
			SYNTAX Integer32
			MAX-ACCESS read-only
			STATUS current
			DESCRIPTION
				"The current operational value of the Key for the
				protocol Partner. The value of this attribute may contain
				the manually configured value carried in
				PortPartnerAdminKey if there is no protocol Partner.
				This is a 16-bit, read-only value."
			::= { sheLagPortEntry 10 }

		
--   1.3.6.1.4.1.231.7.1.2.2.1.4.5.2.1.11
		sheLagPortSelectedAggId OBJECT-TYPE
			SYNTAX Integer32
			MAX-ACCESS read-only
			STATUS current
			DESCRIPTION
				"The identifier value of the Aggregator that this Aggregation
				Port has currently selected. Zero indicates that the Aggregation
				Port has not selected an Aggregator, either because it is in the
				process of detaching from an Aggregator or because there is no
				suitable Aggregator available for it to select. This value is read-only."
			::= { sheLagPortEntry 11 }

		
--   1.3.6.1.4.1.231.7.1.2.2.1.4.5.2.1.12
		sheLagPortAttachedAggId OBJECT-TYPE
			SYNTAX Integer32
			MAX-ACCESS read-only
			STATUS current
			DESCRIPTION
				"The identifier value of the Aggregator that this Aggregation
				Port is currently attached to. Zero indicates that the Aggregation
				Port is not currently attached to an Aggregator. This value is read-only."
			::= { sheLagPortEntry 12 }

		
--   1.3.6.1.4.1.231.7.1.2.2.1.4.5.2.1.13
		sheLagPortActorPort OBJECT-TYPE
			SYNTAX Integer32 (0..65535)
			MAX-ACCESS read-only
			STATUS current
			DESCRIPTION
				"The port number locally assigned to the Aggregation Port.
				The port number is communicated in LACPDUs as the
				Actor_Port. This value is read-only."
			::= { sheLagPortEntry 13 }

		
--   1.3.6.1.4.1.231.7.1.2.2.1.4.5.2.1.14
		sheLagPortActorPortPriority OBJECT-TYPE
			SYNTAX Integer32 (0..65535)
			MAX-ACCESS read-only
			STATUS current
			DESCRIPTION
				"The priority value assigned to this Aggregation Port.
				This is a 2-octet value."
			::= { sheLagPortEntry 14 }

		
--   1.3.6.1.4.1.231.7.1.2.2.1.4.5.2.1.15
		sheLagPortPartnerAdminPort OBJECT-TYPE
			SYNTAX Integer32
			MAX-ACCESS read-only
			STATUS current
			DESCRIPTION
				"The current administrative value of the port number
				for the protocol Partner. This is a 16-bit value.
				The assigned value is used, along with the value of
				PortPartnerAdminSystemPriority,PortPartnerAdminSystemID, PartnerAdminKey,
				and PortPartnerAdminPortPriority,
				in order to achieve manually configured aggregation."
			::= { sheLagPortEntry 15 }

		
--   1.3.6.1.4.1.231.7.1.2.2.1.4.5.2.1.16
		sheLagPortPartnerOperPort OBJECT-TYPE
			SYNTAX Integer32
			MAX-ACCESS read-only
			STATUS current
			DESCRIPTION
				"The operational port number assigned to this Aggregation
				Port by the Aggregation Port's protocol Partner. The value
				of this attribute may contain the manually configured value
				carried in aAggPortPartnerAdminPort if there is no protocol
				Partner. This 16-bit value is read-only."
			::= { sheLagPortEntry 16 }

		
--   1.3.6.1.4.1.231.7.1.2.2.1.4.5.2.1.17
		sheLagPortPartnerAdminPortPriority OBJECT-TYPE
			SYNTAX Integer32 (0..65535)
			MAX-ACCESS read-only
			STATUS current
			DESCRIPTION
				"The current administrative value of the port priority
				for the protocol Partner. This is a 16-bit value.
				The assigned value is used, along with the value of
				PortPartnerAdminSystemPriority, PortPartnerAdminSystemID,
				PortPartnerAdminKey, and PortPartnerAdminPort,
				in order to achieve manually configured aggregation."
			::= { sheLagPortEntry 17 }

		
--   1.3.6.1.4.1.231.7.1.2.2.1.4.5.2.1.18
		sheLagPortPartnerOperPortPriority OBJECT-TYPE
			SYNTAX Integer32 (0..65535)
			MAX-ACCESS read-only
			STATUS current
			DESCRIPTION
				"The priority value assigned to this Aggregation Port
				by the Partner. The value of this attribute may contain the
				manually configured value carried in
				PortPartnerAdminPortPriority if there is no."
			::= { sheLagPortEntry 18 }

		
--   1.3.6.1.4.1.231.7.1.2.2.1.4.5.2.1.19
		sheLagPortActorAdminState OBJECT-TYPE
			SYNTAX SheLagStateType
			MAX-ACCESS read-only
			STATUS current
			DESCRIPTION
				"A string of 8 bits, corresponding to the administrative values
				of Actor_State (43.4.2) as transmitted by the Actor in LACPDUs.
				
				The first bit of string corresponds to bit 7 (Expired).
				If TRUE (encoded as a 1), this flag indicates that the Actor's
				receive machine is in the EXPIRED state
				
				The second of string bit corresponds to bit 6 (Defaulted).
				If TRUE (encoded as a 1), this flag indicates that the Actor's
				receive machine is using Defaulted operational Partner information,
				administratively configured for the Partner.
				
				The third of string bit corresponds to bit 5 (Distributing).
				FALSE (encoded as a 0) means distribution of outgoing frames
				on this link is definitely disabled.
				
				The fourth of string bit corresponds to bit 4(Collecting).
				TRUE (encoded as a 1) means collection of incoming frames on
				this link is definitely enabled.
				
				The fifth of string bit corresponds to bit 3 (Synchronization).
				If FALSE (encoded as a 0), then this link is currently OUT_OF_SYNC, 
				i.e., it is not in the right Aggregation.
				
				The sixth of string bit corresponds to bit 2 (Aggregation).
				If FALSE (encoded as a 0), the link is considered to be Individual, 
				 i.e., this link can be operated only as an individual link.
				
				The seventh of string bit corresponds to bit 1 (LACP_Timeout).
				Short Timeout is encoded as a 1; Long Timeout is encoded as a 0.
				
				The eighth of string bit corresponds to bit 0 of Actor_State (LACP_Activity).
				Active LACP is encoded as a 1; Passive LACP is encoded as a 0.
				
				The values of LACP_Activity,LACP_Timeout and Aggregation allow administrative
				control and could be set by controlgroup.
				"
			::= { sheLagPortEntry 19 }

		
--   1.3.6.1.4.1.231.7.1.2.2.1.4.5.2.1.20
		sheLagPortActorOperState OBJECT-TYPE
			SYNTAX SheLagStateType
			MAX-ACCESS read-only
			STATUS current
			DESCRIPTION
				"A string of 8 bits, corresponding to the current
				operational values of Actor_State as transmitted by the
				Actor in LACPDUs."
			::= { sheLagPortEntry 20 }

		
--   1.3.6.1.4.1.231.7.1.2.2.1.4.5.2.1.21
		sheLagPortPartnerAdminState OBJECT-TYPE
			SYNTAX SheLagStateType
			MAX-ACCESS read-only
			STATUS current
			DESCRIPTION
				"A string of 8 bits, corresponding to the current administrative
				value of Actor_State for the protocol Partner. The assigned value is used in order to achieve
				manually configured aggregation."
			::= { sheLagPortEntry 21 }

		
--   1.3.6.1.4.1.231.7.1.2.2.1.4.5.2.1.22
		sheLagPortPartnerOperState OBJECT-TYPE
			SYNTAX SheLagStateType
			MAX-ACCESS read-only
			STATUS current
			DESCRIPTION
				"A string of 8 bits, corresponding to the current values of
				Actor_State in the most recently received LACPDU transmitted
				by the protocol Partner. In the absence of an active protocol Partner, this
				value may reflect the manually configured value
				PortPartnerAdminState. This attribute value is read-only."
			::= { sheLagPortEntry 22 }

		
--   1.3.6.1.4.1.231.7.1.2.2.1.4.5.2.1.23
		sheLagPortAggregateOrIndividual OBJECT-TYPE
			SYNTAX TruthValue
			MAX-ACCESS read-only
			STATUS current
			DESCRIPTION
				"A read-only Boolean value indicating whether the
				Aggregation Port is able to Aggregate ('TRUE') or is
				only able to operate as an Individual link ('FALSE')."
			::= { sheLagPortEntry 23 }

		
--   1.3.6.1.4.1.231.7.1.2.2.1.4.5.2.1.24
		sheLagPortLacpAvailability OBJECT-TYPE
			SYNTAX TruthValue
			MAX-ACCESS read-only
			STATUS current
			DESCRIPTION
				"This attribute indicates, if this port is available for lacp or not."
			DEFVAL { false }
			::= { sheLagPortEntry 24 }

		
--   1.3.6.1.4.1.231.7.1.2.2.1.4.5.3
		sheLagControl OBJECT IDENTIFIER ::= { sheLag 3 }

		
--   1.3.6.1.4.1.231.7.1.2.2.1.4.5.3.1
		sheLagControlRequest OBJECT-TYPE
			SYNTAX SheBridgeControlRequestType
			MAX-ACCESS read-write
			STATUS current
			DESCRIPTION
				"modifyLagGroupEntry:
				sheLagControlIndex
				sheLagControlGroupActorSystemPriority
				sheLagControlGroupActorAdminKey
				sheLagControlGroupCollectorMaxDelay
				sheLagControlGroupLacpActivity
				sheLagControlGroupMethod
				
				modifyLagPortEntry:
				sheLagControlIndex
				sheLagControlPortActorAdminKey
				sheLagControlPortActorPortPriority
				sheLagControlPortActorAdminState
				sheLagControlPortLacpAvailability
				
				assignBridgePortToLag:
				sheLagControlIndex
				sheLagControlGroupPortList
				
				unassignBridgePortFromLag:
				sheLagControlIndex
				sheLagControlGroupPortList
				
				"
			::= { sheLagControl 1 }

		
--   1.3.6.1.4.1.231.7.1.2.2.1.4.5.3.2
		sheLagControlIndex OBJECT-TYPE
			SYNTAX Integer32
			MAX-ACCESS read-write
			STATUS current
			DESCRIPTION
				"The index of the table entry to be configured."
			::= { sheLagControl 2 }

		
--   1.3.6.1.4.1.231.7.1.2.2.1.4.5.3.3
		sheLagControlStatus OBJECT-TYPE
			SYNTAX SheControlStatusType
			MAX-ACCESS read-only
			STATUS current
			DESCRIPTION
				"The status of a user command. 
				"
			::= { sheLagControl 3 }

		
--   1.3.6.1.4.1.231.7.1.2.2.1.4.5.3.4
		sheLagControlTimer OBJECT-TYPE
			SYNTAX Gauge32
			MAX-ACCESS read-only
			STATUS current
			DESCRIPTION
				"The maximum wait time for the manager for a long running user command. 
				"
			::= { sheLagControl 4 }

		
--   1.3.6.1.4.1.231.7.1.2.2.1.4.5.3.5
		sheLagControlReqResult OBJECT-TYPE
			SYNTAX SheBridgeControlReqResultType
			MAX-ACCESS read-only
			STATUS current
			DESCRIPTION
				"The result of the last user command."
			::= { sheLagControl 5 }

		
--   1.3.6.1.4.1.231.7.1.2.2.1.4.5.3.6
		sheLagControlTimeStamp OBJECT-TYPE
			SYNTAX Unsigned32
			UNITS "sec"
			MAX-ACCESS read-only
			STATUS current
			DESCRIPTION
				"The time stamp of the last command (end of command)."
			::= { sheLagControl 6 }

		
--   1.3.6.1.4.1.231.7.1.2.2.1.4.5.3.7
		sheLagControlGroupActorSystemPriority OBJECT-TYPE
			SYNTAX Integer32 (0..65535)
			MAX-ACCESS read-write
			STATUS current
			DESCRIPTION
				"Look at group-table description..."
			::= { sheLagControl 7 }

		
--   1.3.6.1.4.1.231.7.1.2.2.1.4.5.3.8
		sheLagControlGroupActorAdminKey OBJECT-TYPE
			SYNTAX Integer32 (0..15)
			MAX-ACCESS read-write
			STATUS current
			DESCRIPTION
				"Look at group-table description..."
			::= { sheLagControl 8 }

		
--   1.3.6.1.4.1.231.7.1.2.2.1.4.5.3.9
		sheLagControlGroupCollectorMaxDelay OBJECT-TYPE
			SYNTAX Integer32 (0..65535)
			MAX-ACCESS read-write
			STATUS current
			DESCRIPTION
				"Look at group-table description...
				
				Note:
				R2.8 will not longer use any modification of this parameter and use always NE internal value.
				A modification will be ignored."
			::= { sheLagControl 9 }

		
--   1.3.6.1.4.1.231.7.1.2.2.1.4.5.3.10
		sheLagControlGroupPortList OBJECT-TYPE
			SYNTAX OCTET STRING (SIZE (0..65535))
			MAX-ACCESS read-write
			STATUS current
			DESCRIPTION
				"Look at group-table description..."
			::= { sheLagControl 10 }

		
--   1.3.6.1.4.1.231.7.1.2.2.1.4.5.3.11
		sheLagControlGroupLacpActivity OBJECT-TYPE
			SYNTAX TruthValue
			MAX-ACCESS read-write
			STATUS current
			DESCRIPTION
				"Look at group-table description..."
			::= { sheLagControl 11 }

		
--   1.3.6.1.4.1.231.7.1.2.2.1.4.5.3.12
		sheLagControlGroupMethod OBJECT-TYPE
			SYNTAX SheLagMethodType
			MAX-ACCESS read-write
			STATUS current
			DESCRIPTION
				"Look at group-table description..."
			::= { sheLagControl 12 }

		
--   1.3.6.1.4.1.231.7.1.2.2.1.4.5.3.13
		sheLagControlPortActorAdminKey OBJECT-TYPE
			SYNTAX Integer32
			MAX-ACCESS read-write
			STATUS current
			DESCRIPTION
				"Look at port-table description..."
			::= { sheLagControl 13 }

		
--   1.3.6.1.4.1.231.7.1.2.2.1.4.5.3.14
		sheLagControlPortActorPortPriority OBJECT-TYPE
			SYNTAX Integer32 (0..65535)
			MAX-ACCESS read-write
			STATUS current
			DESCRIPTION
				"Look at port-table description..."
			::= { sheLagControl 14 }

		
--   1.3.6.1.4.1.231.7.1.2.2.1.4.5.3.15
		sheLagControlPortActorAdminState OBJECT-TYPE
			SYNTAX SheLagStateType
			MAX-ACCESS read-write
			STATUS current
			DESCRIPTION
				"Look at port-table description...Only bit 0, 1 and 2 could be configured."
			::= { sheLagControl 15 }

		
--   1.3.6.1.4.1.231.7.1.2.2.1.4.5.3.16
		sheLagControlPortLacpAvailability OBJECT-TYPE
			SYNTAX TruthValue
			MAX-ACCESS read-write
			STATUS current
			DESCRIPTION
				"Look at port-table description..."
			::= { sheLagControl 16 }

		
--   1.3.6.1.4.1.231.7.1.2.2.1.4.5.4
		sheLagNotifications OBJECT IDENTIFIER ::= { sheLag 4 }

		
--   1.3.6.1.4.1.231.7.1.2.2.1.4.5.4.1
		sheLagGroupEntryModified NOTIFICATION-TYPE
			OBJECTS { sheLagControlIndex, sheLagControlTimeStamp, sheLagControlGroupActorSystemPriority, sheLagControlGroupActorAdminKey, sheLagControlGroupCollectorMaxDelay, 
				sheLagControlGroupLacpActivity, sheLagControlGroupMethod }
			STATUS current
			DESCRIPTION 
				"Configuration notification."
			::= { sheLagNotifications 1 }

		
--   1.3.6.1.4.1.231.7.1.2.2.1.4.5.4.2
		sheLagPortEntryModified NOTIFICATION-TYPE
			OBJECTS { sheLagControlIndex, sheLagControlTimeStamp, sheLagControlPortActorAdminKey, sheLagControlPortActorPortPriority, sheLagControlPortActorAdminState, 
				sheLagControlPortLacpAvailability }
			STATUS current
			DESCRIPTION 
				"Configuration notification."
			::= { sheLagNotifications 2 }

		
--   1.3.6.1.4.1.231.7.1.2.2.1.4.5.4.3
		sheLagBridgePortAssigned NOTIFICATION-TYPE
			OBJECTS { sheLagControlIndex, sheLagControlTimeStamp, sheLagControlGroupPortList }
			STATUS current
			DESCRIPTION 
				"LagGroup-Portlist changed notification."
			::= { sheLagNotifications 3 }

		
--   1.3.6.1.4.1.231.7.1.2.2.1.4.5.4.4
		sheLagBridgePortUnassigned NOTIFICATION-TYPE
			OBJECTS { sheLagControlIndex, sheLagControlTimeStamp, sheLagControlGroupPortList }
			STATUS current
			DESCRIPTION 
				"LagGroup-Portlist changed notification."
			::= { sheLagNotifications 4 }

		
--   1.3.6.1.4.1.231.7.1.2.2.1.4.5.5
		sheLagConformance OBJECT IDENTIFIER ::= { sheLag 100 }

		
--   1.3.6.1.4.1.231.7.1.2.2.1.4.5.5.1
		sheLagCompliances OBJECT IDENTIFIER ::= { sheLagConformance 1 }

		
--   1.3.6.1.4.1.231.7.1.2.2.1.4.5.5.1.1
-- this module
-- this module
		sheLagCompliance MODULE-COMPLIANCE
			STATUS current
			DESCRIPTION 
				"Description."
			MODULE -- this module
				MANDATORY-GROUPS { sheLagGroup, sheLagPortGroup, sheLagControlGroup, sheLagNotificationGroup }
			::= { sheLagCompliances 1 }

		
--   1.3.6.1.4.1.231.7.1.2.2.1.4.5.5.2
		sheLagGroups OBJECT IDENTIFIER ::= { sheLagConformance 2 }

		
--   1.3.6.1.4.1.231.7.1.2.2.1.4.5.5.2.1
		sheLagGroup OBJECT-GROUP
			OBJECTS { sheLagGroupMacAddress, sheLagGroupActorSystemPriority, sheLagGroupActorSystemId, sheLagGroupAggregateOrIndividual, sheLagGroupActorAdminKey, 
				sheLagGroupActorOperKey, sheLagGroupPartnerSystemId, sheLagGroupPartnerSystemPriority, sheLagGroupPartnerOperKey, sheLagGroupCollectorMaxDelay, 
				sheLagGroupLacpActivity, sheLagGroupMethod, sheLagGroupPortList, sheLagGroupEntPhysicalIndex }
			STATUS current
			DESCRIPTION 
				"Description."
			::= { sheLagGroups 1 }

		
--   1.3.6.1.4.1.231.7.1.2.2.1.4.5.5.2.2
		sheLagPortGroup OBJECT-GROUP
			OBJECTS { sheLagPortActorSystemPriority, sheLagPortActorSystemId, sheLagPortActorAdminKey, sheLagPortActorOperKey, sheLagPortPartnerAdminSystemPriority, 
				sheLagPortPartnerOperSystemPriority, sheLagPortPartnerAdminSystemId, sheLagPortPartnerOperSystemId, sheLagPortPartnerAdminKey, sheLagPortPartnerOperKey, 
				sheLagPortSelectedAggId, sheLagPortAttachedAggId, sheLagPortActorPort, sheLagPortActorPortPriority, sheLagPortPartnerAdminPort, 
				sheLagPortPartnerOperPort, sheLagPortPartnerAdminPortPriority, sheLagPortPartnerOperPortPriority, sheLagPortActorAdminState, sheLagPortActorOperState, 
				sheLagPortPartnerAdminState, sheLagPortPartnerOperState, sheLagPortAggregateOrIndividual, sheLagPortLacpAvailability }
			STATUS current
			DESCRIPTION 
				"Description."
			::= { sheLagGroups 2 }

		
--   1.3.6.1.4.1.231.7.1.2.2.1.4.5.5.2.3
		sheLagControlGroup OBJECT-GROUP
			OBJECTS { sheLagControlRequest, sheLagControlIndex, sheLagControlStatus, sheLagControlTimer, sheLagControlReqResult, 
				sheLagControlTimeStamp, sheLagControlGroupActorSystemPriority, sheLagControlGroupActorAdminKey, sheLagControlGroupCollectorMaxDelay, sheLagControlGroupPortList, 
				sheLagControlGroupLacpActivity, sheLagControlGroupMethod, sheLagControlPortActorAdminKey, sheLagControlPortActorPortPriority, sheLagControlPortActorAdminState, 
				sheLagControlPortLacpAvailability }
			STATUS current
			DESCRIPTION 
				"Description."
			::= { sheLagGroups 3 }

		
--   1.3.6.1.4.1.231.7.1.2.2.1.4.5.5.2.4
		sheLagNotificationGroup NOTIFICATION-GROUP
			NOTIFICATIONS { sheLagGroupEntryModified, sheLagPortEntryModified, sheLagBridgePortAssigned, sheLagBridgePortUnassigned }
			STATUS current
			DESCRIPTION 
				"Description."
			::= { sheLagGroups 4 }

		
--   1.3.6.1.4.1.231.7.1.2.2.1.4.6
		sheDhcpRelay OBJECT IDENTIFIER ::= { sheBridgeMib 6 }

		
--   1.3.6.1.4.1.231.7.1.2.2.1.4.6.1
		sheDhcpBase OBJECT IDENTIFIER ::= { sheDhcpRelay 1 }

		
--   1.3.6.1.4.1.231.7.1.2.2.1.4.6.1.1
		sheDhcpRelayAdminState OBJECT-TYPE
			SYNTAX SheDhcpRelayAdminStateType
			MAX-ACCESS read-only
			STATUS current
			DESCRIPTION
				"Globaly enable/disable of Dhcp/PPPoE agent.
				
				Telegram handling for DHCP and PPPoE
				
				relay: valid telegrams are handled, invalid telegrams are dropped
				snoop: valid telegrams are forwarded, invalid telegrams are dropped
				bridge: valid telegrams are forwarded, invalid telegrams are forwarded (currently NO support)
				
				handling explanation:
				dhcpPppoeRelayRelay -> dhcp and Pppoe use mode relay
				dhcpPppoeRelaySnoop -> dhcp use mode relay and Pppoe use mode snoop
				
				valid values:
				up(1),              -> releases >= R2.5 run now dhcpPppoeRelayRelay mode
				down(2),            -> releases >= R2.5 run now dhcpPppoeSnoopSnoop mode
				
				dhcpPppoeRelayRelay(4),
				dhcpPppoeRelaySnoop(5),  
				dhcpPppoeRelayBridge(6), (currently NO support)
				dhcpPppoeSnoopRelay(7),  
				dhcpPppoeSnoopSnoop(8),
				dhcpPppoeSnoopBridge(9), (currently NO support)
				dhcpPppoeBridgeRelay(10),(currently NO support)
				dhcpPppoeBridgeSnoop(11),(currently NO support)
				dhcpPppoeBridgeBridge(12)(currently NO support)
				
				NOTE:
				Only release R2.5 and higher can accept new value's 4..12 depending on the state of implementation in NE. "
			::= { sheDhcpBase 1 }

		
--     1.3.6.1.4.1.231.7.1.2.2.3.4.6.1.2
		sheDhcpRelayRemoteId OBJECT-TYPE
			SYNTAX OCTET STRING (SIZE (6..64))
			MAX-ACCESS read-only
			STATUS obsolete
			DESCRIPTION
				"Per default it is the Mac-Address of the DSLAM (length is 6) to be identified for Option 82.
				Could be set by operator. Moved to sheBridgePortTable and sheBridgeBase.
				(obsolete)"
			::= { sheDhcpBase 2 }

		
		sheDhcpUseInnerTagForProtocols OBJECT-TYPE
			SYNTAX TruthValue
			MAX-ACCESS read-only
			STATUS current
			DESCRIPTION
				"This configuration is only valid in double tagged mode.
				If enabled (true), the protocol machines for all DHCP providers will use the informations
				from inner tag of a received frame for evaluation, handling and forwarding.
				Per default always the outer tag will used.
				
				New with SHE R.8."
			DEFVAL { false }
			::= { sheDhcpBase 3 }

		
		shePppoeUseInnerTagForProtocols OBJECT-TYPE
			SYNTAX TruthValue
			MAX-ACCESS read-only
			STATUS current
			DESCRIPTION
				"This configuration is only valid in double tagged mode.
				If enabled (true), the protocol machines for all PPPoE providers will use the informations
				from inner tag of a received frame for evaluation, handling and forwarding.
				Per default always the outer tag will used.
				
				New with SHE R.8."
			DEFVAL { false }
			::= { sheDhcpBase 4 }

		
		sheDhcpStationMoveEnabled OBJECT-TYPE
			SYNTAX TruthValue
			MAX-ACCESS read-only
			STATUS current
			DESCRIPTION
				"This parameter configure the feature 'station move' for service issues.
				
				If enabled, the NE will instantly release all DHCP session informations and possibly
				learned mac addresses for a certain subscriber line if a 'link down' event for this
				line was detected. 
				If disabled, all release actions will be done according to FDB aging time and DHCP 
				lease time configuration.
				
				New with R2.8."
			DEFVAL { false }
			::= { sheDhcpBase 8 }

		
--   1.3.6.1.4.1.231.7.1.2.2.1.4.6.2
		sheDhcpProviderTable OBJECT-TYPE
			SYNTAX SEQUENCE OF SheDhcpProviderEntry
			MAX-ACCESS not-accessible
			STATUS current
			DESCRIPTION
				"The dhcp/pppoe provider table."
			::= { sheDhcpRelay 2 }

		
--   1.3.6.1.4.1.231.7.1.2.2.1.4.6.2.1
		sheDhcpProviderEntry OBJECT-TYPE
			SYNTAX SheDhcpProviderEntry
			MAX-ACCESS not-accessible
			STATUS current
			DESCRIPTION
				"One entry for each known dhcp or pppoe provider (depends on the option settings)."
			INDEX { sheDhcpProviderIndex }
			::= { sheDhcpProviderTable 1 }

		
		SheDhcpProviderEntry ::=
			SEQUENCE { 
				sheDhcpProviderIndex
					Unsigned32,
				sheDhcpProviderName
					OCTET STRING,
				sheDhcpServerIpAddress1
					OCTET STRING,
				sheDhcpServerIpAddress2
					OCTET STRING,
				sheDhcpServerIpAddress3
					OCTET STRING,
				sheDhcpServerGateway
					OCTET STRING,
				sheDhcpVlanId
					Integer32,
				sheDhcpRelayAgentIpAddress
					OCTET STRING,
				sheDhcpRelayAgentNetmask
					OCTET STRING,
				sheDhcpRelayAgentOption
					SheDhcpRelayAgentOptionType,
				sheDhcpCebsMacTranslation
					TruthValue,
				sheDhcpRelayAgentMgmt
					TruthValue,
				sheDhcpInnerVlanId
					Integer32,
				sheDhcpBcastTranslationDs
					TruthValue,
				sheDhcpLinePropertyNodeIdentifier
					OCTET STRING,
				sheDhcpServerIpAddress4
					OCTET STRING
			 }

--   1.3.6.1.4.1.231.7.1.2.2.1.4.6.2.1.1
		sheDhcpProviderIndex OBJECT-TYPE
			SYNTAX Unsigned32 (1..64)
			MAX-ACCESS read-only
			STATUS current
			DESCRIPTION
				"A table index."
			::= { sheDhcpProviderEntry 1 }

		
--   1.3.6.1.4.1.231.7.1.2.2.1.4.6.2.1.2
		sheDhcpProviderName OBJECT-TYPE
			SYNTAX OCTET STRING (SIZE (0..255))
			MAX-ACCESS read-only
			STATUS current
			DESCRIPTION
				"Descriptional name.
				Spaces and other special characters (: o) are not allowed!! "
			::= { sheDhcpProviderEntry 2 }

		
--   1.3.6.1.4.1.231.7.1.2.2.1.4.6.2.1.3
		sheDhcpServerIpAddress1 OBJECT-TYPE
			SYNTAX OCTET STRING (SIZE (4))
			MAX-ACCESS read-only
			STATUS current
			DESCRIPTION
				"There are three entrys and all three backup each other.
				Not necessary for all PPPoE relay agent options and in case of simplified
				Relay Agent.
				
				NOTE:
				Four possible server ip's with R2.8 maintenance!!"
			::= { sheDhcpProviderEntry 3 }

		
--   1.3.6.1.4.1.231.7.1.2.2.1.4.6.2.1.4
		sheDhcpServerIpAddress2 OBJECT-TYPE
			SYNTAX OCTET STRING (SIZE (4))
			MAX-ACCESS read-only
			STATUS current
			DESCRIPTION
				"There are three entrys and all three backup each other.
				Not necessary for all PPPoE relay agent options and in case of simplified
				Relay Agent.
				
				NOTE:
				Four possible server ip's with R2.8 maintenance!!"
			::= { sheDhcpProviderEntry 4 }

		
--   1.3.6.1.4.1.231.7.1.2.2.1.4.6.2.1.5
		sheDhcpServerIpAddress3 OBJECT-TYPE
			SYNTAX OCTET STRING (SIZE (4))
			MAX-ACCESS read-only
			STATUS current
			DESCRIPTION
				"There are three entrys and all three backup each other.
				Not necessary for all PPPoE relay agent options and in case of simplified
				Relay Agent.
				
				NOTE:
				Four possible server ip's with R2.8 maintenance!!"
			::= { sheDhcpProviderEntry 5 }

		
--   1.3.6.1.4.1.231.7.1.2.2.1.4.6.2.1.6
		sheDhcpServerGateway OBJECT-TYPE
			SYNTAX OCTET STRING (SIZE (4))
			MAX-ACCESS read-only
			STATUS obsolete
			DESCRIPTION
				"The gateway address of this dhcp provider.
				Not necessary for all PPPoE relay agent options and in case of simplified DHCP
				Relay Agent.
				
				Note: This parameter is not longer supported starting with release
				SHE R2.6. The IP route configuration was moved to sheSystemIpRouteTable."
			::= { sheDhcpProviderEntry 6 }

		
--   1.3.6.1.4.1.231.7.1.2.2.1.4.6.2.1.7
		sheDhcpVlanId OBJECT-TYPE
			SYNTAX Integer32 (0 | 1..4093)
			MAX-ACCESS read-only
			STATUS obsolete
			DESCRIPTION
				"That points to the VLAN, where the request should be send. 
				A configuration is only in case of simplified DHCP agent possible.
				
				For PPPoE and normal DHCP providers the value of sheDhcpVlanId should be 0. 
				That means, no provider vlan for received request's will be used! 
				
				Note: This parameter is not longer supported starting with release
				SHE R2.6. The IP route configuration was moved to sheSystemIpRouteTable including
				a possible assignment of vlanId."
			::= { sheDhcpProviderEntry 7 }

		
--   1.3.6.1.4.1.231.7.1.2.2.1.4.6.2.1.8
		sheDhcpRelayAgentIpAddress OBJECT-TYPE
			SYNTAX OCTET STRING (SIZE (4))
			MAX-ACCESS read-only
			STATUS current
			DESCRIPTION
				"The relay agent IP address is used to set the GIADDR in DHCP messages.
				
				With R2.6, it can either be configured to an address that denotes a subscriber's subnet.
				If not set, the NE will automatically set to the IP of the interface which
				is used for sending DHCP message to DHCP server. 
				
				In all cases, a configuration is not necessary for all PPPoE relay agent options
				and in case of simplified DHCP Relay Agent."
			::= { sheDhcpProviderEntry 8 }

		
--   1.3.6.1.4.1.231.7.1.2.2.1.4.6.2.1.9
		sheDhcpRelayAgentNetmask OBJECT-TYPE
			SYNTAX OCTET STRING (SIZE (4))
			MAX-ACCESS read-only
			STATUS obsolete
			DESCRIPTION
				"The RelayAgent Netmask.
				Not necessary for all PPPoE relay agent options and in case of simplified DHCP
				Relay Agent.
				
				Note: This parameter is not longer valid starting with release
				SHE R2.6. The IP interface configuration was moved to sheSystemIpHostTable."
			::= { sheDhcpProviderEntry 9 }

		
--   1.3.6.1.4.1.231.7.1.2.2.1.4.6.2.1.10
		sheDhcpRelayAgentOption OBJECT-TYPE
			SYNTAX SheDhcpRelayAgentOptionType
			MAX-ACCESS read-only
			STATUS current
			DESCRIPTION
				"Option 82, depends on the Dhcp - Server functionality.
				If PPPoE is configured also special Options could be implemented.
				
				With R2.7 additional options for LineProperty are possible (value 12..23)."
			DEFVAL { 0 }
			::= { sheDhcpProviderEntry 10 }

		
--   1.3.6.1.4.1.231.7.1.2.2.1.4.6.2.1.11
		sheDhcpCebsMacTranslation OBJECT-TYPE
			SYNTAX TruthValue
			MAX-ACCESS read-only
			STATUS current
			DESCRIPTION
				"Configuration whether CHADDR in a DHCP packet should be changed or not in CEBS environment.
				
				Note:
				Only valid for DHCP provider configuration (check options) and should always false for
				PPPoE providers."
			DEFVAL { false }
			::= { sheDhcpProviderEntry 11 }

		
--   1.3.6.1.4.1.231.7.1.2.2.1.4.6.2.1.12
		sheDhcpRelayAgentMgmt OBJECT-TYPE
			SYNTAX TruthValue
			MAX-ACCESS read-only
			STATUS current
			DESCRIPTION
				"Configuration whether a dhcp provider should be used for mgmt-port relay or not.
				There can be only one dhcp-provider for mgmt-relay."
			::= { sheDhcpProviderEntry 12 }

		
--   1.3.6.1.4.1.231.7.1.2.2.1.4.6.2.1.13
		sheDhcpInnerVlanId OBJECT-TYPE
			SYNTAX Integer32 (0 | 1..4093)
			MAX-ACCESS read-only
			STATUS obsolete
			DESCRIPTION
				"The index of inner-vlan when to forward Requests to the uplink. This vlan tag is
				used for the inner tag on double tagging mode.
				A configuration is only in case of simplified DHCP agent possible.
				
				For PPPoE and normal DHCP providers the value of sheDhcpVlanId should be 0. 
				That means, no provider vlan for received request's will be used! 
				
				Note: This parameter is not longer supported starting with release
				SHE R2.6. The IP route configuration was moved to sheSystemIpRouteTable including
				a possible assignment of vlanId."
			::= { sheDhcpProviderEntry 13 }

		
--  1.3.6.1.4.1.231.7.1.2.2.1.4.6.2.1.14
		sheDhcpBcastTranslationDs OBJECT-TYPE
			SYNTAX TruthValue
			MAX-ACCESS read-only
			STATUS current
			DESCRIPTION
				"Configuration whether destination address in a DHCP downstream packet should be changed or not.
				
				True  - use always unicast address
				False - check broadcast flag from server and use unicast or broadcast address accordingly
				
				Note:
				Only valid for DHCP provider configuration (check options) and should always false for
				PPPoE providers."
			::= { sheDhcpProviderEntry 14 }

		
--  1.3.6.1.4.1.231.7.1.2.2.1.4.6.2.1.16
		sheDhcpLinePropertyNodeIdentifier OBJECT-TYPE
			SYNTAX OCTET STRING (SIZE (0..64))
			MAX-ACCESS read-only
			STATUS current
			DESCRIPTION
				"This parameter defines the name of the access node the DSLAM uses to identifies itself
				by the provider.
				
				New with R2.7."
			::= { sheDhcpProviderEntry 16 }

		
--   1.3.6.1.4.1.231.7.1.2.2.1.4.6.2.1.5
		sheDhcpServerIpAddress4 OBJECT-TYPE
			SYNTAX OCTET STRING (SIZE (4))
			MAX-ACCESS read-only
			STATUS current
			DESCRIPTION
				"Now there are four entrys and all of them backup each other.
				Not necessary for all PPPoE relay agent options and in case of simplified
				Relay Agent.
				
				New with R2.8 maintenance."
			::= { sheDhcpProviderEntry 17 }

		
--   1.3.6.1.4.1.231.7.1.2.2.1.4.6.3
		sheDhcpControl OBJECT IDENTIFIER ::= { sheDhcpRelay 3 }

		
--   1.3.6.1.4.1.231.7.1.2.2.1.4.6.3.1
		sheDhcpControlRequest OBJECT-TYPE
			SYNTAX SheBridgeControlRequestType
			MAX-ACCESS read-write
			STATUS current
			DESCRIPTION
				"setDhcpAdminState:
				sheDhcpControlRelayAdminState
				
				Depending on the used RelayAgentOption value, not all values are needed. If a PPPoE or
				simplified option is used, only the values Name and AgentOption are mandatory.
				
				createDhcpProviderEntry:
				sheDhcpControlProfileName
				sheDhcpControlServerIpAddress1
				sheDhcpControlServerIpAddress2
				sheDhcpControlServerIpAddress3
				sheDhcpControlServerGateway(obsolete)
				sheDhcpControlVlanId
				sheDhcpControlRelayAgentOption
				sheDhcpControlRelayAgentNetmask(obsolete)
				sheDhcpControlRelayAgentIpAddress
				sheDhcpControlCebsMacTranslation
				sheDhcpControlRelayAgentMgmt
				sheDhcpControlInnerVlanId
				sheDhcpControlBcastTranslationDs
				sheDhcpControlLinePropertyNodeIdentifier (new with R2.7)
				sheDhcpControlServerIpAddress4 (new with R2.8 maintenance)
				
				modifyDhcpProviderEntry:
				sheDhcpControlIndex
				sheDhcpControlServerIpAddress1
				sheDhcpControlServerIpAddress2
				sheDhcpControlServerIpAddress3
				sheDhcpControlServerGateway(obsolete)
				sheDhcpControlVlanId
				sheDhcpControlRelayAgentNetmask(obsolete)
				sheDhcpControlRelayAgentIpAddress
				sheDhcpControlRelayAgentOption
				sheDhcpControlCebsMacTranslation
				sheDhcpControlRelayAgentMgmt
				sheDhcpControlInnerVlanId
				sheDhcpControlBcastTranslationDs
				sheDhcpControlLinePropertyNodeIdentifier (new with R2.7)
				sheDhcpControlServerIpAddress4 (new with R2.8 maintenance)
				
				deleteDhcpProviderEntry:
				sheDhcpControlIndex
				
				New with R2.8:
				setDhcpTagForProtocol:
				sheDhcpControlUseInnerTagForProtocols
				
				setDhcpStationMove:
				sheDhcpControlStationMoveEnabled"
			::= { sheDhcpControl 1 }

		
--   1.3.6.1.4.1.231.7.1.2.2.1.4.6.3.2
		sheDhcpControlIndex OBJECT-TYPE
			SYNTAX Integer32 (1..64)
			MAX-ACCESS read-write
			STATUS current
			DESCRIPTION
				"The table index to be configured."
			::= { sheDhcpControl 2 }

		
--   1.3.6.1.4.1.231.7.1.2.2.1.4.6.3.3
		sheDhcpControlStatus OBJECT-TYPE
			SYNTAX SheControlStatusType
			MAX-ACCESS read-only
			STATUS current
			DESCRIPTION
				"The status of a user command. 
				"
			::= { sheDhcpControl 3 }

		
--   1.3.6.1.4.1.231.7.1.2.2.1.4.6.3.4
		sheDhcpControlTimer OBJECT-TYPE
			SYNTAX Gauge32
			MAX-ACCESS read-only
			STATUS current
			DESCRIPTION
				"The maximum wait time for the manager for a long running user command. 
				"
			::= { sheDhcpControl 4 }

		
--   1.3.6.1.4.1.231.7.1.2.2.1.4.6.3.5
		sheDhcpControlReqResult OBJECT-TYPE
			SYNTAX SheBridgeControlReqResultType
			MAX-ACCESS read-only
			STATUS current
			DESCRIPTION
				"The result of the last user command."
			::= { sheDhcpControl 5 }

		
--   1.3.6.1.4.1.231.7.1.2.2.1.4.6.3.6
		sheDhcpControlTimeStamp OBJECT-TYPE
			SYNTAX Unsigned32
			UNITS "sec"
			MAX-ACCESS read-only
			STATUS current
			DESCRIPTION
				"The time stamp of the last command (end of command)."
			::= { sheDhcpControl 6 }

		
--   1.3.6.1.4.1.231.7.1.2.2.1.4.6.3.7
		sheDhcpControlRelayAdminState OBJECT-TYPE
			SYNTAX SheDhcpRelayAdminStateType
			MAX-ACCESS read-write
			STATUS current
			DESCRIPTION
				"Look at base parameter description..."
			::= { sheDhcpControl 7 }

		
--   1.3.6.1.4.1.231.7.1.2.2.1.4.6.3.8
		sheDhcpControlRelayRemoteId OBJECT-TYPE
			SYNTAX OCTET STRING (SIZE (6..64))
			MAX-ACCESS read-write
			STATUS obsolete
			DESCRIPTION
				"Per default it is the Mac-Address of the DSLAM (length is 6) to be identified for Option 82.
				Could be set by operator. (obsoleted in V135)"
			::= { sheDhcpControl 8 }

		
--   1.3.6.1.4.1.231.7.1.2.2.1.4.6.3.9
		sheDhcpControlProviderName OBJECT-TYPE
			SYNTAX OCTET STRING (SIZE (0..255))
			MAX-ACCESS read-write
			STATUS current
			DESCRIPTION
				"Look at table description...
				Spaces and other special characters (: o) are not allowed!! "
			::= { sheDhcpControl 9 }

		
--   1.3.6.1.4.1.231.7.1.2.2.1.4.6.3.10
		sheDhcpControlServerIpAddress1 OBJECT-TYPE
			SYNTAX OCTET STRING (SIZE (4))
			MAX-ACCESS read-write
			STATUS current
			DESCRIPTION
				"Look at table description..."
			::= { sheDhcpControl 10 }

		
--   1.3.6.1.4.1.231.7.1.2.2.1.4.6.3.11
		sheDhcpControlServerIpAddress2 OBJECT-TYPE
			SYNTAX OCTET STRING (SIZE (4))
			MAX-ACCESS read-write
			STATUS current
			DESCRIPTION
				"Look at table description..."
			::= { sheDhcpControl 11 }

		
--   1.3.6.1.4.1.231.7.1.2.2.1.4.6.3.12
		sheDhcpControlServerIpAddress3 OBJECT-TYPE
			SYNTAX OCTET STRING (SIZE (4))
			MAX-ACCESS read-write
			STATUS current
			DESCRIPTION
				"Look at table description..."
			::= { sheDhcpControl 12 }

		
--   1.3.6.1.4.1.231.7.1.2.2.1.4.6.3.13
		sheDhcpControlServerGateway OBJECT-TYPE
			SYNTAX OCTET STRING (SIZE (4))
			MAX-ACCESS read-write
			STATUS current
			DESCRIPTION
				"Look at table description...
				
				Note: A configuration of this parameter is not longer supported starting with release
				SHE R2.6. The IP route configuration was moved to sheSystemIpRouteTable."
			::= { sheDhcpControl 13 }

		
--   1.3.6.1.4.1.231.7.1.2.2.1.4.6.3.14
		sheDhcpControlVlanId OBJECT-TYPE
			SYNTAX Integer32 (0 | 1..4093)
			MAX-ACCESS read-write
			STATUS current
			DESCRIPTION
				"Look at table description...
				
				Note: This parameter is not longer supported starting with release
				SHE R2.6. The IP route configuration was moved to sheSystemIpRouteTable including
				a possible assignment of vlanId."
			::= { sheDhcpControl 14 }

		
--   1.3.6.1.4.1.231.7.1.2.2.1.4.6.3.15
		sheDhcpControlRelayAgentIpAddress OBJECT-TYPE
			SYNTAX OCTET STRING (SIZE (4))
			MAX-ACCESS read-write
			STATUS current
			DESCRIPTION
				"The relay agent IP address is used to set the GIADDR in DHCP messages.
				
				With R2.6, it can either be configured to an address that denotes a subscriber's subnet.
				If not set, the NE will automatically set to the IP of the interface which
				is used for sending DHCP message to DHCP server. 
				
				In all cases, a configuration is not necessary for all PPPoE relay agent options
				and in case of simplified DHCP Relay Agent."
			::= { sheDhcpControl 15 }

		
--   1.3.6.1.4.1.231.7.1.2.2.1.4.6.3.16
		sheDhcpControlRelayAgentNetmask OBJECT-TYPE
			SYNTAX OCTET STRING (SIZE (4))
			MAX-ACCESS read-write
			STATUS current
			DESCRIPTION
				"The RelayAgent Netmask.
				
				Note: A configuration of this parameter is not longer supported starting with release
				SHE R2.6. The IP interface configuration was moved to sheSystemIpHostTable."
			::= { sheDhcpControl 16 }

		
--   1.3.6.1.4.1.231.7.1.2.2.1.4.6.3.17
		sheDhcpControlRelayAgentOption OBJECT-TYPE
			SYNTAX SheDhcpRelayAgentOptionType
			MAX-ACCESS read-write
			STATUS current
			DESCRIPTION
				"Look at table description...
				
				With R2.7 additional options for LineProperty are possible (value 12..23)."
			::= { sheDhcpControl 17 }

		
--   1.3.6.1.4.1.231.7.1.2.2.1.4.6.3.18
		sheDhcpControlCebsMacTranslation OBJECT-TYPE
			SYNTAX TruthValue
			MAX-ACCESS read-write
			STATUS current
			DESCRIPTION
				"configuration whether CHADDR in a DHCP packet should be changed or not in CEBS environment.
				
				Note:
				Only valid for DHCP provider configuration (check options) and should always false for
				PPPoE providers."
			::= { sheDhcpControl 18 }

		
--   1.3.6.1.4.1.231.7.1.2.2.1.4.6.3.19
		sheDhcpControlRelayAgentMgmt OBJECT-TYPE
			SYNTAX TruthValue
			MAX-ACCESS read-write
			STATUS current
			DESCRIPTION
				"Configuration whether a dhcp provider should be used for mgmt-port relay or not. There can be only one dhcp-provider for mgmt-relay."
			::= { sheDhcpControl 19 }

		
--   1.3.6.1.4.1.231.7.1.2.2.1.4.6.3.20
		sheDhcpControlInnerVlanId OBJECT-TYPE
			SYNTAX Integer32 (0 | 1..4093)
			MAX-ACCESS read-write
			STATUS current
			DESCRIPTION
				"The index of inner-vlan when to forward Dhcp Requests to the uplink. 
				This vlan tag is used for the inner tag on double tagging mode.
				Only valid for simplified DHCP agent configuration.
				
				Look at table description.
				
				Note: This parameter is not longer supported starting with release
				SHE R2.6. The IP route configuration was moved to sheSystemIpRouteTable including
				a possible assignment of vlanId."
			::= { sheDhcpControl 20 }

		
--  1.3.6.1.4.1.231.7.1.2.2.1.4.6.3.21
		sheDhcpControlBcastTranslationDs OBJECT-TYPE
			SYNTAX TruthValue
			MAX-ACCESS read-write
			STATUS current
			DESCRIPTION
				"Configuration whether destination address in a DHCP downstream packet should be changed or not.
				
				True  - use always unicast address
				False - check broadcast flag from server and use unicast or broadcast address accordingly
				
				Note:
				Only valid for DHCP provider configuration (check options) and should always false for
				PPPoE providers."
			::= { sheDhcpControl 21 }

		
		sheDhcpControlUseInnerTagForProtocols OBJECT-TYPE
			SYNTAX SheDhcpUseTagForProtocolsType
			MAX-ACCESS read-write
			STATUS current
			DESCRIPTION
				"Used for configuration of global DHCP and PPPoE useTag settings.
				BITS
				{
				dhcpUseInnerTagTrue(0),
				pppoeUseInnerTagTrue(1)
				}
				
				If bit is set to 1 the corresponding global parameter is set to true.
				
				Support with R2.8."
			::= { sheDhcpControl 22 }

		
--  1.3.6.1.4.1.231.7.1.2.2.1.4.6.3.23
		sheDhcpControlLinePropertyNodeIdentifier OBJECT-TYPE
			SYNTAX OCTET STRING (SIZE (0..64))
			MAX-ACCESS read-write
			STATUS current
			DESCRIPTION
				"This parameter defines the name of the access node the DSLAM uses to identifies itself
				by the provider.
				
				New with R2.7."
			::= { sheDhcpControl 23 }

		
		sheDhcpControlStationMoveEnabled OBJECT-TYPE
			SYNTAX TruthValue
			MAX-ACCESS read-write
			STATUS current
			DESCRIPTION
				"This parameter configure the feature 'station move' for service issues.
				
				If enabled, the NE will instantly release all DHCP session informations and possibly
				learned mac addresses for a certain subscriber line if a 'link down' event for this
				line was detected. 
				If disabled, all release actions will be done according to FDB aging time and DHCP 
				lease time configuration.
				
				New with R2.8."
			DEFVAL { false }
			::= { sheDhcpControl 25 }

		
--   1.3.6.1.4.1.231.7.1.2.2.1.4.6.3.26
		sheDhcpControlServerIpAddress4 OBJECT-TYPE
			SYNTAX OCTET STRING (SIZE (4))
			MAX-ACCESS read-write
			STATUS current
			DESCRIPTION
				"Look at table description..."
			::= { sheDhcpControl 26 }

		
--   1.3.6.1.4.1.231.7.1.2.2.1.4.6.5
		sheDhcpNotifications OBJECT IDENTIFIER ::= { sheDhcpRelay 5 }

		
		sheDhcpProviderEntryCreated NOTIFICATION-TYPE
			OBJECTS { sheDhcpControlIndex, sheDhcpControlTimeStamp, sheDhcpControlProviderName, sheDhcpControlServerIpAddress1, sheDhcpControlServerIpAddress2, 
				sheDhcpControlServerIpAddress3, sheDhcpControlServerGateway, sheDhcpControlVlanId, sheDhcpControlRelayAgentOption, sheDhcpControlRelayAgentIpAddress, 
				sheDhcpControlRelayAgentNetmask, sheDhcpControlCebsMacTranslation, sheDhcpControlRelayAgentMgmt, sheDhcpControlInnerVlanId, sheDhcpControlBcastTranslationDs, 
				sheDhcpControlLinePropertyNodeIdentifier, sheDhcpControlServerIpAddress4 }
			STATUS current
			DESCRIPTION 
				"A new dhcp provider table entry was created."
			::= { sheDhcpNotifications 1 }

		
		sheDhcpProviderEntryModified NOTIFICATION-TYPE
			OBJECTS { sheDhcpControlIndex, sheDhcpControlTimeStamp, sheDhcpControlProviderName, sheDhcpControlServerIpAddress1, sheDhcpControlServerIpAddress2, 
				sheDhcpControlServerIpAddress3, sheDhcpControlServerGateway, sheDhcpControlVlanId, sheDhcpControlRelayAgentOption, sheDhcpControlRelayAgentIpAddress, 
				sheDhcpControlRelayAgentNetmask, sheDhcpControlCebsMacTranslation, sheDhcpControlRelayAgentMgmt, sheDhcpControlInnerVlanId, sheDhcpControlBcastTranslationDs, 
				sheDhcpControlLinePropertyNodeIdentifier, sheDhcpControlServerIpAddress4 }
			STATUS current
			DESCRIPTION 
				"A dhcp provider table entry was modified."
			::= { sheDhcpNotifications 2 }

		
		sheDhcpProviderEntryDeleted NOTIFICATION-TYPE
			OBJECTS { sheDhcpControlIndex, sheDhcpControlTimeStamp, sheDhcpControlProviderName }
			STATUS current
			DESCRIPTION 
				"A dhcp provider table entry was deleted."
			::= { sheDhcpNotifications 3 }

		
		sheDhcpRelayAdminStateModified NOTIFICATION-TYPE
			OBJECTS { sheDhcpRelayAdminState, sheDhcpControlReqResult, sheDhcpControlTimeStamp }
			STATUS current
			DESCRIPTION 
				"The dhcp relay admin state was modified."
			::= { sheDhcpNotifications 4 }

		
		sheDhcpRelayOptionModified NOTIFICATION-TYPE
			OBJECTS { sheDhcpControlIndex, sheDhcpControlTimeStamp, sheDhcpControlRelayAgentOption }
			STATUS current
			DESCRIPTION 
				"The dhcp relay option was modified."
			::= { sheDhcpNotifications 5 }

		
		sheDhcpRelayRemoteIdModified NOTIFICATION-TYPE
			OBJECTS { sheDhcpControlTimeStamp, sheDhcpControlRelayRemoteId, sheDhcpControlReqResult }
			STATUS obsolete
			DESCRIPTION 
				"The dhcp relay remote id was modified."
			::= { sheDhcpNotifications 6 }

		
		sheDhcpFloodVlanIdAdded NOTIFICATION-TYPE
			OBJECTS { sheDhcpFloodVlanIdControlTimeStamp, sheDhcpFloodVlanIdControlVlanId }
			STATUS current
			DESCRIPTION 
				"The dhcp flood vlanid was added. It becomes obsolete."
			::= { sheDhcpNotifications 7 }

		
		sheDhcpFloodVlanIdDeleted NOTIFICATION-TYPE
			OBJECTS { sheDhcpFloodVlanIdControlTimeStamp, sheDhcpFloodVlanIdControlVlanId }
			STATUS current
			DESCRIPTION 
				"The dhcp flood vlanid was deleted. It becomes obsolete."
			::= { sheDhcpNotifications 8 }

		
		sheDhcpFloodVlanIdModified NOTIFICATION-TYPE
			OBJECTS { sheDhcpFloodVlanIdControlTimeStamp, sheDhcpFloodVlanIdControlVlanId, sheDhcpFloodVlanIdControlVlanEnabled }
			STATUS current
			DESCRIPTION 
				"The dhcp flood vlanid was modified."
			::= { sheDhcpNotifications 9 }

		
		sheDhcpTagForProtocolsModified NOTIFICATION-TYPE
			OBJECTS { sheDhcpControlTimeStamp, sheDhcpUseInnerTagForProtocols, shePppoeUseInnerTagForProtocols }
			STATUS current
			DESCRIPTION 
				"The dhcp and pppoe global useTag options were modified."
			::= { sheDhcpNotifications 10 }

		
		sheDhcpStationMoveEnableModified NOTIFICATION-TYPE
			OBJECTS { sheDhcpControlTimeStamp, sheDhcpControlStationMoveEnabled }
			STATUS current
			DESCRIPTION 
				"The dhcp station move enable switch was modified."
			::= { sheDhcpNotifications 11 }

		
--   1.3.6.1.4.1.231.7.1.2.2.1.4.6.7
		sheDhcpFloodVlanIdTable OBJECT-TYPE
			SYNTAX SEQUENCE OF SheDhcpFloodVlanIdEntry
			MAX-ACCESS not-accessible
			STATUS current
			DESCRIPTION
				"The dhcp flood vlanid table."
			::= { sheDhcpRelay 7 }

		
--   1.3.6.1.4.1.231.7.1.2.2.1.4.6.7.1
		sheDhcpFloodVlanIdEntry OBJECT-TYPE
			SYNTAX SheDhcpFloodVlanIdEntry
			MAX-ACCESS not-accessible
			STATUS current
			DESCRIPTION
				"One entry for each dhcp flood vlanid."
			INDEX { sheDhcpFloodVlanId }
			::= { sheDhcpFloodVlanIdTable 1 }

		
		SheDhcpFloodVlanIdEntry ::=
			SEQUENCE { 
				sheDhcpFloodVlanId
					Integer32,
				sheDhcpFloodVlanEnabled
					SheDhcpFloodingType
			 }

--   1.3.6.1.4.1.231.7.1.2.2.1.4.6.7.1.2
		sheDhcpFloodVlanId OBJECT-TYPE
			SYNTAX Integer32 (1..4093)
			MAX-ACCESS read-only
			STATUS current
			DESCRIPTION
				"Index of that table. Will be identical to the used sheVlanIndex."
			::= { sheDhcpFloodVlanIdEntry 1 }

		
--   1.3.6.1.4.1.231.7.1.2.2.1.4.6.7.1.2
		sheDhcpFloodVlanEnabled OBJECT-TYPE
			SYNTAX SheDhcpFloodingType
			MAX-ACCESS read-only
			STATUS current
			DESCRIPTION
				"Enable or disable a flooding vlan for DHCP packets. The default is false.
				
				New with R2.8:
				Flooding of DHCP or PPPoE packets could now be separatly enabled. The former command switch
				always both protocol types."
			DEFVAL { disableFloodingDhcpAndPppoE }
			::= { sheDhcpFloodVlanIdEntry 2 }

		
--   1.3.6.1.4.1.231.7.1.2.2.1.4.6.8
		sheDhcpFloodVlanIdControl OBJECT IDENTIFIER ::= { sheDhcpRelay 8 }

		
--   1.3.6.1.4.1.231.7.1.2.2.1.4.6.8.1
		sheDhcpFloodVlanIdControlRequest OBJECT-TYPE
			SYNTAX SheBridgeControlRequestType
			MAX-ACCESS read-write
			STATUS current
			DESCRIPTION
				"
				setDhcpFloodVlanId:
				sheDhcpFloodVlanIdControlVlanId
				sheDhcpFloodVlanIdControlVlanEnabled
				"
			::= { sheDhcpFloodVlanIdControl 1 }

		
--   1.3.6.1.4.1.231.7.1.2.2.1.4.6.8.2
		sheDhcpFloodVlanIdControlStatus OBJECT-TYPE
			SYNTAX SheControlStatusType
			MAX-ACCESS read-only
			STATUS current
			DESCRIPTION
				"The status of a control request"
			::= { sheDhcpFloodVlanIdControl 2 }

		
--   1.3.6.1.4.1.231.7.1.2.2.1.4.6.8.3
		sheDhcpFloodVlanIdControlTimer OBJECT-TYPE
			SYNTAX Gauge32
			MAX-ACCESS read-only
			STATUS current
			DESCRIPTION
				"The maximum wait time for the manager for a long running user command. 
				The manager reads this value from the SHE."
			::= { sheDhcpFloodVlanIdControl 3 }

		
--   1.3.6.1.4.1.231.7.1.2.2.1.4.6.8.4
		sheDhcpFloodVlanIdControlReqResult OBJECT-TYPE
			SYNTAX SheBridgeControlReqResultType
			MAX-ACCESS read-only
			STATUS current
			DESCRIPTION
				"The result of the last user command"
			::= { sheDhcpFloodVlanIdControl 4 }

		
--   1.3.6.1.4.1.231.7.1.2.2.1.4.6.8.5
		sheDhcpFloodVlanIdControlTimeStamp OBJECT-TYPE
			SYNTAX Unsigned32
			MAX-ACCESS read-only
			STATUS current
			DESCRIPTION
				"The time stamp of the last command (end of command)"
			::= { sheDhcpFloodVlanIdControl 5 }

		
--   1.3.6.1.4.1.231.7.1.2.2.1.4.6.8.6
		sheDhcpFloodVlanIdControlVlanId OBJECT-TYPE
			SYNTAX Integer32 (1..4093)
			MAX-ACCESS read-write
			STATUS current
			DESCRIPTION
				"VLAN ID which is controlled for Dhcp flooding"
			::= { sheDhcpFloodVlanIdControl 6 }

		
--   1.3.6.1.4.1.231.7.1.2.2.1.4.6.8.7
		sheDhcpFloodVlanIdControlVlanEnabled OBJECT-TYPE
			SYNTAX SheDhcpFloodingType
			MAX-ACCESS read-write
			STATUS current
			DESCRIPTION
				"look at table.
				
				Expanded with R2.8 maintenance."
			::= { sheDhcpFloodVlanIdControl 7 }

		
--   1.3.6.1.4.1.231.7.1.2.2.1.4.6.6
		sheDhcpConformance OBJECT IDENTIFIER ::= { sheDhcpRelay 100 }

		
--   1.3.6.1.4.1.231.7.1.2.2.1.4.6.6.1
		sheDhcpCompliances OBJECT IDENTIFIER ::= { sheDhcpConformance 1 }

		
--   1.3.6.1.4.1.231.7.1.2.2.1.4.6.6.1.1
-- this module
-- this module
		sheDhcpCompliance MODULE-COMPLIANCE
			STATUS current
			DESCRIPTION 
				"Description."
			MODULE -- this module
				MANDATORY-GROUPS { sheDhcpBaseGroup, sheDhcpProviderGroup, sheDhcpControlGroup, sheDhcpNotificationGroup }
			::= { sheDhcpCompliances 1 }

		
--   1.3.6.1.4.1.231.7.1.2.2.1.4.6.6.2
		sheDhcpRelayGroups OBJECT IDENTIFIER ::= { sheDhcpConformance 2 }

		
--   1.3.6.1.4.1.231.7.1.2.2.1.4.6.6.2.1
		sheDhcpBaseGroup OBJECT-GROUP
			OBJECTS { sheDhcpRelayAdminState, sheDhcpUseInnerTagForProtocols, shePppoeUseInnerTagForProtocols, sheDhcpStationMoveEnabled }
			STATUS current
			DESCRIPTION 
				"Description."
			::= { sheDhcpRelayGroups 1 }

		
--   1.3.6.1.4.1.231.7.1.2.2.1.4.6.6.2.2
		sheDhcpProviderGroup OBJECT-GROUP
			OBJECTS { sheDhcpServerIpAddress1, sheDhcpServerIpAddress2, sheDhcpServerIpAddress3, sheDhcpRelayAgentIpAddress, sheDhcpRelayAgentMgmt, 
				sheDhcpBcastTranslationDs, sheDhcpLinePropertyNodeIdentifier, sheDhcpRelayAgentOption, sheDhcpProviderIndex, sheDhcpProviderName, 
				sheDhcpCebsMacTranslation, sheDhcpServerIpAddress4 }
			STATUS current
			DESCRIPTION 
				"Description."
			::= { sheDhcpRelayGroups 2 }

		
--   1.3.6.1.4.1.231.7.1.2.2.1.4.6.6.2.3
		sheDhcpControlGroup OBJECT-GROUP
			OBJECTS { sheDhcpControlRequest, sheDhcpControlIndex, sheDhcpControlStatus, sheDhcpControlRelayAdminState, sheDhcpControlServerIpAddress1, 
				sheDhcpControlServerIpAddress2, sheDhcpControlServerIpAddress3, sheDhcpControlServerGateway, sheDhcpControlVlanId, sheDhcpControlTimeStamp, 
				sheDhcpControlRelayAgentIpAddress, sheDhcpControlRelayAgentNetmask, sheDhcpControlRelayAgentMgmt, sheDhcpControlInnerVlanId, sheDhcpControlBcastTranslationDs, 
				sheDhcpControlUseInnerTagForProtocols, sheDhcpControlLinePropertyNodeIdentifier, sheDhcpControlRelayAgentOption, sheDhcpControlTimer, sheDhcpControlReqResult, 
				sheDhcpControlProviderName, sheDhcpControlCebsMacTranslation, sheDhcpControlStationMoveEnabled, sheDhcpControlServerIpAddress4 }
			STATUS current
			DESCRIPTION 
				"Description."
			::= { sheDhcpRelayGroups 3 }

		
--   1.3.6.1.4.1.231.7.1.2.2.1.4.6.6.2.4
		sheDhcpNotificationGroup NOTIFICATION-GROUP
			NOTIFICATIONS { sheDhcpRelayAdminStateModified, sheDhcpTagForProtocolsModified, sheDhcpRelayOptionModified, sheDhcpProviderEntryCreated, sheDhcpProviderEntryModified, 
				sheDhcpProviderEntryDeleted, sheDhcpFloodVlanIdAdded, sheDhcpFloodVlanIdDeleted, sheDhcpFloodVlanIdModified, sheDhcpStationMoveEnableModified
				 }
			STATUS current
			DESCRIPTION 
				"Description."
			::= { sheDhcpRelayGroups 4 }

		
--   1.3.6.1.4.1.231.7.1.2.2.1.4.6.6.2.5
		sheDhcpFloodVlanIdGroup OBJECT-GROUP
			OBJECTS { sheDhcpFloodVlanEnabled, sheDhcpFloodVlanId }
			STATUS current
			DESCRIPTION 
				"Description."
			::= { sheDhcpRelayGroups 5 }

		
--   1.3.6.1.4.1.231.7.1.2.2.1.4.6.6.2.6
		sheDhcpFloodVlanIdControlGroup OBJECT-GROUP
			OBJECTS { sheDhcpFloodVlanIdControlRequest, sheDhcpFloodVlanIdControlStatus, sheDhcpFloodVlanIdControlTimer, sheDhcpFloodVlanIdControlReqResult, sheDhcpFloodVlanIdControlTimeStamp, 
				sheDhcpFloodVlanIdControlVlanId, sheDhcpFloodVlanIdControlVlanEnabled }
			STATUS current
			DESCRIPTION 
				"Description."
			::= { sheDhcpRelayGroups 6 }

		
		sheDhcpObsoleteGroup OBJECT-GROUP
			OBJECTS { sheDhcpRelayRemoteId, sheDhcpControlRelayRemoteId, sheDhcpServerGateway, sheDhcpVlanId, sheDhcpRelayAgentNetmask, 
				sheDhcpInnerVlanId }
			STATUS obsolete
			DESCRIPTION 
				"Description."
			::= { sheDhcpRelayGroups 7 }

		
		sheDhcpObsoleteNotificationGroup NOTIFICATION-GROUP
			NOTIFICATIONS { sheDhcpRelayRemoteIdModified }
			STATUS obsolete
			DESCRIPTION 
				"Description."
			::= { sheDhcpRelayGroups 8 }

		
--   1.3.6.1.4.1.231.7.1.2.2.1.4.7
		sheIgmp OBJECT IDENTIFIER ::= { sheBridgeMib 7 }

		
--   1.3.6.1.4.1.231.7.1.2.2.1.4.7.2
		sheIgmpBase OBJECT IDENTIFIER ::= { sheIgmp 2 }

		
--   1.3.6.1.4.1.231.7.1.2.2.1.4.7.2.2
		sheIgmpMode OBJECT-TYPE
			SYNTAX SheIgmpModeType
			MAX-ACCESS read-only
			STATUS current
			DESCRIPTION
				"IGMP operation mode can be
				off
				proxy
				
				That is the general NE igmp on/off switch.
				"
			::= { sheIgmpBase 2 }

		
--   1.3.6.1.4.1.231.7.1.2.2.1.4.7.2.3
		sheIgmpVersion OBJECT-TYPE
			SYNTAX OCTET STRING (SIZE (1))
			MAX-ACCESS read-only
			STATUS obsolete
			DESCRIPTION
				"The version of IGMP which is running on this interface
				(detected by the NE). The NE uses version 2 as default.
				If version 1 members are detected on the IP subnet
				attached to this interface, the NE falls back to version 1.
				
				Note: This parameter is not longer supported starting with release SHE R2.8
				The used version should be configured per IGMP profileVlan entry."
			::= { sheIgmpBase 3 }

		
--   1.3.6.1.4.1.231.7.1.2.2.1.4.7.2.4
		sheIgmpMaxJoinedSubscriber OBJECT-TYPE
			SYNTAX Unsigned32 (1..65535)
			MAX-ACCESS read-only
			STATUS obsolete
			DESCRIPTION
				"The maximum number of subscribers who can join a multicast group in the system.
				
				Note: This parameter is not longer supported starting with release
				SHE R2.6."
			DEFVAL { 400 }
			::= { sheIgmpBase 4 }

		
--   1.3.6.1.4.1.231.7.1.2.2.1.4.7.2.5
		sheIgmpMaxJoinedGroup OBJECT-TYPE
			SYNTAX Unsigned32 (1..1000)
			MAX-ACCESS read-only
			STATUS current
			DESCRIPTION
				"The maximum number of multicast groups that could be joined in the system."
			DEFVAL { 1000 }
			::= { sheIgmpBase 5 }

		
--   1.3.6.1.4.1.231.7.1.2.2.1.4.7.2.6
		sheIgmpVlanTranslationMode OBJECT-TYPE
			SYNTAX SheIgmpVlanMode
			MAX-ACCESS read-only
			STATUS current
			DESCRIPTION
				"Configure VLAN translation mode for the system.
				1 is inner tagged, 2 is outer tagged, default configuration is inner.
				This configuration is only functions when system is configured in double tagging mode.
				
				New with SHE R.8."
			DEFVAL { inner }
			::= { sheIgmpBase 6 }

		
--   1.3.6.1.4.1.231.7.1.2.2.1.4.7.2.7
		sheIgmpVlanDoubleTaggingMode OBJECT-TYPE
			SYNTAX SheIgmpVlanMode
			MAX-ACCESS read-only
			STATUS current
			DESCRIPTION
				"Configure provider VLAN tagging mode for the system,
				1 is inner, 2 is outer, default configuration is outer.
				This configuration is only functions when system is configured in double tagging mode.
				
				New with SHE R.8.
				"
			DEFVAL { outer }
			::= { sheIgmpBase 7 }

		
--   1.3.6.1.4.1.231.7.1.2.2.1.4.7.2.9
		sheIgmpDoubleTaggingControl OBJECT IDENTIFIER ::= { sheIgmpBase 9 }

		
--  1.3.6.1.4.1.231.7.1.2.2.1.4.7.2.9.1
		sheIgmpDoubleTaggingControlRequest OBJECT-TYPE
			SYNTAX SheBridgeControlRequestType
			MAX-ACCESS read-write
			STATUS current
			DESCRIPTION
				"New with SHE R.8.
				setIgmpTagMode:
				sheIgmpControlVlanTranslationMode
				sheIgmpControlVlanDoubleTaggingMode"
			::= { sheIgmpDoubleTaggingControl 1 }

		
--  1.3.6.1.4.1.231.7.1.2.2.1.4.7.2.9.2
		sheIgmpDoubleTaggingControlStatus OBJECT-TYPE
			SYNTAX SheControlStatusType
			MAX-ACCESS read-only
			STATUS current
			DESCRIPTION
				"The status of a user command. 
				"
			::= { sheIgmpDoubleTaggingControl 2 }

		
--  1.3.6.1.4.1.231.7.1.2.2.1.4.7.2.9.3
		sheIgmpDoubleTaggingControlTimeStamp OBJECT-TYPE
			SYNTAX Unsigned32
			UNITS "sec"
			MAX-ACCESS read-only
			STATUS current
			DESCRIPTION
				"The time stamp of the last command (end of command)."
			::= { sheIgmpDoubleTaggingControl 3 }

		
--  1.3.6.1.4.1.231.7.1.2.2.1.4.7.2.9.4
		sheIgmpDoubleTaggingControlReqResult OBJECT-TYPE
			SYNTAX SheBridgeControlReqResultType
			MAX-ACCESS read-only
			STATUS current
			DESCRIPTION
				"The result of the last user command."
			::= { sheIgmpDoubleTaggingControl 4 }

		
--  1.3.6.1.4.1.231.7.1.2.2.1.4.7.2.9.5
		sheIgmpDoubleTaggingControlTimer OBJECT-TYPE
			SYNTAX Gauge32
			MAX-ACCESS read-only
			STATUS current
			DESCRIPTION
				"The maximum wait time for the manager for a long running user command. 
				"
			::= { sheIgmpDoubleTaggingControl 5 }

		
--   1.3.6.1.4.1.231.7.1.2.2.1.4.7.2.9.6
		sheIgmpControlVlanTranslationMode OBJECT-TYPE
			SYNTAX SheIgmpVlanMode
			MAX-ACCESS read-write
			STATUS current
			DESCRIPTION
				"Configure VLAN translation mode for the system, 1 is inner tagged, 2 is outer tagged,
				default configuration is inner. This configuration is only functions when system is configured in double tagging mode.
				New with SHE R.8."
			::= { sheIgmpDoubleTaggingControl 6 }

		
--   1.3.6.1.4.1.231.7.1.2.2.1.4.7.2.9.7
		sheIgmpControlVlanDoubleTaggingMode OBJECT-TYPE
			SYNTAX SheIgmpVlanMode
			MAX-ACCESS read-write
			STATUS current
			DESCRIPTION
				"Configure provider VLAN tagging mode for the system, 1 is inner, 2 is outer,
				default configuration is outer. This configuration is only functions when system is configured in 
				double tagging mode.
				New with SHE R.8.
				"
			::= { sheIgmpDoubleTaggingControl 7 }

		
--   1.3.6.1.4.1.231.7.1.2.2.1.4.7.5
		sheIgmpProfileTable OBJECT-TYPE
			SYNTAX SEQUENCE OF SheIgmpProfileEntry
			MAX-ACCESS not-accessible
			STATUS current
			DESCRIPTION
				"The table has one provider entry. It contains the
				provider VLAN and the host and querier settings."
			::= { sheIgmp 5 }

		
--   1.3.6.1.4.1.231.7.1.2.2.1.4.7.5.1
		sheIgmpProfileEntry OBJECT-TYPE
			SYNTAX SheIgmpProfileEntry
			MAX-ACCESS not-accessible
			STATUS current
			DESCRIPTION
				"In first release we will only support one table entry."
			INDEX { sheIgmpProviderIndex }
			::= { sheIgmpProfileTable 1 }

		
		SheIgmpProfileEntry ::=
			SEQUENCE { 
				sheIgmpProviderIndex
					Unsigned32,
				sheIgmpProviderProfileName
					DisplayString,
				sheIgmpProviderProxyIpAddress
					OCTET STRING,
				sheIgmpProviderRobustness
					Unsigned32,
				sheIgmpProviderQueryInterval
					Unsigned32,
				sheIgmpProviderQueryResponseInterval
					Unsigned32,
				sheIgmpProviderStartupQueryInterval
					Unsigned32,
				sheIgmpProviderStartupQueryCount
					Unsigned32,
				sheIgmpProviderLastMemberQueryInterval
					Unsigned32,
				sheIgmpProviderLastMemberQueryCount
					Unsigned32,
				sheIgmpProviderImmediateLeave
					ShePermissionType,
				sheIgmpProviderUnsolicitedReportInterval
					Unsigned32,
				sheIgmpProviderVersion1RouterTimeout
					Unsigned32,
				sheIgmpProviderVersion1RouterPresentTimeout
					TimeTicks,
				sheIgmpProviderVlanMulticastLimitation
					TruthValue,
				sheIgmpProviderMcastBandwithLimit
					Unsigned32,
				sheIgmpProviderDefaultChannelBandwith
					Unsigned32
			 }

--   1.3.6.1.4.1.231.7.1.2.2.1.4.7.5.1.1
		sheIgmpProviderIndex OBJECT-TYPE
			SYNTAX Unsigned32 (1..16)
			MAX-ACCESS read-only
			STATUS current
			DESCRIPTION
				"A table Index."
			::= { sheIgmpProfileEntry 1 }

		
--   1.3.6.1.4.1.231.7.1.2.2.1.4.7.5.1.2
		sheIgmpProviderProfileName OBJECT-TYPE
			SYNTAX DisplayString
			MAX-ACCESS read-only
			STATUS current
			DESCRIPTION
				"Name for easy profile handling.
				Spaces and other special characters (: o) are not allowed!! "
			::= { sheIgmpProfileEntry 2 }

		
--   1.3.6.1.4.1.231.7.1.2.2.1.4.7.5.1.3
		sheIgmpProviderProxyIpAddress OBJECT-TYPE
			SYNTAX OCTET STRING (SIZE (4))
			MAX-ACCESS read-only
			STATUS current
			DESCRIPTION
				"The source IP address used by the IGMP proxy
				for join and leave messages in upstream direction
				and for queries in downstream direction."
			::= { sheIgmpProfileEntry 3 }

		
--   1.3.6.1.4.1.231.7.1.2.2.1.4.7.5.1.4
		sheIgmpProviderRobustness OBJECT-TYPE
			SYNTAX Unsigned32 (1..255)
			MAX-ACCESS read-only
			STATUS current
			DESCRIPTION
				"The Robustness Variable allows tuning for the expected
				packet loss on a subnet.  If a subnet is expected to be
				lossy, the Robustness Variable may be increased.  IGMP is
				robust to (Robustness Variable-1) packet losses. The
				Robustness Variable MUST NOT be zero, and SHOULD
				NOT be one.
				"
			DEFVAL { 2 }
			::= { sheIgmpProfileEntry 4 }

		
--   1.3.6.1.4.1.231.7.1.2.2.1.4.7.5.1.5
		sheIgmpProviderQueryInterval OBJECT-TYPE
			SYNTAX Unsigned32 (10..250)
			UNITS "seconds"
			MAX-ACCESS read-only
			STATUS current
			DESCRIPTION
				"The frequency at which IGMP Host-Query packets (downstream)
				are transmitted on this interface."
			DEFVAL { 125 }
			::= { sheIgmpProfileEntry 5 }

		
--   1.3.6.1.4.1.231.7.1.2.2.1.4.7.5.1.6
		sheIgmpProviderQueryResponseInterval OBJECT-TYPE
			SYNTAX Unsigned32 (0..255)
			UNITS "1/10 seconds"
			MAX-ACCESS read-only
			STATUS current
			DESCRIPTION
				"The Max Response Time inserted into the periodic
				General Queries. When the subscriber host doesn't
				respond to IGMP query messages, it is unsubscribed from
				the multicast group. It must be less than
				the Query Interval."
			DEFVAL { 100 }
			::= { sheIgmpProfileEntry 6 }

		
--   1.3.6.1.4.1.231.7.1.2.2.1.4.7.5.1.7
		sheIgmpProviderStartupQueryInterval OBJECT-TYPE
			SYNTAX Unsigned32 (1..65535)
			UNITS "seconds"
			MAX-ACCESS read-only
			STATUS current
			DESCRIPTION
				"The startup frequency at which IGMP Host-Query
				packets (downstream) are transmitted on this interface."
			::= { sheIgmpProfileEntry 7 }

		
--   1.3.6.1.4.1.231.7.1.2.2.1.4.7.5.1.8
		sheIgmpProviderStartupQueryCount OBJECT-TYPE
			SYNTAX Unsigned32 (1..255)
			MAX-ACCESS read-only
			STATUS current
			DESCRIPTION
				"The Startup Query Count is the number of Queries sent out
				on startup, separated by the Startup Query Interval."
			DEFVAL { 2 }
			::= { sheIgmpProfileEntry 8 }

		
--   1.3.6.1.4.1.231.7.1.2.2.1.4.7.5.1.9
		sheIgmpProviderLastMemberQueryInterval OBJECT-TYPE
			SYNTAX Unsigned32 (0..255)
			UNITS "1/10 seconds"
			MAX-ACCESS read-only
			STATUS current
			DESCRIPTION
				"The Last Member Query Interval is the Max Response Time
				inserted into Group-Specific Queries sent in response to
				Leave Group messages, and is also the amount of time between
				Group-Specific Query messages.  This value may be tuned to
				modify the leave latency of the network.  A reduced value
				results in reduced time to detect the loss of the last
				member of a group.  The value of this object is irrelevant
				if igmpInterfaceVersion is 1.
				"
			DEFVAL { 10 }
			::= { sheIgmpProfileEntry 9 }

		
--   1.3.6.1.4.1.231.7.1.2.2.1.4.7.5.1.10
		sheIgmpProviderLastMemberQueryCount OBJECT-TYPE
			SYNTAX Unsigned32
			MAX-ACCESS read-only
			STATUS current
			DESCRIPTION
				"The Last Member Query Count is the number of Group-Specific
				Queries sent before the router assumes there are no local
				members. "
			DEFVAL { 2 }
			::= { sheIgmpProfileEntry 10 }

		
--   1.3.6.1.4.1.231.7.1.2.2.1.4.7.5.1.11
		sheIgmpProviderImmediateLeave OBJECT-TYPE
			SYNTAX ShePermissionType
			MAX-ACCESS read-only
			STATUS current
			DESCRIPTION
				"If immediate leave is disabled and the client sends
				a leave message, the switch sends a query message to
				the client. When there is no response from the client,
				it is deleted from the multicast group.
				If immediate leave is enabled, the client is deleted
				from the multicast group when the switch receives the
				leave message.
				
				Note:
				Not longer configurable with R2.8."
			::= { sheIgmpProfileEntry 11 }

		
--   1.3.6.1.4.1.231.7.1.2.2.1.4.7.5.1.12
		sheIgmpProviderUnsolicitedReportInterval OBJECT-TYPE
			SYNTAX Unsigned32
			UNITS "seconds"
			MAX-ACCESS read-only
			STATUS current
			DESCRIPTION
				"The Unsolicited Report Interval is the time between
				repetitions of a host's initial report of membership
				in a group (upstream)."
			DEFVAL { 10 }
			::= { sheIgmpProfileEntry 12 }

		
--   1.3.6.1.4.1.231.7.1.2.2.1.4.7.5.1.13
		sheIgmpProviderVersion1RouterTimeout OBJECT-TYPE
			SYNTAX Unsigned32
			UNITS "seconds"
			MAX-ACCESS read-only
			STATUS current
			DESCRIPTION
				"The Version 1 Router Present Timeout is how long a host
				must wait after hearing a Version 1 Query before it may
				send any IGMPv2 messages.
				The time until the local router will assume that
				there are no longer any IGMP version 1 members on the IP
				subnet attached to this interface.  Upon hearing any IGMPv1
				Membership Report, this value is loaded to a timer. While
				the timer is running, the local router ignores any IGMPv2
				Leave messages for this group that it receives on
				this interface.
				
				With R2.8 and support of IGMPv3 these attribute means OlderVersionRouterTimeout."
			DEFVAL { 400 }
			::= { sheIgmpProfileEntry 13 }

		
--   1.3.6.1.4.1.231.7.1.2.2.1.4.7.5.1.14
		sheIgmpProviderVersion1RouterPresentTimeout OBJECT-TYPE
			SYNTAX TimeTicks
			MAX-ACCESS read-only
			STATUS current
			DESCRIPTION
				"The time remaining until a host will assume that there
				are no longer any IGMP version 1 routers on the IP
				subnet attached to this interface.
				Upon hearing any Version 1 Query, this value is reset
				to the group membership timer. While this time remaining
				is non-zero, it may not send any IGMPv2 messages.
				The time remaining until the local router will assume that
				there are no longer any IGMP version 1 members on the IP
				subnet attached to this interface. Upon hearing any IGMPv1
				Membership Report, this value is reset to the group
				membership timer.  While this time remaining is non-zero,
				the local router ignores any IGMPv2 Leave messages for this
				group that it receives on this interface.
				
				With R2.8 and support of IGMPv3 these attribute means OlderVersionRouterPresentTimeout."
			::= { sheIgmpProfileEntry 14 }

		
		sheIgmpProviderVlanMulticastLimitation OBJECT-TYPE
			SYNTAX TruthValue
			MAX-ACCESS read-only
			STATUS current
			DESCRIPTION
				"Configures all possible multicast addresses for IGMP on a per VLAN basis.
				This parameter indicates whether this IGMP provider have the limitation on
				the multicast group/packages or not. 
				Value can be true(1) or false(2).
				False means all subscriber can join all multicast streams through to this whole VLAN if they are member
				of this vlan (unlimited access).
				True is the default state and means only configured groups/packages could be joined (limited access).
				"
			DEFVAL { true }
			::= { sheIgmpProfileEntry 15 }

		
		sheIgmpProviderMcastBandwithLimit OBJECT-TYPE
			SYNTAX Unsigned32 (0..10000 | 65535)
			UNITS "100 kbps"
			MAX-ACCESS read-only
			STATUS current
			DESCRIPTION
				"This is the configured multicast bandwith limitation per provider.
				The value 65535 (0xFFFF) is a special value and means unlimited access for this provider
				(switch off feature AC - admission control - default).
				
				New parameter with SHE R2.8.
				"
			DEFVAL { 65535 }
			::= { sheIgmpProfileEntry 16 }

		
		sheIgmpProviderDefaultChannelBandwith OBJECT-TYPE
			SYNTAX Unsigned32 (0..500)
			UNITS "100 kbps"
			MAX-ACCESS read-only
			STATUS current
			DESCRIPTION
				"This parameter has a range of 0..500 representing the default channel bandwith 
				with a granularity of 100kBits.
				When a non-premium channel is registered, its channel bandwidth will adopt the default
				bandwith.
				
				New parameter with SHE R2.8
				"
			::= { sheIgmpProfileEntry 17 }

		
--   1.3.6.1.4.1.231.7.1.2.2.1.4.7.6
		sheIgmpProfileControl OBJECT IDENTIFIER ::= { sheIgmp 6 }

		
--   1.3.6.1.4.1.231.7.1.2.2.1.4.7.6.1
		sheIgmpProviderControlRequest OBJECT-TYPE
			SYNTAX SheBridgeControlRequestType
			MAX-ACCESS read-write
			STATUS current
			DESCRIPTION
				"setIgmpMode:
				sheIgmpProviderControlMode
				
				setIgmpMaxJoinedSubscribers: (Note: Not longer supported starting with release
				SHE R2.6.)
				sheIgmpProviderControlMaxJoinedSubscribers
				
				setIgmpMaxJoinedGroup:
				sheIgmpProviderControlMaxJoinedGroup
				
				createIgmpProviderEntry:
				sheIgmpProviderControlProfileName
				sheIgmpProviderControlProxyIpAddress
				sheIgmpProviderControlRoboustness
				sheIgmpProviderControlQueryInterval
				sheIgmpProviderControlQueryResponseInterval
				sheIgmpProviderControlStartupQueryInterval
				sheIgmpProviderControlStartupQueryCount
				sheIgmpProviderControlLastMemberQueryInterval
				sheIgmpProviderControlLastMemberQueryCount
				sheIgmpProviderControlImmediateLeave
				sheIgmpProviderControlUnsolicitedReportInterval
				sheIgmpProviderControlVersion1RouterTimeout
				sheIgmpProviderControlVlanMulticastLimitation 
				
				
				modifyIgmpProviderEntry:
				sheIgmpProviderControlIndex
				sheIgmpProviderControlProfileName
				sheIgmpProviderControlProxyIpAddress
				sheIgmpProviderControlRoboustness
				sheIgmpProviderControlQueryInterval
				sheIgmpProviderControlQueryResponseInterval
				sheIgmpProviderControlStartupQueryInterval
				sheIgmpProviderControlStartupQueryCount
				sheIgmpProviderControlLastMemberQueryInterval
				sheIgmpProviderControlLastMemberQueryCount
				sheIgmpProviderControlImmediateLeave
				sheIgmpProviderControlUnsolicitedReportInterval
				sheIgmpProviderControlVersion1RouterTimeout
				sheIgmpProviderControlVlanMulticastLimitation 
				
				deleteIgmpProviderEntry:
				sheIgmpProviderControlIndex
				
				New with SHE R2.8:
				setIgmpProviderChannelAdmission (743):
				sheIgmpProviderControlIndex
				sheIgmpProviderControlMcastBandwithLimit
				sheIgmpProviderControlDefaultChannelBandwith
				
				"
			::= { sheIgmpProfileControl 1 }

		
--   1.3.6.1.4.1.231.7.1.2.2.1.4.7.6.2
		sheIgmpProviderControlStatus OBJECT-TYPE
			SYNTAX SheControlStatusType
			MAX-ACCESS read-only
			STATUS current
			DESCRIPTION
				"The status of a user command. 
				"
			::= { sheIgmpProfileControl 2 }

		
--   1.3.6.1.4.1.231.7.1.2.2.1.4.7.6.3
		sheIgmpProviderControlTimeStamp OBJECT-TYPE
			SYNTAX Unsigned32
			UNITS "sec"
			MAX-ACCESS read-only
			STATUS current
			DESCRIPTION
				"The time stamp of the last command (end of command)."
			::= { sheIgmpProfileControl 3 }

		
--   1.3.6.1.4.1.231.7.1.2.2.1.4.7.6.4
		sheIgmpProviderControlReqResult OBJECT-TYPE
			SYNTAX SheBridgeControlReqResultType
			MAX-ACCESS read-only
			STATUS current
			DESCRIPTION
				"The result of the last user command."
			::= { sheIgmpProfileControl 4 }

		
--   1.3.6.1.4.1.231.7.1.2.2.1.4.7.6.5
		sheIgmpProviderControlTimer OBJECT-TYPE
			SYNTAX Gauge32
			MAX-ACCESS read-only
			STATUS current
			DESCRIPTION
				"The maximum wait time for the manager for a long running user command. 
				"
			::= { sheIgmpProfileControl 5 }

		
--   1.3.6.1.4.1.231.7.1.2.2.1.4.7.6.6
		sheIgmpProviderControlIndex OBJECT-TYPE
			SYNTAX Unsigned32 (1..16)
			MAX-ACCESS read-write
			STATUS current
			DESCRIPTION
				"index of sheIgmpProviderTable
				parameter for
				- modifyIgmpProviderEntry
				- deleteIgmpProviderEntry
				- setIgmpProviderEntrySourceList "
			::= { sheIgmpProfileControl 6 }

		
--   1.3.6.1.4.1.231.7.1.2.2.1.4.7.6.7
		sheIgmpProviderControlMode OBJECT-TYPE
			SYNTAX SheIgmpModeType
			MAX-ACCESS read-write
			STATUS current
			DESCRIPTION
				"IGMP operation mode can be
				off
				proxy
				parameter for
				- setIgmpMode
				
				That is the general NE igmp on/off switch."
			::= { sheIgmpProfileControl 7 }

		
--   1.3.6.1.4.1.231.7.1.2.2.1.4.7.6.8
		sheIgmpProviderControlProfileName OBJECT-TYPE
			SYNTAX DisplayString
			MAX-ACCESS read-write
			STATUS current
			DESCRIPTION
				"Name for easy profile handling.
				Spaces and other special characters (: o) are not allowed!! 
				parameter for
				- createIgmpProviderEntry
				- modifyIgmpProviderEntry"
			::= { sheIgmpProfileControl 8 }

		
--   1.3.6.1.4.1.231.7.1.2.2.1.4.7.6.9
		sheIgmpProviderControlProxyIpAddress OBJECT-TYPE
			SYNTAX OCTET STRING (SIZE (4))
			MAX-ACCESS read-write
			STATUS current
			DESCRIPTION
				"The source IP address used by the IGMP proxy
				for join and leave messages in upstream direction
				and for queries in downstream direction.
				
				parameter for
				- createIgmpProviderEntry
				- modifyIgmpProviderEntry"
			::= { sheIgmpProfileControl 9 }

		
--   1.3.6.1.4.1.231.7.1.2.2.1.4.7.6.10
		sheIgmpProviderControlRobustness OBJECT-TYPE
			SYNTAX Unsigned32 (1..255)
			MAX-ACCESS read-write
			STATUS current
			DESCRIPTION
				"The Robustness Variable allows tuning for the expected
				packet loss on a subnet.  If a subnet is expected to be
				lossy, the Robustness Variable may be increased.  IGMP is
				robust to (Robustness Variable-1) packet losses. The
				Robustness Variable MUST NOT be zero, and SHOULD
				NOT be one.
				parameter for
				- createIgmpProviderEntry
				- modifyIgmpProviderEntry
				"
			::= { sheIgmpProfileControl 10 }

		
--   1.3.6.1.4.1.231.7.1.2.2.1.4.7.6.11
		sheIgmpProviderControlQueryInterval OBJECT-TYPE
			SYNTAX Unsigned32 (10..250)
			UNITS "seconds"
			MAX-ACCESS read-write
			STATUS current
			DESCRIPTION
				"The frequency at which IGMP Host-Query packets (downstream)
				are transmitted on this interface.
				parameter for
				- createIgmpProviderEntry
				- modifyIgmpProviderEntry"
			::= { sheIgmpProfileControl 11 }

		
--   1.3.6.1.4.1.231.7.1.2.2.1.4.7.6.12
		sheIgmpProviderControlQueryResponseInterval OBJECT-TYPE
			SYNTAX Unsigned32 (0..255)
			UNITS "1/10 seconds"
			MAX-ACCESS read-write
			STATUS current
			DESCRIPTION
				"The Max Response Time inserted into the periodic
				General Queries. When the subscriber host doesn't
				respond to IGMP query messages, it is unsubscribed from
				the multicast group. It must be less than
				the Query Interval.
				parameter for
				- createIgmpProviderEntry
				- modifyIgmpProviderEntry"
			::= { sheIgmpProfileControl 12 }

		
--   1.3.6.1.4.1.231.7.1.2.2.1.4.7.6.13
		sheIgmpProviderControlStartupQueryInterval OBJECT-TYPE
			SYNTAX Unsigned32 (1..65535)
			UNITS "seconds"
			MAX-ACCESS read-write
			STATUS current
			DESCRIPTION
				"The startup frequency at which IGMP Host-Query
				packets (downstream) are transmitted on this interface.
				parameter for
				- createIgmpProviderEntry
				- modifyIgmpProviderEntry"
			::= { sheIgmpProfileControl 13 }

		
--   1.3.6.1.4.1.231.7.1.2.2.1.4.7.6.14
		sheIgmpProviderControlStartupQueryCount OBJECT-TYPE
			SYNTAX Unsigned32 (1..255)
			MAX-ACCESS read-write
			STATUS current
			DESCRIPTION
				"The Startup Query Count is the number of Queries sent out
				on startup, separated by the Startup Query Interval.
				parameter for
				- createIgmpProviderEntry
				- modifyIgmpProviderEntry"
			::= { sheIgmpProfileControl 14 }

		
--   1.3.6.1.4.1.231.7.1.2.2.1.4.7.6.15
		sheIgmpProviderControlLastMemberQueryInterval OBJECT-TYPE
			SYNTAX Unsigned32 (0..255)
			UNITS "1/10 seconds"
			MAX-ACCESS read-write
			STATUS current
			DESCRIPTION
				"The Last Member Query Interval is the Max Response Time
				inserted into Group-Specific Queries sent in response to
				Leave Group messages, and is also the amount of time between
				Group-Specific Query messages.  This value may be tuned to
				modify the leave latency of the network.  A reduced value
				results in reduced time to detect the loss of the last
				member of a group.  The value of this object is irrelevant
				if igmpInterfaceVersion is 1.
				parameter for
				- createIgmpProviderEntry
				- modifyIgmpProviderEntry"
			::= { sheIgmpProfileControl 15 }

		
--   1.3.6.1.4.1.231.7.1.2.2.1.4.7.6.16
		sheIgmpProviderControlLastMemberQueryCount OBJECT-TYPE
			SYNTAX Unsigned32
			MAX-ACCESS read-write
			STATUS current
			DESCRIPTION
				"The Last Member Query Count is the number of Group-Specific
				Queries sent before the router assumes there are no local
				members.
				parameter for
				- createIgmpProviderEntry
				- modifyIgmpProviderEntry"
			::= { sheIgmpProfileControl 16 }

		
--   1.3.6.1.4.1.231.7.1.2.2.1.4.7.6.17
		sheIgmpProviderControlImmediateLeave OBJECT-TYPE
			SYNTAX ShePermissionType
			MAX-ACCESS read-write
			STATUS current
			DESCRIPTION
				"If immediate leave is disabled and the client sends
				a leave message, the switch sends a query message to
				the client. When there is no response from the client,
				it is deleted from the multicast group.
				If immediate leave is enabled, the client is deleted
				from the multicast group when the switch receives the
				leave message.
				parameter for
				- createIgmpProviderEntry
				- modifyIgmpProviderEntry
				
				Note:
				Not longer configurable with R2.8."
			::= { sheIgmpProfileControl 17 }

		
--   1.3.6.1.4.1.231.7.1.2.2.1.4.7.6.18
		sheIgmpProviderControlUnsolicitedReportInterval OBJECT-TYPE
			SYNTAX Unsigned32
			UNITS "seconds"
			MAX-ACCESS read-write
			STATUS current
			DESCRIPTION
				"The Unsolicited Report Interval is the time between
				repetitions of a host's initial report of membership
				in a group (upstream).
				parameter for
				- createIgmpProviderEntry
				- modifyIgmpProviderEntry"
			::= { sheIgmpProfileControl 18 }

		
--   1.3.6.1.4.1.231.7.1.2.2.1.4.7.6.19
		sheIgmpProviderControlVersion1RouterTimeout OBJECT-TYPE
			SYNTAX Unsigned32
			MAX-ACCESS read-write
			STATUS current
			DESCRIPTION
				"The Version 1 Router Present Timeout is how long a host
				must wait after hearing a Version 1 Query before it may
				send any IGMPv2 messages.
				The time until the local router will assume that
				there are no longer any IGMP version 1 members on the IP
				subnet attached to this interface.  Upon hearing any IGMPv1
				Membership Report, this value is loaded to a timer. While
				the timer is running, the local router ignores any IGMPv2
				Leave messages for this group that it receives on
				this interface.
				parameter for
				- createIgmpProviderEntry
				- modifyIgmpProviderEntry
				
				With R2.8 and support of IGMPv3 these attribute means OlderVersionRouterTimeout."
			::= { sheIgmpProfileControl 19 }

		
--   1.3.6.1.4.1.231.7.1.2.2.1.4.7.6.20
		sheIgmpProviderControlMaxJoinedSubscriber OBJECT-TYPE
			SYNTAX Unsigned32 (1..65535)
			MAX-ACCESS read-write
			STATUS obsolete
			DESCRIPTION
				"The maximum number of joined subscribers in the system.
				
				Note: This parameter is not longer supported starting with release
				SHE R2.6."
			::= { sheIgmpProfileControl 20 }

		
--   1.3.6.1.4.1.231.7.1.2.2.1.4.7.6.21
		sheIgmpProviderControlMaxJoinedGroup OBJECT-TYPE
			SYNTAX Unsigned32 (1..1000)
			MAX-ACCESS read-write
			STATUS current
			DESCRIPTION
				"The maximum number of multicast groups that could be joined in the system."
			::= { sheIgmpProfileControl 21 }

		
--    1.3.6.1.4.1.231.7.1.2.2.1.4.7.6.22
		sheIgmpProviderControlVlanMulticastLimitation OBJECT-TYPE
			SYNTAX TruthValue
			MAX-ACCESS read-write
			STATUS current
			DESCRIPTION
				"true(1),false(2)
				look at table
				"
			::= { sheIgmpProfileControl 22 }

		
		sheIgmpProviderControlMcastBandwithLimit OBJECT-TYPE
			SYNTAX Unsigned32 (0..10000 | 65535)
			UNITS "100 kbps"
			MAX-ACCESS read-write
			STATUS current
			DESCRIPTION
				"This is the configured multicast bandwith limitation per provider.
				The value 655353 (0xFFFF) is a special value and means unlimited access for this provider
				(switch off feature AC - admission control).
				
				New parameter with SHE R2.8.
				"
			::= { sheIgmpProfileControl 23 }

		
		sheIgmpProviderControlDefaultChannelBandwith OBJECT-TYPE
			SYNTAX Unsigned32 (0..500)
			UNITS "100 kbps"
			MAX-ACCESS read-write
			STATUS current
			DESCRIPTION
				"This parameter has a range of 0..500 representing the default channel bandwith 
				with a granularity of 100kBits.
				When a non-premium channel is registered, its channel bandwidth will adopt the default
				bandwith.
				
				New parameter with SHE R2.8"
			::= { sheIgmpProfileControl 24 }

		
--   1.3.6.1.4.1.231.7.1.2.2.1.4.7.7
		sheIgmpProfileVlanTable OBJECT-TYPE
			SYNTAX SEQUENCE OF SheIgmpProfileVlanEntry
			MAX-ACCESS not-accessible
			STATUS current
			DESCRIPTION
				"The table assigns a VLANs for multicast traffic to
				multicast provider profiles. Both a Vlan and a profile
				can be assigned only once."
			::= { sheIgmp 7 }

		
--   1.3.6.1.4.1.231.7.1.2.2.1.4.7.7.1
		sheIgmpProfileVlanEntry OBJECT-TYPE
			SYNTAX SheIgmpProfileVlanEntry
			MAX-ACCESS not-accessible
			STATUS current
			DESCRIPTION
				"A table entry assigns a VLAN for multicast traffic to a
				multicast provider profile. Both a Vlan and a profile
				can be assigned only once."
			INDEX { sheIgmpProviderIndex }
			::= { sheIgmpProfileVlanTable 1 }

		
		SheIgmpProfileVlanEntry ::=
			SEQUENCE { 
				sheIgmpProfileVlanVlanId
					Integer32,
				sheIgmpProfileVlanMcastEgressPorts
					OCTET STRING,
				sheIgmpProfileVlanInnerVlanId
					Integer32,
				sheIgmpProfileVlanDot1pPriority
					Unsigned32,
				sheIgmpProfileVlanDot1pReportPriority
					Unsigned32,
				sheIgmpProfileVlanDot1pInnerPriority
					Unsigned32,
				sheIgmpProfileVlanDot1pInnerReportPriority
					Unsigned32,
				sheIgmpProfileVlanForkingMode
					SheIgmpProfileVlanForkingModeType,
				sheIgmpProfileVlanOuterVlanId
					Integer32,
				sheIgmpProfileVlanVersion
					SheIgmpVersionType,
				sheIgmpProfileVlanASMStatus
					SheIgmpProviderASM,
				sheIgmpProfileVlanCxUSnoopingState
					SheIgmpProviderVlanCxuSnoopingState,
				sheIgmpProfileVlanDefaultSourceIdList
					OCTET STRING
			 }

--   1.3.6.1.4.1.231.7.1.2.2.1.4.7.7.1.2
		sheIgmpProfileVlanVlanId OBJECT-TYPE
			SYNTAX Integer32 (1..4093)
			MAX-ACCESS read-only
			STATUS current
			DESCRIPTION
				"The provider specific Vlan for multicast traffic.
				The sheVlanIndex for that Vlan."
			::= { sheIgmpProfileVlanEntry 2 }

		
--   1.3.6.1.4.1.231.7.1.2.2.1.4.7.7.1.3
		sheIgmpProfileVlanMcastEgressPorts OBJECT-TYPE
			SYNTAX OCTET STRING (SIZE (0..8192))
			MAX-ACCESS read-only
			STATUS current
			DESCRIPTION
				"List of all fully configured subscriber ports of this multicast VLAN. 
				The list is updated whenever any part of the
				chain bridgePort->MCastPackage->IgmpGroup changes.
				The octet string is a list of pairs of octets each identifying an sheBridgePortIndex.
				The least significant byte is the second octet."
			::= { sheIgmpProfileVlanEntry 3 }

		
--   1.3.6.1.4.1.231.7.1.2.2.1.4.7.7.1.4
		sheIgmpProfileVlanInnerVlanId OBJECT-TYPE
			SYNTAX Integer32 (0 | 1..4093)
			MAX-ACCESS read-only
			STATUS current
			DESCRIPTION
				"An inner vlanid for this igmp provider vlan. 
				It is used in double tagging mode when sending IGMP packets to uplink. 
				It is useless besides double tagging mode and could be 0 in that case."
			::= { sheIgmpProfileVlanEntry 4 }

		
--   1.3.6.1.4.1.231.7.1.2.2.1.4.7.7.1.5
		sheIgmpProfileVlanDot1pPriority OBJECT-TYPE
			SYNTAX Unsigned32 (0..7)
			MAX-ACCESS read-only
			STATUS current
			DESCRIPTION
				"The priority of an IGMP query that is inserted in vlan tag when a querier sends it to subscribers."
			DEFVAL { 5 }
			::= { sheIgmpProfileVlanEntry 5 }

		
--   1.3.6.1.4.1.231.7.1.2.2.1.4.7.7.1.6
		sheIgmpProfileVlanDot1pReportPriority OBJECT-TYPE
			SYNTAX Unsigned32 (0..7)
			MAX-ACCESS read-only
			STATUS current
			DESCRIPTION
				"The priority of an IGMP report that is inserted in vlan tag when a host sends it to router."
			DEFVAL { 5 }
			::= { sheIgmpProfileVlanEntry 6 }

		
--   1.3.6.1.4.1.231.7.1.2.2.1.4.7.7.1.7
		sheIgmpProfileVlanDot1pInnerPriority OBJECT-TYPE
			SYNTAX Unsigned32 (0..7)
			MAX-ACCESS read-only
			STATUS current
			DESCRIPTION
				"The inner priority of an IGMP query that is inserted in inner vlan tag when a querier sends a query to subscribers. 
				This attribute is used only for double tagging mode."
			DEFVAL { 5 }
			::= { sheIgmpProfileVlanEntry 7 }

		
--   1.3.6.1.4.1.231.7.1.2.2.1.4.7.7.1.8
		sheIgmpProfileVlanDot1pInnerReportPriority OBJECT-TYPE
			SYNTAX Unsigned32 (0..7)
			MAX-ACCESS read-only
			STATUS current
			DESCRIPTION
				"The priority of an IGMP report that is inserted in inner vlan tag when a host sends a report to router. 
				This attribute is used only for double tagging mode."
			DEFVAL { 5 }
			::= { sheIgmpProfileVlanEntry 8 }

		
--    1.3.6.1.4.1.231.7.1.2.2.1.4.7.7.1.9
		sheIgmpProfileVlanForkingMode OBJECT-TYPE
			SYNTAX SheIgmpProfileVlanForkingModeType
			MAX-ACCESS read-only
			STATUS current
			DESCRIPTION
				"IGMP forking function enabled will send the original IGMP messages with actual MAC address of the
				clients (e.g. STB) and the corresponding/preserved customer VLAN ID towards the BRAS/Edge Router
				regardless of IGMP proxy configuration/operation.
				
				Possible values:
				noForking(0),
				ipoeForking(1),
				pppoeForking(2)"
			::= { sheIgmpProfileVlanEntry 9 }

		
		sheIgmpProfileVlanOuterVlanId OBJECT-TYPE
			SYNTAX Integer32 (0 | 1..4093)
			MAX-ACCESS read-only
			STATUS current
			DESCRIPTION
				"An outer vlanid for this igmp provider vlan. 
				It is used in double tagging mode when sending IGMP packets to uplink. 
				It is useless besides double tagging mode and could be 0 in that case.
				
				New with R2.8."
			::= { sheIgmpProfileVlanEntry 10 }

		
		sheIgmpProfileVlanVersion OBJECT-TYPE
			SYNTAX SheIgmpVersionType
			MAX-ACCESS read-only
			STATUS current
			DESCRIPTION
				"Configure the supported IGMP version for that provider specific vlan.
				IGMP frames of wrong version should be silently discarded.
				
				New parameter with SHE R2.8"
			DEFVAL { iGMPv2 }
			::= { sheIgmpProfileVlanEntry 11 }

		
		sheIgmpProfileVlanASMStatus OBJECT-TYPE
			SYNTAX SheIgmpProviderASM
			MAX-ACCESS read-only
			STATUS current
			DESCRIPTION
				"Igmp provider ASM (any source multicast)status. When enabled, 
				any source multicast is allowed for the provider, when disabled, 
				any source multicast is not permitted for the provider.
				Default value is Enable.
				
				New parameter with SHE R2.8"
			DEFVAL { enable }
			::= { sheIgmpProfileVlanEntry 12 }

		
--   1.3.6.1.4.1.231.7.1.2.2.1.4.7.7.1.13
		sheIgmpProfileVlanCxUSnoopingState OBJECT-TYPE
			SYNTAX SheIgmpProviderVlanCxuSnoopingState
			MAX-ACCESS read-only
			STATUS current
			DESCRIPTION
				"It indicates whether IGMP CXU snooping mode is enabled on provider.
				Value 0 is disable;  value 1 is enable.
				Default value is disable.
				
				New parameter with SHE R2.8
				"
			DEFVAL { disable }
			::= { sheIgmpProfileVlanEntry 13 }

		
		sheIgmpProfileVlanDefaultSourceIdList OBJECT-TYPE
			SYNTAX OCTET STRING (SIZE (0..100))
			MAX-ACCESS read-only
			STATUS current
			DESCRIPTION
				"This parameter contains a list of indeces which points to valid entries of the sheIgmpSourceIpAddressTable.
				Each octet represents one index value. The list could be empty (default).
				
				If the configured sheIgmpMcastChannelSourceId of related group's points to index with IP address 0.0.0.0
				(wildcard configuration, ASM), any IGMP report message in network direction is sent as IGMv3
				ASM report.
				If the defaultList contains entries pointing to other non-zero IP-addresses, those (all of them) are used to generate
				an IGMPv3 SSM report packet in network direction.
				In case of IGMP provider mode IGMPv3 or IGMPv3Compatible the default IP list is checked with
				channel as key for any received ASM packet to determine the transmission mode (ASM,SSM) and
				source address for packets sent in network direction.
				This configuration is not valid for IGMPv2 provider mode.
				
				This configuration here will be outvoted by a similar configuration for the related IgmpGroup.
				
				New parameter with SHE R2.8 maintenance."
			DEFVAL { ''h }
			::= { sheIgmpProfileVlanEntry 14 }

		
--   1.3.6.1.4.1.231.7.1.2.2.1.4.7.8
		sheIgmpProfileVlanControl OBJECT IDENTIFIER ::= { sheIgmp 8 }

		
--   1.3.6.1.4.1.231.7.1.2.2.1.4.7.8.1
		sheIgmpProfileVlanControlRequest OBJECT-TYPE
			SYNTAX SheBridgeControlRequestType
			MAX-ACCESS read-write
			STATUS current
			DESCRIPTION
				"createIgmpProfileVlanEntry:
				- sheIgmpProfileVlanControlIndex
				- sheIgmpProfileVlanControlVlanId
				- sheIgmpProfileVlanControlDot1pPriority
				- sheIgmpProfileVlanControlDot1pReportPriority
				- sheIgmpProfileVlanControlDot1pInnerPriority
				- sheIgmpProfileVlanControlDot1pReportInnerPriority
				- sheIgmpProfileVlanControlInnerVlanId
				- sheIgmpProfileVlanControlOuterVlanId  (new with R2.8)
				- sheIgmpProfileVlanControlVersion  (new with R2.8)
				- sheIgmpProfileVlanControlASMStatus (new with R2.8)
				- sheIgmpProfileVlanControlCxuSnoopingState (new with R2.8)
				- sheIgmpProfileVlanControlDefaultSourceIdList (new with R2.8 maintenance)
				
				
				deleteIgmpProfileVlanEntry:
				- sheIgmpProfileVlanControlIndex
				
				modifyIgmpProfileVlanDot1p:
				- sheIgmpProfileVlanControlIndex
				- sheIgmpProfileVlanControlDot1pPriority
				- sheIgmpProfileVlanControlDot1pReportPriority
				- sheIgmpProfileVlanControlDot1pInnerPriority
				- sheIgmpProfileVlanControlDot1pReportInnerPriority
				- sheIgmpProfileVlanControlInnerVlanId
				- sheIgmpProfileVlanControlOuterVlanId  (new with R2.8)
				- sheIgmpProfileVlanControlVersion  (new with R2.8)
				- sheIgmpProfileVlanControlASMStatus (new with R2.8)
				- sheIgmpProfileVlanControlCxuSnoopingState (new with R2.8)
				- sheIgmpProfileVlanControlDefaultSourceIdList (new with R2.8 maintenance)
				
				
				R2.4 only
				modifyIgmpProfileVlanForkingMode:
				- sheIgmpProfileVlanControlIndex
				- sheIgmpProfileVlanControlForkingMode"
			::= { sheIgmpProfileVlanControl 1 }

		
--   1.3.6.1.4.1.231.7.1.2.2.1.4.7.8.2
		sheIgmpProfileVlanControlStatus OBJECT-TYPE
			SYNTAX SheControlStatusType
			MAX-ACCESS read-only
			STATUS current
			DESCRIPTION
				"The status of a user command. 
				"
			::= { sheIgmpProfileVlanControl 2 }

		
--   1.3.6.1.4.1.231.7.1.2.2.1.4.7.8.3
		sheIgmpProfileVlanControlTimeStamp OBJECT-TYPE
			SYNTAX Unsigned32
			UNITS "sec"
			MAX-ACCESS read-only
			STATUS current
			DESCRIPTION
				"The time stamp of the last command (end of command)."
			::= { sheIgmpProfileVlanControl 3 }

		
--   1.3.6.1.4.1.231.7.1.2.2.1.4.7.8.4
		sheIgmpProfileVlanControlReqResult OBJECT-TYPE
			SYNTAX SheBridgeControlReqResultType
			MAX-ACCESS read-only
			STATUS current
			DESCRIPTION
				"The result of the last user command."
			::= { sheIgmpProfileVlanControl 4 }

		
--   1.3.6.1.4.1.231.7.1.2.2.1.4.7.8.5
		sheIgmpProfileVlanControlTimer OBJECT-TYPE
			SYNTAX Gauge32
			MAX-ACCESS read-only
			STATUS current
			DESCRIPTION
				"The maximum wait time for the manager for a long running user command. 
				"
			::= { sheIgmpProfileVlanControl 5 }

		
--   1.3.6.1.4.1.231.7.1.2.2.1.4.7.8.6
		sheIgmpProfileVlanControlIndex OBJECT-TYPE
			SYNTAX Unsigned32 (1)
			MAX-ACCESS read-write
			STATUS current
			DESCRIPTION
				"The index sheIgmpProviderIndex of the provider specific
				multicast profile.
				parameter for
				- createIgmpProfileVlanEntry
				- deleteIgmpProfileVlanEntry"
			::= { sheIgmpProfileVlanControl 6 }

		
--   1.3.6.1.4.1.231.7.1.2.2.1.4.7.8.7
		sheIgmpProfileVlanControlVlanId OBJECT-TYPE
			SYNTAX Integer32 (1..4093)
			MAX-ACCESS read-write
			STATUS current
			DESCRIPTION
				"The provider specific Vlan for multicast traffic.
				The sheVlanIndex for that Vlan.
				parameter for
				- deleteIgmpProfileVlanEntry"
			::= { sheIgmpProfileVlanControl 7 }

		
--   1.3.6.1.4.1.231.7.1.2.2.1.4.7.8.8
		sheIgmpProfileVlanControlInnerVlanId OBJECT-TYPE
			SYNTAX Integer32 (0 | 1..4093)
			MAX-ACCESS read-write
			STATUS current
			DESCRIPTION
				"An inner vlanid for this igmp provider vlan or 0 if not used."
			::= { sheIgmpProfileVlanControl 8 }

		
--   1.3.6.1.4.1.231.7.1.2.2.1.4.7.8.9
		sheIgmpProfileVlanControlDot1pPriority OBJECT-TYPE
			SYNTAX Unsigned32 (0..7)
			MAX-ACCESS read-write
			STATUS current
			DESCRIPTION
				"The priority of an IGMP query that is inserted in vlan tag when a querier sends it to subscribers."
			::= { sheIgmpProfileVlanControl 9 }

		
--   1.3.6.1.4.1.231.7.1.2.2.1.4.7.8.10
		sheIgmpProfileVlanControlDot1pReportPriority OBJECT-TYPE
			SYNTAX Unsigned32 (0..7)
			MAX-ACCESS read-write
			STATUS current
			DESCRIPTION
				"The priority of an IGMP report that is inserted in vlan tag when a host sends it to router."
			::= { sheIgmpProfileVlanControl 10 }

		
--   1.3.6.1.4.1.231.7.1.2.2.1.4.7.8.11
		sheIgmpProfileVlanControlDot1pInnerPriority OBJECT-TYPE
			SYNTAX Unsigned32 (0..7)
			MAX-ACCESS read-write
			STATUS current
			DESCRIPTION
				"The inner priority of an IGMP query that is inserted in inner vlan tag when a querier sends a query to subscribers. 
				This attribute is used only for double tagging mode."
			::= { sheIgmpProfileVlanControl 11 }

		
--   1.3.6.1.4.1.231.7.1.2.2.1.4.7.8.12
		sheIgmpProfileVlanControlDot1pInnerReportPriority OBJECT-TYPE
			SYNTAX Unsigned32 (0..7)
			MAX-ACCESS read-write
			STATUS current
			DESCRIPTION
				"The priority of an IGMP report that is inserted in inner vlan tag when a host sends a report to router. 
				This attribute is used only for double tagging mode."
			::= { sheIgmpProfileVlanControl 12 }

		
--    1.3.6.1.4.1.231.7.1.2.2.1.4.7.8.13
		sheIgmpProfileVlanControlForkingMode OBJECT-TYPE
			SYNTAX SheIgmpProfileVlanForkingModeType
			MAX-ACCESS read-write
			STATUS current
			DESCRIPTION
				"When it's set to 0, it means no forking, 
				when set to 1 it means forking mode is IPoE forking, 
				when set to 2, PPPoE forking is used for the provider"
			::= { sheIgmpProfileVlanControl 13 }

		
		sheIgmpProfileVlanControlOuterVlanId OBJECT-TYPE
			SYNTAX Integer32 (0 | 1..4093)
			MAX-ACCESS read-write
			STATUS current
			DESCRIPTION
				"An outer vlanid for this igmp provider vlan or 0 if not used."
			::= { sheIgmpProfileVlanControl 14 }

		
		sheIgmpProviderControlVersion OBJECT-TYPE
			SYNTAX SheIgmpVersionType
			MAX-ACCESS read-write
			STATUS current
			DESCRIPTION
				"Configure the supported IGMP version for that provider specific vlan.
				IGMP frames of wrong version should be silently discarded.
				
				New parameter with SHE R2.8."
			::= { sheIgmpProfileVlanControl 15 }

		
		sheIgmpProviderControlASMStatus OBJECT-TYPE
			SYNTAX SheIgmpProviderASM
			MAX-ACCESS read-write
			STATUS current
			DESCRIPTION
				"Igmp provider ASM (any source multicast)status. When enabled, 
				any source multicast is allowed for the provider, when disabled, 
				any source multicast is not permitted for the provider.
				Default value is Enable.
				parameter for
				- createIgmpProfileVlanEntry:
				- modifyIgmpProfileVlanDot1p:
				
				New parameter with SHE R2.8."
			::= { sheIgmpProfileVlanControl 16 }

		
--   1.3.6.1.4.1.231.7.1.2.2.1.4.7.8.17
		sheIgmpProfileVlanControlCxUSnoopingState OBJECT-TYPE
			SYNTAX SheIgmpProviderVlanCxuSnoopingState
			MAX-ACCESS read-write
			STATUS current
			DESCRIPTION
				"It indicates whether IGMP CXU snooping mode is enabled on provider.
				Value 0 is disable;  value 1 is enable.
				parameter for
				- createIgmpProfileVlanEntry:
				- modifyIgmpProfileVlanDot1p:
				
				New parameter with SHE R2.8."
			::= { sheIgmpProfileVlanControl 17 }

		
		sheIgmpProfileVlanControlDefaultSourceIdList OBJECT-TYPE
			SYNTAX OCTET STRING (SIZE (0..100))
			MAX-ACCESS read-write
			STATUS current
			DESCRIPTION
				"look at table
				
				New parameter with SHE R2.8 maintenance."
			::= { sheIgmpProfileVlanControl 18 }

		
--   1.3.6.1.4.1.231.7.1.2.2.1.4.7.9
		sheIgmpGroupTable OBJECT-TYPE
			SYNTAX SEQUENCE OF SheIgmpGroupEntry
			MAX-ACCESS not-accessible
			STATUS current
			DESCRIPTION
				"The table contains entries for multicast groups. A group
				has a specific multicast address, belongs to a provider
				and to a multicast group package."
			::= { sheIgmp 9 }

		
--   1.3.6.1.4.1.231.7.1.2.2.1.4.7.9.1
		sheIgmpGroupEntry OBJECT-TYPE
			SYNTAX SheIgmpGroupEntry
			MAX-ACCESS not-accessible
			STATUS current
			DESCRIPTION
				"One entry for each Igmp-Group.
				
				If IGMPv3 is running, each table entry represent a single channel configuration."
			INDEX { sheIgmpGroupIndex }
			::= { sheIgmpGroupTable 1 }

		
		SheIgmpGroupEntry ::=
			SEQUENCE { 
				sheIgmpGroupIndex
					Unsigned32,
				sheIgmpGroupIpAddress
					OCTET STRING,
				sheIgmpGroupName
					OCTET STRING,
				sheIgmpGroupProviderId
					Unsigned32,
				sheIgmpGroupMcastGroupPackageList
					OCTET STRING,
				sheIgmpGroupJoinedPortsList
					OCTET STRING,
				sheIgmpGroupLastMembershipReport
					TimeTicks,
				sheIgmpGroupLastLeaveMessage
					TimeTicks,
				sheIgmpGroupSuppliedCardList
					OCTET STRING,
				sheIgmpGroupIsStatic
					TruthValue,
				sheIgmpMcastChannelSourceId
					Unsigned32,
				sheIgmpMcastChannelBandwith
					Unsigned32,
				sheIgmpMcastChannelDefaultSourceIdList
					OCTET STRING
			 }

--   1.3.6.1.4.1.231.7.1.2.2.1.4.7.9.1.1
		sheIgmpGroupIndex OBJECT-TYPE
			SYNTAX Unsigned32 (1..1000)
			MAX-ACCESS read-only
			STATUS current
			DESCRIPTION
				"A table Index."
			::= { sheIgmpGroupEntry 1 }

		
--   1.3.6.1.4.1.231.7.1.2.2.1.4.7.9.1.2
		sheIgmpGroupIpAddress OBJECT-TYPE
			SYNTAX OCTET STRING (SIZE (4))
			MAX-ACCESS read-only
			STATUS current
			DESCRIPTION
				"The used Multicast IP-Address.
				If these Address is set to 00000000, it should work as a * wildcard configuration,
				it means an any group (S,*) channel.
				"
			::= { sheIgmpGroupEntry 2 }

		
--   1.3.6.1.4.1.231.7.1.2.2.1.4.7.9.1.3
		sheIgmpGroupName OBJECT-TYPE
			SYNTAX OCTET STRING (SIZE (0..255))
			MAX-ACCESS read-only
			STATUS current
			DESCRIPTION
				"A unique name for this multicast group.
				Spaces and other special characters (: o) are not allowed!! "
			::= { sheIgmpGroupEntry 3 }

		
--   1.3.6.1.4.1.231.7.1.2.2.1.4.7.9.1.4
		sheIgmpGroupProviderId OBJECT-TYPE
			SYNTAX Unsigned32 (1..16)
			MAX-ACCESS read-only
			STATUS current
			DESCRIPTION
				"That is the index of the corresponding
				sheIgmpProviderTable entry."
			::= { sheIgmpGroupEntry 4 }

		
--   1.3.6.1.4.1.231.7.1.2.2.1.4.7.9.1.5
		sheIgmpGroupMcastGroupPackageList OBJECT-TYPE
			SYNTAX OCTET STRING (SIZE (0..65535))
			MAX-ACCESS read-only
			STATUS current
			DESCRIPTION
				"That is a list of available corresponding indices of the 
				sheIgmpMcastGroupPackageTable where this group is a member.
				Each index has 16 bit. The least significant byte is the
				second octet."
			::= { sheIgmpGroupEntry 5 }

		
--   1.3.6.1.4.1.231.7.1.2.2.1.4.7.9.1.6
		sheIgmpGroupJoinedPortsList OBJECT-TYPE
			SYNTAX OCTET STRING (SIZE (0..65535))
			MAX-ACCESS read-only
			STATUS current
			DESCRIPTION
				"List of subscribers currently subscribing this
				multicast group. The octet string is a list
				of pairs of octets each identifying an
				sheBridgePortIndex. The least significant byte is the
				second octet. A change in this list will not be reported
				by a trap."
			::= { sheIgmpGroupEntry 6 }

		
--   1.3.6.1.4.1.231.7.1.2.2.1.4.7.9.1.7
		sheIgmpGroupLastMembershipReport OBJECT-TYPE
			SYNTAX TimeTicks
			MAX-ACCESS read-only
			STATUS current
			DESCRIPTION
				"Time since the last membership report has been sent
				upstream by the proxy for this multicast group."
			::= { sheIgmpGroupEntry 7 }

		
--   1.3.6.1.4.1.231.7.1.2.2.1.4.7.9.1.8
		sheIgmpGroupLastLeaveMessage OBJECT-TYPE
			SYNTAX TimeTicks
			MAX-ACCESS read-only
			STATUS current
			DESCRIPTION
				"Time since the last leave group message has been sent
				upstream by the proxy for this multicast group."
			::= { sheIgmpGroupEntry 8 }

		
--   1.3.6.1.4.1.231.7.1.2.2.1.4.7.9.1.9
		sheIgmpGroupSuppliedCardList OBJECT-TYPE
			SYNTAX OCTET STRING (SIZE (0..32))
			MAX-ACCESS read-only
			STATUS current
			DESCRIPTION
				"List of entPhysIndices currently receiving data of this
				multicast group. The octet string is a list
				of pairs of octets each identifying an entPhysIndex for that card.
				The least significant byte is the second octet.
				A change in this list will not be reported by a trap."
			::= { sheIgmpGroupEntry 9 }

		
--   1.3.6.1.4.1.231.7.1.2.2.1.4.7.9.1.10
		sheIgmpGroupIsStatic OBJECT-TYPE
			SYNTAX TruthValue
			MAX-ACCESS read-only
			STATUS current
			DESCRIPTION
				"Enable or disable static multicast group configuration."
			DEFVAL { false }
			::= { sheIgmpGroupEntry 10 }

		
		sheIgmpMcastChannelSourceId OBJECT-TYPE
			SYNTAX Unsigned32 (1..100)
			MAX-ACCESS read-only
			STATUS current
			DESCRIPTION
				"This is a index which points to valid entry of the sheIgmpSourceIpAddressTable.
				
				If the source IP of the index is 0.0.0.0 (default), it should work as a '*' wildcard configuration
				and no restriction of possible source ip addresses are made (*,G). In case of IGMP mode iGMPv3 or 
				iGMPv3Compatible ASM will be used.
				This setting is also valid for mode iGMPv2 usage.
				
				The configuration of other source IP's is only valid if iGMPv3 or iGMPv3Compatible mode is running.
				
				New parameter with SHE R2.8."
			::= { sheIgmpGroupEntry 11 }

		
		sheIgmpMcastChannelBandwith OBJECT-TYPE
			SYNTAX Unsigned32 (0..500)
			UNITS "100 kbps"
			MAX-ACCESS read-only
			STATUS current
			DESCRIPTION
				"The bandwith of this channel, with a range of 0..500 representing the bandwith 
				with a granularity of 100kBits. 
				New parameter with SHE R2.8."
			::= { sheIgmpGroupEntry 12 }

		
		sheIgmpMcastChannelDefaultSourceIdList OBJECT-TYPE
			SYNTAX OCTET STRING (SIZE (0..100))
			MAX-ACCESS read-only
			STATUS current
			DESCRIPTION
				"This parameter contains a list of indeces which points to valid entries of the sheIgmpSourceIpAddressTable.
				Each octet represents one index value. The list could be empty (default).
				
				If the configured sheIgmpMcastChannelSourceId of these group points to index with IP address 0.0.0.0 (wildcard configuration, ASM),
				any IGMP report message in network direction is sent as IGMv3 ASM report. If the defaultList 
				contains entries pointing to other non-zero IP-addresses, those (all of them) are used to generate
				an IGMPv3 SSM report packet in network direction.
				In case of IGMP provider mode IGMPv3 or IGMPv3Compatible the default IP list is checked with
				channel as key for any received ASM packet to determine the transmission mode (ASM,SSM) and
				source address for packets sent in network direction.
				This configuration is not valid for IGMPv2 provider mode.
				
				This configuration here will outvote a similar configuration for the corresponding IgmpProvider.
				
				New parameter with SHE R2.8 maintenance."
			DEFVAL { ''h }
			::= { sheIgmpGroupEntry 13 }

		
--   1.3.6.1.4.1.231.7.1.2.2.1.4.7.10
		sheIgmpGroupControl OBJECT IDENTIFIER ::= { sheIgmp 10 }

		
--   1.3.6.1.4.1.231.7.1.2.2.1.4.7.10.1
		sheIgmpGroupControlRequest OBJECT-TYPE
			SYNTAX SheBridgeControlRequestType
			MAX-ACCESS read-write
			STATUS current
			DESCRIPTION
				"createIgmpGroupEntry:
				sheIgmpGroupControlIpAddress
				sheIgmpGroupControlName
				sheIgmpGroupControlProviderId
				sheIgmpGroupControlMcastGroupPackageList
				sheIgmpGroupControlIsStatic
				sheIgmpMcastChannelControlSourceId (new with R2.8)
				sheIgmpMcastChannelControlDefaultSourceIdList (new with R2.8 maintenance)
				
				modifyIgmpGroupEntry:
				sheIgmpGroupControlIndex
				sheIgmpGroupControlIpAddress
				sheIgmpGroupControlName
				sheIgmpGroupControlMcastGroupPackageList
				sheIgmpGroupControlIsStatic
				sheIgmpMcastChannelControlSourceId (new with R2.8)
				sheIgmpMcastChannelControlDefaultSourceIdList (new with R2.8 maintenance)
				
				deleteIgmpGroupEntry:
				sheIgmpGroupControlIndex
				
				New with SHE R2.8:
				setIgmpMcastChannelParameter:
				sheIgmpGroupControlIndex
				sheIgmpMcastChannelControlBandwith
				"
			::= { sheIgmpGroupControl 1 }

		
--   1.3.6.1.4.1.231.7.1.2.2.1.4.7.10.2
		sheIgmpGroupControlStatus OBJECT-TYPE
			SYNTAX SheControlStatusType
			MAX-ACCESS read-only
			STATUS current
			DESCRIPTION
				"The status of a user command. 
				"
			::= { sheIgmpGroupControl 2 }

		
--   1.3.6.1.4.1.231.7.1.2.2.1.4.7.10.3
		sheIgmpGroupControlTimeStamp OBJECT-TYPE
			SYNTAX Unsigned32
			UNITS "sec"
			MAX-ACCESS read-only
			STATUS current
			DESCRIPTION
				"The time stamp of the last command (end of command)."
			::= { sheIgmpGroupControl 3 }

		
--   1.3.6.1.4.1.231.7.1.2.2.1.4.7.10.4
		sheIgmpGroupControlReqResult OBJECT-TYPE
			SYNTAX SheBridgeControlReqResultType
			MAX-ACCESS read-only
			STATUS current
			DESCRIPTION
				"The result of the last user command."
			::= { sheIgmpGroupControl 4 }

		
--   1.3.6.1.4.1.231.7.1.2.2.1.4.7.10.5
		sheIgmpGroupControlTimer OBJECT-TYPE
			SYNTAX Gauge32
			MAX-ACCESS read-only
			STATUS current
			DESCRIPTION
				"The maximum wait time for the manager for a long running user command. 
				"
			::= { sheIgmpGroupControl 5 }

		
--   1.3.6.1.4.1.231.7.1.2.2.1.4.7.10.6
		sheIgmpGroupControlIndex OBJECT-TYPE
			SYNTAX Integer32 (1..1000)
			MAX-ACCESS read-write
			STATUS current
			DESCRIPTION
				"The index of the sheIgmpGroupEntry to be modified.
				parameter for
				- modifyIgmpGroupEntry
				- deleteIgmpGroupEntry"
			::= { sheIgmpGroupControl 6 }

		
--   1.3.6.1.4.1.231.7.1.2.2.1.4.7.10.7
		sheIgmpGroupControlIpAddress OBJECT-TYPE
			SYNTAX OCTET STRING (SIZE (4))
			MAX-ACCESS read-write
			STATUS current
			DESCRIPTION
				"The used Multicast IP-Address.
				parameter for
				- createIgmpGroupEntry
				- modifyIgmpGroupEntry
				
				If these Address is set to 00000000, it should work as a * wildcard configuration."
			::= { sheIgmpGroupControl 7 }

		
--   1.3.6.1.4.1.231.7.1.2.2.1.4.7.10.8
		sheIgmpGroupControlName OBJECT-TYPE
			SYNTAX OCTET STRING (SIZE (0..255))
			MAX-ACCESS read-write
			STATUS current
			DESCRIPTION
				"A unique name for this multicast group.
				Spaces and other special characters (: o) are not allowed!! 
				parameter for
				- createIgmpGroupEntry
				- modifyIgmpGroupEntry"
			::= { sheIgmpGroupControl 8 }

		
--   1.3.6.1.4.1.231.7.1.2.2.1.4.7.10.9
		sheIgmpGroupControlProviderId OBJECT-TYPE
			SYNTAX Integer32 (1..16)
			MAX-ACCESS read-write
			STATUS current
			DESCRIPTION
				"That is the index of the corresponding
				sheIgmpProviderTable entry.
				parameter for
				- createIgmpGroupEntry
				"
			::= { sheIgmpGroupControl 9 }

		
--   1.3.6.1.4.1.231.7.1.2.2.1.4.7.10.10
		sheIgmpGroupControlMcastGroupPackageList OBJECT-TYPE
			SYNTAX OCTET STRING (SIZE (0..65535))
			MAX-ACCESS read-write
			STATUS current
			DESCRIPTION
				"That is a list of available corresponding indices of the 
				sheIgmpMcastGroupPackageTable where this group is a member.
				Each index has 16 bit.
				parameter for
				- createIgmpGroupEntry
				- modifyIgmpGroupEntry"
			::= { sheIgmpGroupControl 10 }

		
--   1.3.6.1.4.1.231.7.1.2.2.1.4.7.10.11
		sheIgmpGroupControlIsStatic OBJECT-TYPE
			SYNTAX TruthValue
			MAX-ACCESS read-write
			STATUS current
			DESCRIPTION
				"Enable or disable static multicast group configuration."
			::= { sheIgmpGroupControl 11 }

		
--  1.3.6.1.4.1.231.7.1.2.2.1.4.7.10.12
		sheIgmpMcastChannelControlSourceId OBJECT-TYPE
			SYNTAX Unsigned32 (1..100)
			MAX-ACCESS read-write
			STATUS current
			DESCRIPTION
				"look at table.
				
				New parameter with SHE R2.8."
			::= { sheIgmpGroupControl 12 }

		
--  1.3.6.1.4.1.231.7.1.2.2.1.4.7.10.13
		sheIgmpMcastChannelControlBandwith OBJECT-TYPE
			SYNTAX Unsigned32 (0..500)
			UNITS "100 kbps"
			MAX-ACCESS read-write
			STATUS current
			DESCRIPTION
				"look at table.
				
				parameter for:
				-setIgmpMcastChannelParameter:
				
				New parameter with SHE R2.8."
			::= { sheIgmpGroupControl 13 }

		
--  1.3.6.1.4.1.231.7.1.2.2.1.4.7.10.14
		sheIgmpMcastChannelControlDefaultSourceIdList OBJECT-TYPE
			SYNTAX OCTET STRING (SIZE (0..100))
			MAX-ACCESS read-write
			STATUS current
			DESCRIPTION
				"look at table
				
				New parameter with SHE R2.8 maintenance."
			::= { sheIgmpGroupControl 14 }

		
--   1.3.6.1.4.1.231.7.1.2.2.1.4.7.11
		sheIgmpMcastGroupPackageTable OBJECT-TYPE
			SYNTAX SEQUENCE OF SheIgmpMcastGroupPackageEntry
			MAX-ACCESS not-accessible
			STATUS current
			DESCRIPTION
				"The table contains entry's they combines multicast groups
				to a multicast group package."
			::= { sheIgmp 11 }

		
--   1.3.6.1.4.1.231.7.1.2.2.1.4.7.11.1
		sheIgmpMcastGroupPackageEntry OBJECT-TYPE
			SYNTAX SheIgmpMcastGroupPackageEntry
			MAX-ACCESS not-accessible
			STATUS current
			DESCRIPTION
				"One entry for each multicast group package."
			INDEX { sheIgmpMcastGroupPackageIndex }
			::= { sheIgmpMcastGroupPackageTable 1 }

		
		SheIgmpMcastGroupPackageEntry ::=
			SEQUENCE { 
				sheIgmpMcastGroupPackageIndex
					Unsigned32,
				sheIgmpMcastGroupPackageName
					OCTET STRING,
				sheIgmpMcastGroupPackageGroupList
					OCTET STRING
			 }

--   1.3.6.1.4.1.231.7.1.2.2.1.4.7.11.1.1
		sheIgmpMcastGroupPackageIndex OBJECT-TYPE
			SYNTAX Unsigned32 (1..100)
			MAX-ACCESS read-only
			STATUS current
			DESCRIPTION
				"Index of the package-table."
			::= { sheIgmpMcastGroupPackageEntry 1 }

		
--   1.3.6.1.4.1.231.7.1.2.2.1.4.7.11.1.2
		sheIgmpMcastGroupPackageName OBJECT-TYPE
			SYNTAX OCTET STRING (SIZE (0..255))
			MAX-ACCESS read-only
			STATUS current
			DESCRIPTION
				"That should be a descriptional name.
				Spaces and other special characters (: o) are not allowed!! "
			::= { sheIgmpMcastGroupPackageEntry 2 }

		
--   1.3.6.1.4.1.231.7.1.2.2.1.4.7.11.1.3
		sheIgmpMcastGroupPackageGroupList OBJECT-TYPE
			SYNTAX OCTET STRING (SIZE (0..8192))
			MAX-ACCESS read-only
			STATUS current
			DESCRIPTION
				"That is a list of pairs of octets each identifying
				a corresponding index of the sheIgmpGroupTable.
				It shows the groups that are members of the package.
				The list is updated by the NE when the package list of
				a group is modified.
				The least significant byte is the second octet."
			::= { sheIgmpMcastGroupPackageEntry 3 }

		
--   1.3.6.1.4.1.231.7.1.2.2.1.4.7.12
		sheIgmpMcastGroupPackageControl OBJECT IDENTIFIER ::= { sheIgmp 12 }

		
--   1.3.6.1.4.1.231.7.1.2.2.1.4.7.12.1
		sheIgmpMcastGroupPackageControlRequest OBJECT-TYPE
			SYNTAX SheBridgeControlRequestType
			MAX-ACCESS read-write
			STATUS current
			DESCRIPTION
				"createIgmpMcastGroupPackage:
				sheIgmpMcastGroupPackageControlName
				
				deleteIgmpMcastGroupPackage:
				sheIgmpMcastGroupPackageControlIndex"
			::= { sheIgmpMcastGroupPackageControl 1 }

		
--   1.3.6.1.4.1.231.7.1.2.2.1.4.7.12.2
		sheIgmpMcastGroupPackageControlStatus OBJECT-TYPE
			SYNTAX SheControlStatusType
			MAX-ACCESS read-only
			STATUS current
			DESCRIPTION
				"The status of a user command. 
				"
			::= { sheIgmpMcastGroupPackageControl 2 }

		
--   1.3.6.1.4.1.231.7.1.2.2.1.4.7.12.3
		sheIgmpMcastGroupPackageControlTimeStamp OBJECT-TYPE
			SYNTAX Unsigned32
			UNITS "sec"
			MAX-ACCESS read-only
			STATUS current
			DESCRIPTION
				"The time stamp of the last command (end of command)."
			::= { sheIgmpMcastGroupPackageControl 3 }

		
--   1.3.6.1.4.1.231.7.1.2.2.1.4.7.12.4
		sheIgmpMcastGroupPackageControlReqResult OBJECT-TYPE
			SYNTAX SheBridgeControlReqResultType
			MAX-ACCESS read-only
			STATUS current
			DESCRIPTION
				"The result of the last user command."
			::= { sheIgmpMcastGroupPackageControl 4 }

		
--   1.3.6.1.4.1.231.7.1.2.2.1.4.7.12.5
		sheIgmpMcastGroupPackageControlTimer OBJECT-TYPE
			SYNTAX Gauge32
			MAX-ACCESS read-only
			STATUS current
			DESCRIPTION
				"The maximum wait time for the manager for a long running user command. 
				"
			::= { sheIgmpMcastGroupPackageControl 5 }

		
--   1.3.6.1.4.1.231.7.1.2.2.1.4.7.12.6
		sheIgmpMcastGroupPackageControlIndex OBJECT-TYPE
			SYNTAX Unsigned32 (1..100)
			MAX-ACCESS read-write
			STATUS current
			DESCRIPTION
				"A table index."
			::= { sheIgmpMcastGroupPackageControl 6 }

		
--   1.3.6.1.4.1.231.7.1.2.2.1.4.7.12.7
		sheIgmpMcastGroupPackageControlName OBJECT-TYPE
			SYNTAX OCTET STRING (SIZE (0..255))
			MAX-ACCESS read-write
			STATUS current
			DESCRIPTION
				"That should be a descriptional name.
				Spaces and other special characters (: o) are not allowed!! 
				parameter for
				- createIgmpMcastGroupPackage"
			::= { sheIgmpMcastGroupPackageControl 7 }

		
--   1.3.6.1.4.1.231.7.1.2.2.1.4.7.13
		sheIgmpPortGroupsTable OBJECT-TYPE
			SYNTAX SEQUENCE OF SheIgmpPortGroupsEntry
			MAX-ACCESS not-accessible
			STATUS current
			DESCRIPTION
				"For the subscriber bridge ports (first table index is sheBridgePortIndex) the table has
				entries for all multicast groups a port has currently joined.
				Because IgmpV3 allow the configuration of wildcard's for used multicast and/or source IP address,
				R2.8 maintenance modify the second table index to a free running index and add parameter to
				show the used multicast IP address."
			::= { sheIgmp 13 }

		
--   1.3.6.1.4.1.231.7.1.2.2.1.4.7.13.1
		sheIgmpPortGroupsEntry OBJECT-TYPE
			SYNTAX SheIgmpPortGroupsEntry
			MAX-ACCESS not-accessible
			STATUS current
			DESCRIPTION
				"If IGMPv3 is running, it represent a joined channel!"
			INDEX { sheBridgePortIndex, sheIgmpPortGroupsIndex }
			::= { sheIgmpPortGroupsTable 1 }

		
		SheIgmpPortGroupsEntry ::=
			SEQUENCE { 
				sheIgmpPortGroupsStpIpAddress
					OCTET STRING,
				sheIgmpPortGroupsTimeFirstMembRep
					TimeTicks,
				sheIgmpPortGroupsTimeLastMembRep
					TimeTicks,
				sheIgmpPortGroupsFiltermode
					SheIgmpPortGroupsFiltermodeType,
				sheIgmpPortGroupsSourceId
					OCTET STRING,
				sheIgmpPortGroupsIpAddress
					OCTET STRING,
				sheIgmpPortGroupsIndex
					Unsigned32
			 }

--   1.3.6.1.4.1.231.7.1.2.2.1.4.7.13.1.1
		sheIgmpPortGroupsStpIpAddress OBJECT-TYPE
			SYNTAX OCTET STRING (SIZE (4..20))
			MAX-ACCESS read-only
			STATUS current
			DESCRIPTION
				"The IP address of the subsribers host (set top box) that has joined the multicast group.
				Each Ip address is a set of 4 octets.
				
				Expanded with R2.8:
				If Igmpv3 is running up to five boxes could be listed here."
			::= { sheIgmpPortGroupsEntry 1 }

		
--   1.3.6.1.4.1.231.7.1.2.2.1.4.7.13.1.2
		sheIgmpPortGroupsTimeFirstMembRep OBJECT-TYPE
			SYNTAX TimeTicks
			MAX-ACCESS read-only
			STATUS obsolete
			DESCRIPTION
				"The time when the first membership report for the joined multicast group has been received from the subscriber.
				
				Note:
				Set to obsolete with R2.8 - no valid information could be returned!"
			::= { sheIgmpPortGroupsEntry 2 }

		
--    1.3.6.1.4.1.231.7.1.2.2.1.4.7.13.1.3
		sheIgmpPortGroupsTimeLastMembRep OBJECT-TYPE
			SYNTAX TimeTicks
			MAX-ACCESS read-only
			STATUS current
			DESCRIPTION
				"The time when the last membership report for the joined multicast group has been received from the subscriber."
			::= { sheIgmpPortGroupsEntry 3 }

		
		sheIgmpPortGroupsFiltermode OBJECT-TYPE
			SYNTAX SheIgmpPortGroupsFiltermodeType
			MAX-ACCESS read-only
			STATUS current
			DESCRIPTION
				"This parameter may be either INCLUDE or EXCLUDE. In INCLUDE mode, reception of packets
				sent to the specified multicast address is requested *only* from those IP source address
				listed in the  source-id parameter. In EXCLUDE mode, reception of packets sent to the
				given multicast address is requested from all IP source addresses *except* those listed
				in the source-id parameter.
				
				New parameter with SHE R2.8 and only valid for IGMPv3."
			::= { sheIgmpPortGroupsEntry 4 }

		
		sheIgmpPortGroupsSourceId OBJECT-TYPE
			SYNTAX OCTET STRING (SIZE (0..4))
			MAX-ACCESS read-only
			STATUS current
			DESCRIPTION
				"This is an IP unicast addresses from which multicast reception is desired or not desired,
				depending on the filter mode. IP address entry consist of 4 Octets and should be a subset
				or identical to the corresponding sheIgmpMcastChannelSourceId of the joined group.
				
				New parameter with SHE R2.8 and only valid for IGMPv3."
			::= { sheIgmpPortGroupsEntry 5 }

		
		sheIgmpPortGroupsIpAddress OBJECT-TYPE
			SYNTAX OCTET STRING (SIZE (4))
			MAX-ACCESS read-only
			STATUS current
			DESCRIPTION
				"The used Multicast IP-Address of the joined group.
				
				New parameter with SHE R2.8 maintenance.
				"
			::= { sheIgmpPortGroupsEntry 6 }

		
		sheIgmpPortGroupsIndex OBJECT-TYPE
			SYNTAX Unsigned32 (1..1000)
			MAX-ACCESS read-only
			STATUS current
			DESCRIPTION
				"The new second tableIndex starting with R2.8 maintenance.
				It is a free running Index which show the amount of actual joined groups by this subscriber."
			::= { sheIgmpPortGroupsEntry 7 }

		
--   1.3.6.1.4.1.231.7.1.2.2.1.4.7.14
		sheIgmpNotifications OBJECT IDENTIFIER ::= { sheIgmp 14 }

		
--   1.3.6.1.4.1.231.7.1.2.2.1.4.7.14.1
		sheIgmpModeModified NOTIFICATION-TYPE
			OBJECTS { sheIgmpProviderControlTimeStamp, sheIgmpMode }
			STATUS current
			DESCRIPTION 
				"The general IGMP operation mode has been modified
				by the operator."
			::= { sheIgmpNotifications 1 }

		
--   1.3.6.1.4.1.231.7.1.2.2.1.4.7.14.2
		sheIgmpProfileEntryCreated NOTIFICATION-TYPE
			OBJECTS { sheIgmpProviderControlTimeStamp, sheIgmpProviderControlIndex, sheIgmpProviderProfileName, sheIgmpProviderProxyIpAddress, sheIgmpProviderRobustness, 
				sheIgmpProviderQueryInterval, sheIgmpProviderQueryResponseInterval, sheIgmpProviderStartupQueryInterval, sheIgmpProviderStartupQueryCount, sheIgmpProviderLastMemberQueryInterval, 
				sheIgmpProviderLastMemberQueryCount, sheIgmpProviderImmediateLeave, sheIgmpProviderUnsolicitedReportInterval, sheIgmpProviderVersion1RouterTimeout, sheIgmpProviderVlanMulticastLimitation
				 }
			STATUS current
			DESCRIPTION 
				"A new entry in the sheIgmpProfileTable has been created
				by the operator."
			::= { sheIgmpNotifications 2 }

		
--   1.3.6.1.4.1.231.7.1.2.2.1.4.7.14.3
		sheIgmpProfileEntryModified NOTIFICATION-TYPE
			OBJECTS { sheIgmpProviderControlTimeStamp, sheIgmpProviderControlIndex, sheIgmpProviderProfileName, sheIgmpProviderProxyIpAddress, sheIgmpProviderRobustness, 
				sheIgmpProviderQueryInterval, sheIgmpProviderQueryResponseInterval, sheIgmpProviderStartupQueryInterval, sheIgmpProviderStartupQueryCount, sheIgmpProviderLastMemberQueryInterval, 
				sheIgmpProviderLastMemberQueryCount, sheIgmpProviderImmediateLeave, sheIgmpProviderUnsolicitedReportInterval, sheIgmpProviderVersion1RouterTimeout, sheIgmpProviderVlanMulticastLimitation
				 }
			STATUS current
			DESCRIPTION 
				"An entry in the sheIgmpProfileTable has been modified
				by the operator."
			::= { sheIgmpNotifications 3 }

		
--   1.3.6.1.4.1.231.7.1.2.2.1.4.7.14.4
		sheIgmpProfileEntryDeleted NOTIFICATION-TYPE
			OBJECTS { sheIgmpProviderControlTimeStamp, sheIgmpProviderControlIndex }
			STATUS current
			DESCRIPTION 
				"An entry in the sheIgmpProfileTable has been deleted
				by the operator."
			::= { sheIgmpNotifications 4 }

		
--   1.3.6.1.4.1.231.7.1.2.2.1.4.7.14.5
		sheIgmpProfileControlResult NOTIFICATION-TYPE
			OBJECTS { sheIgmpProviderControlTimeStamp, sheIgmpProviderControlRequest, sheIgmpProviderControlReqResult }
			STATUS current
			DESCRIPTION 
				"Notification of port command ending and result in case
				of long running command."
			::= { sheIgmpNotifications 5 }

		
--  1.3.6.1.4.1.231.7.1.2.2.1.4.7.14.6
		sheIgmpProfileVlanEntryCreated NOTIFICATION-TYPE
			OBJECTS { sheIgmpProfileVlanControlTimeStamp, sheIgmpProfileVlanControlVlanId, sheIgmpProfileVlanControlIndex, sheIgmpProfileVlanDot1pPriority, sheIgmpProfileVlanDot1pReportPriority, 
				sheIgmpProfileVlanDot1pInnerPriority, sheIgmpProfileVlanDot1pInnerReportPriority, sheIgmpProfileVlanForkingMode, sheIgmpProfileVlanInnerVlanId, sheIgmpProfileVlanOuterVlanId, 
				sheIgmpProfileVlanVersion, sheIgmpProfileVlanASMStatus, sheIgmpProfileVlanCxUSnoopingState, sheIgmpProfileVlanDefaultSourceIdList }
			STATUS current
			DESCRIPTION 
				"A new entry in the sheIgmpProfileVlanTable has been created by the operator."
			::= { sheIgmpNotifications 6 }

		
--  1.3.6.1.4.1.231.7.1.2.2.1.4.7.14.7
		sheIgmpProfileVlanEntryModified NOTIFICATION-TYPE
			OBJECTS { sheIgmpProfileVlanControlTimeStamp, sheIgmpProfileVlanControlVlanId, sheIgmpProfileVlanControlIndex, sheIgmpProfileVlanMcastEgressPorts }
			STATUS current
			DESCRIPTION 
				"An entry in the sheIgmpProfileVlanTable has been modified by the NE. 
				The sheIgmpProfileVlanMcastEgressPorts has changed."
			::= { sheIgmpNotifications 7 }

		
--   1.3.6.1.4.1.231.7.1.2.2.1.4.7.14.8
		sheIgmpProfileVlanEntryDeleted NOTIFICATION-TYPE
			OBJECTS { sheIgmpProfileVlanControlTimeStamp, sheIgmpProfileVlanControlIndex }
			STATUS current
			DESCRIPTION 
				"An entry in the sheIgmpProfileVlanTable has been
				deleted by the operator."
			::= { sheIgmpNotifications 8 }

		
--   1.3.6.1.4.1.231.7.1.2.2.1.4.7.14.9
		sheIgmpProfileVlanControlResult NOTIFICATION-TYPE
			OBJECTS { sheIgmpProfileVlanControlTimeStamp, sheIgmpProfileVlanControlRequest, sheIgmpProfileVlanControlReqResult }
			STATUS current
			DESCRIPTION 
				"Notification of port command ending and result in case
				of long running command."
			::= { sheIgmpNotifications 9 }

		
--   1.3.6.1.4.1.231.7.1.2.2.1.4.7.14.10
		sheIgmpGroupEntryCreated NOTIFICATION-TYPE
			OBJECTS { sheIgmpGroupControlTimeStamp, sheIgmpGroupControlIndex, sheIgmpGroupIpAddress, sheIgmpGroupName, sheIgmpGroupProviderId, 
				sheIgmpGroupMcastGroupPackageList, sheIgmpGroupIsStatic, sheIgmpMcastChannelSourceId, sheIgmpMcastChannelDefaultSourceIdList }
			STATUS current
			DESCRIPTION 
				"A new entry in the sheIgmpGroupTable has been created by the operator."
			::= { sheIgmpNotifications 10 }

		
--   1.3.6.1.4.1.231.7.1.2.2.1.4.7.14.11
		sheIgmpGroupEntryModified NOTIFICATION-TYPE
			OBJECTS { sheIgmpGroupControlTimeStamp, sheIgmpGroupControlIndex, sheIgmpGroupIpAddress, sheIgmpGroupName, sheIgmpGroupProviderId, 
				sheIgmpGroupMcastGroupPackageList, sheIgmpGroupIsStatic, sheIgmpMcastChannelSourceId, sheIgmpMcastChannelDefaultSourceIdList }
			STATUS current
			DESCRIPTION 
				"An entry in the sheIgmpGroupTable has been modified by the operator."
			::= { sheIgmpNotifications 11 }

		
--   1.3.6.1.4.1.231.7.1.2.2.1.4.7.14.12
		sheIgmpGroupEntryDeleted NOTIFICATION-TYPE
			OBJECTS { sheIgmpGroupControlTimeStamp, sheIgmpGroupControlIndex }
			STATUS current
			DESCRIPTION 
				"An entry in the sheIgmpGroupTable has been deleted
				by the operator."
			::= { sheIgmpNotifications 12 }

		
--   1.3.6.1.4.1.231.7.1.2.2.1.4.7.14.13
		sheIgmpGroupControlResult NOTIFICATION-TYPE
			OBJECTS { sheIgmpGroupControlTimeStamp, sheIgmpGroupControlRequest, sheIgmpGroupControlReqResult }
			STATUS current
			DESCRIPTION 
				"Notification of port command ending and result in case
				of long running command."
			::= { sheIgmpNotifications 13 }

		
--   1.3.6.1.4.1.231.7.1.2.2.1.4.7.14.14
		sheIgmpMcastGroupPackageEntryCreated NOTIFICATION-TYPE
			OBJECTS { sheIgmpMcastGroupPackageControlTimeStamp, sheIgmpMcastGroupPackageControlIndex, sheIgmpMcastGroupPackageName }
			STATUS current
			DESCRIPTION 
				"An entry in the sheIgmpMcastGroupPackageTable has been
				created by the operator."
			::= { sheIgmpNotifications 14 }

		
--   1.3.6.1.4.1.231.7.1.2.2.1.4.7.14.15
		sheIgmpMcastGroupPackageEntryModified NOTIFICATION-TYPE
			OBJECTS { sheIgmpMcastGroupPackageControlTimeStamp, sheIgmpMcastGroupPackageControlIndex, sheIgmpMcastGroupPackageGroupList }
			STATUS current
			DESCRIPTION 
				"An entry in the sheIgmpMcastGroupPackageTable has been
				modified by the NE. The sheIgmpMcastGroupPackageGroupList
				has changed."
			::= { sheIgmpNotifications 15 }

		
--   1.3.6.1.4.1.231.7.1.2.2.1.4.7.14.16
		sheIgmpMcastGroupPackageEntryDeleted NOTIFICATION-TYPE
			OBJECTS { sheIgmpMcastGroupPackageControlTimeStamp, sheIgmpMcastGroupPackageControlIndex }
			STATUS current
			DESCRIPTION 
				"An entry in the sheIgmpMcastGroupPackageTable has been
				deleted by the operator."
			::= { sheIgmpNotifications 16 }

		
--   1.3.6.1.4.1.231.7.1.2.2.1.4.7.14.17
		sheIgmpMcastGroupPackageControlResult NOTIFICATION-TYPE
			OBJECTS { sheIgmpMcastGroupPackageControlTimeStamp, sheIgmpMcastGroupPackageControlRequest, sheIgmpMcastGroupPackageControlReqResult }
			STATUS current
			DESCRIPTION 
				"Notification of port command ending and result in case
				of long running command."
			::= { sheIgmpNotifications 17 }

		
--   1.3.6.1.4.1.231.7.1.2.2.1.4.7.14.18
		sheIgmpMaxJoinedSubscriberModified NOTIFICATION-TYPE
			OBJECTS { sheIgmpProviderControlTimeStamp, sheIgmpMaxJoinedSubscriber }
			STATUS obsolete
			DESCRIPTION 
				"The general IGMP MaxJoinedSubscriber-Value has been modified
				by the operator.
				
				Note: This parameter is not longer supported starting with release
				SHE R2.6."
			::= { sheIgmpNotifications 18 }

		
--   1.3.6.1.4.1.231.7.1.2.2.1.4.7.14.19
		sheIgmpFloodVlanCreated NOTIFICATION-TYPE
			OBJECTS { sheIgmpFloodVlanControlTimestamp, sheIgmpFloodVlanControlVlanId }
			STATUS current
			DESCRIPTION 
				"An entry in the sheIgmpFloodVlanTable was created by the operator."
			::= { sheIgmpNotifications 19 }

		
--   1.3.6.1.4.1.231.7.1.2.2.1.4.7.14.20
		sheIgmpFloodVlanDeleted NOTIFICATION-TYPE
			OBJECTS { sheIgmpFloodVlanControlTimestamp, sheIgmpFloodVlanControlVlanId }
			STATUS current
			DESCRIPTION 
				"An entry in the sheIgmpFloodVlanTable was deleted by the operator."
			::= { sheIgmpNotifications 20 }

		
--   1.3.6.1.4.1.231.7.1.2.2.1.4.7.14.21
		sheIgmpProfileVlanDot1pModified NOTIFICATION-TYPE
			OBJECTS { sheIgmpProfileVlanControlIndex, sheIgmpProfileVlanControlTimeStamp, sheIgmpProfileVlanDot1pPriority, sheIgmpProfileVlanDot1pReportPriority, sheIgmpProfileVlanDot1pInnerPriority, 
				sheIgmpProfileVlanDot1pInnerReportPriority, sheIgmpProfileVlanForkingMode, sheIgmpProfileVlanInnerVlanId, sheIgmpProfileVlanOuterVlanId, sheIgmpProfileVlanVersion, 
				sheIgmpProfileVlanASMStatus, sheIgmpProfileVlanCxUSnoopingState, sheIgmpProfileVlanDefaultSourceIdList }
			STATUS current
			DESCRIPTION 
				"An entry of Dot1p in the sheIgmpProfileVlanTable has been modified by the operator."
			::= { sheIgmpNotifications 21 }

		
--   1.3.6.1.4.1.231.7.1.2.2.1.4.7.14.22
		sheIgmpMaxJoinedGroupModified NOTIFICATION-TYPE
			OBJECTS { sheIgmpProviderControlTimeStamp, sheIgmpMaxJoinedGroup }
			STATUS current
			DESCRIPTION 
				"The maximum number of multicast group that a subscriber can join has been modified by the operator."
			::= { sheIgmpNotifications 22 }

		
		sheIgmpProfileChannelAdmissionModified NOTIFICATION-TYPE
			OBJECTS { sheIgmpProviderControlTimeStamp, sheIgmpProviderControlIndex, sheIgmpProviderControlMcastBandwithLimit, sheIgmpProviderControlDefaultChannelBandwith }
			STATUS current
			DESCRIPTION 
				"IGMP Mcast admission control feature configuration done.
				
				New with R2.8."
			::= { sheIgmpNotifications 24 }

		
		sheIgmpChannelParameterModified NOTIFICATION-TYPE
			OBJECTS { sheIgmpGroupControlTimeStamp, sheIgmpGroupControlIndex, sheIgmpMcastChannelBandwith }
			STATUS current
			DESCRIPTION 
				"IGMPv3 group channel releated parameters modified."
			::= { sheIgmpNotifications 25 }

		
		sheIgmpSourceIpEntryCreated NOTIFICATION-TYPE
			OBJECTS { sheIgmpSourceIpControlTimeStamp, sheIgmpSourceIpControlIndex, sheIgmpSourceIpControlAddress }
			STATUS current
			DESCRIPTION 
				"Igmpv3 SourceIpAddress entry created."
			::= { sheIgmpNotifications 26 }

		
		sheIgmpSourceIpEntryDeleted NOTIFICATION-TYPE
			OBJECTS { sheIgmpSourceIpControlTimeStamp, sheIgmpSourceIpControlIndex, sheIgmpSourceIpControlAddress }
			STATUS current
			DESCRIPTION 
				"Igmpv3 SourceIpAddress entry deleted."
			::= { sheIgmpNotifications 27 }

		
--   1.3.6.1.4.1.231.7.1.2.2.1.4.7.14.34
		sheIgmpTagModeModified NOTIFICATION-TYPE
			OBJECTS { sheIgmpDoubleTaggingControlTimeStamp, sheIgmpControlVlanTranslationMode, sheIgmpControlVlanDoubleTaggingMode }
			STATUS current
			DESCRIPTION 
				"The general IGMP Tag parameterS has been modified by the operator."
			::= { sheIgmpNotifications 34 }

		
--   1.3.6.1.4.1.231.7.1.2.2.1.4.7.16
		sheIgmpPerformance OBJECT IDENTIFIER ::= { sheIgmp 16 }

		
--   1.3.6.1.4.1.231.7.1.2.2.1.4.7.16.1
		sheIgmpPerformanceMonitoring OBJECT IDENTIFIER ::= { sheIgmpPerformance 1 }

		
--   1.3.6.1.4.1.231.7.1.2.2.1.4.7.16.1.1
		sheIgmpPmObjectTable OBJECT-TYPE
			SYNTAX SEQUENCE OF SheIgmpPmObjectEntry
			MAX-ACCESS not-accessible
			STATUS current
			DESCRIPTION
				"The table holds all IGMP PM objects existing in the NE."
			::= { sheIgmpPerformanceMonitoring 1 }

		
--   1.3.6.1.4.1.231.7.1.2.2.1.4.7.16.1.1.1
		sheIgmpPmObjectEntry OBJECT-TYPE
			SYNTAX SheIgmpPmObjectEntry
			MAX-ACCESS not-accessible
			STATUS current
			DESCRIPTION
				"A table entry shows the multicast group a PM object is related to."
			INDEX { sheIgmpPmObjectIndex }
			::= { sheIgmpPmObjectTable 1 }

		
		SheIgmpPmObjectEntry ::=
			SEQUENCE { 
				sheIgmpPmObjectIndex
					Unsigned32,
				sheIgmpPmObjectGroupIndex
					Unsigned32
			 }

--   1.3.6.1.4.1.231.7.1.2.2.1.4.7.16.1.1.1.1
		sheIgmpPmObjectIndex OBJECT-TYPE
			SYNTAX Unsigned32 (1..1000)
			MAX-ACCESS read-only
			STATUS current
			DESCRIPTION
				"Unique index for IGMP PM objects existing in the NE.
				One multicast group can have one PM object, including
				both interval types."
			::= { sheIgmpPmObjectEntry 1 }

		
--   1.3.6.1.4.1.231.7.1.2.2.1.4.7.16.1.1.1.2
		sheIgmpPmObjectGroupIndex OBJECT-TYPE
			SYNTAX Unsigned32 (1..1000)
			MAX-ACCESS read-only
			STATUS current
			DESCRIPTION
				"Index sheIgmpGroupIndex of the sheIgmpGroupTable
				selects the multicast group a PM object is related to."
			::= { sheIgmpPmObjectEntry 2 }

		
--   1.3.6.1.4.1.231.7.1.2.2.1.4.7.16.1.2
		sheIgmpPmCurrentTable OBJECT-TYPE
			SYNTAX SEQUENCE OF SheIgmpPmCurrentEntry
			MAX-ACCESS not-accessible
			STATUS current
			DESCRIPTION
				"This table contains the entries for Performance Monitoring
				for multicast groups of the current 15 minute interval
				and the current day. "
			::= { sheIgmpPerformanceMonitoring 2 }

		
--   1.3.6.1.4.1.231.7.1.2.2.1.4.7.16.1.2.1
		sheIgmpPmCurrentEntry OBJECT-TYPE
			SYNTAX SheIgmpPmCurrentEntry
			MAX-ACCESS not-accessible
			STATUS current
			DESCRIPTION
				"An entry describing the current PM data of a multicast group for a certain interval type.
				Indices are sheIgmpPmObjectIndex and sheIgmpPmCurrentIntervalType."
			INDEX { sheIgmpPmObjectIndex, sheIgmpPmCurrentIntervalType }
			::= { sheIgmpPmCurrentTable 1 }

		
		SheIgmpPmCurrentEntry ::=
			SEQUENCE { 
				sheIgmpPmCurrentIntervalType
					ShePmIntervalType,
				sheIgmpPmCurrentAdminState
					SheAdminStateType,
				sheIgmpPmCurrentSuspectFlag
					ShePmSuspectFlagType,
				sheIgmpPmCurrentHistEntrySize
					Unsigned32,
				sheIgmpPmCurrentHistEntriesAvailable
					Unsigned32,
				sheIgmpPmCurrentElapsedTime
					Unsigned32,
				sheIgmpPmCurrentMembershipReportsFromHost
					Unsigned32,
				sheIgmpPmCurrentPeakMembershipReportsFromHost
					Unsigned32,
				sheIgmpPmCurrentTimeOfPeakMembershipReports
					TimeTicks,
				sheIgmpPmCurrentGroupLeavesFromHost
					Unsigned32,
				sheIgmpPmCurrentPeakGroupLeavesFromHost
					Unsigned32,
				sheIgmpPmCurrentTimeOfPeakGroupLeaves
					TimeTicks,
				sheIgmpPmCurrentMembershipReportsToRouter
					Unsigned32,
				sheIgmpPmCurrentGroupLeavesToRouter
					Unsigned32,
				sheIgmpPmCurrentPeakMulticastLeaves
					Unsigned32
			 }

--   1.3.6.1.4.1.231.7.1.2.2.1.4.7.16.1.2.1.1
		sheIgmpPmCurrentIntervalType OBJECT-TYPE
			SYNTAX ShePmIntervalType
			MAX-ACCESS read-only
			STATUS current
			DESCRIPTION
				"This attribute is used to select between the
				15 min  or the day accumulation types. "
			::= { sheIgmpPmCurrentEntry 1 }

		
--   1.3.6.1.4.1.231.7.1.2.2.1.4.7.16.1.2.1.2
		sheIgmpPmCurrentAdminState OBJECT-TYPE
			SYNTAX SheAdminStateType
			MAX-ACCESS read-write
			STATUS current
			DESCRIPTION
				"This read-write attribute is used to activate (up)
				and deactivate (down) performance monitoring for the
				multicast group and interval type."
			::= { sheIgmpPmCurrentEntry 2 }

		
--   1.3.6.1.4.1.231.7.1.2.2.1.4.7.16.1.2.1.3
		sheIgmpPmCurrentSuspectFlag OBJECT-TYPE
			SYNTAX ShePmSuspectFlagType
			MAX-ACCESS read-only
			STATUS current
			DESCRIPTION
				"This read-only attribute will be set to indicate that
				troubles arose during an interval and that the counter
				values are suspect and incomplete. "
			::= { sheIgmpPmCurrentEntry 3 }

		
--   1.3.6.1.4.1.231.7.1.2.2.1.4.7.16.1.2.1.4
		sheIgmpPmCurrentHistEntrySize OBJECT-TYPE
			SYNTAX Unsigned32
			MAX-ACCESS read-only
			STATUS current
			DESCRIPTION
				"The number of history entries configured for
				the multicast group and interval type. This attribute
				is used for history data collection. The default value
				is 1 and means at least one history entry is desired."
			DEFVAL { 1 }
			::= { sheIgmpPmCurrentEntry 4 }

		
--   1.3.6.1.4.1.231.7.1.2.2.1.4.7.16.1.2.1.5
		sheIgmpPmCurrentHistEntriesAvailable OBJECT-TYPE
			SYNTAX Unsigned32
			MAX-ACCESS read-only
			STATUS current
			DESCRIPTION
				"This read-only attribute indicates how many HistEntries
				are already available. The range of values is between 0
				and sheIgmpPmCurrentHistEntrySize. Thereby 0 means
				that this entry is not valid."
			::= { sheIgmpPmCurrentEntry 5 }

		
--   1.3.6.1.4.1.231.7.1.2.2.1.4.7.16.1.2.1.6
		sheIgmpPmCurrentElapsedTime OBJECT-TYPE
			SYNTAX Unsigned32
			MAX-ACCESS read-only
			STATUS current
			DESCRIPTION
				"This read-only attribute represents the difference
				between the current time and the start of the present
				summary interval. Units are seconds when 15 minute
				interval is selected or minutes for day interval.
				(Note: accurate to the sample time interval)."
			::= { sheIgmpPmCurrentEntry 6 }

		
--   1.3.6.1.4.1.231.7.1.2.2.1.4.7.16.1.2.1.7
		sheIgmpPmCurrentMembershipReportsFromHost OBJECT-TYPE
			SYNTAX Unsigned32
			MAX-ACCESS read-only
			STATUS current
			DESCRIPTION
				"Successful join requests for the multicast group
				received from the subscriber ports."
			::= { sheIgmpPmCurrentEntry 7 }

		
--   1.3.6.1.4.1.231.7.1.2.2.1.4.7.16.1.2.1.8
		sheIgmpPmCurrentPeakMembershipReportsFromHost OBJECT-TYPE
			SYNTAX Unsigned32
			MAX-ACCESS read-only
			STATUS current
			DESCRIPTION
				"Peak of successful join requests per second for the
				multicast group received from the subscriber ports."
			::= { sheIgmpPmCurrentEntry 8 }

		
--   1.3.6.1.4.1.231.7.1.2.2.1.4.7.16.1.2.1.9
		sheIgmpPmCurrentTimeOfPeakMembershipReports OBJECT-TYPE
			SYNTAX TimeTicks
			MAX-ACCESS read-only
			STATUS current
			DESCRIPTION
				"Time and date of the peak of successful join requests per
				second for the multicast group received from the
				subscriber ports."
			::= { sheIgmpPmCurrentEntry 9 }

		
--   1.3.6.1.4.1.231.7.1.2.2.1.4.7.16.1.2.1.10
		sheIgmpPmCurrentGroupLeavesFromHost OBJECT-TYPE
			SYNTAX Unsigned32
			MAX-ACCESS read-only
			STATUS current
			DESCRIPTION
				"IGMP group leave messages for the multicast group
				received from the subscriber ports."
			::= { sheIgmpPmCurrentEntry 10 }

		
--   1.3.6.1.4.1.231.7.1.2.2.1.4.7.16.1.2.1.11
		sheIgmpPmCurrentPeakGroupLeavesFromHost OBJECT-TYPE
			SYNTAX Unsigned32
			MAX-ACCESS read-only
			STATUS current
			DESCRIPTION
				"Peak of IGMP group leave messages per
				second for the multicast group received from the
				subscriber ports."
			::= { sheIgmpPmCurrentEntry 11 }

		
--   1.3.6.1.4.1.231.7.1.2.2.1.4.7.16.1.2.1.12
		sheIgmpPmCurrentTimeOfPeakGroupLeaves OBJECT-TYPE
			SYNTAX TimeTicks
			MAX-ACCESS read-only
			STATUS current
			DESCRIPTION
				"Time and date of the peak of IGMP group leave messages per
				second for the multicast group received from the
				subscriber ports."
			::= { sheIgmpPmCurrentEntry 12 }

		
--   1.3.6.1.4.1.231.7.1.2.2.1.4.7.16.1.2.1.13
		sheIgmpPmCurrentMembershipReportsToRouter OBJECT-TYPE
			SYNTAX Unsigned32
			MAX-ACCESS read-only
			STATUS current
			DESCRIPTION
				"Successful join requests for the multicast group
				sent to the router."
			::= { sheIgmpPmCurrentEntry 13 }

		
--   1.3.6.1.4.1.231.7.1.2.2.1.4.7.16.1.2.1.14
		sheIgmpPmCurrentGroupLeavesToRouter OBJECT-TYPE
			SYNTAX Unsigned32
			MAX-ACCESS read-only
			STATUS current
			DESCRIPTION
				"IGMP group leave messages for the multicast group
				sent to the router."
			::= { sheIgmpPmCurrentEntry 14 }

		
--   1.3.6.1.4.1.231.7.1.2.2.1.4.7.16.1.2.1.15
		sheIgmpPmCurrentPeakMulticastLeaves OBJECT-TYPE
			SYNTAX Unsigned32
			MAX-ACCESS read-only
			STATUS current
			DESCRIPTION
				"The peak number of the multicast tree leaves (branches)
				for the multicast group shows the peak number of joined
				subscriber ports."
			::= { sheIgmpPmCurrentEntry 15 }

		
--   1.3.6.1.4.1.231.7.1.2.2.1.4.7.16.1.3
		sheIgmpPmHistoryTableTable OBJECT-TYPE
			SYNTAX SEQUENCE OF SheIgmpPmHistoryTableEntry
			MAX-ACCESS not-accessible
			STATUS current
			DESCRIPTION
				"A table containing all IGMP PM history data. Indices of
				the table are the PM object, the interval type and the
				record number."
			::= { sheIgmpPerformanceMonitoring 3 }

		
--   1.3.6.1.4.1.231.7.1.2.2.1.4.7.16.1.3.1
		sheIgmpPmHistoryTableEntry OBJECT-TYPE
			SYNTAX SheIgmpPmHistoryTableEntry
			MAX-ACCESS not-accessible
			STATUS current
			DESCRIPTION
				"An entry describing the history PM data 
				of a multicast group for a certain interval type
				and record number."
			INDEX { sheIgmpPmObjectIndex, sheIgmpPmHistoryIntervalType, sheIgmpPmHistoryEntryNumber }
			::= { sheIgmpPmHistoryTableTable 1 }

		
		SheIgmpPmHistoryTableEntry ::=
			SEQUENCE { 
				sheIgmpPmHistoryIntervalType
					ShePmIntervalType,
				sheIgmpPmHistoryEntryNumber
					Unsigned32,
				sheIgmpPmHistorySuspectFlag
					ShePmSuspectFlagType,
				sheIgmpPmHistoryPeriodEndTime
					TimeTicks,
				sheIgmpPmHistoryMembershipReportsFromHost
					Unsigned32,
				sheIgmpPmHistoryPeakMembershipReportsFromHost
					Unsigned32,
				sheIgmpPmHistoryTimeOfPeakMembershipReports
					TimeTicks,
				sheIgmpPmHistoryGroupLeavesFromHost
					Unsigned32,
				sheIgmpPmHistoryPeakGroupLeavesFromHost
					Unsigned32,
				sheIgmpPmHistoryTimeOfPeakGroupLeaves
					TimeTicks,
				sheIgmpPmHistoryMembershipReportsToRouter
					Unsigned32,
				sheIgmpPmHistoryGroupLeavesToRouter
					Unsigned32,
				sheIgmpPmHistoryPeakMulticastLeaves
					Unsigned32
			 }

--   1.3.6.1.4.1.231.7.1.2.2.1.4.7.16.1.3.1.1
		sheIgmpPmHistoryIntervalType OBJECT-TYPE
			SYNTAX ShePmIntervalType
			MAX-ACCESS read-only
			STATUS current
			DESCRIPTION
				"This attribute is used to select between the
				15 min  or the day accumulation types. "
			::= { sheIgmpPmHistoryTableEntry 1 }

		
--   1.3.6.1.4.1.231.7.1.2.2.1.4.7.16.1.3.1.2
		sheIgmpPmHistoryEntryNumber OBJECT-TYPE
			SYNTAX Unsigned32
			MAX-ACCESS read-only
			STATUS current
			DESCRIPTION
				"This attribute is an index used to address the PM history
				entry. Entry 1 is the most recent. The range of values is
				between 1 and sheIgmpPmCurrentHistEntrySize."
			::= { sheIgmpPmHistoryTableEntry 2 }

		
--   1.3.6.1.4.1.231.7.1.2.2.1.4.7.16.1.3.1.3
		sheIgmpPmHistorySuspectFlag OBJECT-TYPE
			SYNTAX ShePmSuspectFlagType
			MAX-ACCESS read-only
			STATUS current
			DESCRIPTION
				"This read-only attribute will be set to indicate that
				troubles arose during an interval and that the counter
				values are suspect and incomplete. "
			::= { sheIgmpPmHistoryTableEntry 3 }

		
--   1.3.6.1.4.1.231.7.1.2.2.1.4.7.16.1.3.1.4
		sheIgmpPmHistoryPeriodEndTime OBJECT-TYPE
			SYNTAX TimeTicks
			MAX-ACCESS read-only
			STATUS current
			DESCRIPTION
				"Date/time at the end of the selected interval."
			::= { sheIgmpPmHistoryTableEntry 4 }

		
--   1.3.6.1.4.1.231.7.1.2.2.1.4.7.16.1.3.1.5
		sheIgmpPmHistoryMembershipReportsFromHost OBJECT-TYPE
			SYNTAX Unsigned32
			MAX-ACCESS read-only
			STATUS current
			DESCRIPTION
				"Successful join requests for the multicast group
				received from the subscriber ports."
			::= { sheIgmpPmHistoryTableEntry 5 }

		
--   1.3.6.1.4.1.231.7.1.2.2.1.4.7.16.1.3.1.6
		sheIgmpPmHistoryPeakMembershipReportsFromHost OBJECT-TYPE
			SYNTAX Unsigned32
			MAX-ACCESS read-only
			STATUS current
			DESCRIPTION
				"Peak of successful join requests per second for the
				multicast group received from the subscriber ports."
			::= { sheIgmpPmHistoryTableEntry 6 }

		
--   1.3.6.1.4.1.231.7.1.2.2.1.4.7.16.1.3.1.7
		sheIgmpPmHistoryTimeOfPeakMembershipReports OBJECT-TYPE
			SYNTAX TimeTicks
			MAX-ACCESS read-only
			STATUS current
			DESCRIPTION
				"Time and date of the peak of successful join requests per
				second for the multicast group received from the
				subscriber ports."
			::= { sheIgmpPmHistoryTableEntry 7 }

		
--   1.3.6.1.4.1.231.7.1.2.2.1.4.7.16.1.3.1.8
		sheIgmpPmHistoryGroupLeavesFromHost OBJECT-TYPE
			SYNTAX Unsigned32
			MAX-ACCESS read-only
			STATUS current
			DESCRIPTION
				"IGMP group leave messages for the multicast group
				received from the subscriber ports."
			::= { sheIgmpPmHistoryTableEntry 8 }

		
--   1.3.6.1.4.1.231.7.1.2.2.1.4.7.16.1.3.1.9
		sheIgmpPmHistoryPeakGroupLeavesFromHost OBJECT-TYPE
			SYNTAX Unsigned32
			MAX-ACCESS read-only
			STATUS current
			DESCRIPTION
				"Peak of IGMP group leave messages per
				second for the multicast group received from the
				subscriber ports."
			::= { sheIgmpPmHistoryTableEntry 9 }

		
--   1.3.6.1.4.1.231.7.1.2.2.1.4.7.16.1.3.1.10
		sheIgmpPmHistoryTimeOfPeakGroupLeaves OBJECT-TYPE
			SYNTAX TimeTicks
			MAX-ACCESS read-only
			STATUS current
			DESCRIPTION
				"Time and date of the peak of IGMP group leave messages per
				second for the multicast group received from the
				subscriber ports."
			::= { sheIgmpPmHistoryTableEntry 10 }

		
--   1.3.6.1.4.1.231.7.1.2.2.1.4.7.16.1.3.1.11
		sheIgmpPmHistoryMembershipReportsToRouter OBJECT-TYPE
			SYNTAX Unsigned32
			MAX-ACCESS read-only
			STATUS current
			DESCRIPTION
				"Successful join requests for the multicast group
				sent to the router."
			::= { sheIgmpPmHistoryTableEntry 11 }

		
--   1.3.6.1.4.1.231.7.1.2.2.1.4.7.16.1.3.1.12
		sheIgmpPmHistoryGroupLeavesToRouter OBJECT-TYPE
			SYNTAX Unsigned32
			MAX-ACCESS read-only
			STATUS current
			DESCRIPTION
				"IGMP group leave messages for the multicast group
				sent to the router."
			::= { sheIgmpPmHistoryTableEntry 12 }

		
--   1.3.6.1.4.1.231.7.1.2.2.1.4.7.16.1.3.1.13
		sheIgmpPmHistoryPeakMulticastLeaves OBJECT-TYPE
			SYNTAX Unsigned32
			MAX-ACCESS read-only
			STATUS current
			DESCRIPTION
				"The peak number of the multicast tree leaves (branches)
				for the multicast group shows the peak number of joined
				subscriber ports."
			::= { sheIgmpPmHistoryTableEntry 13 }

		
--   1.3.6.1.4.1.231.7.1.2.2.1.4.7.16.2
		sheIgmpPerformanceControl OBJECT IDENTIFIER ::= { sheIgmpPerformance 2 }

		
--   1.3.6.1.4.1.231.7.1.2.2.1.4.7.16.2.1
		sheIgmpPmControlRequest OBJECT-TYPE
			SYNTAX SheBridgeControlRequestType
			MAX-ACCESS read-write
			STATUS current
			DESCRIPTION
				"createPmObject
				sheIgmpPmControlGroupIndex
				sheIgmpPmControlHistEntrySize
				
				modifyPmObject
				sheIgmpPmControlObjectIndex
				sheIgmpPmControlIntervalType
				sheIgmpPmControlHistEntrySize
				
				deletePmObject
				sheIgmpPmControlObjectIndex"
			::= { sheIgmpPerformanceControl 1 }

		
--   1.3.6.1.4.1.231.7.1.2.2.1.4.7.16.2.2
		sheIgmpPmControlStatus OBJECT-TYPE
			SYNTAX SheControlStatusType
			MAX-ACCESS read-only
			STATUS current
			DESCRIPTION
				"The status of a user command. 
				"
			::= { sheIgmpPerformanceControl 2 }

		
--   1.3.6.1.4.1.231.7.1.2.2.1.4.7.16.2.3
		sheIgmpPmControlTimeStamp OBJECT-TYPE
			SYNTAX Unsigned32
			UNITS "sec"
			MAX-ACCESS read-only
			STATUS current
			DESCRIPTION
				"The time stamp of the last command (end of command)."
			::= { sheIgmpPerformanceControl 3 }

		
--   1.3.6.1.4.1.231.7.1.2.2.1.4.7.16.2.4
		sheIgmpPmControlReqResult OBJECT-TYPE
			SYNTAX SheBridgeControlReqResultType
			MAX-ACCESS read-only
			STATUS current
			DESCRIPTION
				"The result of the last user command."
			::= { sheIgmpPerformanceControl 4 }

		
--   1.3.6.1.4.1.231.7.1.2.2.1.4.7.16.2.5
		sheIgmpPmControlTimer OBJECT-TYPE
			SYNTAX Gauge32
			MAX-ACCESS read-only
			STATUS current
			DESCRIPTION
				"The maximum wait time for the manager for a long
				running user command. 
				"
			::= { sheIgmpPerformanceControl 5 }

		
--   1.3.6.1.4.1.231.7.1.2.2.1.4.7.16.2.6
		sheIgmpPmControlObjectIndex OBJECT-TYPE
			SYNTAX Unsigned32
			MAX-ACCESS read-write
			STATUS current
			DESCRIPTION
				"Index sheIgmpPmObjectIndex of the PM object in the 
				sheIgmpPmObjectTable to be modified or deleted.
				parameter for
				 modifyPmObject
				 deletePmObject"
			::= { sheIgmpPerformanceControl 6 }

		
--   1.3.6.1.4.1.231.7.1.2.2.1.4.7.16.2.7
		sheIgmpPmControlObjectGroupIndex OBJECT-TYPE
			SYNTAX Unsigned32 (1..1000)
			MAX-ACCESS read-write
			STATUS current
			DESCRIPTION
				"Index sheIgmpGroupIndex of the sheIgmpGroupTable selects the multicast group a PM object is
				created for.
				parameter for
				 createPmObject"
			::= { sheIgmpPerformanceControl 7 }

		
--   1.3.6.1.4.1.231.7.1.2.2.1.4.7.16.2.8
		sheIgmpPmControlIntervalType OBJECT-TYPE
			SYNTAX ShePmIntervalType
			MAX-ACCESS read-write
			STATUS current
			DESCRIPTION
				"This attribute is used to select between the
				15 min  or the day accumulation types.
				parameter for
				 modifyPmObject"
			::= { sheIgmpPerformanceControl 8 }

		
--   1.3.6.1.4.1.231.7.1.2.2.1.4.7.16.2.9
		sheIgmpPmControlHistEntrySize OBJECT-TYPE
			SYNTAX Unsigned32
			MAX-ACCESS read-write
			STATUS current
			DESCRIPTION
				"The number of history entries configured for the multicast group and interval type.
				This attribute is used for history data collection. The default value is 1 and means
				at least one history entry is desired. In case of PM object creation the number of 15 min
				entries is set and the number of 24 h entries is always 1.
				parameter for
				 createPmObject
				 modifyPmObject"
			::= { sheIgmpPerformanceControl 9 }

		
--   1.3.6.1.4.1.231.7.1.2.2.1.4.7.16.2.10
		sheIgmpPmControlRemainingHistoryEntries OBJECT-TYPE
			SYNTAX Unsigned32
			MAX-ACCESS read-only
			STATUS current
			DESCRIPTION
				"The number of history entries which are still available
				for the PM data collection within the NE. The memory
				for PM data is limited. The manager can read this
				attribute before/after the execution of PM object
				commands to inform himself about the remaining history
				size."
			::= { sheIgmpPerformanceControl 10 }

		
--   1.3.6.1.4.1.231.7.1.2.2.1.4.7.16.3
		sheIgmpPerformanceNotifications OBJECT IDENTIFIER ::= { sheIgmpPerformance 3 }

		
--   1.3.6.1.4.1.231.7.1.2.2.1.4.7.16.3.1
		sheIgmpPmObjectCreated NOTIFICATION-TYPE
			OBJECTS { sheIgmpPmControlTimeStamp, sheIgmpPmControlObjectIndex, sheIgmpPmObjectGroupIndex, sheIgmpPmCurrentHistEntrySize }
			STATUS current
			DESCRIPTION 
				"IGMP PM object has been created."
			::= { sheIgmpPerformanceNotifications 1 }

		
--   1.3.6.1.4.1.231.7.1.2.2.1.4.7.16.3.2
		sheIgmpPmObjectModified NOTIFICATION-TYPE
			OBJECTS { sheIgmpPmControlTimeStamp, sheIgmpPmControlIntervalType, sheIgmpPmControlObjectIndex, sheIgmpPmObjectGroupIndex, sheIgmpPmCurrentHistEntrySize, 
				sheIgmpPmCurrentHistEntriesAvailable }
			STATUS current
			DESCRIPTION 
				"IGMP PM object has been modified."
			::= { sheIgmpPerformanceNotifications 2 }

		
--   1.3.6.1.4.1.231.7.1.2.2.1.4.7.16.3.3
		sheIgmpPmObjectDeleted NOTIFICATION-TYPE
			OBJECTS { sheIgmpPmControlTimeStamp, sheIgmpPmControlObjectIndex }
			STATUS current
			DESCRIPTION 
				"IGMP PM object has been deleted."
			::= { sheIgmpPerformanceNotifications 3 }

		
--   1.3.6.1.4.1.231.7.1.2.2.1.4.7.16.4
		sheIgmpPerformanceConformance OBJECT IDENTIFIER ::= { sheIgmpPerformance 4 }

		
--   1.3.6.1.4.1.231.7.1.2.2.1.4.7.16.4.1
		sheIgmpPerformanceCompliances OBJECT IDENTIFIER ::= { sheIgmpPerformanceConformance 1 }

		
--   1.3.6.1.4.1.231.7.1.2.2.1.4.7.16.4.1.1
-- this module
-- this module
		sheIgmpPerformanceCompliance MODULE-COMPLIANCE
			STATUS current
			DESCRIPTION 
				"Description."
			MODULE -- this module
				MANDATORY-GROUPS { sheIgmpPmObjectGroup, sheIgmpPmCurrentGroup, sheIgmpPmHistoryGroup, sheIgmpPmControlGroup, sheIgmpPmNotificationGroup
					 }
			::= { sheIgmpPerformanceCompliances 1 }

		
--   1.3.6.1.4.1.231.7.1.2.2.1.4.7.16.4.2
		sheIgmpPerformanceGroups OBJECT IDENTIFIER ::= { sheIgmpPerformanceConformance 2 }

		
--   1.3.6.1.4.1.231.7.1.2.2.1.4.7.16.4.2.1
		sheIgmpPmObjectGroup OBJECT-GROUP
			OBJECTS { sheIgmpPmObjectIndex, sheIgmpPmObjectGroupIndex }
			STATUS current
			DESCRIPTION 
				"Description."
			::= { sheIgmpPerformanceGroups 1 }

		
--   1.3.6.1.4.1.231.7.1.2.2.1.4.7.16.4.2.2
		sheIgmpPmCurrentGroup OBJECT-GROUP
			OBJECTS { sheIgmpPmCurrentIntervalType, sheIgmpPmCurrentAdminState, sheIgmpPmCurrentSuspectFlag, sheIgmpPmCurrentHistEntrySize, sheIgmpPmCurrentHistEntriesAvailable, 
				sheIgmpPmCurrentElapsedTime, sheIgmpPmCurrentMembershipReportsFromHost, sheIgmpPmCurrentPeakMembershipReportsFromHost, sheIgmpPmCurrentTimeOfPeakMembershipReports, sheIgmpPmCurrentGroupLeavesFromHost, 
				sheIgmpPmCurrentPeakGroupLeavesFromHost, sheIgmpPmCurrentTimeOfPeakGroupLeaves, sheIgmpPmCurrentMembershipReportsToRouter, sheIgmpPmCurrentGroupLeavesToRouter, sheIgmpPmCurrentPeakMulticastLeaves
				 }
			STATUS current
			DESCRIPTION 
				"Description."
			::= { sheIgmpPerformanceGroups 2 }

		
--   1.3.6.1.4.1.231.7.1.2.2.1.4.7.16.4.2.3
		sheIgmpPmHistoryGroup OBJECT-GROUP
			OBJECTS { sheIgmpPmHistoryIntervalType, sheIgmpPmHistoryEntryNumber, sheIgmpPmHistorySuspectFlag, sheIgmpPmHistoryPeriodEndTime, sheIgmpPmHistoryMembershipReportsFromHost, 
				sheIgmpPmHistoryPeakMembershipReportsFromHost, sheIgmpPmHistoryTimeOfPeakMembershipReports, sheIgmpPmHistoryGroupLeavesFromHost, sheIgmpPmHistoryPeakGroupLeavesFromHost, sheIgmpPmHistoryTimeOfPeakGroupLeaves, 
				sheIgmpPmHistoryMembershipReportsToRouter, sheIgmpPmHistoryGroupLeavesToRouter, sheIgmpPmHistoryPeakMulticastLeaves }
			STATUS current
			DESCRIPTION 
				"Description."
			::= { sheIgmpPerformanceGroups 3 }

		
--   1.3.6.1.4.1.231.7.1.2.2.1.4.7.16.4.2.4
		sheIgmpPmControlGroup OBJECT-GROUP
			OBJECTS { sheIgmpPmControlRequest, sheIgmpPmControlStatus, sheIgmpPmControlTimeStamp, sheIgmpPmControlReqResult, sheIgmpPmControlTimer, 
				sheIgmpPmControlObjectIndex, sheIgmpPmControlObjectGroupIndex, sheIgmpPmControlIntervalType, sheIgmpPmControlHistEntrySize, sheIgmpPmControlRemainingHistoryEntries
				 }
			STATUS current
			DESCRIPTION 
				"Description."
			::= { sheIgmpPerformanceGroups 4 }

		
--   1.3.6.1.4.1.231.7.1.2.2.1.4.7.16.4.2.5
		sheIgmpPmNotificationGroup NOTIFICATION-GROUP
			NOTIFICATIONS { sheIgmpPmObjectCreated, sheIgmpPmObjectModified, sheIgmpPmObjectDeleted }
			STATUS current
			DESCRIPTION 
				"Description."
			::= { sheIgmpPerformanceGroups 5 }

		
--   1.3.6.1.4.1.231.7.1.2.2.1.4.7.17
		sheIgmpStatistics OBJECT IDENTIFIER ::= { sheIgmp 17 }

		
--   1.3.6.1.4.1.231.7.1.2.2.1.4.7.17.1
		sheIgmpStatsGroupTable OBJECT-TYPE
			SYNTAX SEQUENCE OF SheIgmpStatsGroupEntry
			MAX-ACCESS not-accessible
			STATUS current
			DESCRIPTION
				"The table holds IGMP statistics group table in the NE."
			::= { sheIgmpStatistics 1 }

		
--   1.3.6.1.4.1.231.7.1.2.2.1.4.7.17.1.1		
		sheIgmpStatsGroupEntry OBJECT-TYPE
			SYNTAX SheIgmpStatsGroupEntry
			MAX-ACCESS not-accessible
			STATUS current
			DESCRIPTION
				"The table entry shows the IGMP group statistics."
			INDEX { sheIgmpStatsGroupIndex }
			::= { sheIgmpStatsGroupTable 1 }

		
		SheIgmpStatsGroupEntry ::=
			SEQUENCE { 
				sheIgmpStatsGroupIndex
					Unsigned32,
				sheIgmpStatsGroupTimeSinceLastMembershipReport
					TimeTicks
			 }

--   1.3.6.1.4.1.231.7.1.2.2.1.4.7.17.1.1.1
		sheIgmpStatsGroupIndex OBJECT-TYPE
			SYNTAX Unsigned32 (1..65535)
			MAX-ACCESS read-only
			STATUS current
			DESCRIPTION
				"Identifier of sheIgmpGroupTable"
			::= { sheIgmpStatsGroupEntry 1 }

		
--   1.3.6.1.4.1.231.7.1.2.2.1.4.7.17.1.1.2
		sheIgmpStatsGroupTimeSinceLastMembershipReport OBJECT-TYPE
			SYNTAX TimeTicks
			MAX-ACCESS read-only
			STATUS current
			DESCRIPTION
				"Time since last Membership Report was received for acticve dynamic multicast cross-connection."
			::= { sheIgmpStatsGroupEntry 2 }

		
--   1.3.6.1.4.1.231.7.1.2.2.1.4.7.17.2
		sheIgmpStatsBase OBJECT IDENTIFIER ::= { sheIgmpStatistics 2 }

		
--   1.3.6.1.4.1.231.7.1.2.2.1.4.7.17.2.1
		sheIgmpStatsNumberOfGroupsToRouter OBJECT-TYPE
			SYNTAX Counter32
			MAX-ACCESS read-only
			STATUS current
			DESCRIPTION
				"The Number of active multicast connections cross-connected by the DSLAM"
			::= { sheIgmpStatsBase 1 }

		
--   1.3.6.1.4.1.231.7.1.2.2.1.4.7.17.2.2
		sheIgmpStatsNumberOfGroupsToHost OBJECT-TYPE
			SYNTAX Counter32
			MAX-ACCESS read-only
			STATUS current
			DESCRIPTION
				"The Number of different ip multicast groups currently connected to end users"
			::= { sheIgmpStatsBase 2 }

		
--   1.3.6.1.4.1.231.7.1.2.2.1.4.7.17.2.3
		sheIgmpStatsNumberOfQueryReceived OBJECT-TYPE
			SYNTAX Counter32
			MAX-ACCESS read-only
			STATUS current
			DESCRIPTION
				"The Number of Igmp query message received by DSLAM"
			::= { sheIgmpStatsBase 3 }

		
--   1.3.6.1.4.1.231.7.1.2.2.1.4.7.17.2.4
		sheIgmpStatsNumberOfReportReceived OBJECT-TYPE
			SYNTAX Counter32
			MAX-ACCESS read-only
			STATUS current
			DESCRIPTION
				"The Number of Igmp report message received by DSLAM"
			::= { sheIgmpStatsBase 4 }

		
--   1.3.6.1.4.1.231.7.1.2.2.1.4.7.17.2.5
		sheIgmpStatsNumberOfLeaveReceived OBJECT-TYPE
			SYNTAX Counter32
			MAX-ACCESS read-only
			STATUS current
			DESCRIPTION
				"The Number of Igmp leave message received by DSLAM"
			::= { sheIgmpStatsBase 5 }

		
--   1.3.6.1.4.1.231.7.1.2.2.1.4.7.17.2.6
		sheIgmpStatsNumberOfInvalidReceived OBJECT-TYPE
			SYNTAX Counter32
			MAX-ACCESS read-only
			STATUS current
			DESCRIPTION
				"The Number of invalid message received by DSLAM"
			::= { sheIgmpStatsBase 6 }

		
--   1.3.6.1.4.1.231.7.1.2.2.1.4.7.17.2.7
		sheIgmpStatsPeakNumberOfActiveGroupToRouter OBJECT-TYPE
			SYNTAX Counter32
			MAX-ACCESS read-only
			STATUS current
			DESCRIPTION
				"The number of active multicast connections cross-connected
				by the DSLAM per second when the peak"
			::= { sheIgmpStatsBase 7 }

		
--   1.3.6.1.4.1.231.7.1.2.2.1.4.7.17.2.8
		sheIgmpStatsTimeOfPeakNumberOfActiveGroupToRouter OBJECT-TYPE
			SYNTAX TimeTicks
			MAX-ACCESS read-only
			STATUS current
			DESCRIPTION
				"Time and date of the peak of active multicast connections cross-connected by the DSLAM"
			::= { sheIgmpStatsBase 8 }

		
--   1.3.6.1.4.1.231.7.1.2.2.1.4.7.17.2.9
		sheIgmpStatsPeakNumberOfActiveGroupFromHost OBJECT-TYPE
			SYNTAX Counter32
			MAX-ACCESS read-only
			STATUS current
			DESCRIPTION
				"The number of different ip multicast groups currently connected to end users per second when the peak"
			::= { sheIgmpStatsBase 9 }

		
--   1.3.6.1.4.1.231.7.1.2.2.1.4.7.17.2.10
		sheIgmpStatsTimeOfPeakNumberOfActiveGroupFromHost OBJECT-TYPE
			SYNTAX TimeTicks
			MAX-ACCESS read-only
			STATUS current
			DESCRIPTION
				"Time and date of the peak of different ip multicast groups currently connected to end users"
			::= { sheIgmpStatsBase 10 }

		
--   1.3.6.1.4.1.231.7.1.2.2.1.4.7.17.2.11
		sheIgmpStatsNumberOfMsgPerSec OBJECT-TYPE
			SYNTAX Gauge32
			MAX-ACCESS read-only
			STATUS current
			DESCRIPTION
				"IGMP-messages-rate. The number of IGMP messages received by the DSLAM in one second."
			::= { sheIgmpStatsBase 11 }

		
--   1.3.6.1.4.1.231.7.1.2.2.1.4.7.17.2.12
		sheIgmpStatsPeakNumberOfMsgPerSec OBJECT-TYPE
			SYNTAX Gauge32
			MAX-ACCESS read-only
			STATUS current
			DESCRIPTION
				"Peak-IGMP-messages-rate. The maximum value of IGMP-messages-rate."
			::= { sheIgmpStatsBase 12 }

		
--   1.3.6.1.4.1.231.7.1.2.2.1.4.7.17.2.13
		sheIgmpStatsTimeOfPeakNumberOfMsgPerSec OBJECT-TYPE
			SYNTAX TimeTicks
			MAX-ACCESS read-only
			STATUS current
			DESCRIPTION
				"Time and date of the peak of IGMP-messages-rate."
			::= { sheIgmpStatsBase 13 }

		
--   1.3.6.1.4.1.231.7.1.2.2.1.4.7.17.3 
		sheIgmpStatsBaseControl OBJECT IDENTIFIER ::= { sheIgmpStatistics 3 }

		
--   1.3.6.1.4.1.231.7.1.2.2.1.4.7.17.3.1
		sheIgmpStatsBaseControlRequest OBJECT-TYPE
			SYNTAX SheIgmpStatsBaseControlRequestType
			MAX-ACCESS read-write
			STATUS current
			DESCRIPTION
				"Controlrequest for configuration.
				741 - clearIgmpStatsBase"
			::= { sheIgmpStatsBaseControl 1 }

		
--   1.3.6.1.4.1.231.7.1.2.2.1.4.7.17.3.2
		sheIgmpStatsBaseControlStatus OBJECT-TYPE
			SYNTAX SheIgmpStatsBaseControlStatusType
			MAX-ACCESS read-only
			STATUS current
			DESCRIPTION
				"Describes the status of a user command group, used for block commands while a command execution is in process.
				Values : idle, busy, passed, failed.
					- idle: default, no command in process
					- busy: command execution in process, attempts to start another user command on this control block are rejected
					- passed/failed: status at end of command
				"
			::= { sheIgmpStatsBaseControl 2 }

		
--   1.3.6.1.4.1.231.7.1.2.2.1.4.7.17.3.3
		sheIgmpStatsBaseControlTimestamp OBJECT-TYPE
			SYNTAX Unsigned32
			MAX-ACCESS read-only
			STATUS current
			DESCRIPTION
				"The time stamp of the last command (end of command)"
			::= { sheIgmpStatsBaseControl 3 }

		
--   1.3.6.1.4.1.231.7.1.2.2.1.4.7.17.3.4
		sheIgmpStatsBaseControlReqResult OBJECT-TYPE
			SYNTAX SheIgmpStatsBaseControlReqResultType
			MAX-ACCESS read-only
			STATUS current
			DESCRIPTION
				"Result of the last command"
			::= { sheIgmpStatsBaseControl 4 }

		
--   1.3.6.1.4.1.231.7.1.2.2.1.4.7.17.4
		sheIgmpStatsPortTable OBJECT-TYPE
			SYNTAX SEQUENCE OF SheIgmpStatsPortEntry
			MAX-ACCESS not-accessible
			STATUS current
			DESCRIPTION
				"The table holds IGMP statistics port table in the NE."
			::= { sheIgmpStatistics 4 }

		
--   1.3.6.1.4.1.231.7.1.2.2.1.4.7.17.4.1
		sheIgmpStatsPortEntry OBJECT-TYPE
			SYNTAX SheIgmpStatsPortEntry
			MAX-ACCESS not-accessible
			STATUS current
			DESCRIPTION
				"The table entry shows the IGMP port statistics."
			INDEX { sheBridgePortIndex }
			::= { sheIgmpStatsPortTable 1 }

		
		SheIgmpStatsPortEntry ::=
			SEQUENCE { 
				sheIgmpStatsPortNumberOfGroups
					Counter32,
				sheIgmpStatsPortNumberOfQueryReceived
					Counter32,
				sheIgmpStatsPortNumberOfReportReceived
					Counter32,
				sheIgmpStatsPortNumberOfLeaveReceived
					Counter32,
				sheIgmpStatsPortNumberOfInvalidReceived
					Counter32,
				sheIgmpStatsPortPeakNumberOfActiveGroup
					Gauge32,
				sheIgmpStatsPortTimeOfPeakNumberOfActiveGroup
					TimeTicks,
				sheIgmpStatsPortNumberOfDroppedByCA
					Gauge32,
				sheIgmpStatsPortNumberOfDroppedByAC
					Gauge32
			 }

--   1.3.6.1.4.1.231.7.1.2.2.1.4.7.17.4.1.1
		sheIgmpStatsPortNumberOfGroups OBJECT-TYPE
			SYNTAX Counter32
			MAX-ACCESS read-only
			STATUS current
			DESCRIPTION
				"The Number of different ip multicast groups currently connected to end user"
			::= { sheIgmpStatsPortEntry 1 }

		
--   1.3.6.1.4.1.231.7.1.2.2.1.4.7.17.4.1.2
		sheIgmpStatsPortNumberOfQueryReceived OBJECT-TYPE
			SYNTAX Counter32
			MAX-ACCESS read-only
			STATUS current
			DESCRIPTION
				"The Number of Igmp query message received from a subscriber port"
			::= { sheIgmpStatsPortEntry 2 }

		
--   1.3.6.1.4.1.231.7.1.2.2.1.4.7.17.4.1.3
		sheIgmpStatsPortNumberOfReportReceived OBJECT-TYPE
			SYNTAX Counter32
			MAX-ACCESS read-only
			STATUS current
			DESCRIPTION
				"The Number of Igmp report message received from a subscriber port"
			::= { sheIgmpStatsPortEntry 3 }

		
--   1.3.6.1.4.1.231.7.1.2.2.1.4.7.17.4.1.4
		sheIgmpStatsPortNumberOfLeaveReceived OBJECT-TYPE
			SYNTAX Counter32
			MAX-ACCESS read-only
			STATUS current
			DESCRIPTION
				"The Number of Igmp leave message received from a subscriber port"
			::= { sheIgmpStatsPortEntry 4 }

		
--   1.3.6.1.4.1.231.7.1.2.2.1.4.7.17.4.1.5
		sheIgmpStatsPortNumberOfInvalidReceived OBJECT-TYPE
			SYNTAX Counter32
			MAX-ACCESS read-only
			STATUS current
			DESCRIPTION
				"The Number of invalid message received from a subscriber port"
			::= { sheIgmpStatsPortEntry 5 }

		
--   1.3.6.1.4.1.231.7.1.2.2.1.4.7.17.4.1.6
		sheIgmpStatsPortPeakNumberOfActiveGroup OBJECT-TYPE
			SYNTAX Gauge32
			MAX-ACCESS read-only
			STATUS current
			DESCRIPTION
				"Number of active multicast group when the peak"
			::= { sheIgmpStatsPortEntry 6 }

		
--   1.3.6.1.4.1.231.7.1.2.2.1.4.7.17.4.1.7
		sheIgmpStatsPortTimeOfPeakNumberOfActiveGroup OBJECT-TYPE
			SYNTAX TimeTicks
			MAX-ACCESS read-only
			STATUS current
			DESCRIPTION
				"Time and date of the peak of active multicast group"
			::= { sheIgmpStatsPortEntry 7 }

		
--  1.3.6.1.4.1.231.7.1.2.2.1.4.7.17.4.1.8
		sheIgmpStatsPortNumberOfDroppedByCA OBJECT-TYPE
			SYNTAX Gauge32
			MAX-ACCESS read-only
			STATUS current
			DESCRIPTION
				"Number of IGMP msg dropped by conditional access (if CPV failed or if max number of active m/c channels is exceeded).
				
				New parameter with SHE R2.8."
			::= { sheIgmpStatsPortEntry 8 }

		
--  1.3.6.1.4.1.231.7.1.2.2.1.4.7.17.4.1.9
		sheIgmpStatsPortNumberOfDroppedByAC OBJECT-TYPE
			SYNTAX Gauge32
			MAX-ACCESS read-only
			STATUS current
			DESCRIPTION
				"Number of IGMP msg dropped by admission control (if max m/c bandwidth on a bport is exceeded or if max number of non-premium channels is exceeded).
				
				New parameter with SHE R2.8."
			::= { sheIgmpStatsPortEntry 9 }

		
--   1.3.6.1.4.1.231.7.1.2.2.1.4.7.17.5
		sheIgmpStatsPortControl OBJECT IDENTIFIER ::= { sheIgmpStatistics 5 }

		
--   1.3.6.1.4.1.231.7.1.2.2.1.4.7.17.5.1
		sheIgmpStatsPortControlRequest OBJECT-TYPE
			SYNTAX SheIgmpStatsPortControlRequestType
			MAX-ACCESS read-write
			STATUS current
			DESCRIPTION
				"Controlrequest for configuration.
				742 - clearIgmpStatsPort"
			::= { sheIgmpStatsPortControl 1 }

		
--   1.3.6.1.4.1.231.7.1.2.2.1.4.7.17.5.2
		sheIgmpStatsPortControlStatus OBJECT-TYPE
			SYNTAX SheIgmpStatsPortControlStatusType
			MAX-ACCESS read-only
			STATUS current
			DESCRIPTION
				"Describes the status of a user command group, used for block commands while a command execution is in process.
				Values : idle, busy, passed, failed.
					- idle: default, no command in process
					- busy: command execution in process, attempts to start another user command on this control block are rejected
					- passed/failed: status at end of command
				"
			::= { sheIgmpStatsPortControl 2 }

		
--   1.3.6.1.4.1.231.7.1.2.2.1.4.7.17.5.3
		sheIgmpStatsPortControlTimestamp OBJECT-TYPE
			SYNTAX Unsigned32
			MAX-ACCESS read-only
			STATUS current
			DESCRIPTION
				"The time stamp of the last command (end of command)"
			::= { sheIgmpStatsPortControl 3 }

		
--   1.3.6.1.4.1.231.7.1.2.2.1.4.7.17.5.4
		sheIgmpStatsPortControlReqResult OBJECT-TYPE
			SYNTAX SheIgmpStatsPortControlReqResultType
			MAX-ACCESS read-only
			STATUS current
			DESCRIPTION
				"Result of the last command"
			::= { sheIgmpStatsPortControl 4 }

		
--   1.3.6.1.4.1.231.7.1.2.2.1.4.7.17.5.5
		sheIgmpStatsPortControlBridgePortIndex OBJECT-TYPE
			SYNTAX Unsigned32
			MAX-ACCESS read-write
			STATUS current
			DESCRIPTION
				"Table index (A bridgePort-identifier)"
			::= { sheIgmpStatsPortControl 5 }

		
		sheIgmpStatsProviderTable OBJECT-TYPE
			SYNTAX SEQUENCE OF SheIgmpStatsProviderEntry
			MAX-ACCESS not-accessible
			STATUS current
			DESCRIPTION
				"The table contains entries for statistics of igmp providers of DSLAM"
			::= { sheIgmpStatistics 6 }

		
		sheIgmpStatsProviderEntry OBJECT-TYPE
			SYNTAX SheIgmpStatsProviderEntry
			MAX-ACCESS not-accessible
			STATUS current
			DESCRIPTION
				"The table entry shows the IGMP provider statistics."
			INDEX { sheIgmpProviderIndex }
			::= { sheIgmpStatsProviderTable 1 }

		
		SheIgmpStatsProviderEntry ::=
			SEQUENCE { 
				sheIgmpStatsProviderNumberOfChannelsToRouter
					Counter32,
				sheIgmpStatsProviderNumberOfChannelsToHost
					Counter32,
				sheIgmpStatsProviderNumberOfQueryReceived
					Counter32,
				sheIgmpStatsProviderNumberOfReportReceived
					Counter32,
				sheIgmpStatsProviderNumberOfLeaveReceived
					Counter32,
				sheIgmpStatsProviderNumberOfInvalidReceived
					Counter32,
				sheIgmpStatsProviderPeakNumberOfActiveChannelToRouter
					Counter32,
				sheIgmpStatsProviderTimeOfPeakNumberOfActiveChannelToRouter
					TimeTicks,
				sheIgmpStatsProviderPeakNumberOfActiveChannelFromHost
					Counter32,
				sheIgmpStatsProviderTimeOfPeakNumberOfActiveChannelFromHost
					TimeTicks,
				sheIgmpStatsProviderNumberOfMsgPerSec
					Gauge32,
				sheIgmpStatsProviderPeakNumberOfMsgPerSec
					Gauge32,
				sheIgmpStatsProviderTimeOfPeakNumberOfMsgPerSec
					TimeTicks
			 }

		sheIgmpStatsProviderNumberOfChannelsToRouter OBJECT-TYPE
			SYNTAX Counter32
			MAX-ACCESS read-only
			STATUS current
			DESCRIPTION
				"The Number of active multicast channels connections cross-connected 
				by a provider"
			::= { sheIgmpStatsProviderEntry 1 }

		
		sheIgmpStatsProviderNumberOfChannelsToHost OBJECT-TYPE
			SYNTAX Counter32
			MAX-ACCESS read-only
			STATUS current
			DESCRIPTION
				"The Number of different ip multicast channels currently connected to end users"
			::= { sheIgmpStatsProviderEntry 2 }

		
		sheIgmpStatsProviderNumberOfQueryReceived OBJECT-TYPE
			SYNTAX Counter32
			MAX-ACCESS read-only
			STATUS current
			DESCRIPTION
				"The Number of Igmp query message received by provider."
			::= { sheIgmpStatsProviderEntry 3 }

		
		sheIgmpStatsProviderNumberOfReportReceived OBJECT-TYPE
			SYNTAX Counter32
			MAX-ACCESS read-only
			STATUS current
			DESCRIPTION
				"The Number of Igmp report message received by provider."
			::= { sheIgmpStatsProviderEntry 4 }

		
		sheIgmpStatsProviderNumberOfLeaveReceived OBJECT-TYPE
			SYNTAX Counter32
			MAX-ACCESS read-only
			STATUS current
			DESCRIPTION
				"The Number of Igmp leave message received by provider."
			::= { sheIgmpStatsProviderEntry 5 }

		
		sheIgmpStatsProviderNumberOfInvalidReceived OBJECT-TYPE
			SYNTAX Counter32
			MAX-ACCESS read-only
			STATUS current
			DESCRIPTION
				"The Number of invalid message received by provider."
			::= { sheIgmpStatsProviderEntry 6 }

		
		sheIgmpStatsProviderPeakNumberOfActiveChannelToRouter OBJECT-TYPE
			SYNTAX Counter32
			MAX-ACCESS read-only
			STATUS current
			DESCRIPTION
				"The number of active multicast connections cross-connected
				by the provider per second when the peak."
			::= { sheIgmpStatsProviderEntry 7 }

		
		sheIgmpStatsProviderTimeOfPeakNumberOfActiveChannelToRouter OBJECT-TYPE
			SYNTAX TimeTicks
			MAX-ACCESS read-only
			STATUS current
			DESCRIPTION
				"Time and date of the peak of active multicast connections cross-connected by the provider."
			::= { sheIgmpStatsProviderEntry 8 }

		
		sheIgmpStatsProviderPeakNumberOfActiveChannelFromHost OBJECT-TYPE
			SYNTAX Counter32
			MAX-ACCESS read-only
			STATUS current
			DESCRIPTION
				"The number of different ip multicast channels currently connected to end users per second when the peak"
			::= { sheIgmpStatsProviderEntry 9 }

		
		sheIgmpStatsProviderTimeOfPeakNumberOfActiveChannelFromHost OBJECT-TYPE
			SYNTAX TimeTicks
			MAX-ACCESS read-only
			STATUS current
			DESCRIPTION
				"Time and date of the peak of different ip multicast channels currently connected to end users"
			::= { sheIgmpStatsProviderEntry 10 }

		
		sheIgmpStatsProviderNumberOfMsgPerSec OBJECT-TYPE
			SYNTAX Gauge32
			MAX-ACCESS read-only
			STATUS current
			DESCRIPTION
				"IGMP-messages-rate. The number of IGMP messages received by the provider in one second."
			::= { sheIgmpStatsProviderEntry 11 }

		
		sheIgmpStatsProviderPeakNumberOfMsgPerSec OBJECT-TYPE
			SYNTAX Gauge32
			MAX-ACCESS read-only
			STATUS current
			DESCRIPTION
				"Peak-IGMP-messages-rate. The maximum value of IGMP-messages-rate."
			::= { sheIgmpStatsProviderEntry 12 }

		
		sheIgmpStatsProviderTimeOfPeakNumberOfMsgPerSec OBJECT-TYPE
			SYNTAX TimeTicks
			MAX-ACCESS read-only
			STATUS current
			DESCRIPTION
				"Time and date of the peak of IGMP-messages-rate."
			::= { sheIgmpStatsProviderEntry 13 }

		
--  1.3.6.1.4.1.231.7.1.2.2.1.4.7.17.6.2
		sheIgmpStatsProviderControl OBJECT IDENTIFIER ::= { sheIgmpStatistics 7 }

		
--  1.3.6.1.4.1.231.7.1.2.2.1.4.7.17.7.1
		sheIgmpStatsProviderControlRequest OBJECT-TYPE
			SYNTAX SheIgmpStatsProviderControlRequestType
			MAX-ACCESS read-write
			STATUS current
			DESCRIPTION
				"Controlrequest for configuration.
				743 - clearIgmpStatsProvider:
				sheIgmpStatsProviderIndex"
			::= { sheIgmpStatsProviderControl 1 }

		
--  1.3.6.1.4.1.231.7.1.2.2.1.4.7.17.7.2
		sheIgmpStatsProviderControlStatus OBJECT-TYPE
			SYNTAX SheIgmpStatsBaseControlStatusType
			MAX-ACCESS read-only
			STATUS current
			DESCRIPTION
				"Describes the status of a user command group, used for block commands while a command execution is in process.
				Values : idle, busy, passed, failed.
					- idle: default, no command in process
					- busy: command execution in process, attempts to start another user command on this control block are rejected
					- passed/failed: status at end of command
				"
			::= { sheIgmpStatsProviderControl 2 }

		
--  1.3.6.1.4.1.231.7.1.2.2.1.4.7.17.7.3
		sheIgmpStatsProviderControlTimestamp OBJECT-TYPE
			SYNTAX Unsigned32
			MAX-ACCESS read-only
			STATUS current
			DESCRIPTION
				"The time stamp of the last command (end of command)"
			::= { sheIgmpStatsProviderControl 3 }

		
--  1.3.6.1.4.1.231.7.1.2.2.1.4.7.17.7.4
		sheIgmpStatsProviderControlReqResult OBJECT-TYPE
			SYNTAX SheIgmpStatsBaseControlReqResultType
			MAX-ACCESS read-only
			STATUS current
			DESCRIPTION
				"Result of the last command"
			::= { sheIgmpStatsProviderControl 4 }

		
--  1.3.6.1.4.1.231.7.1.2.2.1.4.7.17.7.5
		sheIgmpStatsProviderControlProviderIndex OBJECT-TYPE
			SYNTAX Unsigned32
			MAX-ACCESS read-write
			STATUS current
			DESCRIPTION
				"A provider index."
			::= { sheIgmpStatsProviderControl 5 }

		
--   1.3.6.1.4.1.231.7.1.2.2.1.4.7.18
		sheIgmpFloodVlanTable OBJECT-TYPE
			SYNTAX SEQUENCE OF SheIgmpFloodVlanEntry
			MAX-ACCESS not-accessible
			STATUS current
			DESCRIPTION
				"The table has one provider entry. It contains the
				provider VLAN and the host and querier settings."
			::= { sheIgmp 18 }

		
--   1.3.6.1.4.1.231.7.1.2.2.1.4.7.18.1
		sheIgmpFloodVlanEntry OBJECT-TYPE
			SYNTAX SheIgmpFloodVlanEntry
			MAX-ACCESS not-accessible
			STATUS current
			DESCRIPTION
				"In first release we will only support one table entry."
			INDEX { sheIgmpFloodVlanId }
			::= { sheIgmpFloodVlanTable 1 }

		
		SheIgmpFloodVlanEntry ::=
			SEQUENCE { 
				sheIgmpFloodVlanId
					INTEGER
			 }

--   1.3.6.1.4.1.231.7.1.2.2.1.4.7.18.1.1
		sheIgmpFloodVlanId OBJECT-TYPE
			SYNTAX INTEGER (1..4093)
			MAX-ACCESS read-only
			STATUS current
			DESCRIPTION
				"A vlanid of which a packet has a destination address as reserved multicast should be flooded without processing. 
				It is for igmp under L2VPN."
			::= { sheIgmpFloodVlanEntry 1 }

		
--   1.3.6.1.4.1.231.7.1.2.2.1.4.7.19
		sheIgmpFloodVlanControl OBJECT IDENTIFIER ::= { sheIgmp 19 }

		
--   1.3.6.1.4.1.231.7.1.2.2.1.4.7.19.1
		sheIgmpFloodVlanControlRequest OBJECT-TYPE
			SYNTAX SheIgmpFloodVlanControlRequestType
			MAX-ACCESS read-write
			STATUS current
			DESCRIPTION
				"createIgmpFloodVlan(743)
				sheIgmpFloodVlanControlVlanId
				
				deleteIgmpFloodVlan(744)
				         sheIgmpFloodVlanControlVlanId
				         "
			::= { sheIgmpFloodVlanControl 1 }

		
--   1.3.6.1.4.1.231.7.1.2.2.1.4.7.19.2
		sheIgmpFloodVlanControlStatus OBJECT-TYPE
			SYNTAX SheControlStatusType
			MAX-ACCESS read-only
			STATUS current
			DESCRIPTION
				"The status of a user command."
			::= { sheIgmpFloodVlanControl 2 }

		
--   1.3.6.1.4.1.231.7.1.2.2.1.4.7.19.3
		sheIgmpFloodVlanControlTimestamp OBJECT-TYPE
			SYNTAX Unsigned32
			MAX-ACCESS read-only
			STATUS current
			DESCRIPTION
				"The time stamp of the last command (end of command)."
			::= { sheIgmpFloodVlanControl 3 }

		
--   1.3.6.1.4.1.231.7.1.2.2.1.4.7.19.4
		sheIgmpFloodVlanControlTimer OBJECT-TYPE
			SYNTAX Gauge32
			MAX-ACCESS read-only
			STATUS current
			DESCRIPTION
				"Maximum command execution time (timeout) in seconds in case of a long running command."
			::= { sheIgmpFloodVlanControl 4 }

		
--   1.3.6.1.4.1.231.7.1.2.2.1.4.7.19.5
		sheIgmpFloodVlanControlReqResult OBJECT-TYPE
			SYNTAX SheBridgeControlReqResultType
			MAX-ACCESS read-only
			STATUS current
			DESCRIPTION
				"The result of the last user command."
			::= { sheIgmpFloodVlanControl 5 }

		
--   1.3.6.1.4.1.231.7.1.2.2.1.4.7.19.6
		sheIgmpFloodVlanControlVlanId OBJECT-TYPE
			SYNTAX INTEGER (1..4093)
			MAX-ACCESS read-write
			STATUS current
			DESCRIPTION
				"Table index"
			::= { sheIgmpFloodVlanControl 6 }

		
		sheIgmpSourceIpAddressTable OBJECT-TYPE
			SYNTAX SEQUENCE OF SheIgmpSourceIpAddressEntry
			MAX-ACCESS not-accessible
			STATUS current
			DESCRIPTION
				"New IGMPv3 configuration with SHE R2.8."
			::= { sheIgmp 20 }

		
		sheIgmpSourceIpAddressEntry OBJECT-TYPE
			SYNTAX SheIgmpSourceIpAddressEntry
			MAX-ACCESS not-accessible
			STATUS current
			DESCRIPTION
				"This is an unordered list of zero or more IP unicast addresses from which multicast
				reception is possible. An implementation MAY impose a limit on the size of source lists,
				but that limit MUST NOT be less than 64 addresses per list. When an operation causes
				the source list size limit to be exceeded, the service interface MUST return an error."
			INDEX { sheIgmpSourceIpIndex }
			::= { sheIgmpSourceIpAddressTable 1 }

		
		SheIgmpSourceIpAddressEntry ::=
			SEQUENCE { 
				sheIgmpSourceIpIndex
					Unsigned32,
				sheIgmpSourceIpAddress
					OCTET STRING
			 }

		sheIgmpSourceIpIndex OBJECT-TYPE
			SYNTAX Unsigned32 (1..100)
			MAX-ACCESS read-only
			STATUS current
			DESCRIPTION
				"Table Index. A maximum number of 100 different addresses could be configured inside the NE.
				These index will be configured in sheIgmpGroupSourceList to select the valid source ip address
				per group (channel).
				
				A default configuration with IP 0.0.0.0 is always available and could not be changed or removed.
				Only valid for IGMPv3 configuration.
				New parameter with SHE R2.8."
			::= { sheIgmpSourceIpAddressEntry 1 }

		
		sheIgmpSourceIpAddress OBJECT-TYPE
			SYNTAX OCTET STRING (SIZE (4))
			MAX-ACCESS read-only
			STATUS current
			DESCRIPTION
				"This is IP unicast addresses from which multicast reception is possible.
				If the source IP is 0.0.0.0, it should work as a '*' wildcard configuration (per default available).
				
				The configuration is only valid if IGMPv3 is running.
				New parameter with SHE R2.8.
				"
			::= { sheIgmpSourceIpAddressEntry 2 }

		
--   1.3.6.1.4.1.231.7.1.2.2.1.4.7.21
		sheIgmpSourceIpAddressControl OBJECT IDENTIFIER ::= { sheIgmp 21 }

		
		sheIgmpSourceIpControlRequest OBJECT-TYPE
			SYNTAX SheBridgeControlRequestType
			MAX-ACCESS read-write
			STATUS current
			DESCRIPTION
				"createIgmpSourceIpAddressEntry:
				sheIgmpSourceIpControlAddress
				
				deleteIgmpSourceIpAddressEntry:
				sheIgmpSourceIpControlIndex"
			::= { sheIgmpSourceIpAddressControl 1 }

		
		sheIgmpSourceIpControlStatus OBJECT-TYPE
			SYNTAX SheControlStatusType
			MAX-ACCESS read-only
			STATUS current
			DESCRIPTION
				"The status of a user command. 
				"
			::= { sheIgmpSourceIpAddressControl 2 }

		
		sheIgmpSourceIpControlTimeStamp OBJECT-TYPE
			SYNTAX Unsigned32
			UNITS "sec"
			MAX-ACCESS read-only
			STATUS current
			DESCRIPTION
				"The time stamp of the last command (end of command)."
			::= { sheIgmpSourceIpAddressControl 3 }

		
		sheIgmpSourceIpControlReqResult OBJECT-TYPE
			SYNTAX SheBridgeControlReqResultType
			MAX-ACCESS read-only
			STATUS current
			DESCRIPTION
				"The result of the last user command."
			::= { sheIgmpSourceIpAddressControl 4 }

		
		sheIgmpSourceIpControlTimer OBJECT-TYPE
			SYNTAX Gauge32
			MAX-ACCESS read-only
			STATUS current
			DESCRIPTION
				"The maximum wait time for the manager for a long running user command. 
				"
			::= { sheIgmpSourceIpAddressControl 5 }

		
		sheIgmpSourceIpControlIndex OBJECT-TYPE
			SYNTAX Unsigned32 (1..100)
			MAX-ACCESS read-write
			STATUS current
			DESCRIPTION
				"A table index used for delete an entry."
			::= { sheIgmpSourceIpAddressControl 6 }

		
		sheIgmpSourceIpControlAddress OBJECT-TYPE
			SYNTAX OCTET STRING (SIZE (4))
			MAX-ACCESS read-write
			STATUS current
			DESCRIPTION
				"This is IP unicast addresses from which multicast reception is possible.
				The configuration is only valid if IGMPv3 is running.
				
				New parameter with SHE R2.8."
			::= { sheIgmpSourceIpAddressControl 7 }

		
		sheIgmpBridgePortConfig OBJECT IDENTIFIER ::= { sheIgmp 22 }

		
		sheIgmpBridgePortProviderConfigTable OBJECT-TYPE
			SYNTAX SEQUENCE OF SheIgmpBridgePortProviderConfigEntry
			MAX-ACCESS not-accessible
			STATUS current
			DESCRIPTION
				"For the subscriber bridge ports (first table index is sheBridgePortIndex) the table has
				entries for all multicast provider Vlan a port has currently joined (second table index is sheIgmpProfileVlanVlanId).
				
				New supported with SHE R2.8!"
			::= { sheIgmpBridgePortConfig 1 }

		
		sheIgmpBridgePortProviderConfigEntry OBJECT-TYPE
			SYNTAX SheIgmpBridgePortProviderConfigEntry
			MAX-ACCESS not-accessible
			STATUS current
			DESCRIPTION
				"The MCast configuration settiongs per BridgePort."
			INDEX { sheBridgePortIndex, sheIgmpBridgePortProviderVlanId }
			::= { sheIgmpBridgePortProviderConfigTable 1 }

		
		SheIgmpBridgePortProviderConfigEntry ::=
			SEQUENCE { 
				sheIgmpBridgePortProviderVlanId
					Integer32,
				sheIgmpBridgePortProviderTranslationVlanId
					Integer32,
				sheIgmpBridgePortProviderAllowedVlanIdList
					OCTET STRING,
				sheIgmpBridgePortProviderMcastRemainBandwith
					Unsigned32,
				sheIgmpBridgePortProviderMcastACStatus
					SheIgmpProviderACStatus
			 }

		sheIgmpBridgePortProviderVlanId OBJECT-TYPE
			SYNTAX Integer32 (1..4093)
			MAX-ACCESS read-only
			STATUS current
			DESCRIPTION
				"MCast Provider VLAN id for the bridge port (second tableindex).
				
				New parameter with SHE R2.8."
			::= { sheIgmpBridgePortProviderConfigEntry 1 }

		
		sheIgmpBridgePortProviderTranslationVlanId OBJECT-TYPE
			SYNTAX Integer32 (1..4093)
			MAX-ACCESS read-only
			STATUS current
			DESCRIPTION
				"Translation VLAN id for the bridge port.
				New parameter with SHE R2.8."
			::= { sheIgmpBridgePortProviderConfigEntry 2 }

		
		sheIgmpBridgePortProviderAllowedVlanIdList OBJECT-TYPE
			SYNTAX OCTET STRING (SIZE (0..32))
			MAX-ACCESS read-only
			STATUS current
			DESCRIPTION
				"The octet string is a list of two octet entries each identifying a sheVlanIndex
				which is allowed on these bridgeport.
				The least significant byte is the second octet. The octet string has a variable
				length of up to 32 octets (max 16 vlan entrys).
				A entry with 0xffff is a wildCard to indicate that each vlan is allowed.
				
				New parameter with SHE R2.8."
			::= { sheIgmpBridgePortProviderConfigEntry 3 }

		
		sheIgmpBridgePortProviderMcastRemainBandwith OBJECT-TYPE
			SYNTAX Unsigned32 (0..10000)
			UNITS "100 kbps"
			MAX-ACCESS read-only
			STATUS current
			DESCRIPTION
				"It is the bridge port remaining multicast bandwidth per provider.
				
				New parameter with SHE R2.8."
			::= { sheIgmpBridgePortProviderConfigEntry 4 }

		
		sheIgmpBridgePortProviderMcastACStatus OBJECT-TYPE
			SYNTAX SheIgmpProviderACStatus
			MAX-ACCESS read-only
			STATUS current
			DESCRIPTION
				"It indicate the bridge port AC (admission control )status per provider.
				It can be accept or deny.
				When it is accepted, it indicates the provider still has enough bandwidth for multicast access. 
				When it is denied, it indicates the provider is short of bandwidth for multicast access.
				1 means accept, 0 means deny
				
				New parameter with SHE R2.8. "
			::= { sheIgmpBridgePortProviderConfigEntry 5 }

		
		sheIgmpBridgePortProviderControl OBJECT IDENTIFIER ::= { sheIgmpBridgePortConfig 2 }

		
		sheIgmpBridgePortProviderControlRequest OBJECT-TYPE
			SYNTAX SheBridgeControlRequestType
			MAX-ACCESS read-write
			STATUS current
			DESCRIPTION
				"createIgmpBridgePortProviderEntry(763):
				sheIgmpBridgePortProviderControlIndex
				sheIgmpBridgePortProviderControlProviderVlanId
				sheIgmpBridgePortProviderControlTranslationVlanId
				sheIgmpBridgePortProviderControlAllowedVlanIdList
								
				modifyIgmpBridgePortProviderEntry(764):
				sheIgmpBridgePortProviderControlIndex
				sheIgmpBridgePortProviderControlProviderVlanId
				sheIgmpBridgePortProviderControlTranslationVlanId
				sheIgmpBridgePortProviderControlAllowedVlanIdList
								
				deleteIgmpBridgePortProviderEntry(765):
				sheIgmpBridgePortProviderControlIndex
				sheIgmpBridgePortProviderControlProviderVlanId"
			::= { sheIgmpBridgePortProviderControl 1 }

		
		sheIgmpBridgePortProviderControlIndex OBJECT-TYPE
			SYNTAX Integer32
			MAX-ACCESS read-write
			STATUS current
			DESCRIPTION
				"The index of the bridgePort to be configured."
			::= { sheIgmpBridgePortProviderControl 2 }

		
		sheIgmpBridgePortProviderControlStatus OBJECT-TYPE
			SYNTAX SheControlStatusType
			MAX-ACCESS read-only
			STATUS current
			DESCRIPTION
				"The status of a user command. 
				"
			::= { sheIgmpBridgePortProviderControl 3 }

		
		sheIgmpBridgePortProviderControlTimer OBJECT-TYPE
			SYNTAX Gauge32
			MAX-ACCESS read-only
			STATUS current
			DESCRIPTION
				"The maximum wait time for the manager for a long running user command. 
				"
			::= { sheIgmpBridgePortProviderControl 4 }

		
		sheIgmpBridgePortProviderControlReqResult OBJECT-TYPE
			SYNTAX SheBridgeControlReqResultType
			MAX-ACCESS read-only
			STATUS current
			DESCRIPTION
				"The result of the last user command."
			::= { sheIgmpBridgePortProviderControl 5 }

		
		sheIgmpBridgePortProviderControlTimeStamp OBJECT-TYPE
			SYNTAX Unsigned32
			UNITS "sec"
			MAX-ACCESS read-only
			STATUS current
			DESCRIPTION
				"The time stamp of the last command (end of command)."
			::= { sheIgmpBridgePortProviderControl 6 }

		
		sheIgmpBridgePortProviderControlProviderVlanId OBJECT-TYPE
			SYNTAX Integer32 (1..4093)
			MAX-ACCESS read-write
			STATUS current
			DESCRIPTION
				"MCast Provider VLAN id for the bridge port (second tableindex).
				
				New parameter with SHE R2.8."
			::= { sheIgmpBridgePortProviderControl 7 }

		
		sheIgmpBridgePortProviderControlTranslationVlanId OBJECT-TYPE
			SYNTAX Integer32 (1..4093)
			MAX-ACCESS read-write
			STATUS current
			DESCRIPTION
				"Translation VLAN id for the bridge port.
				
				New parameter with SHE R2.8."
			::= { sheIgmpBridgePortProviderControl 8 }

		
		sheIgmpBridgePortProviderControlAllowedVlanIdList OBJECT-TYPE
			SYNTAX OCTET STRING (SIZE (0..32))
			MAX-ACCESS read-write
			STATUS current
			DESCRIPTION
				"The octet string is a list of two octet entries each identifying a sheVlanIndex
				which is allowed on these bridgeport.
				The least significant byte is the second octet. The octet string has a variable
				length of up to 32 octets (max 16 vlan entrys).
				A entry with 0xffff is a wildCard to indicate that each vlan is allowed.
				
				New parameter with SHE R2.8."
			::= { sheIgmpBridgePortProviderControl 9 }

		
		sheIgmpBridgePortNotifications OBJECT IDENTIFIER ::= { sheIgmpBridgePortConfig 5 }

		
		sheIgmpBridgePortProviderParameterCreated NOTIFICATION-TYPE
			OBJECTS { sheIgmpBridgePortProviderControlIndex, sheIgmpBridgePortProviderControlTimeStamp, sheIgmpBridgePortProviderControlProviderVlanId, sheIgmpBridgePortProviderControlTranslationVlanId, sheIgmpBridgePortProviderControlAllowedVlanIdList
				 }
			STATUS current
			DESCRIPTION 
				"send trap when bridgeport R2.8 igmp provider parameter was created."
			::= { sheIgmpBridgePortNotifications 1 }

		
		sheIgmpBridgePortProviderParameterModified NOTIFICATION-TYPE
			OBJECTS { sheIgmpBridgePortProviderControlIndex, sheIgmpBridgePortProviderControlTimeStamp, sheIgmpBridgePortProviderControlProviderVlanId, sheIgmpBridgePortProviderControlTranslationVlanId, sheIgmpBridgePortProviderControlAllowedVlanIdList
				 }
			STATUS current
			DESCRIPTION 
				"send trap when bridgeport R2.8 igmp provider parameter was modified."
			::= { sheIgmpBridgePortNotifications 2 }

		
		sheIgmpBridgePortProviderParameterDeleted NOTIFICATION-TYPE
			OBJECTS { sheIgmpBridgePortProviderControlIndex, sheIgmpBridgePortProviderControlTimeStamp, sheIgmpBridgePortProviderControlProviderVlanId, sheIgmpBridgePortProviderControlTranslationVlanId, sheIgmpBridgePortProviderControlAllowedVlanIdList
				 }
			STATUS current
			DESCRIPTION 
				"send trap when bridgeport R2.8 igmp provider parameter was deleted."
			::= { sheIgmpBridgePortNotifications 3 }

		
--   1.3.6.1.4.1.231.7.1.2.2.1.4.7.15
		sheIgmpConformance OBJECT IDENTIFIER ::= { sheIgmp 100 }

		
--   1.3.6.1.4.1.231.7.1.2.2.1.4.7.15.1
		sheIgmpCompliances OBJECT IDENTIFIER ::= { sheIgmpConformance 1 }

		
--   1.3.6.1.4.1.231.7.1.2.2.1.4.7.15.1.1
-- this module
-- this module
		sheIgmpCompliance MODULE-COMPLIANCE
			STATUS current
			DESCRIPTION 
				"Description."
			MODULE -- this module
				MANDATORY-GROUPS { sheIgmpBaseGroup, sheIgmpGroupGroup, sheIgmpGroupControlGroup, sheIgmpMcastGroupPackageGroup, sheIgmpMcastGroupPackageControlGroup, 
					sheIgmpPortGroupsGroup, sheIgmpNotificationGroup, sheIgmpBridgePortGroup, sheIgmpBridgePortControlGroup, sheIgmpBridgePortNotificationGroup, 
					sheIgmpProfileVlanGroup, sheIgmpProfileGroup, sheIgmpProfileControlGroup, sheIgmpProfileVlanControlGroup }
			::= { sheIgmpCompliances 1 }

		
--   1.3.6.1.4.1.231.7.1.2.2.1.4.7.15.2
		sheIgmpGroups OBJECT IDENTIFIER ::= { sheIgmpConformance 2 }

		
--   1.3.6.1.4.1.231.7.1.2.2.1.4.7.15.2.1
		sheIgmpBaseGroup OBJECT-GROUP
			OBJECTS { sheIgmpMode, sheIgmpMaxJoinedGroup, sheIgmpSourceIpIndex, sheIgmpSourceIpAddress, sheIgmpSourceIpControlRequest, 
				sheIgmpSourceIpControlStatus, sheIgmpSourceIpControlTimeStamp, sheIgmpSourceIpControlReqResult, sheIgmpSourceIpControlTimer, sheIgmpSourceIpControlIndex, 
				sheIgmpSourceIpControlAddress, sheIgmpVlanTranslationMode, sheIgmpVlanDoubleTaggingMode, sheIgmpDoubleTaggingControlRequest, sheIgmpDoubleTaggingControlStatus, 
				sheIgmpDoubleTaggingControlTimeStamp, sheIgmpDoubleTaggingControlReqResult, sheIgmpDoubleTaggingControlTimer, sheIgmpControlVlanTranslationMode, sheIgmpControlVlanDoubleTaggingMode
				 }
			STATUS current
			DESCRIPTION 
				"Description."
			::= { sheIgmpGroups 1 }

		
--   1.3.6.1.4.1.231.7.1.2.2.1.4.7.15.2.2
		sheIgmpProfileGroup OBJECT-GROUP
			OBJECTS { sheIgmpProviderIndex, sheIgmpProviderRobustness, sheIgmpProviderQueryInterval, sheIgmpProviderStartupQueryInterval, sheIgmpProviderLastMemberQueryInterval, 
				sheIgmpProviderLastMemberQueryCount, sheIgmpProviderUnsolicitedReportInterval, sheIgmpProviderQueryResponseInterval, sheIgmpProviderStartupQueryCount, sheIgmpProviderImmediateLeave, 
				sheIgmpProviderProxyIpAddress, sheIgmpProfileVlanVlanId, sheIgmpProfileVlanMcastEgressPorts, sheIgmpProfileVlanInnerVlanId, sheIgmpProviderVlanMulticastLimitation, 
				sheIgmpProviderVersion1RouterPresentTimeout, sheIgmpProviderProfileName, sheIgmpProviderVersion1RouterTimeout, sheIgmpProviderMcastBandwithLimit, sheIgmpProviderDefaultChannelBandwith
				 }
			STATUS current
			DESCRIPTION 
				"Description."
			::= { sheIgmpGroups 2 }

		
--   1.3.6.1.4.1.231.7.1.2.2.1.4.7.15.2.3
		sheIgmpProfileControlGroup OBJECT-GROUP
			OBJECTS { sheIgmpProviderControlRequest, sheIgmpProviderControlIndex, sheIgmpProviderControlStatus, sheIgmpProviderControlTimer, sheIgmpProviderControlReqResult, 
				sheIgmpProviderControlRobustness, sheIgmpProviderControlStartupQueryInterval, sheIgmpProviderControlLastMemberQueryInterval, sheIgmpProviderControlTimeStamp, sheIgmpProviderControlProfileName, 
				sheIgmpProviderControlQueryInterval, sheIgmpProviderControlQueryResponseInterval, sheIgmpProviderControlImmediateLeave, sheIgmpProviderControlVersion1RouterTimeout, sheIgmpProviderControlStartupQueryCount, 
				sheIgmpProviderControlLastMemberQueryCount, sheIgmpProviderControlProxyIpAddress, sheIgmpProviderControlMaxJoinedGroup, sheIgmpProviderControlASMStatus, sheIgmpProviderControlUnsolicitedReportInterval, 
				sheIgmpProviderControlMode, sheIgmpProviderControlVlanMulticastLimitation, sheIgmpProviderControlVersion, sheIgmpProviderControlMcastBandwithLimit, sheIgmpProviderControlDefaultChannelBandwith
				 }
			STATUS current
			DESCRIPTION 
				"Description."
			::= { sheIgmpGroups 3 }

		
--   1.3.6.1.4.1.231.7.1.2.2.1.4.7.15.2.4
		sheIgmpProfileVlanGroup OBJECT-GROUP
			OBJECTS { sheIgmpProfileVlanVlanId, sheIgmpProfileVlanMcastEgressPorts, sheIgmpProfileVlanInnerVlanId, sheIgmpProfileVlanDot1pPriority, sheIgmpProfileVlanDot1pReportPriority, 
				sheIgmpProfileVlanDot1pInnerPriority, sheIgmpProfileVlanDot1pInnerReportPriority, sheIgmpProfileVlanForkingMode, sheIgmpProfileVlanOuterVlanId, sheIgmpProfileVlanVersion, 
				sheIgmpProfileVlanASMStatus, sheIgmpProfileVlanCxUSnoopingState, sheIgmpProfileVlanDefaultSourceIdList }
			STATUS current
			DESCRIPTION 
				"Description."
			::= { sheIgmpGroups 4 }

		
--   1.3.6.1.4.1.231.7.1.2.2.1.4.7.15.2.5
		sheIgmpProfileVlanControlGroup OBJECT-GROUP
			OBJECTS { sheIgmpProfileVlanControlRequest, sheIgmpProfileVlanControlStatus, sheIgmpProfileVlanControlTimeStamp, sheIgmpProfileVlanControlReqResult, sheIgmpProfileVlanControlTimer, 
				sheIgmpProfileVlanControlInnerVlanId, sheIgmpProfileVlanControlDot1pPriority, sheIgmpProfileVlanControlDot1pReportPriority, sheIgmpProfileVlanControlDot1pInnerPriority, sheIgmpProfileVlanControlDot1pInnerReportPriority, 
				sheIgmpProfileVlanControlVlanId, sheIgmpProfileVlanControlIndex, sheIgmpProfileVlanControlForkingMode, sheIgmpProfileVlanControlOuterVlanId, sheIgmpProviderControlASMStatus, 
				sheIgmpProviderControlVersion, sheIgmpProfileVlanControlCxUSnoopingState, sheIgmpProfileVlanControlDefaultSourceIdList }
			STATUS current
			DESCRIPTION 
				"Description."
			::= { sheIgmpGroups 5 }

		
--   1.3.6.1.4.1.231.7.1.2.2.1.4.7.15.2.6
		sheIgmpGroupGroup OBJECT-GROUP
			OBJECTS { sheIgmpGroupIndex, sheIgmpGroupIpAddress, sheIgmpGroupJoinedPortsList, sheIgmpGroupLastMembershipReport, sheIgmpGroupLastLeaveMessage, 
				sheIgmpGroupSuppliedCardList, sheIgmpGroupProviderId, sheIgmpGroupName, sheIgmpGroupMcastGroupPackageList, sheIgmpGroupIsStatic, 
				sheIgmpMcastChannelSourceId, sheIgmpMcastChannelBandwith, sheIgmpMcastChannelDefaultSourceIdList }
			STATUS current
			DESCRIPTION 
				"Description."
			::= { sheIgmpGroups 6 }

		
--   1.3.6.1.4.1.231.7.1.2.2.1.4.7.15.2.7
		sheIgmpGroupControlGroup OBJECT-GROUP
			OBJECTS { sheIgmpGroupControlRequest, sheIgmpGroupControlIndex, sheIgmpGroupControlStatus, sheIgmpGroupControlTimer, sheIgmpGroupControlReqResult, 
				sheIgmpGroupControlIpAddress, sheIgmpGroupControlProviderId, sheIgmpGroupControlTimeStamp, sheIgmpGroupControlName, sheIgmpGroupControlMcastGroupPackageList, 
				sheIgmpGroupControlIsStatic, sheIgmpMcastChannelControlSourceId, sheIgmpMcastChannelControlBandwith, sheIgmpMcastChannelControlDefaultSourceIdList }
			STATUS current
			DESCRIPTION 
				"Description."
			::= { sheIgmpGroups 7 }

		
--   1.3.6.1.4.1.231.7.1.2.2.1.4.7.15.2.8
		sheIgmpMcastGroupPackageGroup OBJECT-GROUP
			OBJECTS { sheIgmpMcastGroupPackageIndex, sheIgmpMcastGroupPackageName, sheIgmpMcastGroupPackageGroupList }
			STATUS current
			DESCRIPTION 
				"Description."
			::= { sheIgmpGroups 8 }

		
--   1.3.6.1.4.1.231.7.1.2.2.1.4.7.15.2.9
		sheIgmpMcastGroupPackageControlGroup OBJECT-GROUP
			OBJECTS { sheIgmpMcastGroupPackageControlRequest, sheIgmpMcastGroupPackageControlIndex, sheIgmpMcastGroupPackageControlStatus, sheIgmpMcastGroupPackageControlTimer, sheIgmpMcastGroupPackageControlReqResult, 
				sheIgmpMcastGroupPackageControlTimeStamp, sheIgmpMcastGroupPackageControlName }
			STATUS current
			DESCRIPTION 
				"Description."
			::= { sheIgmpGroups 9 }

		
--   1.3.6.1.4.1.231.7.1.2.2.1.4.7.15.2.10
		sheIgmpPortGroupsGroup OBJECT-GROUP
			OBJECTS { sheIgmpPortGroupsStpIpAddress, sheIgmpPortGroupsTimeLastMembRep, sheIgmpPortGroupsFiltermode, sheIgmpPortGroupsSourceId, sheIgmpPortGroupsIpAddress, 
				sheIgmpPortGroupsIndex }
			STATUS current
			DESCRIPTION 
				"Description."
			::= { sheIgmpGroups 10 }

		
--   1.3.6.1.4.1.231.7.1.2.2.1.4.7.15.2.11
		sheIgmpNotificationGroup NOTIFICATION-GROUP
			NOTIFICATIONS { sheIgmpGroupEntryCreated, sheIgmpGroupEntryModified, sheIgmpGroupEntryDeleted, sheIgmpMcastGroupPackageEntryCreated, sheIgmpProfileControlResult, 
				sheIgmpProfileVlanControlResult, sheIgmpGroupControlResult, sheIgmpMcastGroupPackageControlResult, sheIgmpMcastGroupPackageEntryModified, sheIgmpProfileVlanEntryModified, 
				sheIgmpMcastGroupPackageEntryDeleted, sheIgmpModeModified, sheIgmpProfileVlanDot1pModified, sheIgmpSourceIpEntryCreated, sheIgmpSourceIpEntryDeleted, 
				sheIgmpMaxJoinedGroupModified, sheIgmpProfileEntryCreated, sheIgmpProfileEntryModified, sheIgmpProfileEntryDeleted, sheIgmpProfileVlanEntryCreated, 
				sheIgmpProfileVlanEntryDeleted, sheIgmpFloodVlanCreated, sheIgmpFloodVlanDeleted, sheIgmpChannelParameterModified, sheIgmpProfileChannelAdmissionModified, 
				sheIgmpTagModeModified }
			STATUS current
			DESCRIPTION 
				"Description."
			::= { sheIgmpGroups 11 }

		
--   1.3.6.1.4.1.231.7.1.2.2.1.4.7.15.2.12
		sheIgmpStatisticsGroup OBJECT-GROUP
			OBJECTS { sheIgmpStatsGroupIndex, sheIgmpStatsGroupTimeSinceLastMembershipReport, sheIgmpStatsNumberOfGroupsToRouter, sheIgmpStatsNumberOfGroupsToHost, sheIgmpStatsNumberOfQueryReceived, 
				sheIgmpStatsNumberOfReportReceived, sheIgmpStatsNumberOfLeaveReceived, sheIgmpStatsNumberOfInvalidReceived, sheIgmpStatsPeakNumberOfActiveGroupToRouter, sheIgmpStatsTimeOfPeakNumberOfActiveGroupToRouter, 
				sheIgmpStatsPeakNumberOfActiveGroupFromHost, sheIgmpStatsTimeOfPeakNumberOfActiveGroupFromHost, sheIgmpStatsNumberOfMsgPerSec, sheIgmpStatsPeakNumberOfMsgPerSec, sheIgmpStatsTimeOfPeakNumberOfMsgPerSec, 
				sheIgmpStatsBaseControlRequest, sheIgmpStatsBaseControlStatus, sheIgmpStatsBaseControlTimestamp, sheIgmpStatsBaseControlReqResult, sheIgmpStatsPortNumberOfGroups, 
				sheIgmpStatsPortNumberOfQueryReceived, sheIgmpStatsPortNumberOfReportReceived, sheIgmpStatsPortNumberOfLeaveReceived, sheIgmpStatsPortNumberOfInvalidReceived, sheIgmpStatsPortPeakNumberOfActiveGroup, 
				sheIgmpStatsPortTimeOfPeakNumberOfActiveGroup, sheIgmpStatsPortNumberOfDroppedByCA, sheIgmpStatsPortNumberOfDroppedByAC, sheIgmpStatsPortControlRequest, sheIgmpStatsPortControlStatus, 
				sheIgmpStatsPortControlTimestamp, sheIgmpStatsPortControlReqResult, sheIgmpStatsPortControlBridgePortIndex, sheIgmpFloodVlanId, sheIgmpFloodVlanControlRequest, 
				sheIgmpFloodVlanControlStatus, sheIgmpFloodVlanControlTimestamp, sheIgmpFloodVlanControlTimer, sheIgmpFloodVlanControlReqResult, sheIgmpFloodVlanControlVlanId, 
				sheIgmpStatsProviderNumberOfChannelsToRouter, sheIgmpStatsProviderNumberOfChannelsToHost, sheIgmpStatsProviderNumberOfQueryReceived, sheIgmpStatsProviderNumberOfReportReceived, sheIgmpStatsProviderNumberOfLeaveReceived, 
				sheIgmpStatsProviderNumberOfInvalidReceived, sheIgmpStatsProviderPeakNumberOfActiveChannelToRouter, sheIgmpStatsProviderTimeOfPeakNumberOfActiveChannelToRouter, sheIgmpStatsProviderPeakNumberOfActiveChannelFromHost, sheIgmpStatsProviderTimeOfPeakNumberOfActiveChannelFromHost, 
				sheIgmpStatsProviderNumberOfMsgPerSec, sheIgmpStatsProviderPeakNumberOfMsgPerSec, sheIgmpStatsProviderTimeOfPeakNumberOfMsgPerSec, sheIgmpStatsProviderControlRequest, sheIgmpStatsProviderControlStatus, 
				sheIgmpStatsProviderControlTimestamp, sheIgmpStatsProviderControlReqResult, sheIgmpStatsProviderControlProviderIndex }
			STATUS current
			DESCRIPTION 
				"Description."
			::= { sheIgmpGroups 12 }

		
--   1.3.6.1.4.1.231.7.1.2.2.1.4.7.15.2.13
		sheIgmpFloodVlanTableGroup OBJECT-GROUP
			OBJECTS { sheIgmpFloodVlanId }
			STATUS current
			DESCRIPTION 
				"Description."
			::= { sheIgmpGroups 13 }

		
--   1.3.6.1.4.1.231.7.1.2.2.1.4.7.15.2.14
		sheIgmpFloodVlanControlGroup OBJECT-GROUP
			OBJECTS { sheIgmpFloodVlanControlRequest, sheIgmpFloodVlanControlStatus, sheIgmpFloodVlanControlTimestamp, sheIgmpFloodVlanControlTimer, sheIgmpFloodVlanControlReqResult, 
				sheIgmpFloodVlanControlVlanId }
			STATUS current
			DESCRIPTION 
				"Description."
			::= { sheIgmpGroups 14 }

		
		sheIgmpObsoleteGroup OBJECT-GROUP
			OBJECTS { sheIgmpMaxJoinedSubscriber, sheIgmpProviderControlMaxJoinedSubscriber, sheIgmpVersion, sheIgmpPortGroupsTimeFirstMembRep }
			STATUS obsolete
			DESCRIPTION 
				"Description."
			::= { sheIgmpGroups 15 }

		
		sheIgmpObsoleteNotificationGroup NOTIFICATION-GROUP
			NOTIFICATIONS { sheIgmpMaxJoinedSubscriberModified }
			STATUS obsolete
			DESCRIPTION 
				"Description."
			::= { sheIgmpGroups 16 }

		
		sheIgmpBridgePortGroup OBJECT-GROUP
			OBJECTS { sheIgmpBridgePortProviderVlanId, sheIgmpBridgePortProviderTranslationVlanId, sheIgmpBridgePortProviderAllowedVlanIdList, sheIgmpBridgePortProviderMcastRemainBandwith, sheIgmpBridgePortProviderMcastACStatus
				 }
			STATUS current
			DESCRIPTION 
				"Description."
			::= { sheIgmpGroups 17 }

		
		sheIgmpBridgePortControlGroup OBJECT-GROUP
			OBJECTS { sheIgmpBridgePortProviderControlRequest, sheIgmpBridgePortProviderControlIndex, sheIgmpBridgePortProviderControlStatus, sheIgmpBridgePortProviderControlTimer, sheIgmpBridgePortProviderControlReqResult, 
				sheIgmpBridgePortProviderControlTimeStamp, sheIgmpBridgePortProviderControlProviderVlanId, sheIgmpBridgePortProviderControlTranslationVlanId, sheIgmpBridgePortProviderControlAllowedVlanIdList }
			STATUS current
			DESCRIPTION 
				"Description."
			::= { sheIgmpGroups 18 }

		
		sheIgmpBridgePortNotificationGroup NOTIFICATION-GROUP
			NOTIFICATIONS { sheIgmpBridgePortProviderParameterCreated, sheIgmpBridgePortProviderParameterModified, sheIgmpBridgePortProviderParameterDeleted }
			STATUS current
			DESCRIPTION 
				"Description."
			::= { sheIgmpGroups 19 }

		
--   1.3.6.1.4.1.231.7.1.2.2.1.4.8
		sheQueueConfiguration OBJECT IDENTIFIER ::= { sheBridgeMib 8 }

		
--   1.3.6.1.4.1.231.7.1.2.2.1.4.8.1
		sheQueuePriorityTable OBJECT-TYPE
			SYNTAX SEQUENCE OF SheQueuePriorityEntry
			MAX-ACCESS not-accessible
			STATUS current
			DESCRIPTION
				"Configure the .1p prioritys of each queue for upstream and downstream direction."
			::= { sheQueueConfiguration 1 }

		
--   1.3.6.1.4.1.231.7.1.2.2.1.4.8.1.1
		sheQueuePriorityEntry OBJECT-TYPE
			SYNTAX SheQueuePriorityEntry
			MAX-ACCESS not-accessible
			STATUS current
			DESCRIPTION
				"One entry for each priority."
			INDEX { sheQueuePriority }
			::= { sheQueuePriorityTable 1 }

		
		SheQueuePriorityEntry ::=
			SEQUENCE { 
				sheQueuePriority
					Integer32,
				sheQueueNumber
					Integer32
			 }

--   1.3.6.1.4.1.231.7.1.2.2.1.4.8.1.1.1
		sheQueuePriority OBJECT-TYPE
			SYNTAX Integer32 (1..8)
			MAX-ACCESS read-only
			STATUS current
			DESCRIPTION
				"The index of that table. It represents the .1p Priority + 1,because
				priority values will have a range from 0-7 but index has to start always
				with 1."
			::= { sheQueuePriorityEntry 1 }

		
--   1.3.6.1.4.1.231.7.1.2.2.1.4.8.1.1.2
		sheQueueNumber OBJECT-TYPE
			SYNTAX Integer32 (1..8)
			MAX-ACCESS read-only
			STATUS current
			DESCRIPTION
				"That represents the Queue-Number. Only applicable for ingress queues on iu,
				because cxu_b will always use only one queue for traffic."
			::= { sheQueuePriorityEntry 2 }

		
--   1.3.6.1.4.1.231.7.1.2.2.1.4.8.2
		sheReducedQueuePriorityTable OBJECT-TYPE
			SYNTAX SEQUENCE OF SheReducedQueuePriorityEntry
			MAX-ACCESS not-accessible
			STATUS current
			DESCRIPTION
				"There could a shrinking of queues on the iu in downstream direction
				(depending on the used IU type).
				So the available .1p-prioritys has to be mapped on a set of only four 
				available queue-numbers."
			::= { sheQueueConfiguration 2 }

		
--   1.3.6.1.4.1.231.7.1.2.2.1.4.8.2.1
		sheReducedQueuePriorityEntry OBJECT-TYPE
			SYNTAX SheReducedQueuePriorityEntry
			MAX-ACCESS not-accessible
			STATUS current
			DESCRIPTION
				"One entry for each priority."
			INDEX { sheReducedQueuePriority }
			::= { sheReducedQueuePriorityTable 1 }

		
		SheReducedQueuePriorityEntry ::=
			SEQUENCE { 
				sheReducedQueuePriority
					Integer32,
				sheReducedQueueNumber
					Integer32
			 }

--   1.3.6.1.4.1.231.7.1.2.2.1.4.8.2.1.1
		sheReducedQueuePriority OBJECT-TYPE
			SYNTAX Integer32 (1..8)
			MAX-ACCESS read-only
			STATUS current
			DESCRIPTION
				"The index of that table. It represents the .1p Priority + 1,because
				priority values will have a range from 0-7 but index has to start always
				with 1."
			::= { sheReducedQueuePriorityEntry 1 }

		
--   1.3.6.1.4.1.231.7.1.2.2.1.4.8.2.1.2
		sheReducedQueueNumber OBJECT-TYPE
			SYNTAX Integer32 (1..4)
			MAX-ACCESS read-only
			STATUS current
			DESCRIPTION
				"Number of the outgoing queue, where this priority is mapped on."
			::= { sheReducedQueuePriorityEntry 2 }

		
--   1.3.6.1.4.1.231.7.1.2.2.1.4.8.3
		sheQueueControl OBJECT IDENTIFIER ::= { sheQueueConfiguration 3 }

		
--   1.3.6.1.4.1.231.7.1.2.2.1.4.8.3.1
		sheQueueControlRequest OBJECT-TYPE
			SYNTAX SheBridgeControlRequestType
			MAX-ACCESS read-write
			STATUS current
			DESCRIPTION
				"modifyQueuePriorityMapping:
				sheQueueControlIndex
				sheQueueControlQueueNumber
				
				modifyReducedQueuePriorityMapping:
				sheQueueControlIndex
				sheQueueControlQueueNumber
				
				"
			::= { sheQueueControl 1 }

		
--   1.3.6.1.4.1.231.7.1.2.2.1.4.8.3.2
		sheQueueControlIndex OBJECT-TYPE
			SYNTAX Integer32
			MAX-ACCESS read-write
			STATUS current
			DESCRIPTION
				"The table-index to be modified."
			::= { sheQueueControl 2 }

		
--   1.3.6.1.4.1.231.7.1.2.2.1.4.8.3.3
		sheQueueControlStatus OBJECT-TYPE
			SYNTAX SheControlStatusType
			MAX-ACCESS read-only
			STATUS current
			DESCRIPTION
				"The status of a user command. 
				"
			::= { sheQueueControl 3 }

		
--   1.3.6.1.4.1.231.7.1.2.2.1.4.8.3.4
		sheQueueControlTimer OBJECT-TYPE
			SYNTAX Gauge32
			MAX-ACCESS read-only
			STATUS current
			DESCRIPTION
				"The maximum wait time for the manager for a long running user command. 
				"
			::= { sheQueueControl 4 }

		
--   1.3.6.1.4.1.231.7.1.2.2.1.4.8.3.5
		sheQueueControlReqResult OBJECT-TYPE
			SYNTAX SheBridgeControlReqResultType
			MAX-ACCESS read-only
			STATUS current
			DESCRIPTION
				"The result of the last user command."
			::= { sheQueueControl 5 }

		
--   1.3.6.1.4.1.231.7.1.2.2.1.4.8.3.6
		sheQueueControlTimeStamp OBJECT-TYPE
			SYNTAX Unsigned32
			UNITS "sec"
			MAX-ACCESS read-only
			STATUS current
			DESCRIPTION
				"The time stamp of the last command (end of command)."
			::= { sheQueueControl 6 }

		
--   1.3.6.1.4.1.231.7.1.2.2.1.4.8.3.7
		sheQueueControlQueueNumber OBJECT-TYPE
			SYNTAX Integer32 (1..8)
			MAX-ACCESS read-write
			STATUS current
			DESCRIPTION
				"The range for this value depends on the used ControlRequest. In case of the 
				Controlrequest is modifyReducedQueuePriorityMapping, the range is only 1..4! "
			::= { sheQueueControl 7 }

		
--   1.3.6.1.4.1.231.7.1.2.2.1.4.8.4
		sheQueueModeTable OBJECT-TYPE
			SYNTAX SEQUENCE OF SheQueueModeEntry
			MAX-ACCESS not-accessible
			STATUS current
			DESCRIPTION
				"Configure queue mode depending on the interfacetype."
			::= { sheQueueConfiguration 4 }

		
--   1.3.6.1.4.1.231.7.1.2.2.1.4.8.4.1
		sheQueueModeEntry OBJECT-TYPE
			SYNTAX SheQueueModeEntry
			MAX-ACCESS not-accessible
			STATUS current
			DESCRIPTION
				"One entry for each interface type."
			INDEX { sheQueueModeInterfaceTypeIndex }
			::= { sheQueueModeTable 1 }

		
		SheQueueModeEntry ::=
			SEQUENCE { 
				sheQueueModeInterfaceTypeIndex
					SheBridgeInterfaceType,
				sheQueueConfigurationMode
					SheQueueModeType
			 }

--   1.3.6.1.4.1.231.7.1.2.2.1.4.8.4.1.1
		sheQueueModeInterfaceTypeIndex OBJECT-TYPE
			SYNTAX SheBridgeInterfaceType
			MAX-ACCESS read-only
			STATUS current
			DESCRIPTION
				"Describes the interface type, were this queue configuration should be used.
				uplink
				downlink
				cascading
				subcascading
				"
			::= { sheQueueModeEntry 1 }

		
--   1.3.6.1.4.1.231.7.1.2.2.1.4.8.4.1.2
		sheQueueConfigurationMode OBJECT-TYPE
			SYNTAX SheQueueModeType
			MAX-ACCESS read-only
			STATUS current
			DESCRIPTION
				"Describes the queue mode, for this interface type. 
				strict
				weighted
				
				Note:
				Mode 'weighted' could mean 'weighted round robin' (wrr) or 'weighted fair queueing' (wfq)
				and depends on the individual HW restrictions of the used board's."
			DEFVAL { strict }
			::= { sheQueueModeEntry 2 }

		
--   1.3.6.1.4.1.231.7.1.2.2.1.4.8.5
		sheQueueModeControl OBJECT IDENTIFIER ::= { sheQueueConfiguration 5 }

		
--   1.3.6.1.4.1.231.7.1.2.2.1.4.8.5.1
		sheQueueModeControlRequest OBJECT-TYPE
			SYNTAX SheBridgeControlRequestType
			MAX-ACCESS read-write
			STATUS current
			DESCRIPTION
				"modifyQueueModeEntry:
				sheQueueModeControlIndex
				sheQueueModeControlMode"
			::= { sheQueueModeControl 1 }

		
--   1.3.6.1.4.1.231.7.1.2.2.1.4.8.5.2
		sheQueueModeControlIndex OBJECT-TYPE
			SYNTAX Integer32 (1..3)
			MAX-ACCESS read-write
			STATUS current
			DESCRIPTION
				"The table index to be modified."
			::= { sheQueueModeControl 2 }

		
--   1.3.6.1.4.1.231.7.1.2.2.1.4.8.5.3
		sheQueueModeControlStatus OBJECT-TYPE
			SYNTAX SheControlStatusType
			MAX-ACCESS read-only
			STATUS current
			DESCRIPTION
				"The status of a user command. 
				"
			::= { sheQueueModeControl 3 }

		
--   1.3.6.1.4.1.231.7.1.2.2.1.4.8.5.4
		sheQueueModeControlTimer OBJECT-TYPE
			SYNTAX Gauge32
			MAX-ACCESS read-only
			STATUS current
			DESCRIPTION
				"The maximum wait time for the manager for a long running user command. 
				"
			::= { sheQueueModeControl 4 }

		
--   1.3.6.1.4.1.231.7.1.2.2.1.4.8.5.5
		sheQueueModeControlReqResult OBJECT-TYPE
			SYNTAX SheBridgeControlReqResultType
			MAX-ACCESS read-only
			STATUS current
			DESCRIPTION
				"The result of the last user command."
			::= { sheQueueModeControl 5 }

		
--   1.3.6.1.4.1.231.7.1.2.2.1.4.8.5.6
		sheQueueModeControlTimeStamp OBJECT-TYPE
			SYNTAX Unsigned32
			UNITS "sec"
			MAX-ACCESS read-only
			STATUS current
			DESCRIPTION
				"The time stamp of the last command (end of command)."
			::= { sheQueueModeControl 6 }

		
--   1.3.6.1.4.1.231.7.1.2.2.1.4.8.5.7
		sheQueueModeControlMode OBJECT-TYPE
			SYNTAX SheQueueModeType
			MAX-ACCESS read-write
			STATUS current
			DESCRIPTION
				"Set the queue mode."
			::= { sheQueueModeControl 7 }

		
--   1.3.6.1.4.1.231.7.1.2.2.1.4.8.6
		sheQueueWeightTable OBJECT-TYPE
			SYNTAX SEQUENCE OF SheQueueWeightEntry
			MAX-ACCESS not-accessible
			STATUS current
			DESCRIPTION
				"Configure weight's of queues for upstream direction."
			::= { sheQueueConfiguration 6 }

		
--   1.3.6.1.4.1.231.7.1.2.2.1.4.8.6.1
		sheQueueWeightEntry OBJECT-TYPE
			SYNTAX SheQueueWeightEntry
			MAX-ACCESS not-accessible
			STATUS current
			DESCRIPTION
				"One entry for each queue."
			INDEX { sheQueueIndex }
			::= { sheQueueWeightTable 1 }

		
		SheQueueWeightEntry ::=
			SEQUENCE { 
				sheQueueIndex
					Unsigned32,
				sheQueueWeight
					Unsigned32,
				sheQueueWeightWatermarkLow
					Integer32,
				sheQueueWeightWatermarkHigh
					Integer32
			 }

--   1.3.6.1.4.1.231.7.1.2.2.1.4.8.6.1.1
		sheQueueIndex OBJECT-TYPE
			SYNTAX Unsigned32 (1..8)
			MAX-ACCESS read-only
			STATUS current
			DESCRIPTION
				"A table index. This index represents the Queue-Number."
			::= { sheQueueWeightEntry 1 }

		
--   1.3.6.1.4.1.231.7.1.2.2.1.4.8.6.1.2
		sheQueueWeight OBJECT-TYPE
			SYNTAX Unsigned32 (1..100)
			MAX-ACCESS read-only
			STATUS current
			DESCRIPTION
				"A weight value for queue if mode is not strict.
				Depending on used HW (CXU types, IU types) works not on all interface types.
				Weights are interpreted not as absolute values but only in relation to the sum of 
				the weights of all queues. If a weight of a queue is set to 100, this queue will 
				work in 'strict' mode against lower prio queues again."
			DEFVAL { 100 }
			::= { sheQueueWeightEntry 2 }

		
--   1.3.6.1.4.1.231.7.1.2.2.1.4.8.6.1.3
		sheQueueWeightWatermarkLow OBJECT-TYPE
			SYNTAX Integer32
			UNITS "%"
			MAX-ACCESS read-only
			STATUS current
			DESCRIPTION
				"A low watermark value for a NE internal color aware queue handling.
				This value represents a % - Value of usage of the total Queue-Size. 
				
				Default values:
				-------------------
				Queue | Low  |
				-------------------
				1     | 20 % |
				2     | 20 % |
				3     | 20 % |
				4     | 20 % |
				5     | 30 % |
				6     | 30 % |
				7     | 15 % |
				8     | 15 % |"
			::= { sheQueueWeightEntry 3 }

		
--   1.3.6.1.4.1.231.7.1.2.2.1.4.8.6.1.4
		sheQueueWeightWatermarkHigh OBJECT-TYPE
			SYNTAX Integer32
			UNITS "%"
			MAX-ACCESS read-only
			STATUS current
			DESCRIPTION
				"A high watermark value for a NE internal color aware queue handling.
				High watermark defines additional the total used queue size as %-value of the theoretical
				possible queue size.
				
				Default Values:
				------------
				Queue | High
				------------
				1     | 30 %
				2     | 30 %
				3     | 30 %
				4     | 30 %
				5     | 40 %
				6     | 40 %
				7     | 20 %
				8     | 20 %"
			::= { sheQueueWeightEntry 4 }

		
--   1.3.6.1.4.1.231.7.1.2.2.1.4.8.7
		sheQueueWeightControl OBJECT IDENTIFIER ::= { sheQueueConfiguration 7 }

		
--   1.3.6.1.4.1.231.7.1.2.2.1.4.8.7.1
		sheQueueWeightControlRequest OBJECT-TYPE
			SYNTAX SheBridgeControlRequestType
			MAX-ACCESS read-write
			STATUS current
			DESCRIPTION
				"modifyQueueWeightEntry:
				sheQueueWeightControlIndex
				sheQueueWeightControlWeight
				sheQueueWeightControlWatermarkLow
				sheQueueWeightControlWatermarkHigh
				
				"
			::= { sheQueueWeightControl 1 }

		
--   1.3.6.1.4.1.231.7.1.2.2.1.4.8.7.2
		sheQueueWeightControlIndex OBJECT-TYPE
			SYNTAX Integer32 (1..8)
			MAX-ACCESS read-write
			STATUS current
			DESCRIPTION
				"The table-entry to be modified."
			::= { sheQueueWeightControl 2 }

		
--   1.3.6.1.4.1.231.7.1.2.2.1.4.8.7.3
		sheQueueWeightControlStatus OBJECT-TYPE
			SYNTAX SheControlStatusType
			MAX-ACCESS read-only
			STATUS current
			DESCRIPTION
				"The status of a user command. 
				"
			::= { sheQueueWeightControl 3 }

		
--   1.3.6.1.4.1.231.7.1.2.2.1.4.8.7.4
		sheQueueWeightControlTimer OBJECT-TYPE
			SYNTAX Gauge32
			MAX-ACCESS read-only
			STATUS current
			DESCRIPTION
				"The maximum wait time for the manager for a long running user command. 
				"
			::= { sheQueueWeightControl 4 }

		
--   1.3.6.1.4.1.231.7.1.2.2.1.4.8.7.5
		sheQueueWeightControlReqResult OBJECT-TYPE
			SYNTAX SheBridgeControlReqResultType
			MAX-ACCESS read-only
			STATUS current
			DESCRIPTION
				"The result of the last user command."
			::= { sheQueueWeightControl 5 }

		
--   1.3.6.1.4.1.231.7.1.2.2.1.4.8.7.6
		sheQueueWeightControlTimeStamp OBJECT-TYPE
			SYNTAX Unsigned32
			UNITS "sec"
			MAX-ACCESS read-only
			STATUS current
			DESCRIPTION
				"The time stamp of the last command (end of command)."
			::= { sheQueueWeightControl 6 }

		
--   1.3.6.1.4.1.231.7.1.2.2.1.4.8.7.7
		sheQueueWeightControlWeight OBJECT-TYPE
			SYNTAX Unsigned32 (1..100)
			MAX-ACCESS read-write
			STATUS current
			DESCRIPTION
				"Look at weight-table description."
			::= { sheQueueWeightControl 7 }

		
--   1.3.6.1.4.1.231.7.1.2.2.1.4.8.7.8
		sheQueueWeightControlWatermarkLow OBJECT-TYPE
			SYNTAX Unsigned32
			UNITS "%"
			MAX-ACCESS read-write
			STATUS current
			DESCRIPTION
				"Not needed for configuration in current scenario. This value represents a
				% - Value of usage of the total Queue-Size. "
			::= { sheQueueWeightControl 8 }

		
--   1.3.6.1.4.1.231.7.1.2.2.1.4.8.7.9
		sheQueueWeightControlWatermarkHigh OBJECT-TYPE
			SYNTAX Unsigned32
			UNITS "%"
			MAX-ACCESS read-write
			STATUS current
			DESCRIPTION
				"Not needed for configuration in current scenario.This value represents a
				% - Value of usage of the total Queue-Size. "
			::= { sheQueueWeightControl 9 }

		
--   1.3.6.1.4.1.231.7.1.2.2.1.4.8.9
		sheQueueNotifications OBJECT IDENTIFIER ::= { sheQueueConfiguration 9 }

		
--   1.3.6.1.4.1.231.7.1.2.2.1.4.8.9.1
		sheQueuePriorityMappingModified NOTIFICATION-TYPE
			OBJECTS { sheQueueControlIndex, sheQueueControlTimeStamp, sheQueueControlQueueNumber }
			STATUS current
			DESCRIPTION 
				"Configuration notification for priority mapping table."
			::= { sheQueueNotifications 1 }

		
--   1.3.6.1.4.1.231.7.1.2.2.1.4.8.9.2
		sheReducedQueuePriorityMappingModified NOTIFICATION-TYPE
			OBJECTS { sheQueueControlIndex, sheQueueControlTimeStamp, sheQueueControlQueueNumber }
			STATUS current
			DESCRIPTION 
				"Configuration notification for shrink mapping table."
			::= { sheQueueNotifications 2 }

		
--   1.3.6.1.4.1.231.7.1.2.2.1.4.8.9.3
		sheQueueModeEntryModified NOTIFICATION-TYPE
			OBJECTS { sheQueueModeControlIndex, sheQueueModeControlTimeStamp, sheQueueModeControlMode }
			STATUS current
			DESCRIPTION 
				"Configuration notification for queue mode table."
			::= { sheQueueNotifications 3 }

		
--   1.3.6.1.4.1.231.7.1.2.2.1.4.8.9.4
		sheQueueWeightEntryModified NOTIFICATION-TYPE
			OBJECTS { sheQueueWeightControlIndex, sheQueueWeightControlTimeStamp, sheQueueWeightControlWeight, sheQueueWeightControlWatermarkLow, sheQueueWeightControlWatermarkHigh
				 }
			STATUS current
			DESCRIPTION 
				"Configuration notification for queue weight table."
			::= { sheQueueNotifications 4 }

		
--   1.3.6.1.4.1.231.7.1.2.2.1.4.8.9.5
		sheCardQueueEntryConfigured NOTIFICATION-TYPE
			OBJECTS { sheCardQueueControlIndex, sheCardQueueControlTimeStamp, sheCardQueueControlInterfaceTypeIndex, sheCardQueueControlSchedulingMode, sheCardQueueControlQueue1Weight, 
				sheCardQueueControlQueue1Watermarks, sheCardQueueControlQueue2Weight, sheCardQueueControlQueue2Watermarks, sheCardQueueControlQueue3Weight, sheCardQueueControlQueue3Watermarks, 
				sheCardQueueControlQueue4Weight, sheCardQueueControlQueue4Watermarks, sheCardQueueControlQueue5Weight, sheCardQueueControlQueue5Watermarks, sheCardQueueControlQueue6Weight, 
				sheCardQueueControlQueue6Watermarks, sheCardQueueControlQueue7Weight, sheCardQueueControlQueue7Watermarks, sheCardQueueControlQueue8Weight, sheCardQueueControlQueue8Watermarks, 
				sheCardQueueControlColourAwareTCSource, sheCardQueueControlColourMarking, sheCardQueueControlDiscardPolicy, sheCardQueueControlMode, sheCardQueueControlHqsSecondStageInputQueue, 
				sheCardQueueControlHqsFirstStagePir, sheCardQueueControlHqsFirstStagePbs }
			STATUS current
			DESCRIPTION 
				"Configure the queue handling for a card."
			::= { sheQueueNotifications 5 }

		
--   1.3.6.1.4.1.231.7.1.2.2.1.4.8.9.6
		sheCardQueueEntryDeleted NOTIFICATION-TYPE
			OBJECTS { sheCardQueueControlIndex, sheCardQueueControlTimeStamp, sheCardQueueControlInterfaceTypeIndex }
			STATUS current
			DESCRIPTION 
				"Delete the queue handling for a card."
			::= { sheQueueNotifications 6 }

		
--   1.3.6.1.4.1.231.7.1.2.2.1.4.8.9.5
		sheCardQueueEntryConfigResult NOTIFICATION-TYPE
			OBJECTS { sheCardQueueControlIndex, sheCardQueueControlTimeStamp, sheCardQueueControlInterfaceTypeIndex, sheCardQueueControlStatus, sheCardQueueControlReqResult
				 }
			STATUS current
			DESCRIPTION 
				"Result trap for long running command to configure the queue handling for a card."
			::= { sheQueueNotifications 7 }

		
--   1.3.6.1.4.1.231.7.1.2.2.1.4.8.10
		sheCardQueueConfigurationTable OBJECT-TYPE
			SYNTAX SEQUENCE OF SheCardQueueConfigurationEntry
			MAX-ACCESS not-accessible
			STATUS current
			DESCRIPTION
				"Configure the queue handling individuell per configured card. This will replace the
				general queue configuration settings. Per default, no indivudell settings are made and
				this table is empty (could be change during development).
				
				NEW supported with R2.8!"
			::= { sheQueueConfiguration 10 }

		
--   1.3.6.1.4.1.231.7.1.2.2.1.4.8.10.1
		sheCardQueueConfigurationEntry OBJECT-TYPE
			SYNTAX SheCardQueueConfigurationEntry
			MAX-ACCESS not-accessible
			STATUS current
			DESCRIPTION
				"One entry for each card, if these card should not use the global NE 
				queue configuration parameters. 
				If a card type will never uses the global NE parameters, a entry for this card
				will be automatically created during card creation process.   
				This table uses two indices:
				First index is the entPhysicalIndex from entPhysicalTable for the card.
				Second index is sheCardQueueInterfaceTypeIndex from this table."
			INDEX { entPhysicalIndex, sheCardQueueInterfaceTypeIndex }
			::= { sheCardQueueConfigurationTable 1 }

		
		SheCardQueueConfigurationEntry ::=
			SEQUENCE { 
				sheCardQueueInterfaceTypeIndex
					SheBridgeInterfaceType,
				sheCardQueueSchedulingMode
					SheQueueModeType,
				sheCardQueue1Weight
					Unsigned32,
				sheCardQueue1Watermarks
					Unsigned32,
				sheCardQueue2Weight
					Unsigned32,
				sheCardQueue2Watermarks
					Unsigned32,
				sheCardQueue3Weight
					Unsigned32,
				sheCardQueue3Watermarks
					Unsigned32,
				sheCardQueue4Weight
					Unsigned32,
				sheCardQueue4Watermarks
					Unsigned32,
				sheCardQueue5Weight
					Unsigned32,
				sheCardQueue5Watermarks
					Unsigned32,
				sheCardQueue6Weight
					Unsigned32,
				sheCardQueue6Watermarks
					Unsigned32,
				sheCardQueue7Weight
					Unsigned32,
				sheCardQueue7Watermarks
					Unsigned32,
				sheCardQueue8Weight
					Unsigned32,
				sheCardQueue8Watermarks
					Unsigned32,
				sheCardQueueColourAwareTCSource
					SheQueueColourAwareType,
				sheCardQueueColourMarking
					SheQueueColourAwareType,
				sheCardQueueDiscardPolicy
					SheQueueDiscardPolicyType,
				sheCardQueueMode
					SheCardQueueModeType,
				sheCardQueueHqsSecondStageInputQueue
					Unsigned32,
				sheCardQueueHqsFirstStagePir
					Unsigned32,
				sheCardQueueHqsFirstStagePbs
					Unsigned32
			 }

--   1.3.6.1.4.1.231.7.1.2.2.1.4.8.10.1.1
		sheCardQueueInterfaceTypeIndex OBJECT-TYPE
			SYNTAX SheBridgeInterfaceType
			MAX-ACCESS read-only
			STATUS current
			DESCRIPTION
				"Describes the interface type, were this queue configuration should be used.
				Valid values for this configuration's are:
				uplink(1)   -> for central board means uplink, for IU means interlink to cxu
				downlink(2) -> for central board means interlink to IU's, for IU means subcriber 
				"
			::= { sheCardQueueConfigurationEntry 1 }

		
--   1.3.6.1.4.1.231.7.1.2.2.1.4.8.10.1.10
		sheCardQueueSchedulingMode OBJECT-TYPE
			SYNTAX SheQueueModeType
			MAX-ACCESS read-only
			STATUS current
			DESCRIPTION
				"Describes the queue scheduling mode. 
				strict
				weighted
				
				Note:
				Mode 'weighted' could mean 'weighted round robin' (wrr) or 'weighted fair queueing' (wfq)
				and depends on the individual HW restrictions of the used board's."
			DEFVAL { strict }
			::= { sheCardQueueConfigurationEntry 10 }

		
--   1.3.6.1.4.1.231.7.1.2.2.1.4.8.10.1.11
		sheCardQueue1Weight OBJECT-TYPE
			SYNTAX Unsigned32 (1..100)
			MAX-ACCESS read-only
			STATUS current
			DESCRIPTION
				"A weight value for queue 1 if mode is not strict.
				Depending on used HW (CXU types, IU types) works not on all interface types.
				Weights are interpreted not as absolute values but only in relation to the sum of 
				the weights of all queues. If a weight of a queue is set to 100, this queue will 
				work in 'strict' mode against lower prio queues again."
			DEFVAL { 100 }
			::= { sheCardQueueConfigurationEntry 11 }

		
--   1.3.6.1.4.1.231.7.1.2.2.1.4.8.10.1.12
		sheCardQueue1Watermarks OBJECT-TYPE
			SYNTAX Unsigned32
			UNITS "%"
			MAX-ACCESS read-only
			STATUS current
			DESCRIPTION
				"A watermark configuration for a NE internal colour aware queue handling for queue number 1.
				The lower two octets representing the low watermark and the higher two octets
				the high watermark value.
				This value's represents a % - value of usage of the total Queue-Size. 
				
				Example: 0x00500032 -> high watermark = 0x0050 = 80%
				                    -> low watermark  = 0x0032 = 50%   
				
				The maximum value for a single watermark is 0x0064 = 100 %.
				The high watermark defines additional the total used queue size as %-value of the theoretical
				possible queue size."
			DEFVAL { '001E0014'h }
			::= { sheCardQueueConfigurationEntry 12 }

		
--   1.3.6.1.4.1.231.7.1.2.2.1.4.8.10.1.13
		sheCardQueue2Weight OBJECT-TYPE
			SYNTAX Unsigned32 (1..100)
			MAX-ACCESS read-only
			STATUS current
			DESCRIPTION
				"A weight value for queue 2 if mode is not strict.
				Depending on used HW (CXU types, IU types) works not on all interface types.
				Weights are interpreted not as absolute values but only in relation to the sum of 
				the weights of all queues. If a weight of a queue is set to 100, this queue will 
				work in 'strict' mode against lower prio queues again."
			DEFVAL { 100 }
			::= { sheCardQueueConfigurationEntry 13 }

		
--   1.3.6.1.4.1.231.7.1.2.2.1.4.8.10.1.14
		sheCardQueue2Watermarks OBJECT-TYPE
			SYNTAX Unsigned32
			UNITS "%"
			MAX-ACCESS read-only
			STATUS current
			DESCRIPTION
				"A watermark configuration for a NE internal colour aware queue handling for queue number 2.
				The lower two octets representing the low watermark and the higher two octets
				the high watermark value.
				This value's represents a % - value of usage of the total Queue-Size. 
				
				Example: 0x00500032 -> high watermark = 0x0050 = 80%
				                    -> low watermark  = 0x0032 = 50%  
				
				The maximum value for a single watermark is 0x0064 = 100 %. 
				The high watermark defines additional the total used queue size as %-value of the theoretical
				possible queue size."
			DEFVAL { '001E0014'h }
			::= { sheCardQueueConfigurationEntry 14 }

		
--   1.3.6.1.4.1.231.7.1.2.2.1.4.8.10.1.15
		sheCardQueue3Weight OBJECT-TYPE
			SYNTAX Unsigned32 (1..100)
			MAX-ACCESS read-only
			STATUS current
			DESCRIPTION
				"A weight value for queue 3 if mode is not strict.
				Depending on used HW (CXU types, IU types) works not on all interface types.
				Weights are interpreted not as absolute values but only in relation to the sum of 
				the weights of all queues. If a weight of a queue is set to 100, this queue will 
				work in 'strict' mode against lower prio queues again."
			DEFVAL { 100 }
			::= { sheCardQueueConfigurationEntry 15 }

		
--   1.3.6.1.4.1.231.7.1.2.2.1.4.8.10.1.16
		sheCardQueue3Watermarks OBJECT-TYPE
			SYNTAX Unsigned32
			UNITS "%"
			MAX-ACCESS read-only
			STATUS current
			DESCRIPTION
				"A watermark configuration for a NE internal colour aware queue handling for queue number 3.
				The lower two octets representing the low watermark and the higher two octets
				the high watermark value.
				This value's represents a % - value of usage of the total Queue-Size. 
				
				Example: 0x00500032 -> high watermark = 0x0050 = 80%
				                    -> low watermark  = 0x0032 = 50% 
				
				The maximum value for a single watermark is 0x0064 = 100 %.  
				The high watermark defines additional the total used queue size as %-value of the theoretical
				possible queue size."
			DEFVAL { '001E0014'h }
			::= { sheCardQueueConfigurationEntry 16 }

		
--   1.3.6.1.4.1.231.7.1.2.2.1.4.8.10.1.17
		sheCardQueue4Weight OBJECT-TYPE
			SYNTAX Unsigned32 (1..100)
			MAX-ACCESS read-only
			STATUS current
			DESCRIPTION
				"A weight value for queue 4 if mode is not strict.
				Depending on used HW (CXU types, IU types) works not on all interface types.
				Weights are interpreted not as absolute values but only in relation to the sum of 
				the weights of all queues. If a weight of a queue is set to 100, this queue will 
				work in 'strict' mode against lower prio queues again."
			DEFVAL { 100 }
			::= { sheCardQueueConfigurationEntry 17 }

		
--   1.3.6.1.4.1.231.7.1.2.2.1.4.8.10.1.18
		sheCardQueue4Watermarks OBJECT-TYPE
			SYNTAX Unsigned32
			UNITS "%"
			MAX-ACCESS read-only
			STATUS current
			DESCRIPTION
				"A watermark configuration for a NE internal colour aware queue handling for queue number 4.
				The lower two octets representing the low watermark and the higher two octets
				the high watermark value.
				This value's represents a % - value of usage of the total Queue-Size. 
				
				Example: 0x00500032 -> high watermark = 0x0050 = 80%
				                    -> low watermark  = 0x0032 = 50% 
				
				The maximum value for a single watermark is 0x0064 = 100 %.  
				The high watermark defines additional the total used queue size as %-value of the theoretical
				possible queue size."
			DEFVAL { '001E0014'h }
			::= { sheCardQueueConfigurationEntry 18 }

		
--   1.3.6.1.4.1.231.7.1.2.2.1.4.8.10.1.19
		sheCardQueue5Weight OBJECT-TYPE
			SYNTAX Unsigned32 (1..100)
			MAX-ACCESS read-only
			STATUS current
			DESCRIPTION
				"A weight value for queue 5 if mode is not strict.
				Depending on used HW (CXU types, IU types) works not on all interface types.
				Weights are interpreted not as absolute values but only in relation to the sum of 
				the weights of all queues. If a weight of a queue is set to 100, this queue will 
				work in 'strict' mode against lower prio queues again."
			DEFVAL { 100 }
			::= { sheCardQueueConfigurationEntry 19 }

		
--   1.3.6.1.4.1.231.7.1.2.2.1.4.8.10.1.20
		sheCardQueue5Watermarks OBJECT-TYPE
			SYNTAX Unsigned32
			UNITS "%"
			MAX-ACCESS read-only
			STATUS current
			DESCRIPTION
				"A watermark configuration for a NE internal colour aware queue handling for queue number 5.
				The lower two octets representing the low watermark and the higher two octets
				the high watermark value.
				This value's represents a % - value of usage of the total Queue-Size.
				Depending on the card type,these configuration could have no effect!! 
				
				Example: 0x00500032 -> high watermark = 0x0050 = 80%
				                    -> low watermark  = 0x0032 = 50% 
				
				The maximum value for a single watermark is 0x0064 = 100 %.
				The high watermark defines additional the total used queue size as %-value of the theoretical
				possible queue size.  "
			DEFVAL { '0028001E'h }
			::= { sheCardQueueConfigurationEntry 20 }

		
--   1.3.6.1.4.1.231.7.1.2.2.1.4.8.10.1.21
		sheCardQueue6Weight OBJECT-TYPE
			SYNTAX Unsigned32 (1..100)
			MAX-ACCESS read-only
			STATUS current
			DESCRIPTION
				"A weight value for queue 6 if mode is not strict.
				Depending on used HW (CXU types, IU types) works not on all interface types.
				Weights are interpreted not as absolute values but only in relation to the sum of 
				the weights of all queues. If a weight of a queue is set to 100, this queue will 
				work in 'strict' mode against lower prio queues again."
			DEFVAL { 100 }
			::= { sheCardQueueConfigurationEntry 21 }

		
--   1.3.6.1.4.1.231.7.1.2.2.1.4.8.10.1.22
		sheCardQueue6Watermarks OBJECT-TYPE
			SYNTAX Unsigned32
			UNITS "%"
			MAX-ACCESS read-only
			STATUS current
			DESCRIPTION
				"A watermark configuration for a NE internal colour aware queue handling for queue number 6.
				The lower two octets representing the low watermark and the higher two octets
				the high watermark value.
				This value's represents a % - value of usage of the total Queue-Size.
				Depending on the card type,these configuration could have no effect!! 
				 
				Example: 0x00500032 -> high watermark = 0x0050 = 80%
				                    -> low watermark  = 0x0032 = 50%   
				
				The maximum value for a single watermark is 0x0064 = 100 %.
				The high watermark defines additional the total used queue size as %-value of the theoretical
				possible queue size."
			DEFVAL { '0028001E'h }
			::= { sheCardQueueConfigurationEntry 22 }

		
--   1.3.6.1.4.1.231.7.1.2.2.1.4.8.10.1.23
		sheCardQueue7Weight OBJECT-TYPE
			SYNTAX Unsigned32 (1..100)
			MAX-ACCESS read-only
			STATUS current
			DESCRIPTION
				"A weight value for queue 7 if mode is not strict.
				Depending on used HW (CXU types, IU types) works not on all interface types.
				Weights are interpreted not as absolute values but only in relation to the sum of 
				the weights of all queues. If a weight of a queue is set to 100, this queue will 
				work in 'strict' mode against lower prio queues again."
			DEFVAL { 100 }
			::= { sheCardQueueConfigurationEntry 23 }

		
--   1.3.6.1.4.1.231.7.1.2.2.1.4.8.10.1.24
		sheCardQueue7Watermarks OBJECT-TYPE
			SYNTAX Unsigned32
			UNITS "%"
			MAX-ACCESS read-only
			STATUS current
			DESCRIPTION
				"A watermark configuration for a NE internal colour aware queue handling for queue number 7.
				The lower two octets representing the low watermark and the higher two octets
				the high watermark value.
				This value's represents a % - value of usage of the total Queue-Size.
				Depending on the card type,these configuration could have no effect!! 
				 
				Example: 0x00500032 -> high watermark = 0x0050 = 80%
				                    -> low watermark  = 0x0032 = 50%   
				
				The maximum value for a single watermark is 0x0064 = 100 %.
				The high watermark defines additional the total used queue size as %-value of the theoretical
				possible queue size."
			DEFVAL { '0014000F'h }
			::= { sheCardQueueConfigurationEntry 24 }

		
--   1.3.6.1.4.1.231.7.1.2.2.1.4.8.10.1.25
		sheCardQueue8Weight OBJECT-TYPE
			SYNTAX Unsigned32 (1..100)
			MAX-ACCESS read-only
			STATUS current
			DESCRIPTION
				"A weight value for queue 8 if mode is not strict.
				Depending on used HW (CXU types, IU types) works not on all interface types.
				Weights are interpreted not as absolute values but only in relation to the sum of 
				the weights of all queues. If a weight of a queue is set to 100, this queue will 
				work in 'strict' mode against lower prio queues again."
			DEFVAL { 100 }
			::= { sheCardQueueConfigurationEntry 25 }

		
--   1.3.6.1.4.1.231.7.1.2.2.1.4.8.10.1.26
		sheCardQueue8Watermarks OBJECT-TYPE
			SYNTAX Unsigned32
			UNITS "%"
			MAX-ACCESS read-only
			STATUS current
			DESCRIPTION
				"A watermark configuration for a NE internal colour aware queue handling for queue number 8.
				The lower two octets representing the low watermark and the higher two octets
				the high watermark value.
				This value's represents a % - value of usage of the total Queue-Size.
				Depending on the card type,these configuration could have no effect!! 
				 
				Example: 0x00500032 -> high watermark = 0x0050 = 80%
				                    -> low watermark  = 0x0032 = 50%   
				
				The maximum value for a single watermark is 0x0064 = 100 %.
				The high watermark defines additional the total used queue size as %-value of the theoretical
				possible queue size."
			DEFVAL { '0014000F'h }
			::= { sheCardQueueConfigurationEntry 26 }

		
--   1.3.6.1.4.1.231.7.1.2.2.1.4.8.10.1.27
		sheCardQueueColourAwareTCSource OBJECT-TYPE
			SYNTAX SheQueueColourAwareType
			MAX-ACCESS read-only
			STATUS current
			DESCRIPTION
				"Configure, how the current traffic class of a frame should detected.
				Valid values:
				 none(0),
				 dscp(2),
				 providerBridge(4)
				
				Configuration will be currently ignored! Starting support planed for R3.5!"
			DEFVAL { none }
			::= { sheCardQueueConfigurationEntry 27 }

		
--   1.3.6.1.4.1.231.7.1.2.2.1.4.8.10.1.28
		sheCardQueueColourMarking OBJECT-TYPE
			SYNTAX SheQueueColourAwareType
			MAX-ACCESS read-only
			STATUS current
			DESCRIPTION
				"Configure, if and how the current colour should be marked. Colour marking will only work in upstream direction.
				Valid values:
				 none(0),
				 dscp(2),
				 providerBridge(4)
				
				Configuration will be currently ignored! Starting support planed for 3.5!"
			DEFVAL { none }
			::= { sheCardQueueConfigurationEntry 28 }

		
--   1.3.6.1.4.1.231.7.1.2.2.1.4.8.10.1.29
		sheCardQueueDiscardPolicy OBJECT-TYPE
			SYNTAX SheQueueDiscardPolicyType
			MAX-ACCESS read-only
			STATUS current
			DESCRIPTION
				"Describes the policy in case of frame discards.
				Possible values:
				tailDrop(1),
				wRed(2)
				
				Configuration will be currently ignored! Starting support planed for R3.5!"
			DEFVAL { tailDrop }
			::= { sheCardQueueConfigurationEntry 29 }

		
		sheCardQueueMode OBJECT-TYPE
			SYNTAX SheCardQueueModeType
			MAX-ACCESS read-only
			STATUS current
			DESCRIPTION
				"This parameter describe the general queue mode for this card.
				Depending on the used card type not all modes are available. 
				modeHQS will only be supported by DSL cards with Convergate chipset and only in downstream direction.
				mode8QueueFlat will only be supported by VDSL2 and Shdsl2 cards and only in downstream direction.
				
				mode4QueueFlat(1)  -> 4 queues per port
				mode8QueueFlat(2)  -> 8 queues per port
				modeHQS(3)         -> 8 queues with hierarchical queuing and scheduling.
				
				New parameter with R2.8.
				"
			DEFVAL { mode4QueueFlat }
			::= { sheCardQueueConfigurationEntry 30 }

		
		sheCardQueueHqsSecondStageInputQueue OBJECT-TYPE
			SYNTAX Unsigned32 (5..8)
			MAX-ACCESS read-only
			STATUS current
			DESCRIPTION
				"This parameter is only valid for queuemode 'modeHQS' and is don't care for the others.
				The queue of the second level scheduler (queuenumbers 5-8) in which the frames of the
				first level scheduler will be enqueued could be selected here.
				
				New parameter with R2.8."
			DEFVAL { 5 }
			::= { sheCardQueueConfigurationEntry 31 }

		
		sheCardQueueHqsFirstStagePir OBJECT-TYPE
			SYNTAX Unsigned32 (0..32760)
			UNITS "kBit/s"
			MAX-ACCESS read-only
			STATUS current
			DESCRIPTION
				"This parameter configures the peek information rate of the first stage scheduler if
				queuemode modeHQS is running. Otherwise don't care.
				
				Note:
				The PIR of the first level queuing block should not be higher than the emission rate of the
				respective second level queue into which the first level queues are enqueued.
				The given value could be adapted (rounded) in the NE to fullfill different HW dependencies.
				That will not shown here. For example, IU's with Convergate chipset will round the configured
				value to multiples of 1 kByte/s. 
				
				New parameter with R2.8."
			::= { sheCardQueueConfigurationEntry 32 }

		
		sheCardQueueHqsFirstStagePbs OBJECT-TYPE
			SYNTAX Unsigned32 (0..16000)
			UNITS "Byte"
			MAX-ACCESS read-only
			STATUS current
			DESCRIPTION
				"This parameter configures the peek burst size of the first stage scheduler if
				queuemode modeHQS is running. Otherwise don't care.
				
				New parameter with R2.8."
			::= { sheCardQueueConfigurationEntry 33 }

		
--   1.3.6.1.4.1.231.7.1.2.2.1.4.8.11
		sheCardQueueConfigurationControl OBJECT IDENTIFIER ::= { sheQueueConfiguration 11 }

		
--   1.3.6.1.4.1.231.7.1.2.2.1.4.8.11.1
		sheCardQueueControlRequest OBJECT-TYPE
			SYNTAX SheBridgeControlRequestType
			MAX-ACCESS read-write
			STATUS current
			DESCRIPTION
				"configureCardQueueConfigurationEntry:
				sheCardQueueConfigurationControlIndex
				sheCardQueueControlInterfaceTypeIndex
				...
				
				
				deleteCardQueueConfigurationEntry:
				sheCardQueueConfigurationControlIndex
				sheCardQueueControlInterfaceTypeIndex
				
				"
			::= { sheCardQueueConfigurationControl 1 }

		
--   1.3.6.1.4.1.231.7.1.2.2.1.4.8.11.2
		sheCardQueueControlIndex OBJECT-TYPE
			SYNTAX PhysicalIndex
			MAX-ACCESS read-write
			STATUS current
			DESCRIPTION
				"The first index (entPhysicalIndex of card) to identify the table-entry to be configured."
			::= { sheCardQueueConfigurationControl 2 }

		
--   1.3.6.1.4.1.231.7.1.2.2.1.4.8.11.3
		sheCardQueueControlStatus OBJECT-TYPE
			SYNTAX SheControlStatusType
			MAX-ACCESS read-only
			STATUS current
			DESCRIPTION
				"The status of a user command. 
				"
			::= { sheCardQueueConfigurationControl 3 }

		
--   1.3.6.1.4.1.231.7.1.2.2.1.4.8.11.4
		sheCardQueueControlTimer OBJECT-TYPE
			SYNTAX Gauge32
			MAX-ACCESS read-only
			STATUS current
			DESCRIPTION
				"The maximum wait time for the manager for a long running user command. 
				"
			::= { sheCardQueueConfigurationControl 4 }

		
--   1.3.6.1.4.1.231.7.1.2.2.1.4.8.11.5
		sheCardQueueControlReqResult OBJECT-TYPE
			SYNTAX SheBridgeControlReqResultType
			MAX-ACCESS read-only
			STATUS current
			DESCRIPTION
				"The result of the last user command."
			::= { sheCardQueueConfigurationControl 5 }

		
--   1.3.6.1.4.1.231.7.1.2.2.1.4.8.11.6
		sheCardQueueControlTimeStamp OBJECT-TYPE
			SYNTAX Unsigned32
			UNITS "sec"
			MAX-ACCESS read-only
			STATUS current
			DESCRIPTION
				"The time stamp of the last command (end of command)."
			::= { sheCardQueueConfigurationControl 6 }

		
--   1.3.6.1.4.1.231.7.1.2.2.1.4.8.11.7
		sheCardQueueControlInterfaceTypeIndex OBJECT-TYPE
			SYNTAX SheBridgeInterfaceType
			MAX-ACCESS read-write
			STATUS current
			DESCRIPTION
				"The second index to identify the table-entry to be configured."
			::= { sheCardQueueConfigurationControl 7 }

		
--   1.3.6.1.4.1.231.7.1.2.2.1.4.8.11.16
		sheCardQueueControlSchedulingMode OBJECT-TYPE
			SYNTAX SheQueueModeType
			MAX-ACCESS read-write
			STATUS current
			DESCRIPTION
				"Set the queue scheduling mode."
			::= { sheCardQueueConfigurationControl 16 }

		
--   1.3.6.1.4.1.231.7.1.2.2.1.4.8.11.17
		sheCardQueueControlQueue1Weight OBJECT-TYPE
			SYNTAX Unsigned32 (1..100)
			MAX-ACCESS read-write
			STATUS current
			DESCRIPTION
				"Look at table description."
			::= { sheCardQueueConfigurationControl 17 }

		
--   1.3.6.1.4.1.231.7.1.2.2.1.4.8.11.18
		sheCardQueueControlQueue1Watermarks OBJECT-TYPE
			SYNTAX Unsigned32
			UNITS "%"
			MAX-ACCESS read-write
			STATUS current
			DESCRIPTION
				"Look at table description."
			::= { sheCardQueueConfigurationControl 18 }

		
--    1.3.6.1.4.1.231.7.1.2.2.1.4.8.11.19
		sheCardQueueControlQueue2Weight OBJECT-TYPE
			SYNTAX Unsigned32 (1..100)
			MAX-ACCESS read-write
			STATUS current
			DESCRIPTION
				"Look at table description."
			::= { sheCardQueueConfigurationControl 19 }

		
--    1.3.6.1.4.1.231.7.1.2.2.1.4.8.11.20
		sheCardQueueControlQueue2Watermarks OBJECT-TYPE
			SYNTAX Unsigned32
			UNITS "%"
			MAX-ACCESS read-write
			STATUS current
			DESCRIPTION
				"Look at table description."
			::= { sheCardQueueConfigurationControl 20 }

		
--    1.3.6.1.4.1.231.7.1.2.2.1.4.8.11.21
		sheCardQueueControlQueue3Weight OBJECT-TYPE
			SYNTAX Unsigned32 (1..100)
			MAX-ACCESS read-write
			STATUS current
			DESCRIPTION
				"Look at table description."
			::= { sheCardQueueConfigurationControl 21 }

		
--    1.3.6.1.4.1.231.7.1.2.2.1.4.8.11.22
		sheCardQueueControlQueue3Watermarks OBJECT-TYPE
			SYNTAX Unsigned32
			UNITS "%"
			MAX-ACCESS read-write
			STATUS current
			DESCRIPTION
				"Look at table description."
			::= { sheCardQueueConfigurationControl 22 }

		
--    1.3.6.1.4.1.231.7.1.2.2.1.4.8.11.23
		sheCardQueueControlQueue4Weight OBJECT-TYPE
			SYNTAX Unsigned32 (1..100)
			MAX-ACCESS read-write
			STATUS current
			DESCRIPTION
				"Look at table description."
			::= { sheCardQueueConfigurationControl 23 }

		
--    1.3.6.1.4.1.231.7.1.2.2.1.4.8.11.24
		sheCardQueueControlQueue4Watermarks OBJECT-TYPE
			SYNTAX Unsigned32
			UNITS "%"
			MAX-ACCESS read-write
			STATUS current
			DESCRIPTION
				"Look at table description."
			::= { sheCardQueueConfigurationControl 24 }

		
--    1.3.6.1.4.1.231.7.1.2.2.1.4.8.11.25
		sheCardQueueControlQueue5Weight OBJECT-TYPE
			SYNTAX Unsigned32 (1..100)
			MAX-ACCESS read-write
			STATUS current
			DESCRIPTION
				"Look at table description."
			::= { sheCardQueueConfigurationControl 25 }

		
--    1.3.6.1.4.1.231.7.1.2.2.1.4.8.11.26
		sheCardQueueControlQueue5Watermarks OBJECT-TYPE
			SYNTAX Unsigned32
			UNITS "%"
			MAX-ACCESS read-write
			STATUS current
			DESCRIPTION
				"Look at table description."
			::= { sheCardQueueConfigurationControl 26 }

		
--    1.3.6.1.4.1.231.7.1.2.2.1.4.8.11.27
		sheCardQueueControlQueue6Weight OBJECT-TYPE
			SYNTAX Unsigned32 (1..100)
			MAX-ACCESS read-write
			STATUS current
			DESCRIPTION
				"Look at table description."
			::= { sheCardQueueConfigurationControl 27 }

		
--    1.3.6.1.4.1.231.7.1.2.2.1.4.8.11.28
		sheCardQueueControlQueue6Watermarks OBJECT-TYPE
			SYNTAX Unsigned32
			UNITS "%"
			MAX-ACCESS read-write
			STATUS current
			DESCRIPTION
				"Look at table description."
			::= { sheCardQueueConfigurationControl 28 }

		
--    1.3.6.1.4.1.231.7.1.2.2.1.4.8.11.29
		sheCardQueueControlQueue7Weight OBJECT-TYPE
			SYNTAX Unsigned32 (1..100)
			MAX-ACCESS read-write
			STATUS current
			DESCRIPTION
				"Look at table description."
			::= { sheCardQueueConfigurationControl 29 }

		
--    1.3.6.1.4.1.231.7.1.2.2.1.4.8.11.30
		sheCardQueueControlQueue7Watermarks OBJECT-TYPE
			SYNTAX Unsigned32
			UNITS "%"
			MAX-ACCESS read-write
			STATUS current
			DESCRIPTION
				"Look at table description."
			::= { sheCardQueueConfigurationControl 30 }

		
--    1.3.6.1.4.1.231.7.1.2.2.1.4.8.11.31
		sheCardQueueControlQueue8Weight OBJECT-TYPE
			SYNTAX Unsigned32 (1..100)
			MAX-ACCESS read-write
			STATUS current
			DESCRIPTION
				"Look at table description."
			::= { sheCardQueueConfigurationControl 31 }

		
--    1.3.6.1.4.1.231.7.1.2.2.1.4.8.11.32
		sheCardQueueControlQueue8Watermarks OBJECT-TYPE
			SYNTAX Unsigned32
			UNITS "%"
			MAX-ACCESS read-write
			STATUS current
			DESCRIPTION
				"Look at table description."
			::= { sheCardQueueConfigurationControl 32 }

		
--   1.3.6.1.4.1.231.7.1.2.2.1.4.8.11.33
		sheCardQueueControlColourAwareTCSource OBJECT-TYPE
			SYNTAX SheQueueColourAwareType
			MAX-ACCESS read-write
			STATUS current
			DESCRIPTION
				"Look at table description."
			::= { sheCardQueueConfigurationControl 33 }

		
--   1.3.6.1.4.1.231.7.1.2.2.1.4.8.11.34
		sheCardQueueControlColourMarking OBJECT-TYPE
			SYNTAX SheQueueColourAwareType
			MAX-ACCESS read-write
			STATUS current
			DESCRIPTION
				"Look at table description."
			::= { sheCardQueueConfigurationControl 34 }

		
--   1.3.6.1.4.1.231.7.1.2.2.1.4.8.11.35
		sheCardQueueControlDiscardPolicy OBJECT-TYPE
			SYNTAX SheQueueDiscardPolicyType
			MAX-ACCESS read-write
			STATUS current
			DESCRIPTION
				"Look at table description."
			::= { sheCardQueueConfigurationControl 35 }

		
		sheCardQueueControlMode OBJECT-TYPE
			SYNTAX SheCardQueueModeType
			MAX-ACCESS read-write
			STATUS current
			DESCRIPTION
				"This parameter set the general queue mode for this card.
				Depending on the used card type not all modes are available. 
				modeHQS will only be supported by DSL cards with Convergate chipset and only in downstream direction.
				mode8QueueFlat will only be supported by VDSL2 and Shdsl2 cards and only in downstream direction.
				
				mode4QueueFlat(1)  -> 4 queues per port
				mode8QueueFlat(2)  -> 8 queues per port
				modeHQS(3)         -> 8 queues with hierarchical queuing and scheduling.
				
				New parameter with R2.8."
			::= { sheCardQueueConfigurationControl 36 }

		
		sheCardQueueControlHqsSecondStageInputQueue OBJECT-TYPE
			SYNTAX Unsigned32 (5..8)
			MAX-ACCESS read-write
			STATUS current
			DESCRIPTION
				"This parameter is only valid for queuemode 'modeHQS' and is don't care for the others.
				The queue of the second level scheduler (queuenumbers 1-4) in which the frames of the
				first level scheduler will be enqueued could be selected here.
				
				New parameter with R2.8."
			::= { sheCardQueueConfigurationControl 37 }

		
		sheCardQueueControlHqsFirstStagePir OBJECT-TYPE
			SYNTAX Unsigned32 (0..32760)
			UNITS "kBit/s"
			MAX-ACCESS read-write
			STATUS current
			DESCRIPTION
				"This parameter configures the peek information rate of the first stage scheduler if
				queuemode modeHQS is running. Otherwise don't care.
				
				Note:
				The PIR of the first level queuing block should not be higher than the emission rate of the
				respective second level queue into which the first level queues are enqueued.
				The given value could be adapted (rounded) in the NE to fullfill different HW dependencies.
				That will not shown here. For example, IU's with Convergate chipset will round the configured
				value to multiples of 1 kByte/s. 
				
				New parameter with R2.8."
			::= { sheCardQueueConfigurationControl 38 }

		
		sheCardQueueControlHqsFirstStagePbs OBJECT-TYPE
			SYNTAX Unsigned32 (0..16000)
			UNITS "Byte"
			MAX-ACCESS read-write
			STATUS current
			DESCRIPTION
				"This parameter configures the peek burst size of the first stage scheduler if
				queuemode modeHQS is running. Otherwise don't care.
				
				New parameter with R2.8."
			::= { sheCardQueueConfigurationControl 39 }

		
--  1.3.6.1.4.1.231.7.1.2.2.1.4.8.12
		sheShapingProfileTable OBJECT-TYPE
			SYNTAX SEQUENCE OF SheShapingProfileEntry
			MAX-ACCESS not-accessible
			STATUS current
			DESCRIPTION
				"The shaping profile table."
			::= { sheQueueConfiguration 12 }

		
--  1.3.6.1.4.1.231.7.1.2.2.1.4.8.12.1
		sheShapingProfileEntry OBJECT-TYPE
			SYNTAX SheShapingProfileEntry
			MAX-ACCESS not-accessible
			STATUS current
			DESCRIPTION
				"One entry for each shaping profile. Selection of the used profile will
				be done via ShapingProfileAssignmentTable."
			INDEX { sheShapingProfileIndex }
			::= { sheShapingProfileTable 1 }

		
		SheShapingProfileEntry ::=
			SEQUENCE { 
				sheShapingProfileIndex
					Unsigned32,
				sheShapingProfileName
					OCTET STRING,
				sheShapingProfileCir
					Integer32,
				sheShapingProfileCbs
					Integer32
			 }

--  1.3.6.1.4.1.231.7.1.2.2.1.4.8.12.1.1
		sheShapingProfileIndex OBJECT-TYPE
			SYNTAX Unsigned32 (1..300)
			MAX-ACCESS read-only
			STATUS current
			DESCRIPTION
				"A profile-table index."
			::= { sheShapingProfileEntry 1 }

		
--  1.3.6.1.4.1.231.7.1.2.2.1.4.8.12.1.2
		sheShapingProfileName OBJECT-TYPE
			SYNTAX OCTET STRING (SIZE (0..32))
			MAX-ACCESS read-only
			STATUS current
			DESCRIPTION
				"A descriptional name for this Shaping profile.
				Spaces and other special characters (: o) are not allowed!! "
			::= { sheShapingProfileEntry 2 }

		
--  1.3.6.1.4.1.231.7.1.2.2.1.4.8.12.1.3
		sheShapingProfileCir OBJECT-TYPE
			SYNTAX Integer32 (0..102400)
			UNITS "kBit/s"
			MAX-ACCESS read-only
			STATUS current
			DESCRIPTION
				"The Committed Information Rate for downstream shaping. "
			::= { sheShapingProfileEntry 3 }

		
--  1.3.6.1.4.1.231.7.1.2.2.1.4.8.12.1.4
		sheShapingProfileCbs OBJECT-TYPE
			SYNTAX Integer32 (96..333000)
			UNITS "Bytes"
			MAX-ACCESS read-only
			STATUS current
			DESCRIPTION
				"The Committed Burst Size for downstream shaping. "
			::= { sheShapingProfileEntry 4 }

		
--  1.3.6.1.4.1.231.7.1.2.2.1.4.8.13
		sheShapingProfileControl OBJECT IDENTIFIER ::= { sheQueueConfiguration 13 }

		
--  1.3.6.1.4.1.231.7.1.2.2.1.4.8.13.1
		sheShapingProfileControlRequest OBJECT-TYPE
			SYNTAX SheBridgeControlRequestType
			MAX-ACCESS read-write
			STATUS current
			DESCRIPTION
				"createShapingProfile:
				sheShapingProfileControlName
				sheShapingProfileControlCir
				sheShapingProfileControlCbs
				
				deleteShapingProfile:
				sheShapingProfileControlIndex
				
				modifyShapingProfile:
				sheShapingProfileControlIndex
				sheShapingProfileControlName
				sheShapingProfileControlCir
				sheShapingProfileControlCbs"
			::= { sheShapingProfileControl 1 }

		
--  1.3.6.1.4.1.231.7.1.2.2.1.4.8.13.2
		sheShapingProfileControlIndex OBJECT-TYPE
			SYNTAX Unsigned32 (1..300)
			MAX-ACCESS read-write
			STATUS current
			DESCRIPTION
				"Index of the configured table entry. Needed for modify or delete."
			::= { sheShapingProfileControl 2 }

		
--  1.3.6.1.4.1.231.7.1.2.2.1.4.8.13.3
		sheShapingProfileControlStatus OBJECT-TYPE
			SYNTAX SheControlStatusType
			MAX-ACCESS read-only
			STATUS current
			DESCRIPTION
				"The status of a user command. 
				"
			::= { sheShapingProfileControl 3 }

		
--  1.3.6.1.4.1.231.7.1.2.2.1.4.8.13.4
		sheShapingProfileControlTimer OBJECT-TYPE
			SYNTAX Gauge32
			MAX-ACCESS read-only
			STATUS current
			DESCRIPTION
				"The maximum wait time for the manager for a long running user command. 
				"
			::= { sheShapingProfileControl 4 }

		
--  1.3.6.1.4.1.231.7.1.2.2.1.4.8.13.5
		sheShapingProfileControlReqResult OBJECT-TYPE
			SYNTAX SheBridgeControlReqResultType
			MAX-ACCESS read-only
			STATUS current
			DESCRIPTION
				"The result of the last user command."
			::= { sheShapingProfileControl 5 }

		
--  1.3.6.1.4.1.231.7.1.2.2.1.4.8.13.6
		sheShapingProfileControlTimeStamp OBJECT-TYPE
			SYNTAX Unsigned32
			UNITS "sec"
			MAX-ACCESS read-only
			STATUS current
			DESCRIPTION
				"The time stamp of the last command (end of command)."
			::= { sheShapingProfileControl 6 }

		
--  1.3.6.1.4.1.231.7.1.2.2.1.4.8.13.7
		sheShapingProfileControlProfileName OBJECT-TYPE
			SYNTAX OCTET STRING (SIZE (0..32))
			MAX-ACCESS read-write
			STATUS current
			DESCRIPTION
				"look at ShapingProfileTable...
				Spaces and other special characters (: o) are not allowed!! "
			::= { sheShapingProfileControl 7 }

		
--  1.3.6.1.4.1.231.7.1.2.2.1.4.8.13.8
		sheShapingProfileControlProfileCir OBJECT-TYPE
			SYNTAX Integer32 (0..102400)
			UNITS "kBit/s"
			MAX-ACCESS read-write
			STATUS current
			DESCRIPTION
				"look at ShapingProfileTable..."
			::= { sheShapingProfileControl 8 }

		
--  1.3.6.1.4.1.231.7.1.2.2.1.4.8.13.9
		sheShapingProfileControlProfileCbs OBJECT-TYPE
			SYNTAX Integer32 (96..333000)
			UNITS "Bytes"
			MAX-ACCESS read-write
			STATUS current
			DESCRIPTION
				"look at ShapingProfileTable..."
			::= { sheShapingProfileControl 9 }

		
--  1.3.6.1.4.1.231.7.1.2.2.1.4.8.14
		sheShapingProfileAssignmentTable OBJECT-TYPE
			SYNTAX SEQUENCE OF SheShapingProfileAssignmentEntry
			MAX-ACCESS not-accessible
			STATUS current
			DESCRIPTION
				"The shaping profile assignment table."
			::= { sheQueueConfiguration 14 }

		
--  1.3.6.1.4.1.231.7.1.2.2.1.4.8.14.1
		sheShapingProfileAssignmentEntry OBJECT-TYPE
			SYNTAX SheShapingProfileAssignmentEntry
			MAX-ACCESS not-accessible
			STATUS current
			DESCRIPTION
				"One entry for each assigned shaping profile.
				The assignment will use two indeces. First index is the ifIndex of the used
				subscriber port. Second index is the queue number.
				
				New with R2.8:
				There are two special values for queuenumber are supported, which allow to assign
				such a shaping profile to the lower (1..4) or upper (5..8) queue-group.
				If mode4QueueFlat is running, only the lower group is available.
				One shaping profile for all queues in queuemode mode8QueueFlat or modeHqs is not supported."
			INDEX { ifIndex, sheShapingProfileAssignmentQueueNumber }
			::= { sheShapingProfileAssignmentTable 1 }

		
		SheShapingProfileAssignmentEntry ::=
			SEQUENCE { 
				sheShapingProfileAssignmentQueueNumber
					Unsigned32,
				sheShapingProfileAssignmentProfileIndex
					Unsigned32
			 }

--  1.3.6.1.4.1.231.7.1.2.2.1.4.8.14.1.1
		sheShapingProfileAssignmentQueueNumber OBJECT-TYPE
			SYNTAX Unsigned32 (0 | 1..8 | 255)
			MAX-ACCESS read-only
			STATUS current
			DESCRIPTION
				"The second index of this table. 
				That represents the used Queue-Number for this ShapingProfile assignment.
				
				Note: Depending on the used card type, the number of available queues could be 
				restricted to 4. An assignment to 8 queues will always be possible and the IU will
				then ignore the upper 4 queue configurations. 
				
				New with R2.8:
				Two special values allow the assignment of a shapingProfile to a group of queues
				for this DSL-port and not only to a single queue of this port.
				'0' will assign this to the DSL port.
				For IU_CG boards, this is not fully supported in queue mode 'mode8QueueFlat'.
				Here this setting will only apply to the higher prio queue group (queue 5..8).
				Additionally a specific shaper should be configured for the lower prio queue group
				(queue 1..4) with value '255'.
				"
			::= { sheShapingProfileAssignmentEntry 1 }

		
--  1.3.6.1.4.1.231.7.1.2.2.1.4.8.14.1.2
		sheShapingProfileAssignmentProfileIndex OBJECT-TYPE
			SYNTAX Unsigned32 (1..300)
			MAX-ACCESS read-only
			STATUS current
			DESCRIPTION
				"This value represents a valid index from sheShapingProfileTable which should be
				used for this DSL-Port and Queue-Number."
			::= { sheShapingProfileAssignmentEntry 2 }

		
--  1.3.6.1.4.1.231.7.1.2.2.1.4.8.15
		sheShapingProfileAssignmentControl OBJECT IDENTIFIER ::= { sheQueueConfiguration 15 }

		
--  1.3.6.1.4.1.231.7.1.2.2.1.4.8.13.1
		sheShapingProfileAssignmentControlRequest OBJECT-TYPE
			SYNTAX SheBridgeControlRequestType
			MAX-ACCESS read-write
			STATUS current
			DESCRIPTION
				"assignShapingProfile:
				sheShapingProfileAssignmentControlIndex
				sheShapingProfileAssignmentControlQueueNumber
				sheShapingProfileAssignmentControlProfileIndex
				
				deleteShapingProfileAssignment:
				sheShapingProfileAssignmentControlIndex
				sheShapingProfileAssignmentControlQueueNumber"
			::= { sheShapingProfileAssignmentControl 1 }

		
--  1.3.6.1.4.1.231.7.1.2.2.1.4.8.15.2
		sheShapingProfileAssignmentControlIndex OBJECT-TYPE
			SYNTAX InterfaceIndex
			MAX-ACCESS read-write
			STATUS current
			DESCRIPTION
				"ifIndex of the DSL-Interface where a shaping profile should be assigned.
				First index value for assignment."
			::= { sheShapingProfileAssignmentControl 2 }

		
--  1.3.6.1.4.1.231.7.1.2.2.1.4.8.15.3
		sheShapingProfileAssignmentControlStatus OBJECT-TYPE
			SYNTAX SheControlStatusType
			MAX-ACCESS read-only
			STATUS current
			DESCRIPTION
				"The status of a user command. 
				"
			::= { sheShapingProfileAssignmentControl 3 }

		
--  1.3.6.1.4.1.231.7.1.2.2.1.4.8.15.4
		sheShapingProfileAssignmentControlTimer OBJECT-TYPE
			SYNTAX Gauge32
			MAX-ACCESS read-only
			STATUS current
			DESCRIPTION
				"The maximum wait time for the manager for a long running user command. 
				"
			::= { sheShapingProfileAssignmentControl 4 }

		
--  1.3.6.1.4.1.231.7.1.2.2.1.4.8.15.5
		sheShapingProfileAssignmentControlReqResult OBJECT-TYPE
			SYNTAX SheBridgeControlReqResultType
			MAX-ACCESS read-only
			STATUS current
			DESCRIPTION
				"The result of the last user command."
			::= { sheShapingProfileAssignmentControl 5 }

		
--  1.3.6.1.4.1.231.7.1.2.2.1.4.8.15.6
		sheShapingProfileAssignmentControlTimeStamp OBJECT-TYPE
			SYNTAX Unsigned32
			UNITS "sec"
			MAX-ACCESS read-only
			STATUS current
			DESCRIPTION
				"The time stamp of the last command (end of command)."
			::= { sheShapingProfileAssignmentControl 6 }

		
--  1.3.6.1.4.1.231.7.1.2.2.1.4.8.15.7
		sheShapingProfileAssignmentControlQueueNumber OBJECT-TYPE
			SYNTAX Unsigned32 (0 | 1..8 | 255)
			MAX-ACCESS read-write
			STATUS current
			DESCRIPTION
				"QueueNumber of the DSL-Interface where a shaping profile should be assigned.
				Second index value for assignment.
				
				New with R2.8:
				Two special values allow the assignment of a shapingProfile to a group of queues
				for this DSL-port and not only to a single queue of this port.
				'0' will assign this to the DSL port.
				For IU_CG boards, this is not fully supported in queue mode 'mode8QueueFlat'.
				Here this setting will only apply to the higher prio queue group (queue 5..8).
				Additionally a specific shaper should be configured for the lower prio queue group
				(queue 1..4) with value '255'."
			::= { sheShapingProfileAssignmentControl 7 }

		
--  1.3.6.1.4.1.231.7.1.2.2.1.4.8.15.8
		sheShapingProfileAssignmentControlProfileIndex OBJECT-TYPE
			SYNTAX Unsigned32 (1..300)
			MAX-ACCESS read-write
			STATUS current
			DESCRIPTION
				"This value represents a valid index from sheShapingProfileTable which should be
				used for this DSL-Port and Queue-Number."
			::= { sheShapingProfileAssignmentControl 8 }

		
		sheShapingNotifications OBJECT IDENTIFIER ::= { sheQueueConfiguration 16 }

		
		sheShapingProfileCreated NOTIFICATION-TYPE
			OBJECTS { sheShapingProfileControlIndex, sheShapingProfileControlTimeStamp, sheShapingProfileControlProfileName, sheShapingProfileControlProfileCir, sheShapingProfileControlProfileCbs
				 }
			STATUS current
			DESCRIPTION 
				"Configuration notification. A new shaping profile was created in sheShapingProfileTable."
			::= { sheShapingNotifications 2 }

		
		sheShapingProfileModified NOTIFICATION-TYPE
			OBJECTS { sheShapingProfileControlIndex, sheShapingProfileControlTimeStamp, sheShapingProfileControlProfileName, sheShapingProfileControlProfileCir, sheShapingProfileControlProfileCbs
				 }
			STATUS current
			DESCRIPTION 
				"Configuration notification. A shaping profile was modified in sheShapingProfileTable."
			::= { sheShapingNotifications 3 }

		
		sheShapingProfileDeleted NOTIFICATION-TYPE
			OBJECTS { sheShapingProfileControlIndex, sheShapingProfileControlTimeStamp }
			STATUS current
			DESCRIPTION 
				"Configuration notification. A shaping profile was deleted from sheShapingProfileTable."
			::= { sheShapingNotifications 4 }

		
		sheShapingProfileAssigned NOTIFICATION-TYPE
			OBJECTS { sheShapingProfileAssignmentControlIndex, sheShapingProfileAssignmentControlQueueNumber, sheShapingProfileAssignmentControlTimeStamp, sheShapingProfileAssignmentControlProfileIndex }
			STATUS current
			DESCRIPTION 
				"Configuration notification. A shaping profile from sheShapingProfileTable was 
				assigned to port.queuenumber."
			::= { sheShapingNotifications 5 }

		
		sheShapingProfileAssignmentDeleted NOTIFICATION-TYPE
			OBJECTS { sheShapingProfileAssignmentControlIndex, sheShapingProfileAssignmentControlQueueNumber, sheShapingProfileAssignmentControlTimeStamp }
			STATUS current
			DESCRIPTION 
				"Configuration notification. An existing shaping profile assignment was deleted
				from sheShapingProfileAssignmentTable."
			::= { sheShapingNotifications 6 }

		
--   1.3.6.1.4.1.231.7.1.2.2.1.4.8.100
		sheQueueConformance OBJECT IDENTIFIER ::= { sheQueueConfiguration 100 }

		
--   1.3.6.1.4.1.231.7.1.2.2.1.4.8.11.1
		sheQueueCompliances OBJECT IDENTIFIER ::= { sheQueueConformance 1 }

		
--   1.3.6.1.4.1.231.7.1.2.2.1.4.8.11.1.1
-- this module
-- this module
		sheQueueCompliance MODULE-COMPLIANCE
			STATUS current
			DESCRIPTION 
				"Description."
			MODULE -- this module
				MANDATORY-GROUPS { sheQueuePriorityGroup, sheQueueModeGroup, sheQueueModeControlGroup, sheQueueWeightGroup, sheQueueWeightControlGroup, 
					sheQueueCardGroup, sheQueueCardControlGroup, sheShapingGroup, sheShapingControlGroup, sheShapingNotificationGroup, 
					sheQueueNotificationGroup, sheQueuePriorityControlGroup }
			::= { sheQueueCompliances 1 }

		
--   1.3.6.1.4.1.231.7.1.2.2.1.4.8.11.2
		sheQueueGroups OBJECT IDENTIFIER ::= { sheQueueConformance 2 }

		
--   1.3.6.1.4.1.231.7.1.2.2.1.4.8.11.2.1
		sheQueuePriorityGroup OBJECT-GROUP
			OBJECTS { sheQueuePriority, sheQueueNumber, sheReducedQueuePriority, sheReducedQueueNumber }
			STATUS current
			DESCRIPTION 
				"Description."
			::= { sheQueueGroups 1 }

		
--   1.3.6.1.4.1.231.7.1.2.2.1.4.8.11.2.3
		sheQueuePriorityControlGroup OBJECT-GROUP
			OBJECTS { sheQueueControlRequest, sheQueueControlIndex, sheQueueControlStatus, sheQueueControlTimer, sheQueueControlTimeStamp, 
				sheQueueControlReqResult, sheQueueControlQueueNumber }
			STATUS current
			DESCRIPTION 
				"Description."
			::= { sheQueueGroups 3 }

		
--   1.3.6.1.4.1.231.7.1.2.2.1.4.8.11.2.4
		sheQueueModeGroup OBJECT-GROUP
			OBJECTS { sheQueueModeInterfaceTypeIndex, sheQueueConfigurationMode }
			STATUS current
			DESCRIPTION 
				"Description."
			::= { sheQueueGroups 4 }

		
--   1.3.6.1.4.1.231.7.1.2.2.1.4.8.11.2.5
		sheQueueModeControlGroup OBJECT-GROUP
			OBJECTS { sheQueueModeControlRequest, sheQueueModeControlIndex, sheQueueModeControlStatus, sheQueueModeControlTimer, sheQueueModeControlReqResult, 
				sheQueueModeControlTimeStamp, sheQueueModeControlMode }
			STATUS current
			DESCRIPTION 
				"Description."
			::= { sheQueueGroups 5 }

		
--   1.3.6.1.4.1.231.7.1.2.2.1.4.8.11.2.6
		sheQueueWeightGroup OBJECT-GROUP
			OBJECTS { sheQueueIndex, sheQueueWeight, sheQueueWeightWatermarkLow, sheQueueWeightWatermarkHigh }
			STATUS current
			DESCRIPTION 
				"Description."
			::= { sheQueueGroups 6 }

		
--   1.3.6.1.4.1.231.7.1.2.2.1.4.8.11.2.7
		sheQueueWeightControlGroup OBJECT-GROUP
			OBJECTS { sheQueueWeightControlRequest, sheQueueWeightControlIndex, sheQueueWeightControlStatus, sheQueueWeightControlTimer, sheQueueWeightControlReqResult, 
				sheQueueWeightControlTimeStamp, sheQueueWeightControlWeight, sheQueueWeightControlWatermarkLow, sheQueueWeightControlWatermarkHigh }
			STATUS current
			DESCRIPTION 
				"Description."
			::= { sheQueueGroups 7 }

		
		sheQueueCardGroup OBJECT-GROUP
			OBJECTS { sheCardQueueInterfaceTypeIndex, sheCardQueueSchedulingMode, sheCardQueue1Weight, sheCardQueue1Watermarks, sheCardQueue2Weight, 
				sheCardQueue2Watermarks, sheCardQueue3Weight, sheCardQueue3Watermarks, sheCardQueue4Weight, sheCardQueue4Watermarks, 
				sheCardQueue5Weight, sheCardQueue5Watermarks, sheCardQueue6Weight, sheCardQueue6Watermarks, sheCardQueue7Weight, 
				sheCardQueue7Watermarks, sheCardQueue8Weight, sheCardQueue8Watermarks, sheCardQueueColourAwareTCSource, sheCardQueueColourMarking, 
				sheCardQueueDiscardPolicy, sheCardQueueMode, sheCardQueueHqsSecondStageInputQueue, sheCardQueueHqsFirstStagePir, sheCardQueueHqsFirstStagePbs
				 }
			STATUS current
			DESCRIPTION 
				"Description."
			::= { sheQueueGroups 8 }

		
		sheQueueCardControlGroup OBJECT-GROUP
			OBJECTS { sheCardQueueControlRequest, sheCardQueueControlIndex, sheCardQueueControlStatus, sheCardQueueControlTimer, sheCardQueueControlReqResult, 
				sheCardQueueControlTimeStamp, sheCardQueueControlInterfaceTypeIndex, sheCardQueueControlSchedulingMode, sheCardQueueControlQueue1Weight, sheCardQueueControlQueue1Watermarks, 
				sheCardQueueControlQueue2Weight, sheCardQueueControlQueue2Watermarks, sheCardQueueControlQueue3Weight, sheCardQueueControlQueue3Watermarks, sheCardQueueControlQueue4Weight, 
				sheCardQueueControlQueue4Watermarks, sheCardQueueControlQueue5Weight, sheCardQueueControlQueue5Watermarks, sheCardQueueControlQueue6Weight, sheCardQueueControlQueue6Watermarks, 
				sheCardQueueControlQueue7Weight, sheCardQueueControlQueue7Watermarks, sheCardQueueControlQueue8Weight, sheCardQueueControlQueue8Watermarks, sheCardQueueControlColourAwareTCSource, 
				sheCardQueueControlColourMarking, sheCardQueueControlDiscardPolicy, sheCardQueueControlMode, sheCardQueueControlHqsSecondStageInputQueue, sheCardQueueControlHqsFirstStagePir, 
				sheCardQueueControlHqsFirstStagePbs }
			STATUS current
			DESCRIPTION 
				"Description."
			::= { sheQueueGroups 9 }

		
--   1.3.6.1.4.1.231.7.1.2.2.1.4.8.11.2.8
		sheQueueNotificationGroup NOTIFICATION-GROUP
			NOTIFICATIONS { sheQueuePriorityMappingModified, sheQueueModeEntryModified, sheQueueWeightEntryModified, sheReducedQueuePriorityMappingModified, sheCardQueueEntryConfigured, 
				sheCardQueueEntryDeleted, sheCardQueueEntryConfigResult }
			STATUS current
			DESCRIPTION 
				"Description."
			::= { sheQueueGroups 10 }

		
		sheShapingGroup OBJECT-GROUP
			OBJECTS { sheShapingProfileIndex, sheShapingProfileName, sheShapingProfileCir, sheShapingProfileCbs, sheShapingProfileAssignmentQueueNumber, 
				sheShapingProfileAssignmentProfileIndex }
			STATUS current
			DESCRIPTION 
				"Description."
			::= { sheQueueGroups 11 }

		
		sheShapingControlGroup OBJECT-GROUP
			OBJECTS { sheShapingProfileControlRequest, sheShapingProfileControlIndex, sheShapingProfileControlStatus, sheShapingProfileControlTimer, sheShapingProfileControlReqResult, 
				sheShapingProfileControlTimeStamp, sheShapingProfileControlProfileName, sheShapingProfileControlProfileCir, sheShapingProfileControlProfileCbs, sheShapingProfileAssignmentControlRequest, 
				sheShapingProfileAssignmentControlIndex, sheShapingProfileAssignmentControlStatus, sheShapingProfileAssignmentControlTimer, sheShapingProfileAssignmentControlReqResult, sheShapingProfileAssignmentControlTimeStamp, 
				sheShapingProfileAssignmentControlQueueNumber, sheShapingProfileAssignmentControlProfileIndex }
			STATUS current
			DESCRIPTION 
				"Description."
			::= { sheQueueGroups 12 }

		
		sheShapingNotificationGroup NOTIFICATION-GROUP
			NOTIFICATIONS { sheShapingProfileCreated, sheShapingProfileModified, sheShapingProfileDeleted, sheShapingProfileAssigned, sheShapingProfileAssignmentDeleted
				 }
			STATUS current
			DESCRIPTION 
				"Description."
			::= { sheQueueGroups 13 }

		
--   1.3.6.1.4.1.231.7.1.2.2.1.4.9
		sheErp OBJECT IDENTIFIER ::= { sheBridgeMib 9 }

		
--   1.3.6.1.4.1.231.7.1.2.2.1.4.9.1
		sheErpBase OBJECT IDENTIFIER ::= { sheErp 1 }

		
--   1.3.6.1.4.1.231.7.1.2.2.1.4.9.1.1
		sheErpBaseParam OBJECT IDENTIFIER ::= { sheErpBase 1 }

		
--   1.3.6.1.4.1.231.7.1.2.2.1.4.9.1.1.1
		sheErpDomainTrafficVlan OBJECT-TYPE
			SYNTAX OCTET STRING (SIZE (4096))
			MAX-ACCESS read-only
			STATUS current
			DESCRIPTION
				"This octet string with 4096 octets maps payload VLANs
				to ERP domains: one octet containing the sheErpDomainIndex
				per VLAN. The octet number is the sheVlanIndex.
				You can assign a VLAN to only one ERP domain at a time.
				In this way the ERP domains of the sheErpDomainTable
				can be used on a per-VLAN basis. The value 0
				indicates that no ERP domain is assigned to that VLAN."
			::= { sheErpBaseParam 1 }

		
--   1.3.6.1.4.1.231.7.1.2.2.1.4.9.1.2
		sheErpBaseControl OBJECT IDENTIFIER ::= { sheErpBase 2 }

		
--   1.3.6.1.4.1.231.7.1.2.2.1.4.9.1.2.1
		sheErpBaseControlRequest OBJECT-TYPE
			SYNTAX SheBridgeControlRequestType
			MAX-ACCESS read-write
			STATUS current
			DESCRIPTION
				"A SetRequest on this attribute starts a command
				execution process in the NetElement.
				
				- modifyErpDomainTrafficVlan
				  parameters:
				    sheErpBaseControlDomainTrafficVlan"
			::= { sheErpBaseControl 1 }

		
--   1.3.6.1.4.1.231.7.1.2.2.1.4.9.1.2.2
		sheErpBaseControlStatus OBJECT-TYPE
			SYNTAX SheControlStatusType
			MAX-ACCESS read-only
			STATUS current
			DESCRIPTION
				"Describes the status of a user command group, used
				for block commands while a command execution
				is in process.
				Values : idle, busy, passed, failed.
				idle: default, no command in process
				busy: command execution in process, attempts to start
				      another user command on this control block
				      are rejected
				passed/failed: status at end of command"
			::= { sheErpBaseControl 2 }

		
--   1.3.6.1.4.1.231.7.1.2.2.1.4.9.1.2.3
		sheErpBaseControlTimestamp OBJECT-TYPE
			SYNTAX Unsigned32
			UNITS "sec"
			MAX-ACCESS read-only
			STATUS current
			DESCRIPTION
				"Time stamp attribute set at the end of a command."
			::= { sheErpBaseControl 3 }

		
--   1.3.6.1.4.1.231.7.1.2.2.1.4.9.1.2.4
		sheErpBaseControlReqResult OBJECT-TYPE
			SYNTAX SheBridgeControlReqResultType
			MAX-ACCESS read-only
			STATUS current
			DESCRIPTION
				"Command result (error code) attribute."
			::= { sheErpBaseControl 4 }

		
--   1.3.6.1.4.1.231.7.1.2.2.1.4.9.1.2.5
		sheErpBaseControlTimer OBJECT-TYPE
			SYNTAX Unsigned32
			MAX-ACCESS read-only
			STATUS current
			DESCRIPTION
				"Maximum command execution time (timeout) in seconds
				in case of a long running command."
			::= { sheErpBaseControl 5 }

		
--   1.3.6.1.4.1.231.7.1.2.2.1.4.9.1.2.6
		sheErpBaseControlDomainTrafficVlan OBJECT-TYPE
			SYNTAX OCTET STRING (SIZE (4096))
			MAX-ACCESS read-write
			STATUS current
			DESCRIPTION
				"This octet string with 4096 octets maps payload VLANs
				to ERP domains: one octet containing the sheErpDomainIndex
				per VLAN. The octet number is the sheVlanIndex.
				You can assign a VLAN to only one ERP domain at a time.
				In this way the ERP domains of the sheErpDomainTable
				can be used on a per-VLAN basis. The value 0
				indicates that no ERP domain is assigned to that VLAN.
				parameter for
				- modifyErpDomainTrafficVlan"
			::= { sheErpBaseControl 6 }

		
--   1.3.6.1.4.1.231.7.1.2.2.1.4.9.2
		sheErpDomain OBJECT IDENTIFIER ::= { sheErp 2 }

		
--   1.3.6.1.4.1.231.7.1.2.2.1.4.9.2.1
		sheErpDomainTable OBJECT-TYPE
			SYNTAX SEQUENCE OF SheErpDomainEntry
			MAX-ACCESS not-accessible
			STATUS current
			DESCRIPTION
				"ERP domains configuration table with static entries."
			::= { sheErpDomain 1 }

		
--   1.3.6.1.4.1.231.7.1.2.2.1.4.9.2.1.1
		sheErpDomainEntry OBJECT-TYPE
			SYNTAX SheErpDomainEntry
			MAX-ACCESS not-accessible
			STATUS current
			DESCRIPTION
				"ERP Domain entry."
			INDEX { sheErpDomainIndex }
			::= { sheErpDomainTable 1 }

		
		SheErpDomainEntry ::=
			SEQUENCE { 
				sheErpDomainIndex
					Unsigned32,
				sheErpDomainName
					DisplayString,
				sheErpDomainPrimaryPort
					SheBridgePortIndexOrInvalid,
				sheErpDomainSecondaryPort
					SheBridgePortIndexOrInvalid,
				sheErpDomainWaitToRestoreTime
					Unsigned32,
				sheErpDomainTestPacketInterval
					Unsigned32,
				sheErpDomainLearningDisabledTime
					Unsigned32,
				sheErpDomainProtectionActivation
					ShePermissionType,
				sheErpDomainOperatorRequest
					SheErpDomainOperatorRequestType,
				sheErpDomainNodeMode
					SheErpNodeType,
				sheErpDomainControlVlan
					SheVlanIdOrInvalid,
				sheErpDomainNodeStatus
					SheErpDomainNodeStatusType,
				sheErpDomainRingStatus
					SheErpDomainRingStatusType,
				sheErpDomainLotp
					TruthValue,
				sheErpDomainUlotp
					TruthValue,
				sheErpDomainMultipleRm
					TruthValue,
				sheErpDomainRmReach
					TruthValue,
				sheErpDomainLotpTrapEnable
					ShePermissionType,
				sheErpDomainUlotpTrapEnable
					ShePermissionType,
				sheErpDomainMultipleRmTrapEnable
					ShePermissionType,
				sheErpDomainRmReachTrapEnable
					ShePermissionType,
				sheErpDomainAlarmSeverityIndex
					SheAlarmSevProfileIndex
			 }

--   1.3.6.1.4.1.231.7.1.2.2.1.4.9.2.1.1.1
		sheErpDomainIndex OBJECT-TYPE
			SYNTAX Unsigned32 (1..64)
			MAX-ACCESS read-only
			STATUS current
			DESCRIPTION
				"An index value that uniquely identifies an ERP domain."
			::= { sheErpDomainEntry 1 }

		
--   1.3.6.1.4.1.231.7.1.2.2.1.4.9.2.1.1.2
		sheErpDomainName OBJECT-TYPE
			SYNTAX DisplayString
			MAX-ACCESS read-only
			STATUS current
			DESCRIPTION
				"The associated name of the ERP Domain.
				Spaces and other special characters (: o) are not allowed!! "
			::= { sheErpDomainEntry 2 }

		
--   1.3.6.1.4.1.231.7.1.2.2.1.4.9.2.1.1.3
		sheErpDomainPrimaryPort OBJECT-TYPE
			SYNTAX SheBridgePortIndexOrInvalid
			MAX-ACCESS read-only
			STATUS current
			DESCRIPTION
				"The sheBridgePortIndex of the sheBridgePortTable
				that represents the primary port of the ERP domain.
				The allowed range is 1-65535. Only Ethernet interfaces
				possible. The value -1 is used to indicate that
				it is unassigned (Invalid)."
			DEFVAL { -1 }
			::= { sheErpDomainEntry 3 }

		
--   1.3.6.1.4.1.231.7.1.2.2.1.4.9.2.1.1.4
		sheErpDomainSecondaryPort OBJECT-TYPE
			SYNTAX SheBridgePortIndexOrInvalid
			MAX-ACCESS read-only
			STATUS current
			DESCRIPTION
				"The sheBridgePortIndex of the sheBridgePortTable
				that represents the secondary port of the ERP domain.
				The allowed range is 1-65535. Only Ethernet interfaces
				possible. The value -1 is used to indicate that
				it is unassigned (Invalid)."
			DEFVAL { -1 }
			::= { sheErpDomainEntry 4 }

		
--   1.3.6.1.4.1.231.7.1.2.2.1.4.9.2.1.1.5
		sheErpDomainWaitToRestoreTime OBJECT-TYPE
			SYNTAX Unsigned32 (2..720)
			UNITS "1 s"
			MAX-ACCESS read-only
			STATUS current
			DESCRIPTION
				"Time in seconds taken to verify that ring integrity is
				maintained before switch to Idle state after all links
				have recovered from Link Failure, Link Degrade or
				Loss of Test Packet. Range 2..720."
			DEFVAL { 2 }
			::= { sheErpDomainEntry 5 }

		
--   1.3.6.1.4.1.231.7.1.2.2.1.4.9.2.1.1.6
		sheErpDomainTestPacketInterval OBJECT-TYPE
			SYNTAX Unsigned32 (10..500)
			UNITS "1 ms"
			MAX-ACCESS read-only
			STATUS current
			DESCRIPTION
				"Time interval , in milliseconds, between consecutive
				transmission of test packets. The Test Packet Interval
				is used to define the time to initiate protection due to
				Loss of Test Packets, The value of Test Packet Interval
				is between 10 ms and 500 ms in 10 ms steps."
			DEFVAL { 10 }
			::= { sheErpDomainEntry 6 }

		
--   1.3.6.1.4.1.231.7.1.2.2.1.4.9.2.1.1.7
		sheErpDomainLearningDisabledTime OBJECT-TYPE
			SYNTAX Unsigned32 (0..500)
			UNITS "1 ms"
			MAX-ACCESS read-only
			STATUS current
			DESCRIPTION
				"Configures the time during which learning is disabled
				after a FDB flush. The learning is only disabled for the
				protected VLAN of the domain on the ERP ports.
				The value of the Learning Disabled Time is between
				0 and 500 ms in steps of 10 ms."
			DEFVAL { 50 }
			::= { sheErpDomainEntry 7 }

		
--   1.3.6.1.4.1.231.7.1.2.2.1.4.9.2.1.1.8
		sheErpDomainProtectionActivation OBJECT-TYPE
			SYNTAX ShePermissionType
			MAX-ACCESS read-only
			STATUS current
			DESCRIPTION
				"Represents if ERP Protection activation is activated or
				deactivated (admin state). When the ERP domain is activated the ERP
				process will start running. All alarms/traps are cleared
				and the ERP protection state is reported as unknown.
				The domain will enter deactivated state. The ERP
				protection activation default value is deactivated.
				deny(0)   - protection inactive
				permit(1) - protection active
				"
			::= { sheErpDomainEntry 8 }

		
--   1.3.6.1.4.1.231.7.1.2.2.1.4.9.2.1.1.9
		sheErpDomainOperatorRequest OBJECT-TYPE
			SYNTAX SheErpDomainOperatorRequestType
			MAX-ACCESS read-only
			STATUS current
			DESCRIPTION
				"Two operators requests are possible for one ERP domain.
				For Normal nodes operator requests are ignored.
				manualToSecondary(1) - Manual Switch to Secondary port -
				This command enables to swap the roles of primary and
				secondary port on the RM Node.
				clear(2) - Clear -
				This command disables a previous Manual Switch to
				Secondary port."
			DEFVAL { 2 }
			::= { sheErpDomainEntry 9 }

		
--   1.3.6.1.4.1.231.7.1.2.2.1.4.9.2.1.1.10
		sheErpDomainNodeMode OBJECT-TYPE
			SYNTAX SheErpNodeType
			MAX-ACCESS read-only
			STATUS current
			DESCRIPTION
				"An ERP domain may operate in two modes. RM Node or Normal
				Node. The description of these two modes is included in
				ERP concept specification. Only one node per domain
				could be a rm node.
				normalNode(1)
				rmNode(2)"
			DEFVAL { 1 }
			::= { sheErpDomainEntry 10 }

		
--   1.3.6.1.4.1.231.7.1.2.2.1.4.9.2.1.1.11
		sheErpDomainControlVlan OBJECT-TYPE
			SYNTAX SheVlanIdOrInvalid
			MAX-ACCESS read-only
			STATUS current
			DESCRIPTION
				"Represents the VLAN ID sheVlanIndex of the control VLAN
				of the domain. The control VLAN may not be used in other
				domains as control VLAN or as protected VLAN. The control
				VLAN must be a VLAN with a high priority QoS profile."
			DEFVAL { -1 }
			::= { sheErpDomainEntry 11 }

		
--   1.3.6.1.4.1.231.7.1.2.2.1.4.9.2.1.1.12
		sheErpDomainNodeStatus OBJECT-TYPE
			SYNTAX SheErpDomainNodeStatusType
			MAX-ACCESS read-only
			STATUS current
			DESCRIPTION
				"Reflects the domain node status.
				rmIdle(1)
				primaryProtecting(2)
				protecting(3)
				idle(4)
				failed-S(5)
				failed-P(6)
				preForward(7)
				isolated(8)
				deactivated(9)
				backoff(10)"
			::= { sheErpDomainEntry 12 }

		
--   1.3.6.1.4.1.231.7.1.2.2.1.4.9.2.1.1.13
		sheErpDomainRingStatus OBJECT-TYPE
			SYNTAX SheErpDomainRingStatusType
			MAX-ACCESS read-only
			STATUS current
			DESCRIPTION
				"Actual protection state of the ERP domain on the ring.
				The following three states are defined:
				Normal - All ring nodes are available and used.
				Protecting - At least one Link on the ring is failed.
				Unknown - This state is used when the ERP protection
				is not activated, or when the Multiple Failures are
				detected in a Normal Node."
			::= { sheErpDomainEntry 13 }

		
--   1.3.6.1.4.1.231.7.1.2.2.1.4.9.2.1.1.14
		sheErpDomainLotp OBJECT-TYPE
			SYNTAX TruthValue
			MAX-ACCESS read-only
			STATUS current
			DESCRIPTION
				"Erp domain Loss of Test Packet alarm status.
				Only meaningful for RM nodes.
				true(1)  - alarm active
				false(2) - alarm inactive
				"
			::= { sheErpDomainEntry 14 }

		
--   1.3.6.1.4.1.231.7.1.2.2.1.4.9.2.1.1.15
		sheErpDomainUlotp OBJECT-TYPE
			SYNTAX TruthValue
			MAX-ACCESS read-only
			STATUS current
			DESCRIPTION
				"Erp domain Unidirectional Detection of  Loss of Test
				Packet alarm status.
				Only meaningful for RM nodes.
				true(1)  - alarm active
				false(2) - alarm inactive
				
				"
			::= { sheErpDomainEntry 15 }

		
--   1.3.6.1.4.1.231.7.1.2.2.1.4.9.2.1.1.16
		sheErpDomainMultipleRm OBJECT-TYPE
			SYNTAX TruthValue
			MAX-ACCESS read-only
			STATUS current
			DESCRIPTION
				"Erp domain Multiple Redundancy Manager alarm status.
				Only meaningful for RM nodes.
				true(1)  - alarm active
				false(2) - alarm inactive
				"
			::= { sheErpDomainEntry 16 }

		
--   1.3.6.1.4.1.231.7.1.2.2.1.4.9.2.1.1.17
		sheErpDomainRmReach OBJECT-TYPE
			SYNTAX TruthValue
			MAX-ACCESS read-only
			STATUS current
			DESCRIPTION
				"RM Node reacheability alarm status.
				Erp domain detection of mutiple failures in the ring
				cause the RM Node to become unreacheable to this
				normal node (only meaningful for normal nodes).
				true(1)  - RM Node is unreacheable, alarm active
				false(2) - RM Node is reacheable, alarm inactive
				"
			::= { sheErpDomainEntry 17 }

		
--   1.3.6.1.4.1.231.7.1.2.2.1.4.9.2.1.1.18
		sheErpDomainLotpTrapEnable OBJECT-TYPE
			SYNTAX ShePermissionType
			MAX-ACCESS read-only
			STATUS current
			DESCRIPTION
				"Erp domain Loss of Test Packet Trap.
				Configures sending OF LOTP traps when detected by the
				RM node.
				deny(0)
				permit(1)"
			DEFVAL { permit }
			::= { sheErpDomainEntry 18 }

		
--   1.3.6.1.4.1.231.7.1.2.2.1.4.9.2.1.1.19
		sheErpDomainUlotpTrapEnable OBJECT-TYPE
			SYNTAX ShePermissionType
			MAX-ACCESS read-only
			STATUS current
			DESCRIPTION
				"Erp domain Unidirectional Loss of Test Packet Trap.
				Configures sending of ULOTP traps when detected by the
				RM node.
				deny(0)
				permit(1)"
			DEFVAL { permit }
			::= { sheErpDomainEntry 19 }

		
--   1.3.6.1.4.1.231.7.1.2.2.1.4.9.2.1.1.20
		sheErpDomainMultipleRmTrapEnable OBJECT-TYPE
			SYNTAX ShePermissionType
			MAX-ACCESS read-only
			STATUS current
			DESCRIPTION
				"Erp domain multiple RM nodes Trap.
				Configures sending of MultipleRM traps when detected by
				the RM node.
				deny(0)
				permit(1)"
			DEFVAL { permit }
			::= { sheErpDomainEntry 20 }

		
--   1.3.6.1.4.1.231.7.1.2.2.1.4.9.2.1.1.21
		sheErpDomainRmReachTrapEnable OBJECT-TYPE
			SYNTAX ShePermissionType
			MAX-ACCESS read-only
			STATUS current
			DESCRIPTION
				"Erp domain multiple failures trap.
				Configures sending of RMNodeReacheablility traps when
				detected by the normal node.
				deny(0)
				permit(1)
				"
			DEFVAL { permit }
			::= { sheErpDomainEntry 21 }

		
--   1.3.6.1.4.1.231.7.1.2.2.1.4.9.2.1.1.22
		sheErpDomainAlarmSeverityIndex OBJECT-TYPE
			SYNTAX SheAlarmSevProfileIndex
			MAX-ACCESS read-only
			STATUS current
			DESCRIPTION
				"Index to the AlarmSeverityProfileTable. Defines the
				actual AlarmSeverities for all alarms per ERP domain."
			DEFVAL { 1 }
			::= { sheErpDomainEntry 22 }

		
--   1.3.6.1.4.1.231.7.1.2.2.1.4.9.2.2
		sheErpDomainControl OBJECT IDENTIFIER ::= { sheErpDomain 2 }

		
--   1.3.6.1.4.1.231.7.1.2.2.1.4.9.2.2.1
		sheErpDomainControlRequest OBJECT-TYPE
			SYNTAX SheBridgeControlRequestType
			MAX-ACCESS read-write
			STATUS current
			DESCRIPTION
				"A SetRequest on this attribute starts a command
				execution process in the NetElement.
				
				modifyErpDomainEntry(826)
				parameters:
				- sheErpDomainControlDomainIndex
				- sheErpDomainControlDomainName
				- sheErpDomainControlDomainPrimaryPort
				- sheErpDomainControlDomainSecondaryPort
				- sheErpDomainControlWaitToRestoreTime
				- sheErpDomainControlTestPacketInterval
				- sheErpDomainControlLearningDisabledTime
				- sheErpDomainControlDomainNodeMode
				- sheErpDomainControlDomainControlVlan
				- sheErpDomainControlLotpTrapEnable
				- sheErpDomainControlUlotpTrapEnable
				- sheErpDomainControlMultipleRmTrapEnable
				- sheErpDomainControlRmReachTrapEnable
				- sheErpDomainControlAlarmSeverityIndex
				
				activateErpDomain(827)
				- sheErpDomainControlDomainIndex
				- sheErpDomainControlProtectionActivation
				
				operatorRequestErpDomain(828)
				- sheErpDomainControlDomainIndex
				- sheErpDomainControlOperatorRequest
				"
			::= { sheErpDomainControl 1 }

		
--   1.3.6.1.4.1.231.7.1.2.2.1.4.9.2.2.2
		sheErpDomainControlStatus OBJECT-TYPE
			SYNTAX SheControlStatusType
			MAX-ACCESS read-only
			STATUS current
			DESCRIPTION
				"Describes the status of a user command group, used
				for block commands while a command execution
				is in process.
				Values : idle, busy, passed, failed.
				idle: default, no command in process
				busy: command execution in process, attempts to start
				      another user command on this control block
				      are rejected
				passed/failed: status at end of command"
			::= { sheErpDomainControl 2 }

		
--   1.3.6.1.4.1.231.7.1.2.2.1.4.9.2.2.3
		sheErpDomainControlTimestamp OBJECT-TYPE
			SYNTAX Unsigned32
			UNITS "sec"
			MAX-ACCESS read-only
			STATUS current
			DESCRIPTION
				"Time stamp attribute set at the end of a command."
			::= { sheErpDomainControl 3 }

		
--   1.3.6.1.4.1.231.7.1.2.2.1.4.9.2.2.4
		sheErpDomainControlReqResult OBJECT-TYPE
			SYNTAX SheBridgeControlReqResultType
			MAX-ACCESS read-only
			STATUS current
			DESCRIPTION
				"Command result (error code) attribute."
			::= { sheErpDomainControl 4 }

		
--   1.3.6.1.4.1.231.7.1.2.2.1.4.9.2.2.5
		sheErpDomainControlTimer OBJECT-TYPE
			SYNTAX Unsigned32
			MAX-ACCESS read-only
			STATUS current
			DESCRIPTION
				"Maximum command execution time (timeout) in seconds
				in case of a long running command."
			::= { sheErpDomainControl 5 }

		
--   1.3.6.1.4.1.231.7.1.2.2.1.4.9.2.2.6
		sheErpDomainControlDomainIndex OBJECT-TYPE
			SYNTAX Unsigned32 (1..64)
			MAX-ACCESS read-write
			STATUS current
			DESCRIPTION
				"An index value that uniquely identifies an ERP domain.
				parameter for
				- modifyErpDomainEntry
				- modifyErpDomainTraps
				- activateErpDomain
				- operatorRequestErpDomain"
			::= { sheErpDomainControl 6 }

		
--   1.3.6.1.4.1.231.7.1.2.2.1.4.9.2.2.7
		sheErpDomainControlDomainName OBJECT-TYPE
			SYNTAX DisplayString
			MAX-ACCESS read-write
			STATUS current
			DESCRIPTION
				"The associated name of the ERP Domain.
				Spaces and other special characters (: o) are not allowed!! 
				parameter for
				- modifyErpDomainEntry"
			::= { sheErpDomainControl 7 }

		
--   1.3.6.1.4.1.231.7.1.2.2.1.4.9.2.2.8
		sheErpDomainControlDomainPrimaryPort OBJECT-TYPE
			SYNTAX SheBridgePortIndexOrInvalid
			MAX-ACCESS read-write
			STATUS current
			DESCRIPTION
				"The sheBridgePortIndex of the sheBridgePortTable
				that represents the primary port of the ERP domain.
				The allowed range is 1-65535. Only Ethernet interfaces
				possible. The value -1 is used to indicate that
				it is unassigned (Invalid).
				parameter for
				- modifyErpDomainEntry"
			::= { sheErpDomainControl 8 }

		
--   1.3.6.1.4.1.231.7.1.2.2.1.4.9.2.2.9
		sheErpDomainControlDomainSecondaryPort OBJECT-TYPE
			SYNTAX SheBridgePortIndexOrInvalid
			MAX-ACCESS read-write
			STATUS current
			DESCRIPTION
				"The sheBridgePortIndex of the sheBridgePortTable
				that represents the secondary port of the ERP domain.
				The allowed range is 1-65535. Only Ethernet interfaces
				possible. The value -1 is used to indicate that
				it is unassigned (Invalid).
				parameter for
				- modifyErpDomainEntry"
			::= { sheErpDomainControl 9 }

		
--   1.3.6.1.4.1.231.7.1.2.2.1.4.9.2.2.10
		sheErpDomainControlWaitToRestoreTime OBJECT-TYPE
			SYNTAX Unsigned32 (2..720)
			UNITS "1 s"
			MAX-ACCESS read-write
			STATUS current
			DESCRIPTION
				"Time in seconds taken to verify that ring integrity is
				maintained before switch to Idle state after all links
				have recovered from Link Failure, Link Degrade or
				Loss of Test Packet.
				parameter for
				- modifyErpDomainEntry"
			::= { sheErpDomainControl 10 }

		
--   1.3.6.1.4.1.231.7.1.2.2.1.4.9.2.2.11
		sheErpDomainControlTestPacketInterval OBJECT-TYPE
			SYNTAX Unsigned32 (10..500)
			UNITS "1 ms"
			MAX-ACCESS read-write
			STATUS current
			DESCRIPTION
				"Time interval , in milliseconds, between consecutive
				transmission of test packets. The Test Packet Interval
				is used to define the time to initiate protection due to
				Loss of Test Packets, The value of Test Packet Interval
				is between 10 ms and 500 ms in 10 ms steps.
				parameter for
				- modifyErpDomainEntry"
			::= { sheErpDomainControl 11 }

		
--   1.3.6.1.4.1.231.7.1.2.2.1.4.9.2.2.12
		sheErpDomainControlLearningDisabledTime OBJECT-TYPE
			SYNTAX Unsigned32 (0..500)
			UNITS "1 ms"
			MAX-ACCESS read-write
			STATUS current
			DESCRIPTION
				"Configures the time during which learning is disabled
				after a FDB flush. The learning is only disabled for the
				protected VLAN of the domain on the ERP ports.
				The value of the Learning Disabled Time is between
				0 and 500 ms in steps of 10 ms.
				parameter for
				- modifyErpDomainEntry"
			::= { sheErpDomainControl 12 }

		
--   1.3.6.1.4.1.231.7.1.2.2.1.4.9.2.2.13
		sheErpDomainControlProtectionActivation OBJECT-TYPE
			SYNTAX ShePermissionType
			MAX-ACCESS read-write
			STATUS current
			DESCRIPTION
				"Represents if ERP Protection activation is activated or
				deactivated. When the ERP domain is activated the ERP
				process will start running. All alarms/traps are cleared
				and the ERP protection state is reported as unknown.
				The domain will enter deactivated state. The ERP
				protection activation default value is deactivated.
				deny(0)   - protection inactive
				permit(1) - protection active
				parameter for
				- activateErpDomain"
			::= { sheErpDomainControl 13 }

		
--   1.3.6.1.4.1.231.7.1.2.2.1.4.9.2.2.14
		sheErpDomainControlOperatorRequest OBJECT-TYPE
			SYNTAX SheErpDomainOperatorRequestType
			MAX-ACCESS read-write
			STATUS current
			DESCRIPTION
				"Two operators requests are possible for one ERP domain.
				For Normal nodes operator requests are ignored.
				manualToSecondary(1) - Manual Switch to Secondary port -
				This command enables to swap the roles of primary and
				secondary port on the RM Node.
				clear(2) - Clear -
				This command disables a previous Manual Switch to
				Secondary port.
				parameter for
				- operatorRequestErpDomain"
			::= { sheErpDomainControl 14 }

		
--   1.3.6.1.4.1.231.7.1.2.2.1.4.9.2.2.15
		sheErpDomainControlDomainNodeMode OBJECT-TYPE
			SYNTAX SheErpNodeType
			MAX-ACCESS read-write
			STATUS current
			DESCRIPTION
				"An ERP domain may operate in two modes. RM Node or Normal
				Node. The description of these two modes is included in
				ERP concept specification. Only one node per domain
				could be a rm node.
				normalNode(1)
				rmNode(2)
				parameter for
				- modifyErpDomainEntry
				"
			::= { sheErpDomainControl 15 }

		
--   1.3.6.1.4.1.231.7.1.2.2.1.4.9.2.2.16
		sheErpDomainControlDomainControlVlan OBJECT-TYPE
			SYNTAX SheVlanIdOrInvalid
			MAX-ACCESS read-write
			STATUS current
			DESCRIPTION
				"Represents the VLAN ID sheVlanIndex of the control VLAN
				of the domain. The control VLAN may not be used in other
				domains as control VLAN or as protected VLAN. The control
				VLAN must be a VLAN with a high priority QoS profile.
				parameter for
				- modifyErpDomainEntry"
			::= { sheErpDomainControl 16 }

		
--   1.3.6.1.4.1.231.7.1.2.2.1.4.9.2.2.17
		sheErpDomainControlLotpTrapEnable OBJECT-TYPE
			SYNTAX ShePermissionType
			MAX-ACCESS read-write
			STATUS current
			DESCRIPTION
				"Erp domain Loss of Test Packet Trap.
				Configures sending OF LOTP traps when detected by the
				RM node.
				deny(0)
				permit(1)
				parameter for
				- modifyErpDomainEntry"
			::= { sheErpDomainControl 17 }

		
--   1.3.6.1.4.1.231.7.1.2.2.1.4.9.2.2.18
		sheErpDomainControlUlotpTrapEnable OBJECT-TYPE
			SYNTAX ShePermissionType
			MAX-ACCESS read-write
			STATUS current
			DESCRIPTION
				"Erp domain Unidirectional Loss of Test Packet Trap.
				Configures sending of ULOTP traps when detected by the
				RM node.
				deny(0)
				permit(1)
				parameter for
				- modifyErpDomainEntry"
			::= { sheErpDomainControl 18 }

		
--   1.3.6.1.4.1.231.7.1.2.2.1.4.9.2.2.19
		sheErpDomainControlMultipleRmTrapEnable OBJECT-TYPE
			SYNTAX ShePermissionType
			MAX-ACCESS read-write
			STATUS current
			DESCRIPTION
				"Erp domain multiple RM nodes Trap.
				Configures sending of MultipleRM traps when detected by
				the RM node.
				deny(0)
				permit(1)
				parameter for
				- modifyErpDomainEntry"
			::= { sheErpDomainControl 19 }

		
--   1.3.6.1.4.1.231.7.1.2.2.1.4.9.2.2.20
		sheErpDomainControlRmReachTrapEnable OBJECT-TYPE
			SYNTAX ShePermissionType
			MAX-ACCESS read-write
			STATUS current
			DESCRIPTION
				"Erp domain multiple failures trap.
				Configures sending of RMNodeReacheablility traps when
				detected by the normal node.
				deny(0)
				permit(1)
				parameter for
				- modifyErpDomainEntry"
			::= { sheErpDomainControl 20 }

		
--   1.3.6.1.4.1.231.7.1.2.2.1.4.9.2.2.21
		sheErpDomainControlAlarmSeverityIndex OBJECT-TYPE
			SYNTAX SheAlarmSevProfileIndex
			MAX-ACCESS read-write
			STATUS current
			DESCRIPTION
				"Index to the AlarmSeverityProfileTable. Defines the
				actual AlarmSeverities for all alarms per ERP domain.
				parameter for
				- modifyErpDomainEntry"
			::= { sheErpDomainControl 21 }

		
		sheErpDomainGlobalGroup OBJECT IDENTIFIER ::= { sheErpDomain 3 }

		
		sheErpDomainGlobalMacLearningDelay OBJECT-TYPE
			SYNTAX SheEnableType
			MAX-ACCESS read-only
			STATUS current
			DESCRIPTION
				"Enable / disable the MAC learning delay globaly.
				Default: disable
				When this parameter is set to enable, ERP enhancement solution will be actived. 
				ERP module will apply hardware MAC learning after FDB flush. if this parameter is set to disable, 
				ERP module will work the same as before."
			::= { sheErpDomainGlobalGroup 1 }

		
		sheErpDomainGlobalMacLearningDelayTimer OBJECT-TYPE
			SYNTAX Unsigned32
			UNITS "10 msec"
			MAX-ACCESS read-only
			STATUS current
			DESCRIPTION
				"Configure the MAC learning delay time.
				Value range: 10~to be defined, the increasement granularity is 10 ms
				default: to be defined.
				This parameter specify how long the hardware MAC learning will last 
				in condition that sheErpDomainMacLearningDelay is enabled."
			::= { sheErpDomainGlobalGroup 2 }

		
		sheErpDomainGlobalControl OBJECT IDENTIFIER ::= { sheErpDomain 4 }

		
		sheErpDomainGlobalControlRequest OBJECT-TYPE
			SYNTAX SheBridgeControlRequestType
			MAX-ACCESS read-write
			STATUS current
			DESCRIPTION
				"A SetRequest on this attribute starts a command
				execution process in the NetElement.
				
				modifyErpDomainGlobalGroup(829)
				parameters:
				sheErpDomainGlobalMacLearningDelay   
				sheErpDomainGolobalMacLearningDelayTimer"
			::= { sheErpDomainGlobalControl 1 }

		
		sheErpDomainGlobalControlStatus OBJECT-TYPE
			SYNTAX SheControlStatusType
			MAX-ACCESS read-only
			STATUS current
			DESCRIPTION
				"Describes the status of a user command group, used
				for block commands while a command execution
				is in process.
				Values : idle, busy, passed, failed.
				idle: default, no command in process
				busy: command execution in process, attempts to start
				      another user command on this control block
				      are rejected
				passed/failed: status at end of command"
			::= { sheErpDomainGlobalControl 2 }

		
		sheErpDomainGlobalControlTimestamp OBJECT-TYPE
			SYNTAX Unsigned32
			UNITS "sec"
			MAX-ACCESS read-only
			STATUS current
			DESCRIPTION
				"Time stamp attribute set at the end of a command."
			::= { sheErpDomainGlobalControl 3 }

		
		sheErpDomainGlobalControlReqResult OBJECT-TYPE
			SYNTAX SheBridgeControlReqResultType
			MAX-ACCESS read-only
			STATUS current
			DESCRIPTION
				"Command result (error code) attribute."
			::= { sheErpDomainGlobalControl 4 }

		
		sheErpDomainGlobalControlTimer OBJECT-TYPE
			SYNTAX Unsigned32
			MAX-ACCESS read-only
			STATUS current
			DESCRIPTION
				"Maximum command execution time (timeout) in seconds
				in case of a long running command."
			::= { sheErpDomainGlobalControl 5 }

		
		sheErpDomainGlobalControlMacLearningDelay OBJECT-TYPE
			SYNTAX SheEnableType
			MAX-ACCESS read-write
			STATUS current
			DESCRIPTION
				" Enable / disable the MAC learning delay globaly."
			::= { sheErpDomainGlobalControl 6 }

		
		sheErpDomainGlobalControlMacLearningDelayTimer OBJECT-TYPE
			SYNTAX Unsigned32
			UNITS "10 msec"
			MAX-ACCESS read-write
			STATUS current
			DESCRIPTION
				"Configure the MAC learning delay time."
			::= { sheErpDomainGlobalControl 7 }

		
--   1.3.6.1.4.1.231.7.1.2.2.1.4.9.3
		sheErpNotifications OBJECT IDENTIFIER ::= { sheErp 3 }

		
--   1.3.6.1.4.1.231.7.1.2.2.1.4.9.3.1
		sheErpEvents OBJECT IDENTIFIER ::= { sheErpNotifications 1 }

		
--   1.3.6.1.4.1.231.7.1.2.2.1.4.9.3.1.1
		sheErpDomainRingStatusChange NOTIFICATION-TYPE
			OBJECTS { sheErpDomainControlTimestamp, sheErpDomainControlDomainIndex, sheErpDomainRingStatus }
			STATUS current
			DESCRIPTION 
				"This trap is set whenever there is a change in the
				erpDomainRingStatus."
			::= { sheErpEvents 1 }

		
--   1.3.6.1.4.1.231.7.1.2.2.1.4.9.3.1.2
		sheErpDomainNodeStatusChange NOTIFICATION-TYPE
			OBJECTS { sheErpDomainControlTimestamp, sheErpDomainControlDomainIndex, sheErpDomainNodeStatus }
			STATUS current
			DESCRIPTION 
				"This trap is set whenever there is a change in the
				erpDomainNodeStatus."
			::= { sheErpEvents 2 }

		
--   1.3.6.1.4.1.231.7.1.2.2.1.4.9.3.1.3
		sheErpDomainTrafficVlanModified NOTIFICATION-TYPE
			OBJECTS { sheErpBaseControlTimestamp, sheErpDomainTrafficVlan }
			STATUS current
			DESCRIPTION 
				"Mapping of ERP domains to traffic VLANs modified."
			::= { sheErpEvents 3 }

		
--   1.3.6.1.4.1.231.7.1.2.2.1.4.9.3.1.4
		sheErpDomainEntryModified NOTIFICATION-TYPE
			OBJECTS { sheErpDomainControlTimestamp, sheErpDomainControlDomainIndex, sheErpDomainName, sheErpDomainPrimaryPort, sheErpDomainSecondaryPort, 
				sheErpDomainWaitToRestoreTime, sheErpDomainTestPacketInterval, sheErpDomainLearningDisabledTime, sheErpDomainNodeMode, sheErpDomainControlVlan, 
				sheErpDomainLotpTrapEnable, sheErpDomainUlotpTrapEnable, sheErpDomainMultipleRmTrapEnable, sheErpDomainRmReachTrapEnable, sheErpDomainAlarmSeverityIndex
				 }
			STATUS current
			DESCRIPTION 
				"ERP domain entry modified."
			::= { sheErpEvents 4 }

		
--   1.3.6.1.4.1.231.7.1.2.2.1.4.9.3.1.5
		sheErpDomainProtectionModified NOTIFICATION-TYPE
			OBJECTS { sheErpDomainControlTimestamp, sheErpDomainControlDomainIndex, sheErpDomainProtectionActivation }
			STATUS current
			DESCRIPTION 
				"The ERP domain activation has been modified
				by the operator."
			::= { sheErpEvents 5 }

		
--   1.3.6.1.4.1.231.7.1.2.2.1.4.9.3.1.6
		sheErpDomainManualSwitch NOTIFICATION-TYPE
			OBJECTS { sheErpDomainControlTimestamp, sheErpDomainControlDomainIndex, sheErpDomainOperatorRequest }
			STATUS current
			DESCRIPTION 
				"The ERP domain RM node port swap has been modified
				by the operator."
			::= { sheErpEvents 6 }

		
		sheErpDomainGlobalGroupModified NOTIFICATION-TYPE
			OBJECTS { sheErpDomainGlobalControlTimestamp, sheErpDomainGlobalControlReqResult, sheErpDomainGlobalControlMacLearningDelay, sheErpDomainGlobalControlMacLearningDelayTimer }
			STATUS current
			DESCRIPTION 
				"Modify global parameters of ERP domain."
			::= { sheErpEvents 7 }

		
--   1.3.6.1.4.1.231.7.1.2.2.1.4.9.3.2
		sheErpAlarms OBJECT IDENTIFIER ::= { sheErpNotifications 2 }

		
--   1.3.6.1.4.1.231.7.1.2.2.1.4.9.3.2.1
		sheErpDomainLotpAlmTrap NOTIFICATION-TYPE
			OBJECTS { sheAlarmTimeAndDate, sheAlarmReportingSource, sheAlarmReportingSourceType, sheAlarmSeverity }
			STATUS current
			DESCRIPTION 
				"Loss of TestPackets state change trap."
			::= { sheErpAlarms 1 }

		
--   1.3.6.1.4.1.231.7.1.2.2.1.4.9.3.2.2
		sheErpDomainUlotpAlmTrap NOTIFICATION-TYPE
			OBJECTS { sheAlarmTimeAndDate, sheAlarmReportingSource, sheAlarmReportingSourceType, sheAlarmSeverity }
			STATUS current
			DESCRIPTION 
				"Unidirectional Loss of TestPackets state change trap."
			::= { sheErpAlarms 2 }

		
--   1.3.6.1.4.1.231.7.1.2.2.1.4.9.3.2.3
		sheErpDomainMultipleRmAlmTrap NOTIFICATION-TYPE
			OBJECTS { sheAlarmTimeAndDate, sheAlarmReportingSource, sheAlarmReportingSourceType, sheAlarmSeverity }
			STATUS current
			DESCRIPTION 
				"Multiple RM state change trap."
			::= { sheErpAlarms 3 }

		
--   1.3.6.1.4.1.231.7.1.2.2.1.4.9.3.2.4
		sheErpDomainRmReachAlmTrap NOTIFICATION-TYPE
			OBJECTS { sheAlarmTimeAndDate, sheAlarmReportingSource, sheAlarmReportingSourceType, sheAlarmSeverity }
			STATUS current
			DESCRIPTION 
				"Rm Node Unreacheable state change trap."
			::= { sheErpAlarms 4 }

		
--   1.3.6.1.4.1.231.7.1.2.2.1.4.9.4
		sheErpConformance OBJECT IDENTIFIER ::= { sheErp 100 }

		
--   1.3.6.1.4.1.231.7.1.2.2.1.4.9.4.1
		sheErpCompliances OBJECT IDENTIFIER ::= { sheErpConformance 1 }

		
--   1.3.6.1.4.1.231.7.1.2.2.1.4.9.4.1.1
-- this module
-- this module
		sheErpCompliance MODULE-COMPLIANCE
			STATUS current
			DESCRIPTION 
				"Description."
			MODULE -- this module
				MANDATORY-GROUPS { sheErpBaseGroup, sheErpBaseControlGroup, sheErpDomainGroup, sheErpDomainControlGroup, sheErpNotificationGroup
					 }
			::= { sheErpCompliances 1 }

		
--   1.3.6.1.4.1.231.7.1.2.2.1.4.9.4.2
		sheErpGroups OBJECT IDENTIFIER ::= { sheErpConformance 2 }

		
--   1.3.6.1.4.1.231.7.1.2.2.1.4.9.4.2.1
		sheErpBaseGroup OBJECT-GROUP
			OBJECTS { sheErpDomainTrafficVlan }
			STATUS current
			DESCRIPTION 
				"Description."
			::= { sheErpGroups 1 }

		
--   1.3.6.1.4.1.231.7.1.2.2.1.4.9.4.2.2
		sheErpBaseControlGroup OBJECT-GROUP
			OBJECTS { sheErpBaseControlRequest, sheErpBaseControlStatus, sheErpBaseControlTimestamp, sheErpBaseControlReqResult, sheErpBaseControlTimer, 
				sheErpBaseControlDomainTrafficVlan }
			STATUS current
			DESCRIPTION 
				"Description."
			::= { sheErpGroups 2 }

		
--   1.3.6.1.4.1.231.7.1.2.2.1.4.9.4.2.3
		sheErpDomainGroup OBJECT-GROUP
			OBJECTS { sheErpDomainIndex, sheErpDomainName, sheErpDomainPrimaryPort, sheErpDomainSecondaryPort, sheErpDomainWaitToRestoreTime, 
				sheErpDomainTestPacketInterval, sheErpDomainLearningDisabledTime, sheErpDomainProtectionActivation, sheErpDomainOperatorRequest, sheErpDomainNodeMode, 
				sheErpDomainControlVlan, sheErpDomainNodeStatus, sheErpDomainRingStatus, sheErpDomainLotp, sheErpDomainUlotp, 
				sheErpDomainMultipleRm, sheErpDomainRmReach, sheErpDomainLotpTrapEnable, sheErpDomainUlotpTrapEnable, sheErpDomainMultipleRmTrapEnable, 
				sheErpDomainRmReachTrapEnable, sheErpDomainAlarmSeverityIndex, sheErpDomainGlobalMacLearningDelay, sheErpDomainGlobalMacLearningDelayTimer }
			STATUS current
			DESCRIPTION 
				"Description."
			::= { sheErpGroups 3 }

		
--   1.3.6.1.4.1.231.7.1.2.2.1.4.9.4.2.4
		sheErpDomainControlGroup OBJECT-GROUP
			OBJECTS { sheErpDomainControlRequest, sheErpDomainControlStatus, sheErpDomainControlTimestamp, sheErpDomainControlReqResult, sheErpDomainControlTimer, 
				sheErpDomainControlDomainIndex, sheErpDomainControlDomainName, sheErpDomainControlDomainPrimaryPort, sheErpDomainControlDomainSecondaryPort, sheErpDomainControlWaitToRestoreTime, 
				sheErpDomainControlTestPacketInterval, sheErpDomainControlLearningDisabledTime, sheErpDomainControlProtectionActivation, sheErpDomainControlOperatorRequest, sheErpDomainControlDomainNodeMode, 
				sheErpDomainControlDomainControlVlan, sheErpDomainControlLotpTrapEnable, sheErpDomainControlUlotpTrapEnable, sheErpDomainControlMultipleRmTrapEnable, sheErpDomainControlRmReachTrapEnable, 
				sheErpDomainControlAlarmSeverityIndex, sheErpDomainGlobalControlRequest, sheErpDomainGlobalControlStatus, sheErpDomainGlobalControlTimestamp, sheErpDomainGlobalControlReqResult, 
				sheErpDomainGlobalControlTimer, sheErpDomainGlobalControlMacLearningDelay, sheErpDomainGlobalControlMacLearningDelayTimer }
			STATUS current
			DESCRIPTION 
				"Description."
			::= { sheErpGroups 4 }

		
--   1.3.6.1.4.1.231.7.1.2.2.1.4.9.4.2.5
		sheErpNotificationGroup NOTIFICATION-GROUP
			NOTIFICATIONS { sheErpDomainTrafficVlanModified, sheErpDomainEntryModified, sheErpDomainLotpAlmTrap, sheErpDomainUlotpAlmTrap, sheErpDomainMultipleRmAlmTrap, 
				sheErpDomainRmReachAlmTrap, sheErpDomainProtectionModified, sheErpDomainManualSwitch, sheErpDomainNodeStatusChange, sheErpDomainRingStatusChange, 
				sheErpDomainGlobalGroupModified }
			STATUS current
			DESCRIPTION 
				"Description."
			::= { sheErpGroups 5 }

		
--   1.3.6.1.4.1.231.7.1.2.2.1.4.10
		sheBcsc OBJECT IDENTIFIER ::= { sheBridgeMib 10 }

		
--   1.3.6.1.4.1.231.7.1.2.2.1.4.10.1
		sheBcscTable OBJECT-TYPE
			SYNTAX SEQUENCE OF SheBcscEntry
			MAX-ACCESS not-accessible
			STATUS current
			DESCRIPTION
				"This table has one entry for each combination of
				port or vlan and traffic type where broadcast
				storm control has to be performed."
			::= { sheBcsc 1 }

		
--   1.3.6.1.4.1.231.7.1.2.2.1.4.10.1.1
		sheBcscEntry OBJECT-TYPE
			SYNTAX SheBcscEntry
			MAX-ACCESS not-accessible
			STATUS current
			DESCRIPTION
				"Specifies per port or vlan and per traffic type the
				broadcast storm control parameters, i.e. how many
				packets/bits per second can be received."
			INDEX { sheBcscIndex }
			::= { sheBcscTable 1 }

		
		SheBcscEntry ::=
			SEQUENCE { 
				sheBcscIndex
					Unsigned32,
				sheBcscType
					SheBcscTrafficType,
				sheBcscConfigScope
					SheBcscScopeType,
				sheBcscConfigIndex
					Unsigned32,
				sheBcscThresholdType
					SheBcscThresholdType,
				sheBcscThresholdValue
					Unsigned32,
				sheBcscVendorSpecific
					OCTET STRING,
				sheBcscAlarmDebounceTimer
					Unsigned32,
				sheBcscAlarmSeverityIndex
					SheAlarmSevProfileIndex
			 }

--   1.3.6.1.4.1.231.7.1.2.2.1.4.10.1.1.1
		sheBcscIndex OBJECT-TYPE
			SYNTAX Unsigned32 (1..65535)
			MAX-ACCESS read-only
			STATUS current
			DESCRIPTION
				"Primary key for the table."
			::= { sheBcscEntry 1 }

		
--   1.3.6.1.4.1.231.7.1.2.2.1.4.10.1.1.2
		sheBcscType OBJECT-TYPE
			SYNTAX SheBcscTrafficType
			MAX-ACCESS read-only
			STATUS current
			DESCRIPTION
				"Broadcast storm control traffic type.
				1 - Broadcast
				2 - Multicast
				3 - Destination Lookup Failure (unicast)"
			::= { sheBcscEntry 2 }

		
--   1.3.6.1.4.1.231.7.1.2.2.1.4.10.1.1.3
		sheBcscConfigScope OBJECT-TYPE
			SYNTAX SheBcscScopeType
			MAX-ACCESS read-only
			STATUS current
			DESCRIPTION
				"Type of the controlled entity, 
				defines the meaning of sheBcscConfigIndex.
				1 - port
				2 - vlan
				"
			::= { sheBcscEntry 3 }

		
--   1.3.6.1.4.1.231.7.1.2.2.1.4.10.1.1.4
		sheBcscConfigIndex OBJECT-TYPE
			SYNTAX Unsigned32 (1..65535)
			MAX-ACCESS read-only
			STATUS current
			DESCRIPTION
				"Index of the controlled entity.
				In case of port scope, it should be sheBridgePortIndex
				of the sheBridgePortTable and the allowed range is 1-65535.
				In case of vlan scope, it should be sheVlanIndex
				of the sheVlanTable and the allowed range is 1-4093."
			::= { sheBcscEntry 4 }

		
--   1.3.6.1.4.1.231.7.1.2.2.1.4.10.1.1.5
		sheBcscThresholdType OBJECT-TYPE
			SYNTAX SheBcscThresholdType
			MAX-ACCESS read-only
			STATUS current
			DESCRIPTION
				"Defines the counter type, i.e. the meaning
				of the sheBcscThresholdValue.
				1 - packets per second
				2 - bytes per second"
			::= { sheBcscEntry 5 }

		
--   1.3.6.1.4.1.231.7.1.2.2.1.4.10.1.1.6
		sheBcscThresholdValue OBJECT-TYPE
			SYNTAX Unsigned32
			MAX-ACCESS read-only
			STATUS current
			DESCRIPTION
				"Maximum traffic amount of type sheBcscThresholdType.
				If the threshold of a traffic type is reached within
				the 1 second measuring interval, further traffic of
				that type is dropped during the next time period.
				The switch continues to monitor traffic on the port,
				and when the utilization level is below the threshold
				level, the type of traffic that was dropped is
				forwarded again during the next time period."
			::= { sheBcscEntry 6 }

		
--   1.3.6.1.4.1.231.7.1.2.2.1.4.10.1.1.7
		sheBcscVendorSpecific OBJECT-TYPE
			SYNTAX OCTET STRING (SIZE (0..6))
			MAX-ACCESS read-only
			STATUS current
			DESCRIPTION
				"For some vendors, multicast address can be specified."
			::= { sheBcscEntry 7 }

		
--   1.3.6.1.4.1.231.7.1.2.2.1.4.10.1.1.8
		sheBcscAlarmDebounceTimer OBJECT-TYPE
			SYNTAX Unsigned32
			MAX-ACCESS read-only
			STATUS current
			DESCRIPTION
				"The minimum time between two alarm traps sent by the
				BSCS instance."
			::= { sheBcscEntry 8 }

		
--   1.3.6.1.4.1.231.7.1.2.2.1.4.10.1.1.9
		sheBcscAlarmSeverityIndex OBJECT-TYPE
			SYNTAX SheAlarmSevProfileIndex
			MAX-ACCESS read-only
			STATUS current
			DESCRIPTION
				"Index to the AlarmSeverityProfileTable. Defines the
				actual AlarmSeverities for all alarms per BSCS instance."
			::= { sheBcscEntry 9 }

		
--   1.3.6.1.4.1.231.7.1.2.2.1.4.10.2
		sheBcscControl OBJECT IDENTIFIER ::= { sheBcsc 2 }

		
--   1.3.6.1.4.1.231.7.1.2.2.1.4.10.2.1
		sheBcscControlRequest OBJECT-TYPE
			SYNTAX SheBridgeControlRequestType
			MAX-ACCESS read-write
			STATUS current
			DESCRIPTION
				"A SetRequest on this attribute starts a command
				execution process in the NetElement.
				
				501 - createBcscEntry
				parameters:
				sheBcscControlType
				sheBcscControlConfigScope
				sheBcscControlConfigIndex
				sheBcscControlThresholdType
				sheBcscControlThresholdValue
				sheBcscControlVendorSpecific
				sheBcscControlAlarmDebounceTimer
				sheBcscControlAlarmSeverityIndex
				502 - modifyBcscEntry
				parameters:
				sheBcscControlIndex
				sheBcscControlType
				sheBcscControlThresholdType
				sheBcscControlThresholdValue
				sheBcscControlVendorSpecific
				sheBcscControlAlarmDebounceTimer
				sheBcscControlAlarmSeverityIndex
				
				503 - deleteBcscEntry
				parameters:
				sheBcscControlIndex"
			::= { sheBcscControl 1 }

		
--   1.3.6.1.4.1.231.7.1.2.2.1.4.10.2.2
		sheBcscControlStatus OBJECT-TYPE
			SYNTAX SheControlStatusType
			MAX-ACCESS read-only
			STATUS current
			DESCRIPTION
				"Describes the status of a user command group, used
				for block commands while a command execution
				is in process.
				Values : idle, busy, passed, failed.
				idle: default, no command in process
				busy: command execution in process, attempts to start
				      another user command on this control block
				      are rejected
				passed/failed: status at end of command"
			::= { sheBcscControl 2 }

		
--   1.3.6.1.4.1.231.7.1.2.2.1.4.10.2.3
		sheBcscControlTimestamp OBJECT-TYPE
			SYNTAX Unsigned32
			UNITS "sec"
			MAX-ACCESS read-only
			STATUS current
			DESCRIPTION
				"Time stamp attribute set at the end of a command."
			::= { sheBcscControl 3 }

		
--   1.3.6.1.4.1.231.7.1.2.2.1.4.10.2.4
		sheBcscControlReqResult OBJECT-TYPE
			SYNTAX SheBridgeControlReqResultType
			MAX-ACCESS read-only
			STATUS current
			DESCRIPTION
				"Command result (error code) attribute."
			::= { sheBcscControl 4 }

		
--   1.3.6.1.4.1.231.7.1.2.2.1.4.10.2.5
		sheBcscControlTimer OBJECT-TYPE
			SYNTAX Unsigned32
			MAX-ACCESS read-only
			STATUS current
			DESCRIPTION
				"Maximum command execution time (timeout) in seconds
				in case of a long running command."
			::= { sheBcscControl 5 }

		
--   1.3.6.1.4.1.231.7.1.2.2.1.4.10.2.6
		sheBcscControlIndex OBJECT-TYPE
			SYNTAX Unsigned32
			MAX-ACCESS read-write
			STATUS current
			DESCRIPTION
				"Primary key for the table, created by the NE.
				Parameter for
				502 - modifyBcscEntry
				503 - deleteBcscEntry"
			::= { sheBcscControl 6 }

		
--   1.3.6.1.4.1.231.7.1.2.2.1.4.10.2.7
		sheBcscControlType OBJECT-TYPE
			SYNTAX SheBcscTrafficType
			MAX-ACCESS read-write
			STATUS current
			DESCRIPTION
				"Broadcast storm control traffic type.
				1 - Broadcast
				2 - Multicast
				3 - Destination Lookup Failure (unicast)
				Parameter for
				501 - createBcscEntry
				502 - modifyBcscEntry"
			::= { sheBcscControl 7 }

		
--   1.3.6.1.4.1.231.7.1.2.2.1.4.10.2.8
		sheBcscControlConfigScope OBJECT-TYPE
			SYNTAX SheBcscScopeType
			MAX-ACCESS read-write
			STATUS current
			DESCRIPTION
				"Type of the controlled entity, 
				defines the meaning of sheBcscConfigIndex.
				1 - port
				2 - vlan
				Parameter for
				501 - createBcscEntry
				
				"
			::= { sheBcscControl 8 }

		
--   1.3.6.1.4.1.231.7.1.2.2.1.4.10.2.9
		sheBcscControlConfigIndex OBJECT-TYPE
			SYNTAX Unsigned32 (1..65535)
			MAX-ACCESS read-write
			STATUS current
			DESCRIPTION
				"Index of the controlled entity.
				In case of port scope, it should be sheBridgePortIndex
				of the sheBridgePortTable and the allowed range is 1-65535.
				In case of vlan scope, it should be sheVlanIndex
				of the sheVlanTable and the allowed range is 1-4093.
				Parameter for
				501 - createBcscEntry
				"
			::= { sheBcscControl 9 }

		
--   1.3.6.1.4.1.231.7.1.2.2.1.4.10.2.10
		sheBcscControlThresholdType OBJECT-TYPE
			SYNTAX SheBcscThresholdType
			MAX-ACCESS read-write
			STATUS current
			DESCRIPTION
				"Defines the counter type, i.e. the meaning
				of the sheBcscThresholdValue.
				1 - packets per second
				2 - bytes per second
				Parameter for
				501 - createBcscEntry
				502 - modifyBcscEntry"
			::= { sheBcscControl 10 }

		
--   1.3.6.1.4.1.231.7.1.2.2.1.4.10.2.11
		sheBcscControlThresholdValue OBJECT-TYPE
			SYNTAX Unsigned32
			MAX-ACCESS read-write
			STATUS current
			DESCRIPTION
				"Maximum traffic amount of type sheBcscThresholdType.
				If the threshold of a traffic type is reached within
				the 1 second measuring interval, further traffic of
				that type is dropped during the next time period.
				The switch continues to monitor traffic on the port,
				and when the utilization level is below the threshold
				level, the type of traffic that was dropped is
				forwarded again during the next time period.
				Parameter for
				501 - createBcscEntry
				502 - modifyBcscEntry"
			::= { sheBcscControl 11 }

		
--   1.3.6.1.4.1.231.7.1.2.2.1.4.10.2.12
		sheBcscControlVendorSpecific OBJECT-TYPE
			SYNTAX OCTET STRING (SIZE (0..6))
			MAX-ACCESS read-write
			STATUS current
			DESCRIPTION
				"For some vendors, multicast address can be specified.
				Parameter for
				501 - createBcscEntry
				502 - modifyBcscEntry"
			::= { sheBcscControl 12 }

		
--   1.3.6.1.4.1.231.7.1.2.2.1.4.10.2.13
		sheBcscControlAlarmDebounceTimer OBJECT-TYPE
			SYNTAX Integer32
			MAX-ACCESS read-write
			STATUS current
			DESCRIPTION
				"The minimum time between two alarm traps sent by the
				BSCS instance.
				Parameter for
				501 - createBcscEntry
				502 - modifyBcscEntry"
			::= { sheBcscControl 13 }

		
--   1.3.6.1.4.1.231.7.1.2.2.1.4.10.2.14
		sheBcscControlAlarmSeverityIndex OBJECT-TYPE
			SYNTAX Integer32
			MAX-ACCESS read-write
			STATUS current
			DESCRIPTION
				"Index to the AlarmSeverityProfileTable. Defines the
				actual AlarmSeverities for all alarms per BSCS instance.
				Parameter for
				501 - createBcscEntry
				502 - modifyBcscEntry"
			::= { sheBcscControl 14 }

		
--   1.3.6.1.4.1.231.7.1.2.2.1.4.10.3
		sheBcscNotifications OBJECT IDENTIFIER ::= { sheBcsc 3 }

		
--   1.3.6.1.4.1.231.7.1.2.2.1.4.10.3.1
		sheBcscEvents OBJECT IDENTIFIER ::= { sheBcscNotifications 1 }

		
--   1.3.6.1.4.1.231.7.1.2.2.1.4.10.3.1.1
		sheBcscEntryCreated NOTIFICATION-TYPE
			OBJECTS { sheBcscControlTimestamp, sheBcscControlIndex, sheBcscType, sheBcscConfigScope, sheBcscConfigIndex, 
				sheBcscThresholdType, sheBcscThresholdValue, sheBcscVendorSpecific, sheBcscAlarmDebounceTimer, sheBcscAlarmSeverityIndex
				 }
			STATUS current
			DESCRIPTION 
				"New entry in the sheBcscTable has been created."
			::= { sheBcscEvents 1 }

		
--   1.3.6.1.4.1.231.7.1.2.2.1.4.10.3.1.2
		sheBcscEntryModified NOTIFICATION-TYPE
			OBJECTS { sheBcscControlTimestamp, sheBcscControlIndex, sheBcscType, sheBcscConfigScope, sheBcscConfigIndex, 
				sheBcscThresholdType, sheBcscThresholdValue, sheBcscVendorSpecific, sheBcscAlarmDebounceTimer, sheBcscAlarmSeverityIndex
				 }
			STATUS current
			DESCRIPTION 
				"Existing entry in the sheBcscTable has been modified."
			::= { sheBcscEvents 2 }

		
--   1.3.6.1.4.1.231.7.1.2.2.1.4.10.3.1.3
		sheBcscEntryDeleted NOTIFICATION-TYPE
			OBJECTS { sheBcscControlTimestamp, sheBcscControlIndex }
			STATUS current
			DESCRIPTION 
				"Entry in the sheBcscTable has been deleted."
			::= { sheBcscEvents 3 }

		
--   1.3.6.1.4.1.231.7.1.2.2.1.4.10.3.2
		sheBcscAlarms OBJECT IDENTIFIER ::= { sheBcscNotifications 2 }

		
--   1.3.6.1.4.1.231.7.1.2.2.1.4.10.3.2.1
		sheBcscThresholdExceeded NOTIFICATION-TYPE
			OBJECTS { sheAlarmTimeAndDate, sheAlarmReportingSource, sheAlarmReportingSourceType, sheAlarmSeverity }
			STATUS current
			DESCRIPTION 
				"Maximum traffic amount has reached threshold within
				the 1 second measuring interval, further traffic of
				that type is dropped during the next time period."
			::= { sheBcscAlarms 1 }

		
--   1.3.6.1.4.1.231.7.1.2.2.1.4.10.4
		sheBcscConformance OBJECT IDENTIFIER ::= { sheBcsc 100 }

		
--   1.3.6.1.4.1.231.7.1.2.2.1.4.10.4.1
		sheBcscCompliances OBJECT IDENTIFIER ::= { sheBcscConformance 1 }

		
--   1.3.6.1.4.1.231.7.1.2.2.1.4.10.4.1.1
-- this module
-- this module
		sheBcscCompliance MODULE-COMPLIANCE
			STATUS current
			DESCRIPTION 
				"Description."
			MODULE -- this module
				MANDATORY-GROUPS { sheBcscGroup, sheBcscControlGroup, sheBcscNotificationGroup }
			::= { sheBcscCompliances 1 }

		
--   1.3.6.1.4.1.231.7.1.2.2.1.4.10.4.2
		sheBcscGroups OBJECT IDENTIFIER ::= { sheBcscConformance 2 }

		
--   1.3.6.1.4.1.231.7.1.2.2.1.4.10.4.2.1
		sheBcscGroup OBJECT-GROUP
			OBJECTS { sheBcscIndex, sheBcscType, sheBcscConfigScope, sheBcscConfigIndex, sheBcscThresholdType, 
				sheBcscThresholdValue, sheBcscVendorSpecific, sheBcscAlarmDebounceTimer, sheBcscAlarmSeverityIndex }
			STATUS current
			DESCRIPTION 
				"Description."
			::= { sheBcscGroups 1 }

		
--   1.3.6.1.4.1.231.7.1.2.2.1.4.10.4.2.2
		sheBcscControlGroup OBJECT-GROUP
			OBJECTS { sheBcscControlRequest, sheBcscControlStatus, sheBcscControlTimestamp, sheBcscControlReqResult, sheBcscControlTimer, 
				sheBcscControlIndex, sheBcscControlType, sheBcscControlConfigScope, sheBcscControlConfigIndex, sheBcscControlThresholdType, 
				sheBcscControlThresholdValue, sheBcscControlVendorSpecific, sheBcscControlAlarmDebounceTimer, sheBcscControlAlarmSeverityIndex }
			STATUS current
			DESCRIPTION 
				"Description."
			::= { sheBcscGroups 2 }

		
--   1.3.6.1.4.1.231.7.1.2.2.1.4.10.4.2.3
		sheBcscNotificationGroup NOTIFICATION-GROUP
			NOTIFICATIONS { sheBcscEntryCreated, sheBcscEntryModified, sheBcscEntryDeleted, sheBcscThresholdExceeded }
			STATUS current
			DESCRIPTION 
				"Description."
			::= { sheBcscGroups 3 }

		
--   1.3.6.1.4.1.231.7.1.2.2.1.4.11
		sheMstpConfig OBJECT IDENTIFIER ::= { sheBridgeMib 11 }

		
--   1.3.6.1.4.1.231.7.1.2.2.1.4.11.1
		sheMstpBase OBJECT IDENTIFIER ::= { sheMstpConfig 1 }

		
--   1.3.6.1.4.1.231.7.1.2.2.1.4.11.1.1
		sheMstpBaseParam OBJECT IDENTIFIER ::= { sheMstpBase 1 }

		
--   1.3.6.1.4.1.231.7.1.2.2.1.4.11.1.1.1
		sheMstpBaseStatus OBJECT-TYPE
			SYNTAX TruthValue
			MAX-ACCESS read-only
			STATUS current
			DESCRIPTION
				"Enable or disable spanning tree."
			::= { sheMstpBaseParam 1 }

		
--   1.3.6.1.4.1.231.7.1.2.2.1.4.11.1.1.2
		sheMstpBaseConfName OBJECT-TYPE
			SYNTAX OCTET STRING (SIZE (0..32))
			MAX-ACCESS read-only
			STATUS current
			DESCRIPTION
				"The MST configuration determines to which MST region
				Spaces and other special characters (: o) are not allowed!! 
				each switch belongs. The configuration includes the name
				of the region, the revision number, and the MST
				instance-to-VLAN assignment map.
				For two or more switches to be in the same MST region,
				they must have the same VLAN-to-instance mapping,
				the same configuration revision number,
				and the same name."
			::= { sheMstpBaseParam 2 }

		
--   1.3.6.1.4.1.231.7.1.2.2.1.4.11.1.1.3
		sheMstpBaseRevisionLevel OBJECT-TYPE
			SYNTAX Unsigned32 (0..65535)
			MAX-ACCESS read-only
			STATUS current
			DESCRIPTION
				"The MST configuration determines to which MST region
				each switch belongs. The configuration includes the name
				of the region, the revision number, and the MST
				instance-to-VLAN assignment map.
				For two or more switches to be in the same MST region,
				they must have the same VLAN-to-instance mapping,
				the same configuration revision number,
				and the same name.
				The range of the revision number is 0 to 65535."
			::= { sheMstpBaseParam 3 }

		
--   1.3.6.1.4.1.231.7.1.2.2.1.4.11.1.1.4
		sheMstpBaseConfIdVlanIdList OBJECT-TYPE
			SYNTAX OCTET STRING (SIZE (4096))
			MAX-ACCESS read-only
			STATUS current
			DESCRIPTION
				"The MST configuration determines to which MST region
				each switch belongs. The configuration includes the name
				of the region, the revision number, and the MST
				instance-to-VLAN assignment map.
				For two or more switches to be in the same MST region,
				they must have the same VLAN-to-instance mapping,
				the same configuration revision number,
				and the same name.
				The sheMstpBridgeProtoParamTable holds 32 static
				profile entries of spanning tree protocol parameters.
				A profile can be used on a per-VLAN basis.
				This octet String with 4096 octets maps VLANs to
				spanning tree protocol profiles:
				one octet containing the sheMstpBridgeProtoParamIndex
				per VLAN. The octet number is the sheVlanIndex.
				You can assign a VLAN to only one spanning-tree
				instance at a time.
				
				"
			::= { sheMstpBaseParam 4 }

		
--   1.3.6.1.4.1.231.7.1.2.2.1.4.11.1.2
		sheMstpBaseControl OBJECT IDENTIFIER ::= { sheMstpBase 2 }

		
--   1.3.6.1.4.1.231.7.1.2.2.1.4.11.1.2.1
		sheMstpBaseControlRequest OBJECT-TYPE
			SYNTAX SheBridgeControlRequestType
			MAX-ACCESS read-write
			STATUS current
			DESCRIPTION
				"A SetRequest on this attribute starts a command
				execution process in the NetElement.
				
				- modifyMstpBaseStatus
				  parameters:
				    sheMstpBaseControlBaseStatus
				
				- modifyMstpBaseConfig
				  parameters:
				    sheMstpBaseControlConfName
				    sheMstpBaseControlRevisionLevel
				
				- modifyMstpBaseConfIdVlanIdList
				  parameters:
				    sheMstpBaseControlConfIdVlanIdList"
			::= { sheMstpBaseControl 1 }

		
--   1.3.6.1.4.1.231.7.1.2.2.1.4.11.1.2.2
		sheMstpBaseControlStatus OBJECT-TYPE
			SYNTAX SheControlStatusType
			MAX-ACCESS read-only
			STATUS current
			DESCRIPTION
				"Describes the status of a user command group, used
				for block commands while a command execution
				is in process.
				Values : idle, busy, passed, failed.
				idle: default, no command in process
				busy: command execution in process, attempts to start
				      another user command on this control block
				      are rejected
				passed/failed: status at end of command"
			::= { sheMstpBaseControl 2 }

		
--   1.3.6.1.4.1.231.7.1.2.2.1.4.11.1.2.3
		sheMstpBaseControlTimestamp OBJECT-TYPE
			SYNTAX Unsigned32
			UNITS "sec"
			MAX-ACCESS read-only
			STATUS current
			DESCRIPTION
				"Time stamp attribute set at the end of a command."
			::= { sheMstpBaseControl 3 }

		
--   1.3.6.1.4.1.231.7.1.2.2.1.4.11.1.2.4
		sheMstpBaseControlReqResult OBJECT-TYPE
			SYNTAX SheBridgeControlReqResultType
			MAX-ACCESS read-only
			STATUS current
			DESCRIPTION
				"Command result (error code) attribute."
			::= { sheMstpBaseControl 4 }

		
--   1.3.6.1.4.1.231.7.1.2.2.1.4.11.1.2.5
		sheMstpBaseControlTimer OBJECT-TYPE
			SYNTAX Unsigned32
			MAX-ACCESS read-only
			STATUS current
			DESCRIPTION
				"Maximum command execution time (timeout) in seconds
				in case of a long running command."
			::= { sheMstpBaseControl 5 }

		
--   1.3.6.1.4.1.231.7.1.2.2.1.4.11.1.2.6
		sheMstpBaseControlBaseStatus OBJECT-TYPE
			SYNTAX TruthValue
			MAX-ACCESS read-write
			STATUS current
			DESCRIPTION
				"Enable or disable spanning tree.
				parameter of
				- modifyMstpBaseStatus"
			::= { sheMstpBaseControl 6 }

		
--   1.3.6.1.4.1.231.7.1.2.2.1.4.11.1.2.7
		sheMstpBaseControlConfName OBJECT-TYPE
			SYNTAX OCTET STRING (SIZE (0..32))
			MAX-ACCESS read-write
			STATUS current
			DESCRIPTION
				"The MST configuration determines to which MST region
				Spaces and other special characters (: o) are not allowed!! 
				each switch belongs. The configuration includes the name
				of the region, the revision number, and the MST
				instance-to-VLAN assignment map.
				For two or more switches to be in the same MST region,
				they must have the same VLAN-to-instance mapping,
				the same configuration revision number,
				and the same name.
				parameter of
				- modifyMstpBaseConfig"
			::= { sheMstpBaseControl 7 }

		
--   1.3.6.1.4.1.231.7.1.2.2.1.4.11.1.2.8
		sheMstpBaseControlRevisionLevel OBJECT-TYPE
			SYNTAX Unsigned32 (0..65535)
			MAX-ACCESS read-write
			STATUS current
			DESCRIPTION
				"The MST configuration determines to which MST region
				each switch belongs. The configuration includes the name
				of the region, the revision number, and the MST
				instance-to-VLAN assignment map.
				For two or more switches to be in the same MST region,
				they must have the same VLAN-to-instance mapping,
				the same configuration revision number,
				and the same name.
				The range of the revision number is 0 to 65535.
				parameter of
				- modifyMstpBaseConfig"
			::= { sheMstpBaseControl 8 }

		
--   1.3.6.1.4.1.231.7.1.2.2.1.4.11.1.2.9
		sheMstpBaseControlConfIdVlanIdList OBJECT-TYPE
			SYNTAX OCTET STRING (SIZE (4096))
			MAX-ACCESS read-write
			STATUS current
			DESCRIPTION
				"The MST configuration determines to which MST region
				each switch belongs. The configuration includes the name
				of the region, the revision number, and the MST
				instance-to-VLAN assignment map.
				For two or more switches to be in the same MST region,
				they must have the same VLAN-to-instance mapping,
				the same configuration revision number,
				and the same name.
				The sheMstpBridgeProtoParamTable holds 32 static
				profile entries of spanning tree protocol parameters.
				A profile can be used on a per-VLAN basis.
				This octet String with 4096 octets maps VLANs to
				spanning tree protocol profiles:
				one octet containing the sheMstpBridgeProtoParamIndex
				per VLAN. The octet number is the sheVlanIndex.
				You can assign a VLAN to only one spanning-tree
				instance at a time.
				parameter of
				- modifyMstpBaseConfIdVlanIdList"
			::= { sheMstpBaseControl 9 }

		
--   1.3.6.1.4.1.231.7.1.2.2.1.4.11.2
		sheMstp OBJECT IDENTIFIER ::= { sheMstpConfig 2 }

		
--   1.3.6.1.4.1.231.7.1.2.2.1.4.11.2.1
		sheMstpBridgeProtoParamTable OBJECT-TYPE
			SYNTAX SEQUENCE OF SheMstpBridgeProtoParamEntry
			MAX-ACCESS not-accessible
			STATUS current
			DESCRIPTION
				"One table entry holds a profile of spanning tree
				protocol parameters. A profile can be used on a
				per-VLAN basis. The table has 32 static entries."
			::= { sheMstp 1 }

		
--   1.3.6.1.4.1.231.7.1.2.2.1.4.11.2.1.1
		sheMstpBridgeProtoParamEntry OBJECT-TYPE
			SYNTAX SheMstpBridgeProtoParamEntry
			MAX-ACCESS not-accessible
			STATUS current
			DESCRIPTION
				"One table entry holds a profile of spanning tree
				protocol parameters. A profile can be used on a
				per-VLAN basis. The table has 32 static entries.
				Note that each MST region can only support up to 16
				spanning-tree instances."
			INDEX { sheMstpBridgeProtoParamIndex }
			::= { sheMstpBridgeProtoParamTable 1 }

		
		SheMstpBridgeProtoParamEntry ::=
			SEQUENCE { 
				sheMstpBridgeProtoParamIndex
					Unsigned32,
				sheMstpBridgeProtoParamBridgeId
					OCTET STRING,
				sheMstpBridgeProtoParamBridgePriority
					Unsigned32,
				sheMstpBridgeProtoParamTcTime
					TimeTicks,
				sheMstpBridgeProtoParamTcCount
					Counter32,
				sheMstpBridgeProtoParamTc
					TruthValue,
				sheMstpBridgeProtoParamDesignatedRoot
					OCTET STRING,
				sheMstpBridgeProtoParamRootPort
					Unsigned32,
				sheMstpBridgeProtoParamRootPathCost
					Unsigned32
			 }

--   1.3.6.1.4.1.231.7.1.2.2.1.4.11.2.1.1.1
		sheMstpBridgeProtoParamIndex OBJECT-TYPE
			SYNTAX Unsigned32 (1..32)
			MAX-ACCESS read-only
			STATUS current
			DESCRIPTION
				"The primary key for the table. One table entry holds a
				profile of spanning tree protocol parameters.
				A profile can be used on a per-VLAN basis.
				The table has 32 static entries."
			::= { sheMstpBridgeProtoParamEntry 1 }

		
--   1.3.6.1.4.1.231.7.1.2.2.1.4.11.2.1.1.2
		sheMstpBridgeProtoParamBridgeId OBJECT-TYPE
			SYNTAX OCTET STRING (SIZE (8))
			MAX-ACCESS read-only
			STATUS current
			DESCRIPTION
				"Each switch has an unique 8-byte bridge identifier
				(bridge ID), which determines the selection of the
				root switch. The two most-significant bytes are used
				for the switch priority, and the remaining six bytes
				are derived from the switch base MAC address."
			::= { sheMstpBridgeProtoParamEntry 2 }

		
--   1.3.6.1.4.1.231.7.1.2.2.1.4.11.2.1.1.3
		sheMstpBridgeProtoParamBridgePriority OBJECT-TYPE
			SYNTAX Unsigned32 (1..61472)
			MAX-ACCESS read-only
			STATUS current
			DESCRIPTION
				"Each switch has an unique 8-byte bridge identifier
				(bridge ID), which determines the selection of the
				root switch. The two most-significant bytes are used
				for the switch priority, and the remaining six bytes
				are derived from the switch base MAC address.
				When you change the switch priority value, you change
				the probability that the switch will be elected as
				the root switch. Configuring a higher value decreases
				the probability; a lower value increases the
				probability.
				
				The configured value for the MstpBridgeProtoParamPriority should be completed
				by a fixed offsett, depending on the Mstp-Instance ID. That means, a configured 
				priority-value of 4097 is valid  for Mstp instance 1. Instance 2 will use 4098 in that case and instance 32 will have 
				a MstpBridgeProtoParamPriority of 4128.
				Default value should be 32769 for MSTP-Instance 1 and 32800 for instance 32. "
			::= { sheMstpBridgeProtoParamEntry 3 }

		
--   1.3.6.1.4.1.231.7.1.2.2.1.4.11.2.1.1.4
		sheMstpBridgeProtoParamTcTime OBJECT-TYPE
			SYNTAX TimeTicks
			MAX-ACCESS read-only
			STATUS current
			DESCRIPTION
				"The time since the last topology change."
			::= { sheMstpBridgeProtoParamEntry 4 }

		
--   1.3.6.1.4.1.231.7.1.2.2.1.4.11.2.1.1.5
		sheMstpBridgeProtoParamTcCount OBJECT-TYPE
			SYNTAX Counter32
			MAX-ACCESS read-only
			STATUS current
			DESCRIPTION
				"The total number of topology changes detected by
				this bridge since the management entity was last
				reset or initialized.
				"
			::= { sheMstpBridgeProtoParamEntry 5 }

		
--   1.3.6.1.4.1.231.7.1.2.2.1.4.11.2.1.1.6
		sheMstpBridgeProtoParamTc OBJECT-TYPE
			SYNTAX TruthValue
			MAX-ACCESS read-only
			STATUS current
			DESCRIPTION
				"A topology change has been detected."
			::= { sheMstpBridgeProtoParamEntry 6 }

		
--   1.3.6.1.4.1.231.7.1.2.2.1.4.11.2.1.1.7
		sheMstpBridgeProtoParamDesignatedRoot OBJECT-TYPE
			SYNTAX OCTET STRING (SIZE (8))
			MAX-ACCESS read-only
			STATUS current
			DESCRIPTION
				"One switch in the network is elected as the root switch
				of the spanning tree by the Spanning Tree Protocol.
				The unique 8-byte bridge identifier (bridge ID)
				of the designated root switch as executed by this node.
				The two most-significant bytes are used for the
				switch priority, and the remaining six bytes are derived
				from the switch base MAC address. This value is used as
				the Root Identifier parameter in all Configuration
				Bridge PDUs originated by this node."
			::= { sheMstpBridgeProtoParamEntry 7 }

		
--   1.3.6.1.4.1.231.7.1.2.2.1.4.11.2.1.1.8
		sheMstpBridgeProtoParamRootPort OBJECT-TYPE
			SYNTAX Unsigned32
			MAX-ACCESS read-only
			STATUS current
			DESCRIPTION
				"A root port is selected for each switch
				(except the root switch). This port provides the best
				path (lowest cost) when the switch forwards packets to
				the root switch. The designated port to the root bridge,
				identified by the sheBridgePortIndex."
			::= { sheMstpBridgeProtoParamEntry 8 }

		
--   1.3.6.1.4.1.231.7.1.2.2.1.4.11.2.1.1.9
		sheMstpBridgeProtoParamRootPathCost OBJECT-TYPE
			SYNTAX Unsigned32
			MAX-ACCESS read-only
			STATUS current
			DESCRIPTION
				"The shortest distance to the root switch is calculated
				for each switch based on the path cost. Costs for the
				designated path to the root switch as seen from
				this switch.
				"
			::= { sheMstpBridgeProtoParamEntry 9 }

		
--   1.3.6.1.4.1.231.7.1.2.2.1.4.11.2.2
		sheMstpPortParamTable OBJECT-TYPE
			SYNTAX SEQUENCE OF SheMstpPortParamEntry
			MAX-ACCESS not-accessible
			STATUS current
			DESCRIPTION
				"The table holds the MSTP parameters on a per-port basis.
				The first key is a pointer to the MSTP profile
				equal to sheMstpBridgeProtoParamIndex (32 static entries).
				The second key is a pointer to the port
				equal to sheBridgePortIndex.
				There is a static entry for every possible MSTP port.
				That means 8 Ethernet uplink interfaces with
				redundundancy or 4 Ethernet uplink interfaces without
				redundundancy + 2 LAG ports."
			::= { sheMstp 2 }

		
--   1.3.6.1.4.1.231.7.1.2.2.1.4.11.2.2.1
		sheMstpPortParamEntry OBJECT-TYPE
			SYNTAX SheMstpPortParamEntry
			MAX-ACCESS not-accessible
			STATUS current
			DESCRIPTION
				"The table holds the MSTP parameters on a per-port basis.
				A free running index is used as key.
				There is a pointer to the MSTP profile
				equal to sheMstpBridgeProtoParamIndex (32 static entries).
				There is a seconde pointer to the port
				equal to sheBridgePortIndex.
				There is a static entry for every possible MSTP port.
				That means 8 Ethernet uplink interfaces with
				redundundancy or 4 Ethernet uplink interfaces without
				redundundancy + 2 LAG ports."
			INDEX { sheMstpPortParamTableIndex }
			::= { sheMstpPortParamTable 1 }

		
		SheMstpPortParamEntry ::=
			SEQUENCE { 
				sheMstpPortParamTableIndex
					Unsigned32,
				sheMstpPortParamProtoIndex
					Unsigned32,
				sheMstpPortParamPortIndex
					Unsigned32,
				sheMstpPortParamUpTime
					TimeTicks,
				sheMstpPortParamState
					SheMstpPortParamStateType,
				sheMstpPortParamPortId
					OCTET STRING,
				sheMstpPortParamPortPriority
					Unsigned32,
				sheMstpPortParamAdminPathCost
					Unsigned32,
				sheMstpPortParamDesignatedRoot
					OCTET STRING,
				sheMstpPortParamDesignatedBridge
					OCTET STRING,
				sheMstpPortParamDesignatedPort
					OCTET STRING,
				sheMstpPortParamDesignatedCost
					Unsigned32,
				sheMstpPortParamPortRole
					SheMstpPortParamPortRoleType,
				sheMstpPortParamCurrentPathCost
					Unsigned32
			 }

--   1.3.6.1.4.1.231.7.1.2.2.1.4.11.2.2.1.1
		sheMstpPortParamTableIndex OBJECT-TYPE
			SYNTAX Unsigned32 (1..256)
			MAX-ACCESS read-only
			STATUS current
			DESCRIPTION
				"A free running simple table index."
			::= { sheMstpPortParamEntry 1 }

		
--   1.3.6.1.4.1.231.7.1.2.2.1.4.11.2.2.1.2
		sheMstpPortParamProtoIndex OBJECT-TYPE
			SYNTAX Unsigned32 (1..32)
			MAX-ACCESS read-only
			STATUS current
			DESCRIPTION
				"The MSTP profile, the table entry is related to,
				is the first key of the table. 
				This object points to the sheMstpBridgeProtoParamTable
				(same as sheMstpBridgeProtoParamIndex)."
			::= { sheMstpPortParamEntry 2 }

		
--   1.3.6.1.4.1.231.7.1.2.2.1.4.11.2.2.1.3
		sheMstpPortParamPortIndex OBJECT-TYPE
			SYNTAX Unsigned32
			MAX-ACCESS read-only
			STATUS current
			DESCRIPTION
				"The port, the table entry is related to, is the second
				key of the table. This object points to the
				sheBridgePortTable (same as sheBridgePortIndex)."
			::= { sheMstpPortParamEntry 3 }

		
--   1.3.6.1.4.1.231.7.1.2.2.1.4.11.2.2.1.4
		sheMstpPortParamUpTime OBJECT-TYPE
			SYNTAX TimeTicks
			MAX-ACCESS read-only
			STATUS current
			DESCRIPTION
				"The total time the port was in the forwarding state
				since the management entity was last reset or initialized.
				"
			::= { sheMstpPortParamEntry 4 }

		
--   1.3.6.1.4.1.231.7.1.2.2.1.4.11.2.2.1.5
		sheMstpPortParamState OBJECT-TYPE
			SYNTAX SheMstpPortParamStateType
			MAX-ACCESS read-only
			STATUS current
			DESCRIPTION
				"Each Layer 2 interface on a switch using spanning tree
				exists in one of these states:
				Blocking: The interface does not participate in frame
				forwarding.
				Listening: The first transitional state after the
				blocking state when the spanning tree determines
				that the interface should participate in frame forwarding.
				Learning: The interface prepares to participate in frame
				forwarding.
				Forwarding: The interface forwards frames.
				Disabled: The interface is not participating in spanning
				tree because of a shutdown port, no link on the port,
				or no spanning-tree instance running on the port."
			::= { sheMstpPortParamEntry 5 }

		
--   1.3.6.1.4.1.231.7.1.2.2.1.4.11.2.2.1.6
		sheMstpPortParamPortId OBJECT-TYPE
			SYNTAX OCTET STRING (SIZE (2))
			MAX-ACCESS read-only
			STATUS current
			DESCRIPTION
				"The parameter consists of two parts. One part bears a
				fixed relationship to the physical or logical support of
				the Port by real-world equipment; this part assures the
				uniqueness of the Port Identifier among the Ports of a
				single Bridge, and is a small integer assigned by the NE
				in the range from one upwards. The other part of the
				parameter allows adjustment of the priority of the
				Port and is taken as the more significant part in
				priority comparisons. The priority part of this parameter
				can be updated by management."
			::= { sheMstpPortParamEntry 6 }

		
--   1.3.6.1.4.1.231.7.1.2.2.1.4.11.2.2.1.7
		sheMstpPortParamPortPriority OBJECT-TYPE
			SYNTAX Unsigned32 (0..240)
			MAX-ACCESS read-only
			STATUS current
			DESCRIPTION
				"When two interfaces on a switch are part of a loop,
				the spanning-tree port priority and path cost settings
				determine which interface is put in the forwarding state
				and which is put in the blocking state.
				The port priority value represents the location of an
				interface in the network topology and how well
				it is located to pass traffic.
				For priority, the range is 0 to 240. The default is 128.
				The lower the number, the higher the priority."
			::= { sheMstpPortParamEntry 7 }

		
--   1.3.6.1.4.1.231.7.1.2.2.1.4.11.2.2.1.8
		sheMstpPortParamAdminPathCost OBJECT-TYPE
			SYNTAX Unsigned32 (0..200000000)
			MAX-ACCESS read-only
			STATUS current
			DESCRIPTION
				"When two interfaces on a switch are part of a loop,
				the spanning-tree port priority and path cost settings
				determine which interface is put in the forwarding state
				and which is put in the blocking state.
				The path cost value represents media speed.
				A lower path cost represents higher-speed transmission.
				For cost, the range is 0 to 200000000; the default value
				is derived from the media speed of the interface.
				1000 Mbps: 4.
				100 Mbps: 19.
				10 Mbps: 100.
				
				0 means auto selection by the system."
			::= { sheMstpPortParamEntry 8 }

		
--   1.3.6.1.4.1.231.7.1.2.2.1.4.11.2.2.1.9
		sheMstpPortParamDesignatedRoot OBJECT-TYPE
			SYNTAX OCTET STRING (SIZE (8))
			MAX-ACCESS read-only
			STATUS current
			DESCRIPTION
				"One switch in the network is elected as the root switch
				of the spanning tree by the Spanning Tree Protocol.
				The unique 8-byte bridge identifier (bridge ID)
				of the designated root switch as executed by this node.
				The two most-significant bytes are used for the
				switch priority, and the remaining six bytes are derived
				from the switch base MAC address. This value is used as
				the Root Identifier parameter in all Configuration
				Bridge PDUs originated by this node."
			::= { sheMstpPortParamEntry 9 }

		
--   1.3.6.1.4.1.231.7.1.2.2.1.4.11.2.2.1.10
		sheMstpPortParamDesignatedBridge OBJECT-TYPE
			SYNTAX OCTET STRING (SIZE (8))
			MAX-ACCESS read-only
			STATUS current
			DESCRIPTION
				"A designated switch for each LAN segment is selected.
				The designated switch incurs the lowest path
				cost when forwarding packets from that LAN to the
				root switch. The port through which the designated
				switch is attached to the LAN is called the designated
				port."
			::= { sheMstpPortParamEntry 10 }

		
--   1.3.6.1.4.1.231.7.1.2.2.1.4.11.2.2.1.11
		sheMstpPortParamDesignatedPort OBJECT-TYPE
			SYNTAX OCTET STRING (SIZE (2))
			MAX-ACCESS read-only
			STATUS current
			DESCRIPTION
				"The port identifier of the port that transmitted a BPDU
				to me."
			::= { sheMstpPortParamEntry 11 }

		
--   1.3.6.1.4.1.231.7.1.2.2.1.4.11.2.2.1.12
		sheMstpPortParamDesignatedCost OBJECT-TYPE
			SYNTAX Unsigned32
			MAX-ACCESS read-only
			STATUS current
			DESCRIPTION
				"A designated switch for each LAN segment is selected.
				The designated switch incurs the lowest path
				cost when forwarding packets from that LAN to the
				root switch. The port through which the designated
				switch is attached to the LAN is called the designated
				port. Costs for the designated path to the
				designated switch."
			::= { sheMstpPortParamEntry 12 }

		
--   1.3.6.1.4.1.231.7.1.2.2.1.4.11.2.2.1.13
		sheMstpPortParamPortRole OBJECT-TYPE
			SYNTAX SheMstpPortParamPortRoleType
			MAX-ACCESS read-only
			STATUS current
			DESCRIPTION
				"The RSTP provides rapid convergence of the spanning tree
				by assigning one of these port roles to individual ports
				and by determining the active topology.
				
				Root port
				Provides the best path (lowest cost) when the switch
				forwards packets to the root switch.
				
				Designated port
				Connects to the designated switch, which incurs the lowest
				path cost when forwarding packets from that LAN to the
				root switch. The port through which the designated switch
				is attached to the LAN is called the designated port.
				
				Alternate port
				Offers an alternate path toward the root switch to that
				provided by the current root port.
				
				Backup port
				Acts as a backup for the path provided by a designated
				port toward the leaves of the spanning tree. A backup port
				can exist only when two ports are connected together in a
				loopback by a point-to-point link or when a switch has two
				or more connections to a shared LAN segment.
				
				Disabled port
				Has no role within the operation of the spanning tree.
				
				A port with the root or a designated port role is included
				in the active topology. A port with the alternate or
				backup port role is excluded from the active topology."
			::= { sheMstpPortParamEntry 13 }

		
--   1.3.6.1.4.1.231.7.1.2.2.1.4.11.2.2.1.14
		sheMstpPortParamCurrentPathCost OBJECT-TYPE
			SYNTAX Unsigned32 (0..200000000)
			MAX-ACCESS read-only
			STATUS current
			DESCRIPTION
				"These value represent the current pathcost value for this port."
			::= { sheMstpPortParamEntry 14 }

		
--   1.3.6.1.4.1.231.7.1.2.2.1.4.11.2.3
		sheMstpControl OBJECT IDENTIFIER ::= { sheMstp 3 }

		
--   1.3.6.1.4.1.231.7.1.2.2.1.4.11.2.3.1
		sheMstpControlRequest OBJECT-TYPE
			SYNTAX SheBridgeControlRequestType
			MAX-ACCESS read-write
			STATUS current
			DESCRIPTION
				"A SetRequest on this attribute starts a command
				execution process in the NetElement.
							
				sheMstpBridgeProtoParamTable
				- resetMstpTc
				  parameters:
				    sheMstpControlBridgeProtoParamIndex
				- modifyMstpBridgeParamEntry
				  parameters:
				    sheMstpControlBridgeProtoParamIndex
				    sheMstpControlBridgeProtoParamBridgePriority
				
				sheMstpPortParamTable
				- modifyMstpPortParamEntry
				  parameters:
				    sheMstpControlPortParamTableIndex
				    sheMstpControlPortParamPortPriority
				    sheMstpControlPortParamAdminPathCost"
			::= { sheMstpControl 1 }

		
--   1.3.6.1.4.1.231.7.1.2.2.1.4.11.2.3.2
		sheMstpControlStatus OBJECT-TYPE
			SYNTAX SheControlStatusType
			MAX-ACCESS read-only
			STATUS current
			DESCRIPTION
				"Describes the status of a user command group, used
				for block commands while a command execution
				is in process.
				Values : idle, busy, passed, failed.
				idle: default, no command in process
				busy: command execution in process, attempts to start
				      another user command on this control block
				      are rejected
				passed/failed: status at end of command"
			::= { sheMstpControl 2 }

		
--   1.3.6.1.4.1.231.7.1.2.2.1.4.11.2.3.3
		sheMstpControlTimestamp OBJECT-TYPE
			SYNTAX Unsigned32
			UNITS "sec"
			MAX-ACCESS read-only
			STATUS current
			DESCRIPTION
				"Time stamp attribute set at the end of a command."
			::= { sheMstpControl 3 }

		
--   1.3.6.1.4.1.231.7.1.2.2.1.4.11.2.3.4
		sheMstpControlReqResult OBJECT-TYPE
			SYNTAX SheBridgeControlReqResultType
			MAX-ACCESS read-only
			STATUS current
			DESCRIPTION
				"Command result (error code) attribute."
			::= { sheMstpControl 4 }

		
--   1.3.6.1.4.1.231.7.1.2.2.1.4.11.2.3.5
		sheMstpControlTimer OBJECT-TYPE
			SYNTAX Unsigned32
			MAX-ACCESS read-only
			STATUS current
			DESCRIPTION
				"Maximum command execution time (timeout) in seconds
				in case of a long running command."
			::= { sheMstpControl 5 }

		
--   1.3.6.1.4.1.231.7.1.2.2.1.4.11.2.3.6
		sheMstpControlBridgeProtoParamIndex OBJECT-TYPE
			SYNTAX Unsigned32
			MAX-ACCESS read-write
			STATUS current
			DESCRIPTION
				"Selects a table entry that holds a profile of
				spanning tree protocol parameters.
				A profile can be used on a per-VLAN basis.
				Parameter for
				- resetMstpTc
				- modifyMstpBridgeParamEntry"
			::= { sheMstpControl 6 }

		
--   1.3.6.1.4.1.231.7.1.2.2.1.4.11.2.3.7
		sheMstpControlBridgeProtoParamBridgePriority OBJECT-TYPE
			SYNTAX Unsigned32
			UNITS "multiple of 4096 + Mstp-Instance ID"
			MAX-ACCESS read-write
			STATUS current
			DESCRIPTION
				"Each switch has an unique 8-byte bridge identifier
				(bridge ID), which determines the selection of the
				root switch. The two most-significant bytes are used
				for the switch priority, and the remaining six bytes
				are derived from the switch base MAC address.
				When you change the switch priority value, you change
				the probability that the switch will be elected as
				the root switch. Configuring a higher value decreases
				the probability; a lower value increases the
				probability.
				Parameter for
				- modifyMstpBridgeParamEntry"
			::= { sheMstpControl 7 }

		
--   1.3.6.1.4.1.231.7.1.2.2.1.4.11.2.3.8
		sheMstpControlPortParamTableIndex OBJECT-TYPE
			SYNTAX Unsigned32 (1..256)
			MAX-ACCESS read-write
			STATUS current
			DESCRIPTION
				"A free running simple table index."
			::= { sheMstpControl 8 }

		
--   1.3.6.1.4.1.231.7.1.2.2.1.4.11.2.3.9
		sheMstpControlPortParamPortPriority OBJECT-TYPE
			SYNTAX Unsigned32 (0..240)
			UNITS "multiple of 16"
			MAX-ACCESS read-write
			STATUS current
			DESCRIPTION
				"When two interfaces on a switch are part of a loop,
				the spanning-tree port priority and path cost settings
				determine which interface is put in the forwarding state
				and which is put in the blocking state.
				The port priority value represents the location of an
				interface in the network topology and how well
				it is located to pass traffic.
				For priority, the range is 0 to 240. The default is 128.
				The lower the number, the higher the priority.
				parameter for
				- modifyMstpPortParamEntry"
			::= { sheMstpControl 9 }

		
--   1.3.6.1.4.1.231.7.1.2.2.1.4.11.2.3.10
		sheMstpControlPortParamAdminPathCost OBJECT-TYPE
			SYNTAX Unsigned32 (0..200000000)
			MAX-ACCESS read-write
			STATUS current
			DESCRIPTION
				"When two interfaces on a switch are part of a loop,
				the spanning-tree port priority and path cost settings
				determine which interface is put in the forwarding state
				and which is put in the blocking state.
				The path cost value represents media speed.
				A lower path cost represents higher-speed transmission.
				For cost, the range is 0 to 200000000; the default value
				is derived from the media speed of the interface.
				1000 Mbps: 4.
				100 Mbps: 19.
				10 Mbps: 100.
				0 means auto selection by the system.
				parameter for
				- modifyMstpPortParamEntry"
			::= { sheMstpControl 10 }

		
--   1.3.6.1.4.1.231.7.1.2.2.1.4.11.3
		sheCist OBJECT IDENTIFIER ::= { sheMstpConfig 3 }

		
--   1.3.6.1.4.1.231.7.1.2.2.1.4.11.3.1
		sheCistBridgeProtoParam OBJECT IDENTIFIER ::= { sheCist 1 }

		
--   1.3.6.1.4.1.231.7.1.2.2.1.4.11.3.1.1
		sheCistBridgeProtoParamBridgeId OBJECT-TYPE
			SYNTAX OCTET STRING (SIZE (8))
			MAX-ACCESS read-only
			STATUS current
			DESCRIPTION
				"Each switch has an unique 8-byte bridge identifier
				(bridge ID), which determines the selection of the
				root switch. The two most-significant bytes are used
				for the switch priority, and the remaining six bytes
				are derived from the switch base MAC address."
			::= { sheCistBridgeProtoParam 1 }

		
--   1.3.6.1.4.1.231.7.1.2.2.1.4.11.3.1.2
		sheCistBridgeProtoParamBridgePriority OBJECT-TYPE
			SYNTAX Unsigned32 (0..61440)
			MAX-ACCESS read-only
			STATUS current
			DESCRIPTION
				"Each switch has an unique 8-byte bridge identifier
				(bridge ID), which determines the selection of the
				root switch. The two most-significant bytes are used
				for the switch priority, and the remaining six bytes
				are derived from the switch base MAC address.
				When you change the switch priority value, you change
				the probability that the switch will be elected as
				the root switch. Configuring a higher value decreases
				the probability; a lower value increases the
				probability."
			::= { sheCistBridgeProtoParam 2 }

		
--   1.3.6.1.4.1.231.7.1.2.2.1.4.11.3.1.3
		sheCistBridgeProtoParamTcTime OBJECT-TYPE
			SYNTAX TimeTicks
			MAX-ACCESS read-only
			STATUS current
			DESCRIPTION
				"The time since the last topology change."
			REFERENCE
				"IEEE 802.1D-1990: Section 6.8.1.1.3
				"
			::= { sheCistBridgeProtoParam 3 }

		
--   1.3.6.1.4.1.231.7.1.2.2.1.4.11.3.1.4
		sheCistBridgeProtoParamTcCount OBJECT-TYPE
			SYNTAX Counter32
			MAX-ACCESS read-only
			STATUS current
			DESCRIPTION
				"The total number of topology changes detected by
				this bridge since the management entity was last
				reset or initialized.
				"
			REFERENCE
				"IEEE 802.1D-1990: Section 6.8.1.1.3
				"
			::= { sheCistBridgeProtoParam 4 }

		
--   1.3.6.1.4.1.231.7.1.2.2.1.4.11.3.1.5
		sheCistBridgeProtoParamTc OBJECT-TYPE
			SYNTAX TruthValue
			MAX-ACCESS read-only
			STATUS current
			DESCRIPTION
				"A topology change has been detected."
			::= { sheCistBridgeProtoParam 5 }

		
--   1.3.6.1.4.1.231.7.1.2.2.1.4.11.3.1.6
		sheCistBridgeProtoParamDesignatedRoot OBJECT-TYPE
			SYNTAX OCTET STRING (SIZE (8))
			MAX-ACCESS read-only
			STATUS current
			DESCRIPTION
				"One switch in the network is elected as the root switch
				of the spanning tree by the Spanning Tree Protocol.
				The unique 8-byte bridge identifier (bridge ID)
				of the designated root switch as executed by this node.
				The two most-significant bytes are used for the
				switch priority, and the remaining six bytes are derived
				from the switch base MAC address. This value is used as
				the Root Identifier parameter in all Configuration
				Bridge PDUs originated by this node."
			REFERENCE
				"IEEE 802.1D-1990: Section 4.5.3.1
				
				"
			::= { sheCistBridgeProtoParam 6 }

		
--   1.3.6.1.4.1.231.7.1.2.2.1.4.11.3.1.7
		sheCistBridgeProtoParamRootPort OBJECT-TYPE
			SYNTAX Unsigned32
			MAX-ACCESS read-only
			STATUS current
			DESCRIPTION
				"A root port is selected for each switch
				(except the root switch). This port provides the best
				path (lowest cost) when the switch forwards packets to
				the root switch. The designated port to the root bridge,
				identified by the sheBridgePortIndex."
			REFERENCE
				"IEEE 802.1D-1990: Section 4.5.3.3
				"
			::= { sheCistBridgeProtoParam 7 }

		
--   1.3.6.1.4.1.231.7.1.2.2.1.4.11.3.1.8
		sheCistBridgeProtoParamRootPathCost OBJECT-TYPE
			SYNTAX Unsigned32
			MAX-ACCESS read-only
			STATUS current
			DESCRIPTION
				"The shortest distance to the root switch is calculated
				for each switch based on the path cost. Costs for the
				designated path to the root switch as seen from
				this switch.
				"
			REFERENCE
				"IEEE 802.1D-1990: Section 4.5.3.2
				"
			::= { sheCistBridgeProtoParam 8 }

		
--   1.3.6.1.4.1.231.7.1.2.2.1.4.11.3.1.9
		sheCistBridgeProtoParamMaxAge OBJECT-TYPE
			SYNTAX Unsigned32 (600..4000)
			UNITS "10 ms"
			MAX-ACCESS read-only
			STATUS current
			DESCRIPTION
				"The maximum age of spanning tree protocol
				information learned from the network on any port
				before it is discarded (time a bridge port saves its
				configuration BPDU information), in units of hundredths
				of a second.  This is the actual value that this
				bridge is currently using. This is 20 seconds by default
				and can be tuned to be between six and 40 seconds. 
				"
			REFERENCE
				"IEEE 802.1D-1990: Section 4.5.3.4
				
				"
			::= { sheCistBridgeProtoParam 9 }

		
--   1.3.6.1.4.1.231.7.1.2.2.1.4.11.3.1.10
		sheCistBridgeProtoParamHoldTime OBJECT-TYPE
			SYNTAX Unsigned32
			UNITS "10 ms"
			MAX-ACCESS read-only
			STATUS current
			DESCRIPTION
				"This time value determines the interval length
				during which no more than two Configuration bridge
				PDUs shall be transmitted by this node, in units
				of hundredths of a second.
				"
			REFERENCE
				"IEEE 802.1D-1990: Section 4.5.3.14
				"
			::= { sheCistBridgeProtoParam 10 }

		
--   1.3.6.1.4.1.231.7.1.2.2.1.4.11.3.1.11
		sheCistBridgeProtoParamForwardDelay OBJECT-TYPE
			SYNTAX Unsigned32 (400..3000)
			UNITS "10 ms"
			MAX-ACCESS read-only
			STATUS current
			DESCRIPTION
				"This time value, measured in units of hundredths
				of a second, controls how fast a port changes its
				spanning state when moving towards the Forwarding
				state.  The value determines how long the port
				stays in each of the Listening and Learning
				states, which precede the Forwarding state.  This
				value is also used, when a topology change has
				been detected and is underway, to age all dynamic
				entries in the Forwarding Database.  [Note that
				this value is the one that this bridge is
				currently using, in contrast to
				dot1dStpBridgeForwardDelay which is the value that
				this bridge and all others would start using
				if/when this bridge were to become the root.]
				This is by default equal to 15 seconds, but can be
				tuned to be between four and 30 seconds."
			REFERENCE
				"IEEE 802.1D-1990: Section 4.5.3.6
				"
			::= { sheCistBridgeProtoParam 11 }

		
--   1.3.6.1.4.1.231.7.1.2.2.1.4.11.3.1.12
		sheCistBridgeProtoParamBridgeMaxAge OBJECT-TYPE
			SYNTAX Unsigned32 (600..4000)
			UNITS "10 ms"
			MAX-ACCESS read-only
			STATUS current
			DESCRIPTION
				"The value that all bridges use for MaxAge when
				this bridge is acting as the root in units of hundredths
				of a second. Note that 802.1D-1990 specifies that the
				range for this parameter is related to the value of
				dot1dStpBridgeHelloTime. The granularity of this
				timer is specified by 802.1D-1990 to be 1 second.
				An agent may return a badValue error if a set is
				attempted to a value which is not a whole number
				of seconds.
				"
			REFERENCE
				"IEEE 802.1D-1990: Section 4.5.3.8
				"
			DEFVAL { 2000 }
			::= { sheCistBridgeProtoParam 12 }

		
--   1.3.6.1.4.1.231.7.1.2.2.1.4.11.3.1.13
		sheCistBridgeProtoParamBridgeHelloTime OBJECT-TYPE
			SYNTAX Unsigned32 (100..1000)
			UNITS "10 ms"
			MAX-ACCESS read-only
			STATUS current
			DESCRIPTION
				"The value that all bridges use for HelloTime when
				this bridge is acting as the root in units of hundredths
				of a second. The hello time is the time between each
				Bridge Protocol Data Unit (BPDU) that is sent on a port.
				This is equal to two seconds by default, but can be tuned
				to be between one and ten seconds. The granularity of
				this timer is specified by 802.1D-1990 to be 1 second.
				An agent may return a badValue error if a set
				is attempted to a value which is not a whole number
				of seconds.
				
				"
			REFERENCE
				"IEEE 802.1D-1990: Section 4.5.3.9
				"
			DEFVAL { 200 }
			::= { sheCistBridgeProtoParam 13 }

		
--   1.3.6.1.4.1.231.7.1.2.2.1.4.11.3.1.14
		sheCistBridgeProtoParamBridgeForwardDelay OBJECT-TYPE
			SYNTAX Unsigned32 (400..3000)
			UNITS "10 ms"
			MAX-ACCESS read-only
			STATUS current
			DESCRIPTION
				"The value that all bridges use for ForwardDelay
				when this bridge is acting as the root.  Note that
				802.1D-1990 specifies that the range for this
				parameter is related to the value of
				BridgeMaxAge. This time value, measured in units of
				hundredths of a second, controls how fast a port changes
				its spanning state when moving towards the Forwarding
				state.  The value determines how long the port
				stays in each of the Listening and Learning
				states, which precede the Forwarding state.  This
				value is also used, when a topology change has
				been detected and is underway, to age all dynamic
				entries in the Forwarding Database.
				The granularity of this timer is specified by
				802.1D-1990 to be 1 second. An agent may return a
				badValue error if a set is attempted to a value which
				is not a whole number of seconds.
				This is by default equal to 15 seconds, but can be
				tuned to be between four and 30 seconds."
			REFERENCE
				"IEEE 802.1D-1990: Section 4.5.3.10
				"
			DEFVAL { 1500 }
			::= { sheCistBridgeProtoParam 14 }

		
--   1.3.6.1.4.1.231.7.1.2.2.1.4.11.3.1.15
		sheCistBridgeProtoParamForceVer OBJECT-TYPE
			SYNTAX SheCistBridgeProtoParamForceVerType
			MAX-ACCESS read-only
			STATUS current
			DESCRIPTION
				"When RSTP is configuring or reconfiguring the network,
				there is an increased and implementation dependent
				probability that frames that are in transit will be
				misordered or duplicated as network paths change,
				since a Bridge can buffer frames awaiting transmission
				through its Ports. Some LAN protocols, for example,
				LLC Type 2, are particularly sensitive to frame
				misordering and duplication; to support these the
				Force Protocol Version parameter can be used to delay the
				transition of ports to a Forwarding state and further
				reduce the probability of such events.
				The Force Protocol Version parameter for the Bridge
				can take the value 0 (STP Compatibility mode),2
				(the default, normal operation) or 3 (MSTP Compatibility)."
			::= { sheCistBridgeProtoParam 15 }

		
--   1.3.6.1.4.1.231.7.1.2.2.1.4.11.3.1.16
		sheCistBridgeProtoParamRegionalRootId OBJECT-TYPE
			SYNTAX OCTET STRING (SIZE (8))
			MAX-ACCESS read-only
			STATUS current
			DESCRIPTION
				"One switch in the network is elected as the root switch
				of the spanning tree by the Spanning Tree Protocol.
				The unique 8-byte bridge identifier (bridge ID)
				of the designated root switch as executed by this node.
				The two most-significant bytes are used for the
				switch priority, and the remaining six bytes are derived
				from the switch base MAC address. This value is used as
				the Root Identifier parameter in all Configuration
				Bridge PDUs originated by this node."
			::= { sheCistBridgeProtoParam 16 }

		
--   1.3.6.1.4.1.231.7.1.2.2.1.4.11.3.1.17
		sheCistBridgeProtoParamRegionalRootPathCost OBJECT-TYPE
			SYNTAX Unsigned32
			MAX-ACCESS read-only
			STATUS current
			DESCRIPTION
				"The shortest distance to the root switch is calculated
				for each switch based on the path cost. Costs for the
				designated path to the root switch as seen from
				this switch."
			::= { sheCistBridgeProtoParam 17 }

		
--   1.3.6.1.4.1.231.7.1.2.2.1.4.11.3.1.18
		sheCistBridgeProtoParamMaxHops OBJECT-TYPE
			SYNTAX Integer32 (1..40)
			MAX-ACCESS read-only
			STATUS current
			DESCRIPTION
				"Number of possible hops in the region. Only used if forcedVersion = mstp(3)."
			::= { sheCistBridgeProtoParam 18 }

		
--   1.3.6.1.4.1.231.7.1.2.2.1.4.11.3.1.19
		sheCistBridgeProtoParamSelfLoopDetect OBJECT-TYPE
			SYNTAX TruthValue
			MAX-ACCESS read-only
			STATUS current
			DESCRIPTION
				"Enable/Disable the stp self loop detection."
			::= { sheCistBridgeProtoParam 19 }

		
--   1.3.6.1.4.1.231.7.1.2.2.1.4.11.3.3
		sheCistPortParamTable OBJECT-TYPE
			SYNTAX SEQUENCE OF SheCistPortParamEntry
			MAX-ACCESS not-accessible
			STATUS current
			DESCRIPTION
				"The table holds the CIST parameters on a per-port basis.
				The key is a pointer to the port
				equal to sheBridgePortIndex.
				There is a static entry for every possible MSTP port.
				That means 8 Ethernet uplink interfaces with
				redundundancy or 4 Ethernet uplink interfaces without
				redundundancy + 2 LAG ports."
			::= { sheCist 3 }

		
--   1.3.6.1.4.1.231.7.1.2.2.1.4.11.3.3.1
		sheCistPortParamEntry OBJECT-TYPE
			SYNTAX SheCistPortParamEntry
			MAX-ACCESS not-accessible
			STATUS current
			DESCRIPTION
				"The table holds the CIST parameters on a per-port basis.
				The key is a pointer to the port
				equal to sheBridgePortIndex.
				There is a static entry for every possible MSTP port.
				That means 8 Ethernet uplink interfaces with
				redundundancy or 4 Ethernet uplink interfaces without
				redundundancy + 2 LAG ports."
			INDEX { sheCistPortParamIndex }
			::= { sheCistPortParamTable 1 }

		
		SheCistPortParamEntry ::=
			SEQUENCE { 
				sheCistPortParamIndex
					Unsigned32,
				sheCistPortParamUpTime
					TimeTicks,
				sheCistPortParamState
					SheMstpPortParamStateType,
				sheCistPortParamPortId
					OCTET STRING,
				sheCistPortParamPortPriority
					Unsigned32,
				sheCistPortParamAdminPathCost
					Unsigned32,
				sheCistPortParamDesignatedRoot
					OCTET STRING,
				sheCistPortParamDesignatedCost
					Unsigned32,
				sheCistPortParamDesignatedBridge
					OCTET STRING,
				sheCistPortParamDesignatedPort
					OCTET STRING,
				sheCistPortParamTcAck
					TruthValue,
				sheCistPortParamAdminEdgePort
					TruthValue,
				sheCistPortParamOperEdgePort
					TruthValue,
				sheCistPortParamMacEnabled
					TruthValue,
				sheCistPortParamMacOperational
					TruthValue,
				sheCistPortParamAdminPointToPointMac
					SheCistAdminPTPMacType,
				sheCistPortParamOperPointToPointMac
					TruthValue,
				sheCistPortParamRegionalRootId
					OCTET STRING,
				sheCistPortParamRegionalRootPathCost
					Unsigned32,
				sheCistPortParamPortHelloTime
					Unsigned32,
				sheCistPortParamHelloTime
					Unsigned32,
				sheCistPortParamPortRole
					SheMstpPortParamPortRoleType,
				sheCistPortParamCurrentPathCost
					Unsigned32,
				sheCistPortParamLoopDetect
					TruthValue
			 }

--   1.3.6.1.4.1.231.7.1.2.2.1.4.11.3.3.1.1
		sheCistPortParamIndex OBJECT-TYPE
			SYNTAX Unsigned32 (1..65535)
			MAX-ACCESS read-only
			STATUS current
			DESCRIPTION
				"That is the sheBridgePortIndex of the corresponding 
				BridgePort."
			::= { sheCistPortParamEntry 1 }

		
--   1.3.6.1.4.1.231.7.1.2.2.1.4.11.3.3.1.2
		sheCistPortParamUpTime OBJECT-TYPE
			SYNTAX TimeTicks
			MAX-ACCESS read-only
			STATUS current
			DESCRIPTION
				"The total time the port was in the forwarding state
				since the management entity was last reset or initialized.
				"
			::= { sheCistPortParamEntry 2 }

		
--   1.3.6.1.4.1.231.7.1.2.2.1.4.11.3.3.1.3
		sheCistPortParamState OBJECT-TYPE
			SYNTAX SheMstpPortParamStateType
			MAX-ACCESS read-only
			STATUS current
			DESCRIPTION
				"Each Layer 2 interface on a switch using spanning tree
				exists in one of these states:
				Blocking: The interface does not participate in frame
				forwarding.
				Listening: The first transitional state after the
				blocking state when the spanning tree determines
				that the interface should participate in frame forwarding.
				Learning: The interface prepares to participate in frame
				forwarding.
				Forwarding: The interface forwards frames.
				Disabled: The interface is not participating in spanning
				tree because of a shutdown port, no link on the port,
				or no spanning-tree instance running on the port."
			::= { sheCistPortParamEntry 3 }

		
--   1.3.6.1.4.1.231.7.1.2.2.1.4.11.3.3.1.4
		sheCistPortParamPortId OBJECT-TYPE
			SYNTAX OCTET STRING (SIZE (2))
			MAX-ACCESS read-only
			STATUS current
			DESCRIPTION
				"The parameter consists of two parts. One part bears a
				fixed relationship to the physical or logical support of
				the Port by real-world equipment; this part assures the
				uniqueness of the Port Identifier among the Ports of a
				single Bridge, and is a small integer assigned by the NE
				in the range from one upwards. The other part of the
				parameter allows adjustment of the priority of the
				Port and is taken as the more significant part in
				priority comparisons. The priority part of this parameter
				can be updated by management."
			::= { sheCistPortParamEntry 4 }

		
--   1.3.6.1.4.1.231.7.1.2.2.1.4.11.3.3.1.5
		sheCistPortParamPortPriority OBJECT-TYPE
			SYNTAX Unsigned32 (0..240)
			MAX-ACCESS read-only
			STATUS current
			DESCRIPTION
				"When two interfaces on a switch are part of a loop,
				the spanning-tree port priority and path cost settings
				determine which interface is put in the forwarding state
				and which is put in the blocking state.
				The port priority value represents the location of an
				interface in the network topology and how well
				it is located to pass traffic.
				For priority, the range is 0 to 240. The default is 128.
				The lower the number, the higher the priority."
			::= { sheCistPortParamEntry 5 }

		
--   1.3.6.1.4.1.231.7.1.2.2.1.4.11.3.3.1.6
		sheCistPortParamAdminPathCost OBJECT-TYPE
			SYNTAX Unsigned32 (0..200000000)
			MAX-ACCESS read-only
			STATUS current
			DESCRIPTION
				"When two interfaces on a switch are part of a loop,
				the spanning-tree port priority and path cost settings
				determine which interface is put in the forwarding state
				and which is put in the blocking state.
				The path cost value represents media speed.
				A lower path cost represents higher-speed transmission.
				For cost, the range is 1 to 200000000; the default value
				is derived from the media speed of the interface.
				1000 Mbps: 4.
				100 Mbps: 19.
				10 Mbps: 100.
				0 means auto selection by the system."
			::= { sheCistPortParamEntry 6 }

		
--   1.3.6.1.4.1.231.7.1.2.2.1.4.11.3.3.1.7
		sheCistPortParamDesignatedRoot OBJECT-TYPE
			SYNTAX OCTET STRING (SIZE (8))
			MAX-ACCESS read-only
			STATUS current
			DESCRIPTION
				"One switch in the network is elected as the root switch
				of the spanning tree by the Spanning Tree Protocol.
				The unique 8-byte bridge identifier (bridge ID)
				of the designated root switch as executed by this node.
				The two most-significant bytes are used for the
				switch priority, and the remaining six bytes are derived
				from the switch base MAC address. This value is used as
				the Root Identifier parameter in all Configuration
				Bridge PDUs originated by this node."
			::= { sheCistPortParamEntry 7 }

		
--   1.3.6.1.4.1.231.7.1.2.2.1.4.11.3.3.1.8
		sheCistPortParamDesignatedCost OBJECT-TYPE
			SYNTAX Unsigned32
			MAX-ACCESS read-only
			STATUS current
			DESCRIPTION
				"A designated switch for each LAN segment is selected.
				The designated switch incurs the lowest path
				cost when forwarding packets from that LAN to the
				root switch. The port through which the designated
				switch is attached to the LAN is called the designated
				port. Costs for the designated path to the
				designated switch."
			::= { sheCistPortParamEntry 8 }

		
--   1.3.6.1.4.1.231.7.1.2.2.1.4.11.3.3.1.9
		sheCistPortParamDesignatedBridge OBJECT-TYPE
			SYNTAX OCTET STRING (SIZE (8))
			MAX-ACCESS read-only
			STATUS current
			DESCRIPTION
				"A designated switch for each LAN segment is selected.
				The designated switch incurs the lowest path
				cost when forwarding packets from that LAN to the
				root switch. The port through which the designated
				switch is attached to the LAN is called the designated
				port."
			::= { sheCistPortParamEntry 9 }

		
--   1.3.6.1.4.1.231.7.1.2.2.1.4.11.3.3.1.10
		sheCistPortParamDesignatedPort OBJECT-TYPE
			SYNTAX OCTET STRING (SIZE (2))
			MAX-ACCESS read-only
			STATUS current
			DESCRIPTION
				"The port identifier of the port that transmitted a BPDU
				to me."
			::= { sheCistPortParamEntry 10 }

		
--   1.3.6.1.4.1.231.7.1.2.2.1.4.11.3.3.1.11
		sheCistPortParamTcAck OBJECT-TYPE
			SYNTAX TruthValue
			MAX-ACCESS read-only
			STATUS current
			DESCRIPTION
				"A boolean. Set if a Configuration Message with a topology
				change acknowledge flag set is to be transmitted."
			::= { sheCistPortParamEntry 11 }

		
--   1.3.6.1.4.1.231.7.1.2.2.1.4.11.3.3.1.12
		sheCistPortParamAdminEdgePort OBJECT-TYPE
			SYNTAX TruthValue
			MAX-ACCESS read-only
			STATUS current
			DESCRIPTION
				"Port can be configured to be an edge port."
			::= { sheCistPortParamEntry 12 }

		
--   1.3.6.1.4.1.231.7.1.2.2.1.4.11.3.3.1.13
		sheCistPortParamOperEdgePort OBJECT-TYPE
			SYNTAX TruthValue
			MAX-ACCESS read-only
			STATUS current
			DESCRIPTION
				"If port is configured to be an edge port, in the absence
				of a received BPDU, this port is identified as an
				operEdgePort."
			::= { sheCistPortParamEntry 13 }

		
--   1.3.6.1.4.1.231.7.1.2.2.1.4.11.3.3.1.14
		sheCistPortParamMacEnabled OBJECT-TYPE
			SYNTAX TruthValue
			MAX-ACCESS read-only
			STATUS current
			DESCRIPTION
				"The value of this parameter is TRUE if use of
				the MAC entity is permitted; and is otherwise FALSE."
			::= { sheCistPortParamEntry 14 }

		
--   1.3.6.1.4.1.231.7.1.2.2.1.4.11.3.3.1.15
		sheCistPortParamMacOperational OBJECT-TYPE
			SYNTAX TruthValue
			MAX-ACCESS read-only
			STATUS current
			DESCRIPTION
				"The value of this parameter is TRUE if the MAC entity is
				in a functioning state; i.e., the MAC entity can be used
				to transmit and/or receive frames, and its use is
				permitted by management. Its value is otherwise FALSE."
			::= { sheCistPortParamEntry 15 }

		
--   1.3.6.1.4.1.231.7.1.2.2.1.4.11.3.3.1.16
		sheCistPortParamAdminPointToPointMac OBJECT-TYPE
			SYNTAX SheCistAdminPTPMacType
			MAX-ACCESS read-only
			STATUS current
			DESCRIPTION
				"This parameter can take three values:
				a) ForceTrue. The administrator requires the MAC to be
				treated as if it is connected to a point-to-point LAN.
				b) ForceFalse. The administrator requires the MAC to be
				treated as connected to a non-point-to-point LAN.
				c) Auto. The administrator requires the point-to-point
				status of the MAC to be determined by specific MAC
				procedures."
			::= { sheCistPortParamEntry 16 }

		
--   1.3.6.1.4.1.231.7.1.2.2.1.4.11.3.3.1.17
		sheCistPortParamOperPointToPointMac OBJECT-TYPE
			SYNTAX TruthValue
			MAX-ACCESS read-only
			STATUS current
			DESCRIPTION
				"TRUE, if the MAC is connected to a point-to-point LAN,
				otherwise FALSE."
			::= { sheCistPortParamEntry 17 }

		
--   1.3.6.1.4.1.231.7.1.2.2.1.4.11.3.3.1.18
		sheCistPortParamRegionalRootId OBJECT-TYPE
			SYNTAX OCTET STRING (SIZE (8))
			MAX-ACCESS read-only
			STATUS current
			DESCRIPTION
				"The CIST Regional Root is the bridge of this region that
				has the lowest External Root Path Cost through a
				Boundary Port."
			::= { sheCistPortParamEntry 18 }

		
--   1.3.6.1.4.1.231.7.1.2.2.1.4.11.3.3.1.19
		sheCistPortParamRegionalRootPathCost OBJECT-TYPE
			SYNTAX Unsigned32
			MAX-ACCESS read-only
			STATUS current
			DESCRIPTION
				"Path cost to the CIST Regional Root, the bridge of this
				region that has the lowest External Root Path Cost
				through a Boundary Port."
			::= { sheCistPortParamEntry 19 }

		
--   1.3.6.1.4.1.231.7.1.2.2.1.4.11.3.3.1.20
		sheCistPortParamPortHelloTime OBJECT-TYPE
			SYNTAX Unsigned32 (100..1000)
			UNITS "10 ms"
			MAX-ACCESS read-only
			STATUS current
			DESCRIPTION
				"The hello time actual used by that port.
				"
			DEFVAL { 200 }
			::= { sheCistPortParamEntry 20 }

		
--   1.3.6.1.4.1.231.7.1.2.2.1.4.11.3.3.1.21
		sheCistPortParamHelloTime OBJECT-TYPE
			SYNTAX Unsigned32 (100..1000)
			UNITS "10 ms"
			MAX-ACCESS read-only
			STATUS current
			DESCRIPTION
				"The time interval between the generation of Configuration
				BPDUs by the Root."
			DEFVAL { 200 }
			::= { sheCistPortParamEntry 21 }

		
--   1.3.6.1.4.1.231.7.1.2.2.1.4.11.3.3.1.22
		sheCistPortParamPortRole OBJECT-TYPE
			SYNTAX SheMstpPortParamPortRoleType
			MAX-ACCESS read-only
			STATUS current
			DESCRIPTION
				"The RSTP provides rapid convergence of the spanning tree
				by assigning one of these port roles to individual ports
				and by determining the active topology.
				
				Root port
				Provides the best path (lowest cost) when the switch
				forwards packets to the root switch.
				
				Designated port
				Connects to the designated switch, which incurs the lowest
				path cost when forwarding packets from that LAN to the
				root switch. The port through which the designated switch
				is attached to the LAN is called the designated port.
				
				Alternate port
				Offers an alternate path toward the root switch to that
				provided by the current root port.
				
				Backup port
				Acts as a backup for the path provided by a designated
				port toward the leaves of the spanning tree. A backup port
				can exist only when two ports are connected together in a
				loopback by a point-to-point link or when a switch has two
				or more connections to a shared LAN segment.
				
				Disabled port
				Has no role within the operation of the spanning tree.
				
				A port with the root or a designated port role is included
				in the active topology. A port with the alternate or
				backup port role is excluded from the active topology."
			::= { sheCistPortParamEntry 22 }

		
--   1.3.6.1.4.1.231.7.1.2.2.1.4.11.3.3.1.23
		sheCistPortParamCurrentPathCost OBJECT-TYPE
			SYNTAX Unsigned32 (0..200000000)
			MAX-ACCESS read-only
			STATUS current
			DESCRIPTION
				"The current path cost"
			::= { sheCistPortParamEntry 23 }

		
--     1.3.6.1.4.1.231.7.1.2.2.1.4.11.3.3.1.24
		sheCistPortParamLoopDetect OBJECT-TYPE
			SYNTAX TruthValue
			MAX-ACCESS read-only
			STATUS current
			DESCRIPTION
				"The current loop detect state.
				
				Note:
				Only supported by hix5608 R1.3!!"
			DEFVAL { false }
			::= { sheCistPortParamEntry 24 }

		
--   1.3.6.1.4.1.231.7.1.2.2.1.4.11.3.4
		sheCistControl OBJECT IDENTIFIER ::= { sheCist 4 }

		
--   1.3.6.1.4.1.231.7.1.2.2.1.4.11.3.4.1
		sheCistControlRequest OBJECT-TYPE
			SYNTAX SheBridgeControlRequestType
			MAX-ACCESS read-write
			STATUS current
			DESCRIPTION
				"A SetRequest on this attribute starts a command
				execution process in the NetElement.
							
				sheCistBridgeProtoParam
				- resetCistTc
				  parameters:
				    'no'
				- modifyCistBridgeParameters
				  parameters:
				    sheCistControlBridgeProtoParamBridgePriority
				    sheCistControlBridgeProtoParamBridgeMaxAge
				    sheCistControlBridgeProtoParamBridgeHelloTime
				    sheCistControlBridgeProtoParamBridgeForwardDelay
				    sheCistControlBridgeProtoParamForceVer
				    sheCistControlBridgeProtoParamMaxHops
				    sheCistControlBridgeProtoParamSelfLoopDetect
				
				sheCistPortParamTable
				- modifyCistPortParamEntry
				  parameters:
				    sheCistControlPortParamIndex
				    sheCistControlPortParamPortPriority
				    sheCistControlPortParamAdminPathCost
				    sheCistControlPortParamAdminEdgePort
				    sheCistControlPortParamMacEnabled
				    sheCistControlPortParamAdminPointToPointMac"
			::= { sheCistControl 1 }

		
--   1.3.6.1.4.1.231.7.1.2.2.1.4.11.3.4.2
		sheCistControlStatus OBJECT-TYPE
			SYNTAX SheControlStatusType
			MAX-ACCESS read-only
			STATUS current
			DESCRIPTION
				"Describes the status of a user command group, used
				for block commands while a command execution
				is in process.
				Values : idle, busy, passed, failed.
				idle: default, no command in process
				busy: command execution in process, attempts to start
				      another user command on this control block
				      are rejected
				passed/failed: status at end of command"
			::= { sheCistControl 2 }

		
--   1.3.6.1.4.1.231.7.1.2.2.1.4.11.3.4.3
		sheCistControlTimestamp OBJECT-TYPE
			SYNTAX Unsigned32
			UNITS "sec"
			MAX-ACCESS read-only
			STATUS current
			DESCRIPTION
				"Time stamp attribute set at the end of a command."
			::= { sheCistControl 3 }

		
--   1.3.6.1.4.1.231.7.1.2.2.1.4.11.3.4.4
		sheCistControlReqResult OBJECT-TYPE
			SYNTAX SheBridgeControlReqResultType
			MAX-ACCESS read-only
			STATUS current
			DESCRIPTION
				"Command result (error code) attribute."
			::= { sheCistControl 4 }

		
--   1.3.6.1.4.1.231.7.1.2.2.1.4.11.3.4.5
		sheCistControlTimer OBJECT-TYPE
			SYNTAX Unsigned32
			MAX-ACCESS read-only
			STATUS current
			DESCRIPTION
				"Maximum command execution time (timeout) in seconds
				in case of a long running command."
			::= { sheCistControl 5 }

		
--   1.3.6.1.4.1.231.7.1.2.2.1.4.11.3.4.6
		sheCistControlBridgeProtoParamBridgePriority OBJECT-TYPE
			SYNTAX Unsigned32 (0..61440)
			UNITS "multiple of 4096"
			MAX-ACCESS read-write
			STATUS current
			DESCRIPTION
				"Each switch has an unique 8-byte bridge identifier
				(bridge ID), which determines the selection of the
				root switch. The two most-significant bytes are used
				for the switch priority, and the remaining six bytes
				are derived from the switch base MAC address.
				When you change the switch priority value, you change
				the probability that the switch will be elected as
				the root switch. Configuring a higher value decreases
				the probability; a lower value increases the
				probability.
				parameter for
				- modifyCistBridgeParameters"
			::= { sheCistControl 6 }

		
--   1.3.6.1.4.1.231.7.1.2.2.1.4.11.3.4.7
		sheCistControlBridgeProtoParamBridgeMaxAge OBJECT-TYPE
			SYNTAX Unsigned32 (600..4000)
			MAX-ACCESS read-write
			STATUS current
			DESCRIPTION
				"The value that all bridges use for MaxAge when
				this bridge is acting as the root.  Note that
				802.1D-1990 specifies that the range for this
				parameter is related to the value of
				dot1dStpBridgeHelloTime. The granularity of this
				timer is specified by 802.1D-1990 to be 1 second.
				An agent may return a badValue error if a set is
				attempted to a value which is not a whole number
				of seconds.
				parameter for
				- modifyCistBridgeParameters
				"
			REFERENCE
				"IEEE 802.1D-1990: Section 4.5.3.8
				"
			::= { sheCistControl 7 }

		
--   1.3.6.1.4.1.231.7.1.2.2.1.4.11.3.4.8
		sheCistControlBridgeProtoParamBridgeHelloTime OBJECT-TYPE
			SYNTAX Unsigned32 (100..1000)
			MAX-ACCESS read-write
			STATUS current
			DESCRIPTION
				"The value that all bridges use for HelloTime when
				this bridge is acting as the root.  The
				granularity of this timer is specified by 802.1D-
				1990 to be 1 second.  An agent may return a
				badValue error if a set is attempted to a value
				which is not a whole number of seconds.
				parameter for
				- modifyCistBridgeParameters
				"
			REFERENCE
				"IEEE 802.1D-1990: Section 4.5.3.9
				"
			::= { sheCistControl 8 }

		
--   1.3.6.1.4.1.231.7.1.2.2.1.4.11.3.4.9
		sheCistControlBridgeProtoParamBridgeForwardDelay OBJECT-TYPE
			SYNTAX Unsigned32 (400..3000)
			MAX-ACCESS read-write
			STATUS current
			DESCRIPTION
				"The value that all bridges use for ForwardDelay
				when this bridge is acting as the root.  Note that
				802.1D-1990 specifies that the range for this
				parameter is related to the value of
				dot1dStpBridgeMaxAge.  The granularity of this
				timer is specified by 802.1D-1990 to be 1 second.
				An agent may return a badValue error if a set is
				attempted to a value which is not a whole number
				of seconds.
				parameter for
				- modifyCistBridgeParameters
				"
			REFERENCE
				"IEEE 802.1D-1990: Section 4.5.3.10
				"
			::= { sheCistControl 9 }

		
--   1.3.6.1.4.1.231.7.1.2.2.1.4.11.3.4.10
		sheCistControlBridgeProtoParamForceVer OBJECT-TYPE
			SYNTAX SheCistBridgeProtoParamForceVerType
			MAX-ACCESS read-write
			STATUS current
			DESCRIPTION
				"When RSTP is configuring or reconfiguring the network,
				there is an increased and implementation dependent
				probability that frames that are in transit will be
				misordered or duplicated as network paths change,
				since a Bridge can buffer frames awaiting transmission
				through its Ports. Some LAN protocols, for example,
				LLC Type 2, are particularly sensitive to frame
				misordering and duplication; to support these the
				Force Protocol Version parameter can be used to delay the
				transition of ports to a Forwarding state and further
				reduce the probability of such events.
				The Force Protocol Version parameter for the Bridge
				can take the value 0 (STP Compatibility mode),2
				(the default, normal operation).
				Third version is Mstp compatibility. "
			::= { sheCistControl 10 }

		
--   1.3.6.1.4.1.231.7.1.2.2.1.4.11.3.4.11
		sheCistControlBridgeProtoParamMaxHops OBJECT-TYPE
			SYNTAX Integer32 (1..40)
			MAX-ACCESS read-write
			STATUS current
			DESCRIPTION
				"Number of possible hops in the region. Only used if forcedVersion = mstp(3)."
			::= { sheCistControl 11 }

		
--   1.3.6.1.4.1.231.7.1.2.2.1.4.11.3.4.12
		sheCistControlBridgeProtoParamSelfLoopDetect OBJECT-TYPE
			SYNTAX TruthValue
			MAX-ACCESS read-write
			STATUS current
			DESCRIPTION
				"Enable/Disable the stp self loop detection."
			::= { sheCistControl 12 }

		
--   1.3.6.1.4.1.231.7.1.2.2.1.4.11.3.4.13
		sheCistControlPortParamIndex OBJECT-TYPE
			SYNTAX Unsigned32 (1..65535)
			MAX-ACCESS read-write
			STATUS current
			DESCRIPTION
				"Index of the sheCistPortParamTable entry to be modified.
				parameter for
				- modifyCistPortParamEntry"
			::= { sheCistControl 13 }

		
--   1.3.6.1.4.1.231.7.1.2.2.1.4.11.3.4.14
		sheCistControlPortParamPortPriority OBJECT-TYPE
			SYNTAX Unsigned32 (0..240)
			UNITS "multiple of 16"
			MAX-ACCESS read-write
			STATUS current
			DESCRIPTION
				"When two interfaces on a switch are part of a loop,
				the spanning-tree port priority and path cost settings
				determine which interface is put in the forwarding state
				and which is put in the blocking state.
				The port priority value represents the location of an
				interface in the network topology and how well
				it is located to pass traffic.
				For priority, the range is 0 to 240. The default is 128.
				The lower the number, the higher the priority.
				
				parameter for
				- modifyCistPortParamEntry"
			::= { sheCistControl 14 }

		
--   1.3.6.1.4.1.231.7.1.2.2.1.4.11.3.4.15
		sheCistControlPortParamAdminPathCost OBJECT-TYPE
			SYNTAX Unsigned32 (0..200000000)
			MAX-ACCESS read-write
			STATUS current
			DESCRIPTION
				"When two interfaces on a switch are part of a loop,
				the spanning-tree port priority and path cost settings
				determine which interface is put in the forwarding state
				and which is put in the blocking state.
				The path cost value represents media speed.
				A lower path cost represents higher-speed transmission.
				For cost, the range is 1 to 200000000; the default value
				is derived from the media speed of the interface.
				1000 Mbps: 4.
				100 Mbps: 19.
				10 Mbps: 100.
				0 means auto selection by the system.
				parameter for
				- modifyCistPortParamEntry"
			::= { sheCistControl 15 }

		
--   1.3.6.1.4.1.231.7.1.2.2.1.4.11.3.4.16
		sheCistControlPortParamAdminEdgePort OBJECT-TYPE
			SYNTAX TruthValue
			MAX-ACCESS read-write
			STATUS current
			DESCRIPTION
				"Port can be configured to be an edge port.
				parameter for
				- modifyCistPortParamEntry"
			::= { sheCistControl 16 }

		
--   1.3.6.1.4.1.231.7.1.2.2.1.4.11.3.4.17
		sheCistControlPortParamMacEnabled OBJECT-TYPE
			SYNTAX TruthValue
			MAX-ACCESS read-write
			STATUS current
			DESCRIPTION
				"The value of this parameter is TRUE if use of
				the MAC entity is permitted; and is otherwise FALSE.
				parameter for
				- modifyCistPortParamEntry"
			::= { sheCistControl 17 }

		
--   1.3.6.1.4.1.231.7.1.2.2.1.4.11.3.4.18
		sheCistControlPortParamAdminPointToPointMac OBJECT-TYPE
			SYNTAX SheCistAdminPTPMacType
			MAX-ACCESS read-write
			STATUS current
			DESCRIPTION
				"This parameter can take three values:
				a) ForceTrue. The administrator requires the MAC to be
				treated as if it is connected to a point-to-point LAN.
				b) ForceFalse. The administrator requires the MAC to be
				treated as connected to a non-point-to-point LAN.
				c) Auto. The administrator requires the point-to-point
				status of the MAC to be determined by specific MAC
				procedures.
				parameter for
				- modifyCistPortParamEntry"
			::= { sheCistControl 18 }

		
--   1.3.6.1.4.1.231.7.1.2.2.1.4.11.4
		sheMstpNotifications OBJECT IDENTIFIER ::= { sheMstpConfig 4 }

		
--   1.3.6.1.4.1.231.7.1.2.2.1.4.11.4.1
		sheMstpBaseConfigModified NOTIFICATION-TYPE
			OBJECTS { sheMstpBaseControlTimestamp, sheMstpBaseControlBaseStatus, sheMstpBaseRevisionLevel, sheMstpBaseConfName }
			STATUS current
			DESCRIPTION 
				"MSTP base parameters has been modified."
			::= { sheMstpNotifications 1 }

		
--   1.3.6.1.4.1.231.7.1.2.2.1.4.11.4.2
		sheMstpBaseConfIdVlanIdListModified NOTIFICATION-TYPE
			OBJECTS { sheMstpControlTimestamp, sheMstpBaseConfIdVlanIdList }
			STATUS current
			DESCRIPTION 
				"MSTP instance to VLAN ID mapping has been modified."
			::= { sheMstpNotifications 2 }

		
--   1.3.6.1.4.1.231.7.1.2.2.1.4.11.4.3
		sheMstpBridgeTcReset NOTIFICATION-TYPE
			OBJECTS { sheMstpControlTimestamp, sheMstpControlBridgeProtoParamIndex }
			STATUS current
			DESCRIPTION 
				"Mstp topology change detection flag has been reset."
			::= { sheMstpNotifications 3 }

		
--   1.3.6.1.4.1.231.7.1.2.2.1.4.11.4.4
		sheMstpBridgeParamEntryModified NOTIFICATION-TYPE
			OBJECTS { sheMstpControlTimestamp, sheMstpControlBridgeProtoParamIndex, sheMstpBridgeProtoParamBridgePriority, sheMstpBridgeProtoParamBridgeId }
			STATUS current
			DESCRIPTION 
				"Mstp bridge parameter entry has been modified."
			::= { sheMstpNotifications 4 }

		
--   1.3.6.1.4.1.231.7.1.2.2.1.4.11.4.5
		sheMstpPortParamEntryModified NOTIFICATION-TYPE
			OBJECTS { sheMstpControlTimestamp, sheMstpControlPortParamTableIndex, sheMstpPortParamAdminPathCost, sheMstpPortParamPortPriority, sheMstpPortParamPortId
				 }
			STATUS current
			DESCRIPTION 
				"Mstp port parameter entry has been modified."
			::= { sheMstpNotifications 5 }

		
--   1.3.6.1.4.1.231.7.1.2.2.1.4.11.4.6
		sheCistBridgeTcReset NOTIFICATION-TYPE
			OBJECTS { sheCistControlTimestamp }
			STATUS current
			DESCRIPTION 
				"Cist topology change detection flag has been reset."
			::= { sheMstpNotifications 6 }

		
--   1.3.6.1.4.1.231.7.1.2.2.1.4.11.4.7
		sheCistBridgeParamModified NOTIFICATION-TYPE
			OBJECTS { sheCistControlTimestamp, sheCistBridgeProtoParamBridgePriority, sheCistBridgeProtoParamMaxAge, sheCistBridgeProtoParamBridgeHelloTime, sheCistBridgeProtoParamBridgeForwardDelay, 
				sheCistBridgeProtoParamForceVer, sheCistBridgeProtoParamMaxHops, sheCistBridgeProtoParamSelfLoopDetect, sheCistBridgeProtoParamBridgeId }
			STATUS current
			DESCRIPTION 
				"Cist bridge parameters have been modified."
			::= { sheMstpNotifications 7 }

		
--   1.3.6.1.4.1.231.7.1.2.2.1.4.11.4.8
		sheCistPortParamEntryModified NOTIFICATION-TYPE
			OBJECTS { sheCistControlPortParamIndex, sheCistControlTimestamp, sheCistPortParamPortPriority, sheCistPortParamAdminEdgePort, sheCistPortParamMacEnabled, 
				sheCistPortParamAdminPointToPointMac, sheCistPortParamAdminPathCost, sheCistPortParamPortId }
			STATUS current
			DESCRIPTION 
				"Cist port parameter entry has been modified."
			::= { sheMstpNotifications 8 }

		
--   1.3.6.1.4.1.231.7.1.2.2.1.4.11.4.9
		sheMstpPortBridgeGroupAddressChanged NOTIFICATION-TYPE
			OBJECTS { sheMstpPortControlPortIndex, sheMstpPortControlBridgeGroupAddress }
			STATUS current
			DESCRIPTION 
				"MSTP's bridge group address has been changed."
			::= { sheMstpNotifications 9 }

		
--   1.3.6.1.4.1.231.7.1.2.2.1.4.11.4.10
		sheMstpBaseConfigReqResultTrap NOTIFICATION-TYPE
			OBJECTS { sheMstpBaseControlRequest, sheMstpBaseControlStatus, sheMstpBaseControlTimestamp, sheMstpBaseControlReqResult }
			STATUS current
			DESCRIPTION 
				"Configuration end trap for long running commands."
			::= { sheMstpNotifications 10 }

		
--   1.3.6.1.4.1.231.7.1.2.2.1.4.11.4.11		
		sheMstpControlReqResultTrap NOTIFICATION-TYPE
			OBJECTS { sheMstpControlRequest, sheMstpControlStatus, sheMstpControlTimestamp, sheMstpControlReqResult, sheMstpControlBridgeProtoParamIndex, 
				sheMstpControlPortParamTableIndex }
			STATUS current
			DESCRIPTION 
				"Configuration end trap for long running commands.
				Index parameters are used according controlrequest value - otherwise don't care."
			::= { sheMstpNotifications 11 }

		
--   1.3.6.1.4.1.231.7.1.2.2.1.4.11.4.12		
		sheCistControlReqResultTrap NOTIFICATION-TYPE
			OBJECTS { sheCistControlRequest, sheCistControlStatus, sheCistControlTimestamp, sheCistControlReqResult, sheCistControlPortParamIndex
				 }
			STATUS current
			DESCRIPTION 
				"Configuration end trap for long running commands.
				Index parameters are used according controlrequest value - otherwise don't care."
			::= { sheMstpNotifications 12 }

		
--   1.3.6.1.4.1.231.7.1.2.2.1.4.11.6
		sheMstpPort OBJECT IDENTIFIER ::= { sheMstpConfig 6 }

		
--   1.3.6.1.4.1.231.7.1.2.2.1.4.11.6.1
		sheMstpPortTable OBJECT-TYPE
			SYNTAX SEQUENCE OF SheMstpPortEntry
			MAX-ACCESS not-accessible
			STATUS current
			DESCRIPTION
				"The sheMstpPortTable holds a parameter related to overall MSTP protocol such as Bridge Group Address per port. 
				The key is a pointer to the port equal to sheBridgePortIndex. "
			::= { sheMstpPort 1 }

		
--   1.3.6.1.4.1.231.7.1.2.2.1.4.11.6.1.1
		sheMstpPortEntry OBJECT-TYPE
			SYNTAX SheMstpPortEntry
			MAX-ACCESS not-accessible
			STATUS current
			DESCRIPTION
				" Entry of the sheMstpPortTable. "
			INDEX { sheBridgePortIndex }
			::= { sheMstpPortTable 1 }

		
		SheMstpPortEntry ::=
			SEQUENCE { 
				sheMstpPortBridgeGroupAddress
					SheMstpPortControlBridgeGroupAddress
			 }

--   1.3.6.1.4.1.231.7.1.2.2.1.4.11.6.1.1.1
		sheMstpPortBridgeGroupAddress OBJECT-TYPE
			SYNTAX SheMstpPortControlBridgeGroupAddress
			MAX-ACCESS read-only
			STATUS current
			DESCRIPTION
				"MSTP bridge group Address to be used for the port."
			::= { sheMstpPortEntry 1 }

		
--   1.3.6.1.4.1.231.7.1.2.2.1.4.11.6.2
		sheMstpPortControl OBJECT IDENTIFIER ::= { sheMstpPort 2 }

		
--   1.3.6.1.4.1.231.7.1.2.2.1.4.11.6.2.1
		sheMstpPortControlRequest OBJECT-TYPE
			SYNTAX SheBridgeControlRequestType
			MAX-ACCESS read-write
			STATUS current
			DESCRIPTION
				"
				setMstpPortBridgeGroupAddress : 
				sheMstpPortControlPortIndex
				sheMstpPortControlBridgeGroupAddress
				"
			::= { sheMstpPortControl 1 }

		
--   1.3.6.1.4.1.231.7.1.2.2.1.4.11.6.2.2
		sheMstpPortControlStatus OBJECT-TYPE
			SYNTAX SheControlStatusType
			MAX-ACCESS read-only
			STATUS current
			DESCRIPTION
				"The status of a control request"
			::= { sheMstpPortControl 2 }

		
--   1.3.6.1.4.1.231.7.1.2.2.1.4.11.6.2.3
		sheMstpPortControlTimer OBJECT-TYPE
			SYNTAX Unsigned32
			MAX-ACCESS read-only
			STATUS current
			DESCRIPTION
				"The maximum wait time for the manager for command ending.
				For long running commands. The manager reads this value from the DSLAM."
			::= { sheMstpPortControl 3 }

		
--   1.3.6.1.4.1.231.7.1.2.2.1.4.11.6.2.4
		sheMstpPortControlReqResult OBJECT-TYPE
			SYNTAX SheBridgeControlRequestType
			MAX-ACCESS read-only
			STATUS current
			DESCRIPTION
				"The result of the last user command."
			::= { sheMstpPortControl 4 }

		
--   1.3.6.1.4.1.231.7.1.2.2.1.4.11.6.2.5
		sheMstpPortControlTimeStamp OBJECT-TYPE
			SYNTAX Unsigned32
			MAX-ACCESS read-only
			STATUS current
			DESCRIPTION
				"The time stamp of the last command (end of command)."
			::= { sheMstpPortControl 5 }

		
--   1.3.6.1.4.1.231.7.1.2.2.1.4.11.6.2.6
		sheMstpPortControlPortIndex OBJECT-TYPE
			SYNTAX Integer32
			MAX-ACCESS read-write
			STATUS current
			DESCRIPTION
				"This object points to the sheBridgePortTable (same as sheBridgePortIndex)."
			::= { sheMstpPortControl 6 }

		
--   1.3.6.1.4.1.231.7.1.2.2.1.4.11.6.2.7
		sheMstpPortControlBridgeGroupAddress OBJECT-TYPE
			SYNTAX SheMstpPortControlBridgeGroupAddress
			MAX-ACCESS read-write
			STATUS current
			DESCRIPTION
				"MSTP bridge group address to be used for the port."
			::= { sheMstpPortControl 7 }

		
--   1.3.6.1.4.1.231.7.1.2.2.1.4.11.5
		sheMstpConformance OBJECT IDENTIFIER ::= { sheMstpConfig 100 }

		
--   1.3.6.1.4.1.231.7.1.2.2.1.4.11.5.1
		sheMstpCompliances OBJECT IDENTIFIER ::= { sheMstpConformance 1 }

		
--   1.3.6.1.4.1.231.7.1.2.2.1.4.11.5.1.1
-- this module
-- this module
		sheMstpCompliance MODULE-COMPLIANCE
			STATUS current
			DESCRIPTION 
				"Description."
			MODULE -- this module
				MANDATORY-GROUPS { sheMstpBaseParamGroup, sheMstpBaseControlGroup, sheMstpBridgeParamGroup, sheMstpPortParamGroup, sheMstpControlGroup, 
					sheCistBridgeParamGroup, sheCistPortParamGroup, sheCistControlGroup, sheMstpNotificationGroup }
			::= { sheMstpCompliances 1 }

		
--   1.3.6.1.4.1.231.7.1.2.2.1.4.11.5.2
		sheMstpGroups OBJECT IDENTIFIER ::= { sheMstpConformance 2 }

		
--   1.3.6.1.4.1.231.7.1.2.2.1.4.11.5.2.1
		sheMstpBaseParamGroup OBJECT-GROUP
			OBJECTS { sheMstpBaseStatus, sheMstpBaseConfName, sheMstpBaseRevisionLevel, sheMstpBaseConfIdVlanIdList }
			STATUS current
			DESCRIPTION 
				"Description."
			::= { sheMstpGroups 1 }

		
--   1.3.6.1.4.1.231.7.1.2.2.1.4.11.5.2.2
		sheMstpBaseControlGroup OBJECT-GROUP
			OBJECTS { sheMstpBaseControlRequest, sheMstpBaseControlStatus, sheMstpBaseControlTimestamp, sheMstpBaseControlReqResult, sheMstpBaseControlTimer, 
				sheMstpBaseControlBaseStatus, sheMstpBaseControlConfName, sheMstpBaseControlRevisionLevel, sheMstpBaseControlConfIdVlanIdList }
			STATUS current
			DESCRIPTION 
				"Description."
			::= { sheMstpGroups 2 }

		
--   1.3.6.1.4.1.231.7.1.2.2.1.4.11.5.2.3
		sheMstpBridgeParamGroup OBJECT-GROUP
			OBJECTS { sheMstpBridgeProtoParamIndex, sheMstpBridgeProtoParamBridgeId, sheMstpBridgeProtoParamBridgePriority, sheMstpBridgeProtoParamTcTime, sheMstpBridgeProtoParamTcCount, 
				sheMstpBridgeProtoParamTc, sheMstpBridgeProtoParamDesignatedRoot, sheMstpBridgeProtoParamRootPort, sheMstpBridgeProtoParamRootPathCost }
			STATUS current
			DESCRIPTION 
				"Description."
			::= { sheMstpGroups 3 }

		
--   1.3.6.1.4.1.231.7.1.2.2.1.4.11.5.2.4
		sheMstpPortParamGroup OBJECT-GROUP
			OBJECTS { sheMstpPortParamTableIndex, sheMstpPortParamProtoIndex, sheMstpPortParamPortIndex, sheMstpPortParamUpTime, sheMstpPortParamState, 
				sheMstpPortParamPortId, sheMstpPortParamPortPriority, sheMstpPortParamDesignatedRoot, sheMstpPortParamDesignatedBridge, sheMstpPortParamDesignatedCost, 
				sheMstpPortParamPortRole, sheMstpPortBridgeGroupAddress, sheMstpPortParamDesignatedPort, sheMstpPortParamAdminPathCost, sheMstpPortParamCurrentPathCost
				 }
			STATUS current
			DESCRIPTION 
				"Description."
			::= { sheMstpGroups 4 }

		
--   1.3.6.1.4.1.231.7.1.2.2.1.4.11.5.2.5
		sheMstpControlGroup OBJECT-GROUP
			OBJECTS { sheMstpControlRequest, sheMstpControlStatus, sheMstpControlTimestamp, sheMstpControlReqResult, sheMstpControlTimer, 
				sheMstpControlBridgeProtoParamIndex, sheMstpControlBridgeProtoParamBridgePriority, sheMstpControlPortParamTableIndex, sheMstpControlPortParamPortPriority, sheMstpControlPortParamAdminPathCost, 
				sheMstpPortControlRequest, sheMstpPortControlStatus, sheMstpPortControlTimer, sheMstpPortControlReqResult, sheMstpPortControlTimeStamp, 
				sheMstpPortControlPortIndex, sheMstpPortControlBridgeGroupAddress }
			STATUS current
			DESCRIPTION 
				"Description."
			::= { sheMstpGroups 5 }

		
--   1.3.6.1.4.1.231.7.1.2.2.1.4.11.5.2.6
		sheCistBridgeParamGroup OBJECT-GROUP
			OBJECTS { sheCistBridgeProtoParamBridgeId, sheCistBridgeProtoParamBridgePriority, sheCistBridgeProtoParamTcTime, sheCistBridgeProtoParamTcCount, sheCistBridgeProtoParamTc, 
				sheCistBridgeProtoParamDesignatedRoot, sheCistBridgeProtoParamRootPort, sheCistBridgeProtoParamRootPathCost, sheCistBridgeProtoParamMaxAge, sheCistBridgeProtoParamHoldTime, 
				sheCistBridgeProtoParamForwardDelay, sheCistBridgeProtoParamBridgeMaxAge, sheCistBridgeProtoParamBridgeHelloTime, sheCistBridgeProtoParamBridgeForwardDelay, sheCistBridgeProtoParamForceVer, 
				sheCistBridgeProtoParamRegionalRootId, sheCistBridgeProtoParamRegionalRootPathCost, sheCistBridgeProtoParamMaxHops, sheCistBridgeProtoParamSelfLoopDetect }
			STATUS current
			DESCRIPTION 
				"Description."
			::= { sheMstpGroups 6 }

		
--   1.3.6.1.4.1.231.7.1.2.2.1.4.11.5.2.7
		sheCistPortParamGroup OBJECT-GROUP
			OBJECTS { sheCistPortParamIndex, sheCistPortParamUpTime, sheCistPortParamState, sheCistPortParamPortId, sheCistPortParamDesignatedRoot, 
				sheCistPortParamDesignatedCost, sheCistPortParamDesignatedBridge, sheCistPortParamTcAck, sheCistPortParamAdminEdgePort, sheCistPortParamOperEdgePort, 
				sheCistPortParamMacEnabled, sheCistPortParamMacOperational, sheCistPortParamAdminPointToPointMac, sheCistPortParamOperPointToPointMac, sheCistPortParamRegionalRootId, 
				sheCistPortParamRegionalRootPathCost, sheCistPortParamPortHelloTime, sheCistPortParamPortRole, sheCistPortParamDesignatedPort, sheCistPortParamLoopDetect, 
				sheCistPortParamHelloTime, sheCistPortParamPortPriority, sheCistPortParamAdminPathCost, sheCistPortParamCurrentPathCost }
			STATUS current
			DESCRIPTION 
				"Description."
			::= { sheMstpGroups 7 }

		
--   1.3.6.1.4.1.231.7.1.2.2.1.4.11.5.2.8
		sheCistControlGroup OBJECT-GROUP
			OBJECTS { sheCistControlTimestamp, sheCistControlReqResult, sheCistControlTimer, sheCistControlBridgeProtoParamBridgePriority, sheCistControlBridgeProtoParamBridgeMaxAge, 
				sheCistControlBridgeProtoParamBridgeHelloTime, sheCistControlBridgeProtoParamBridgeForwardDelay, sheCistControlPortParamIndex, sheCistControlPortParamAdminEdgePort, sheCistControlPortParamMacEnabled, 
				sheCistControlBridgeProtoParamForceVer, sheCistControlBridgeProtoParamMaxHops, sheCistControlBridgeProtoParamSelfLoopDetect, sheCistControlPortParamAdminPointToPointMac, sheCistControlRequest, 
				sheCistControlStatus, sheCistControlPortParamPortPriority, sheCistControlPortParamAdminPathCost }
			STATUS current
			DESCRIPTION 
				"Description."
			::= { sheMstpGroups 8 }

		
--   1.3.6.1.4.1.231.7.1.2.2.1.4.11.5.2.9
		sheMstpNotificationGroup NOTIFICATION-GROUP
			NOTIFICATIONS { sheMstpBaseConfigModified, sheMstpBaseConfIdVlanIdListModified, sheMstpBridgeTcReset, sheMstpBridgeParamEntryModified, sheMstpPortParamEntryModified, 
				sheCistBridgeTcReset, sheCistBridgeParamModified, sheCistPortParamEntryModified, sheMstpBaseConfigReqResultTrap, sheMstpControlReqResultTrap, 
				sheCistControlReqResultTrap, sheMstpPortBridgeGroupAddressChanged }
			STATUS current
			DESCRIPTION 
				"Description."
			::= { sheMstpGroups 9 }

		
--   1.3.6.1.4.1.231.7.1.2.2.1.4.12
		sheArp OBJECT IDENTIFIER ::= { sheBridgeMib 12 }

		
--   1.3.6.1.4.1.231.7.1.2.2.1.4.12.1
		sheArpBase OBJECT IDENTIFIER ::= { sheArp 1 }

		
--   1.3.6.1.4.1.231.7.1.2.2.1.4.12.1.1
		sheArpBroadcastFloodPermission OBJECT-TYPE
			SYNTAX ShePermissionType
			MAX-ACCESS read-only
			STATUS current
			DESCRIPTION
				"That is the so called China-Bit. ARP request broadcast
				messages received at the network interface (downstream)
				are either sent to each subscriber (flooding) or instead
				are dropped and answered by the NE itself through an
				ARP reply agent. Default is flooding permitted.
				deny (0)
				permit (1)  "
			DEFVAL { permit }
			::= { sheArpBase 1 }

		
--   1.3.6.1.4.1.231.7.1.2.2.1.4.12.2
		sheArpControl OBJECT IDENTIFIER ::= { sheArp 2 }

		
--   1.3.6.1.4.1.231.7.1.2.2.1.4.12.2.1
		sheArpControlRequest OBJECT-TYPE
			SYNTAX SheBridgeControlRequestType
			MAX-ACCESS read-write
			STATUS current
			DESCRIPTION
				"A SetRequest on this attribute starts a command
				execution process in the NetElement.
				
				801 - changeArpHandling
				parameters:
				sheArpControlBroadcastFloodPermission"
			::= { sheArpControl 1 }

		
--   1.3.6.1.4.1.231.7.1.2.2.1.4.12.2.2
		sheArpControlStatus OBJECT-TYPE
			SYNTAX SheControlStatusType
			MAX-ACCESS read-only
			STATUS current
			DESCRIPTION
				"Describes the status of a user command group, used
				for block commands while a command execution
				is in process.
				Values : idle, busy, passed, failed.
				idle: default, no command in process
				busy: command execution in process, attempts to start
				      another user command on this control block
				      are rejected
				passed/failed: status at end of command"
			::= { sheArpControl 2 }

		
--   1.3.6.1.4.1.231.7.1.2.2.1.4.12.2.3
		sheArpControlTimestamp OBJECT-TYPE
			SYNTAX Unsigned32
			UNITS "sec"
			MAX-ACCESS read-only
			STATUS current
			DESCRIPTION
				"Time stamp attribute set at the end of a command."
			::= { sheArpControl 3 }

		
--   1.3.6.1.4.1.231.7.1.2.2.1.4.12.2.4
		sheArpControlReqResult OBJECT-TYPE
			SYNTAX SheBridgeControlReqResultType
			MAX-ACCESS read-only
			STATUS current
			DESCRIPTION
				"Command result (error code) attribute."
			::= { sheArpControl 4 }

		
--   1.3.6.1.4.1.231.7.1.2.2.1.4.12.2.5
		sheArpControlTimer OBJECT-TYPE
			SYNTAX Unsigned32
			MAX-ACCESS read-only
			STATUS current
			DESCRIPTION
				"Maximum command execution time (timeout) in seconds
				in case of a long running command."
			::= { sheArpControl 5 }

		
--   1.3.6.1.4.1.231.7.1.2.2.1.4.12.2.6
		sheArpControlBroadcastFloodPermission OBJECT-TYPE
			SYNTAX ShePermissionType
			MAX-ACCESS read-write
			STATUS current
			DESCRIPTION
				"That is the so called China-Bit. ARP request broadcast
				messages received at the network interface (downstream)
				are either sent to each subscriber (flooding) or instead
				are dropped and answered by the NE itself through an
				ARP reply agent. Default is flooding permitted.
				deny (0)
				permit (1)
				Parameter for
				801 - changeArpHandling"
			::= { sheArpControl 6 }

		
--   1.3.6.1.4.1.231.7.1.2.2.1.4.12.3
		sheArpNotifications OBJECT IDENTIFIER ::= { sheArp 3 }

		
--   1.3.6.1.4.1.231.7.1.2.2.1.4.12.3.1
		sheArpBroadcastFloodPermissionModified NOTIFICATION-TYPE
			OBJECTS { sheArpControlTimestamp, sheArpBroadcastFloodPermission }
			STATUS current
			DESCRIPTION 
				"sheArpControlFloodPermission has been modified."
			::= { sheArpNotifications 2 }

		
--   1.3.6.1.4.1.231.7.1.2.2.1.4.12.3.2
		sheArpFixedIpAddressTableEntryCreated NOTIFICATION-TYPE
			OBJECTS { sheArpFixedIpAddressControlIndex, sheArpFixedIpAddressControlTimestamp, sheArpFixedIpAddressControlBridgePortIndex, sheArpFixedIpAddressControlAddress, sheArpFixedIpAddressControlInnerVlanTag, 
				sheArpFixedIpAddressControlOuterVlanTag }
			STATUS current
			DESCRIPTION 
				"sheArpFixedIpAddressTableEntry created."
			::= { sheArpNotifications 3 }

		
--   1.3.6.1.4.1.231.7.1.2.2.1.4.12.3.3
		sheArpFixedIpAddressTableEntryModified NOTIFICATION-TYPE
			OBJECTS { sheArpFixedIpAddressControlIndex, sheArpFixedIpAddressControlTimestamp, sheArpFixedIpAddressControlBridgePortIndex, sheArpFixedIpAddressControlAddress, sheArpFixedIpAddressControlInnerVlanTag, 
				sheArpFixedIpAddressControlOuterVlanTag }
			STATUS current
			DESCRIPTION 
				"sheArpFixedIpAddressTableEntry modified."
			::= { sheArpNotifications 4 }

		
--   1.3.6.1.4.1.231.7.1.2.2.1.4.12.3.4
		sheArpFixedIpAddressTableEntryDeleted NOTIFICATION-TYPE
			OBJECTS { sheArpFixedIpAddressControlIndex, sheArpFixedIpAddressControlTimestamp }
			STATUS current
			DESCRIPTION 
				"sheArpFixedIpAddressTableEntry deleted."
			::= { sheArpNotifications 5 }

		
--   1.3.6.1.4.1.231.7.1.2.2.1.4.12.5
		sheArpFixedIpAddressTable OBJECT-TYPE
			SYNTAX SEQUENCE OF SheArpFixedIpAddressEntry
			MAX-ACCESS not-accessible
			STATUS current
			DESCRIPTION
				"A set of fixed IP-Addresses for the ARP-Replay-Agent.
				There are two restrictions for the amount of possible IpAddresses on subscriber ports.
				One per bridgePort via sheBridgePortIpAddressPermitCount and
				one per UNI port via sheBridgeBaseMaxIpUNI parameter (global for NE), which could never
				exceeded. Remark this if more then one bridgePort is used on a single UNI port. 
				
				Note: 
				Currently, the SHE system support only 1 fixed IP address configuration per Bridgeport.
				For that reason, the NE will always use the configured Bridgeport index also as 
				selected value for the tableindex sheArpFixedIpAddressIndex. 
				The number of fixed addresses could be expanded in future releases, but such changes
				maybe force an index change for this table."
			::= { sheArp 5 }

		
--   1.3.6.1.4.1.231.7.1.2.2.1.4.12.5.1
		sheArpFixedIpAddressEntry OBJECT-TYPE
			SYNTAX SheArpFixedIpAddressEntry
			MAX-ACCESS not-accessible
			STATUS current
			DESCRIPTION
				"On entry consist of an Index ,one configured IP-Address, the bridgePortIndex of the configured port
				and the assoiated learned mac-address. Index for the Entry are the sheArpFixedIpAddressIndex."
			INDEX { sheArpFixedIpAddressIndex }
			::= { sheArpFixedIpAddressTable 1 }

		
		SheArpFixedIpAddressEntry ::=
			SEQUENCE { 
				sheArpFixedIpAddressIndex
					Integer32,
				sheArpFixedIpAddressBridgePortIndex
					Integer32,
				sheArpFixedIpAddress
					OCTET STRING,
				sheArpFixedIpAddressLearnedMac
					OCTET STRING,
				sheArpFixedIpAntiSpoofingStatus
					SheArpFixedIpAntiSpoofingStatusType,
				sheArpFixedIpAddressInnerVlanTag
					Integer32,
				sheArpFixedIpAddressOuterVlanTag
					Integer32
			 }

--   1.3.6.1.4.1.231.7.1.2.2.1.4.12.5.1.1
		sheArpFixedIpAddressIndex OBJECT-TYPE
			SYNTAX Integer32 (1..65535)
			MAX-ACCESS read-only
			STATUS current
			DESCRIPTION
				"A free running index for this table."
			::= { sheArpFixedIpAddressEntry 1 }

		
--   1.3.6.1.4.1.231.7.1.2.2.1.4.12.5.1.2
		sheArpFixedIpAddressBridgePortIndex OBJECT-TYPE
			SYNTAX Integer32 (1..65535)
			MAX-ACCESS read-only
			STATUS current
			DESCRIPTION
				"The index of the bridgePort were this Ip-Address is configured for."
			::= { sheArpFixedIpAddressEntry 2 }

		
--   1.3.6.1.4.1.231.7.1.2.2.1.4.12.5.1.3
		sheArpFixedIpAddress OBJECT-TYPE
			SYNTAX OCTET STRING (SIZE (4))
			MAX-ACCESS read-only
			STATUS current
			DESCRIPTION
				"A configured fixed ip-address.
				Note:
				There is an additional restriction of possible IpAddresses per UNI port which
				could never exceeded. Remark this if more then one bridgePort is used on a 
				single UNI port.
				"
			::= { sheArpFixedIpAddressEntry 3 }

		
--   1.3.6.1.4.1.231.7.1.2.2.1.4.12.5.1.4
		sheArpFixedIpAddressLearnedMac OBJECT-TYPE
			SYNTAX OCTET STRING (SIZE (6))
			MAX-ACCESS read-only
			STATUS current
			DESCRIPTION
				"The learned mac-address for this ipAddress-entry."
			::= { sheArpFixedIpAddressEntry 4 }

		
--   1.3.6.1.4.1.231.7.1.2.2.1.4.12.5.1.5
		sheArpFixedIpAntiSpoofingStatus OBJECT-TYPE
			SYNTAX SheArpFixedIpAntiSpoofingStatusType
			MAX-ACCESS read-only
			STATUS current
			DESCRIPTION
				"0-inactive: IP Anti-spoofing Disabled.  
				Or in case that an IP Anti-spoofing is enabled but the setting to the line card is failed. 
				1- active: IP Anti-spoofing is enabled and the setting to the line card is successful."
			::= { sheArpFixedIpAddressEntry 5 }

		
		sheArpFixedIpAddressInnerVlanTag OBJECT-TYPE
			SYNTAX Integer32 (0 | 1..4093)
			MAX-ACCESS read-only
			STATUS current
			DESCRIPTION
				"The inner vlan tag, where this configured fixed ip address should be valid on the bridgeport.
				This configuration is needed for IpAs feature and the ARP relay agent.
				0 could be used as wildcard configuration but the feature of use the same IP in different
				Vlan's is not available in that case.
				
				New parameter with R2.8."
			::= { sheArpFixedIpAddressEntry 6 }

		
		sheArpFixedIpAddressOuterVlanTag OBJECT-TYPE
			SYNTAX Integer32 (0 | 1..4093)
			MAX-ACCESS read-only
			STATUS current
			DESCRIPTION
				"The outer vlan tag, where this configured fixed ip address should be valid on the bridgeport.
				This configuration is needed for IpAs feature and the ARP relay agent.
				0 could be used as wildcard configuration but the feature of use the same IP in different
				Vlan's is not available in that case.
				
				New parameter with R2.8."
			::= { sheArpFixedIpAddressEntry 7 }

		
--   1.3.6.1.4.1.231.7.1.2.2.1.4.12.6
		sheArpFixedIpAddressControl OBJECT IDENTIFIER ::= { sheArp 6 }

		
--   1.3.6.1.4.1.231.7.1.2.2.1.4.12.6.1
		sheArpFixedIpAddressControlRequest OBJECT-TYPE
			SYNTAX SheBridgeControlRequestType
			MAX-ACCESS read-write
			STATUS current
			DESCRIPTION
				"A SetRequest on this attribute starts a command
				execution process in the NetElement.
				
				802 - createArpFixedIpAddressEntry
				parameters:
				sheArpFixedIpAddressControlBridgePortIndex
				sheArpFixedIpAddressControlAddress
				sheArpFixedIpAddressControlInnerVlanTag (new with R2.8)
				sheArpFixedIpAddressControlOuterVlanTag (new with R2.8)
				
				803 - modifyArpFixedIpAddressEntry
				parameters:
				sheArpFixedIpAddressControlIndex
				sheArpFixedIpAddressControlBridgePortIndex
				sheArpFixedIpAddressControlAddress
				sheArpFixedIpAddressControlInnerVlanTag (new with R2.8)
				sheArpFixedIpAddressControlOuterVlanTag (new with R2.8)
				
				804 - deleteArpFixedIpAddressEntry
				parameters:
				sheArpFixedIpAddressControlIndex"
			::= { sheArpFixedIpAddressControl 1 }

		
--   1.3.6.1.4.1.231.7.1.2.2.1.4.12.6.2
		sheArpFixedIpAddressControlIndex OBJECT-TYPE
			SYNTAX Integer32 (1..65535)
			MAX-ACCESS read-write
			STATUS current
			DESCRIPTION
				"The index of the table-entry to be configured."
			::= { sheArpFixedIpAddressControl 2 }

		
--   1.3.6.1.4.1.231.7.1.2.2.1.4.12.6.3
		sheArpFixedIpAddressControlStatus OBJECT-TYPE
			SYNTAX SheControlStatusType
			MAX-ACCESS read-only
			STATUS current
			DESCRIPTION
				"Describes the status of a user command group, used
				for block commands while a command execution
				is in process.
				Values : idle, busy, passed, failed.
				idle: default, no command in process
				busy: command execution in process, attempts to start
				      another user command on this control block
				      are rejected
				passed/failed: status at end of command"
			::= { sheArpFixedIpAddressControl 3 }

		
--   1.3.6.1.4.1.231.7.1.2.2.1.4.12.6.4
		sheArpFixedIpAddressControlTimestamp OBJECT-TYPE
			SYNTAX Unsigned32
			UNITS "sec"
			MAX-ACCESS read-only
			STATUS current
			DESCRIPTION
				"Time stamp attribute set at the end of a command."
			::= { sheArpFixedIpAddressControl 4 }

		
--   1.3.6.1.4.1.231.7.1.2.2.1.4.12.6.5
		sheArpFixedIpAddressControlReqResult OBJECT-TYPE
			SYNTAX SheBridgeControlReqResultType
			MAX-ACCESS read-only
			STATUS current
			DESCRIPTION
				"Command result (error code) attribute."
			::= { sheArpFixedIpAddressControl 5 }

		
--   1.3.6.1.4.1.231.7.1.2.2.1.4.12.6.6
		sheArpFixedIpAddressControlTimer OBJECT-TYPE
			SYNTAX Unsigned32
			MAX-ACCESS read-only
			STATUS current
			DESCRIPTION
				"Maximum command execution time (timeout) in seconds
				in case of a long running command."
			::= { sheArpFixedIpAddressControl 6 }

		
--   1.3.6.1.4.1.231.7.1.2.2.1.4.12.6.7
		sheArpFixedIpAddressControlBridgePortIndex OBJECT-TYPE
			SYNTAX Integer32 (1..65535)
			MAX-ACCESS read-write
			STATUS current
			DESCRIPTION
				"Look at table."
			::= { sheArpFixedIpAddressControl 7 }

		
--   1.3.6.1.4.1.231.7.1.2.2.1.4.12.6.8
		sheArpFixedIpAddressControlAddress OBJECT-TYPE
			SYNTAX OCTET STRING (SIZE (4))
			MAX-ACCESS read-write
			STATUS current
			DESCRIPTION
				"look at table."
			::= { sheArpFixedIpAddressControl 8 }

		
		sheArpFixedIpAddressControlInnerVlanTag OBJECT-TYPE
			SYNTAX Integer32 (0 | 1..4093)
			MAX-ACCESS read-write
			STATUS current
			DESCRIPTION
				"look at table.
				
				New parameter with R2.8."
			::= { sheArpFixedIpAddressControl 9 }

		
		sheArpFixedIpAddressControlOuterVlanTag OBJECT-TYPE
			SYNTAX Integer32 (0 | 1..4093)
			MAX-ACCESS read-write
			STATUS current
			DESCRIPTION
				"look at table.
				
				New parameter with R2.8."
			::= { sheArpFixedIpAddressControl 10 }

		
--   1.3.6.1.4.1.231.7.1.2.2.1.4.12.7
		sheDhcpSnoop OBJECT IDENTIFIER ::= { sheArp 7 }

		
--   1.3.6.1.4.1.231.7.1.2.2.1.4.12.7.1
		sheDhcpSnoopingTable OBJECT-TYPE
			SYNTAX SEQUENCE OF SheDhcpSnoopingEntry
			MAX-ACCESS not-accessible
			STATUS current
			DESCRIPTION
				"look at table."
			::= { sheDhcpSnoop 1 }

		
--   1.3.6.1.4.1.231.7.1.2.2.1.4.2.1.1.1
		sheDhcpSnoopingEntry OBJECT-TYPE
			SYNTAX SheDhcpSnoopingEntry
			MAX-ACCESS not-accessible
			STATUS current
			DESCRIPTION
				"One entry for every existing client for a bridgePort."
			INDEX { sheDhcpSnoopingBridgePortIndex, sheDhcpSnoopingIpAddress, sheDhcpSnoopingVlanId }
			::= { sheDhcpSnoopingTable 1 }

		
		SheDhcpSnoopingEntry ::=
			SEQUENCE { 
				sheDhcpSnoopingBridgePortIndex
					Integer32,
				sheDhcpSnoopingIpAddress
					IpAddress,
				sheDhcpSnoopingMacAddress
					OCTET STRING,
				sheDhcpSnoopingRemainingTime
					Integer32,
				sheIpAntiSpoofingStatus
					SheIpAntiSpoofingStatusType,
				sheDhcpSnoopingVlanId
					Unsigned32
			 }

--   1.3.6.1.4.1.231.7.1.2.2.1.4.12.7.1.1
		sheDhcpSnoopingBridgePortIndex OBJECT-TYPE
			SYNTAX Integer32 (1..65535)
			MAX-ACCESS read-only
			STATUS current
			DESCRIPTION
				"BridgePortIndex from bridgePortTable."
			::= { sheDhcpSnoopingEntry 1 }

		
--   1.3.6.1.4.1.231.7.1.2.2.1.4.12.7.1.2                                      
		sheDhcpSnoopingIpAddress OBJECT-TYPE
			SYNTAX IpAddress
			MAX-ACCESS read-only
			STATUS current
			DESCRIPTION
				"A client-assigned IP address from Dhcp server"
			::= { sheDhcpSnoopingEntry 2 }

		
--   1.3.6.1.4.1.231.7.1.2.2.1.4.12.7.1.3
		sheDhcpSnoopingMacAddress OBJECT-TYPE
			SYNTAX OCTET STRING (SIZE (6))
			MAX-ACCESS read-only
			STATUS current
			DESCRIPTION
				"A client's Mac address"
			::= { sheDhcpSnoopingEntry 3 }

		
--   1.3.6.1.4.1.231.7.1.2.2.1.4.12.7.1.4                                      
		sheDhcpSnoopingRemainingTime OBJECT-TYPE
			SYNTAX Integer32 (0..65535)
			UNITS "sec"
			MAX-ACCESS read-only
			STATUS current
			DESCRIPTION
				"Remaining time until the lease time to the IP address is over"
			::= { sheDhcpSnoopingEntry 4 }

		
--   1.3.6.1.4.1.231.7.1.2.2.1.4.12.7.1.5                                       
		sheIpAntiSpoofingStatus OBJECT-TYPE
			SYNTAX SheIpAntiSpoofingStatusType
			MAX-ACCESS read-only
			STATUS current
			DESCRIPTION
				"0-inactive: IP Anti-spoofing Diabled.  
				Or in case that an IP Anti-spoofing is enabled but the setting to the line card is failed. 
				1- active: IP Anti-spoofing is enabled and the setting to the line card is successful."
			::= { sheDhcpSnoopingEntry 5 }

		
		sheDhcpSnoopingVlanId OBJECT-TYPE
			SYNTAX Unsigned32 (1..4093)
			MAX-ACCESS read-only
			STATUS current
			DESCRIPTION
				"VlanIndex from VlanTable.
				This show which VLAN the client uses. "
			::= { sheDhcpSnoopingEntry 6 }

		
--   1.3.6.1.4.1.231.7.1.2.2.1.4.12.7.2
		sheDhcpSnoopControl OBJECT IDENTIFIER ::= { sheDhcpSnoop 2 }

		
--   1.3.6.1.4.1.231.7.1.2.2.1.4.12.7.2.1
		sheDhcpSnoopControlRequest OBJECT-TYPE
			SYNTAX SheBridgeControlRequestType
			MAX-ACCESS read-write
			STATUS current
			DESCRIPTION
				"
				deleteSnoopEntry(706),
				- it deletes a DHCP Snoop Entry as an ADMIN account.
				parameters:
				sheDhcpSnoopControlRequest
				sheDhcpSnoopControlBridgePortIndex
				sheDhcpSnoopControlIpAddress
				sheDhcpSnoopControlVlanId
				 
				ipAntiSpoofingSet(707),
				- it enables or diables an IP Anti-spoofing at NE.
				parameters:
				sheDhcpSnoopControlRequest
				sheIpAntiSpoofingControlEnable
				
				ipAntiSpoofingGracePeriodSet(708)
				- it sets a grace period when enabling an IP Anti-Spoofing. 
				parameters:
				sheDhcpSnoopControlRequest
				sheIpAntiSpoofingControlGracePeriod			           
				"
			::= { sheDhcpSnoopControl 1 }

		
--   1.3.6.1.4.1.231.7.1.2.2.1.4.12.7.2.2
		sheDhcpSnoopControlStatus OBJECT-TYPE
			SYNTAX SheControlStatusType
			MAX-ACCESS read-only
			STATUS current
			DESCRIPTION
				" "
			::= { sheDhcpSnoopControl 2 }

		
--   1.3.6.1.4.1.231.7.1.2.2.1.4.12.7.2.3
		sheDhcpSnoopControlTimer OBJECT-TYPE
			SYNTAX Gauge32
			MAX-ACCESS read-only
			STATUS current
			DESCRIPTION
				"Wait time for the manager on long lasting commands"
			::= { sheDhcpSnoopControl 3 }

		
--   1.3.6.1.4.1.231.7.1.2.2.1.4.12.7.2.4
		sheDhcpSnoopControlTimeStamp OBJECT-TYPE
			SYNTAX Unsigned32
			MAX-ACCESS read-only
			STATUS current
			DESCRIPTION
				"Time stamp attribute set at the end of a command"
			::= { sheDhcpSnoopControl 4 }

		
--   1.3.6.1.4.1.231.7.1.2.2.1.4.12.7.2.5
		sheDhcpSnoopControlReqResult OBJECT-TYPE
			SYNTAX SheBridgeControlReqResultType
			MAX-ACCESS read-only
			STATUS current
			DESCRIPTION
				"Result of the last command"
			::= { sheDhcpSnoopControl 5 }

		
--   1.3.6.1.4.1.231.7.1.2.2.1.4.12.7.2.6
		sheDhcpSnoopControlBridgePortIndex OBJECT-TYPE
			SYNTAX Integer32 (1..65535)
			MAX-ACCESS read-write
			STATUS current
			DESCRIPTION
				"A BridgePort Index to delete from table."
			::= { sheDhcpSnoopControl 6 }

		
--   1.3.6.1.4.1.231.7.1.2.2.1.4.12.7.2.7
		sheDhcpSnoopControlIpAddress OBJECT-TYPE
			SYNTAX IpAddress
			MAX-ACCESS read-write
			STATUS current
			DESCRIPTION
				"The IP address of the snoop entry to delete"
			::= { sheDhcpSnoopControl 7 }

		
--   1.3.6.1.4.1.231.7.1.2.2.1.4.12.7.2.8
		sheIpAntiSpoofingControlEnable OBJECT-TYPE
			SYNTAX TruthValue
			MAX-ACCESS read-write
			STATUS current
			DESCRIPTION
				"True : Enable
				False : Disable
				
				Note for R2.8:
				There is an additional per bridgeport configuration for IpAs with R2.8 available
				(sheBridgePortIpAsMode), which will be outvoted by this configuration
				if set to 'enable'. The configuration of the valid triple Ip-InnerTag-OuterTag
				will be done via DHCP or StaticIpAddress configuration."
			::= { sheDhcpSnoopControl 8 }

		
--   1.3.6.1.4.1.231.7.1.2.2.1.4.12.7.2.9
		sheIpAntiSpoofingControlGracePeriod OBJECT-TYPE
			SYNTAX Integer32 (1..65535)
			UNITS "sec"
			MAX-ACCESS read-write
			STATUS current
			DESCRIPTION
				"It is a wait time for retrieving an IP address from DHCP Server. 
				It prevents clients from not being set from DHCP 
				and finally being dropped when setting an IP Anti-Spoofing Enable. "
			::= { sheDhcpSnoopControl 9 }

		
		sheDhcpSnoopControlVlanId OBJECT-TYPE
			SYNTAX Unsigned32 (1..4093)
			MAX-ACCESS read-write
			STATUS current
			DESCRIPTION
				"VlanIndex from VlanTable.
				This show which VLAN the client uses. "
			::= { sheDhcpSnoopControl 10 }

		
--   1.3.6.1.4.1.231.7.1.2.2.1.4.12.7.3
		sheIpAntiSpoofingInfo OBJECT IDENTIFIER ::= { sheDhcpSnoop 3 }

		
--   1.3.6.1.4.1.231.7.1.2.2.1.4.12.7.3.1
		sheIpAntiSpoofingEnable OBJECT-TYPE
			SYNTAX TruthValue
			MAX-ACCESS read-only
			STATUS current
			DESCRIPTION
				"This configuration enable/disable the IpAs feature for all subscriber ports of the NE.
				True : Enable
				False : Disable
				
				Bridgeports on IU cards with wintegra chipset will not check any Vlan dependencies.
				If this switch was enabled', only cards with convergate chipset will made check 
				for the triple Ip-innerTag-OuterTag.
				
				Note for R2.8:
				There is an additional per bridgeport configuration for IpAs with R2.8 available
				(sheBridgePortIpAsMode), which will be outvoted by this configuration
				if set to 'enable'. The configuration of the valid triple Ip-InnerTag-OuterTag
				will be done via DHCP or StaticIpAddress configuration."
			DEFVAL { false }
			::= { sheIpAntiSpoofingInfo 1 }

		
--   1.3.6.1.4.1.231.7.1.2.2.1.4.12.7.3.2
		sheIpAntiSpoofingGracePeriod OBJECT-TYPE
			SYNTAX Integer32 (1..65535)
			UNITS "sec"
			MAX-ACCESS read-only
			STATUS current
			DESCRIPTION
				"It is a wait time for retrieving an IP address from DHCP Server. 
				It prevents clients from not being set from DHCP and finally being dropped
				when setting an IP Anti-Spoofing Enable. "
			::= { sheIpAntiSpoofingInfo 2 }

		
--   1.3.6.1.4.1.231.7.1.2.2.1.4.12.7.3.3
		sheIpAntiSpoofingRemainingTime OBJECT-TYPE
			SYNTAX Integer32 (0..65535)
			UNITS "sec"
			MAX-ACCESS read-only
			STATUS current
			DESCRIPTION
				"After user sets up an IP Anti-Spoofing, there is some interval until this function is actually adjusted to a LineCard. 
				It is called GracePeriod. This attruibute indicates the remaining time of real adjustment. "
			::= { sheIpAntiSpoofingInfo 3 }

		
--   1.3.6.1.4.1.231.7.1.2.2.1.4.12.7.4
		sheIpAntiSpoofingNotifications OBJECT IDENTIFIER ::= { sheDhcpSnoop 4 }

		
--   1.3.6.1.4.1.231.7.1.2.2.1.4.12.7.4.1
		sheIpAntiSpoofingEvents OBJECT IDENTIFIER ::= { sheIpAntiSpoofingNotifications 1 }

		
--   1.3.6.1.4.1.231.7.1.2.2.1.4.12.7.4.1.1
		sheIpAntiSpoofingChanged NOTIFICATION-TYPE
			OBJECTS { sheIpAntiSpoofingControlEnable }
			STATUS current
			DESCRIPTION 
				"It notifies that the Ip Anti-Spoofing setting is changed. 
				If sheIpAntiSpoofingEnableis True, it indicates IP Anti-Spoofing Enable. 
				If sheIpAntiSpoofingEnable is False, it means IP Anti-Spoofing Disable. "
			::= { sheIpAntiSpoofingEvents 1 }

		
--   1.3.6.1.4.1.231.7.1.2.2.1.4.12.7.4.1.2
		sheIpAntiSpoofingGracePeriodChanged NOTIFICATION-TYPE
			OBJECTS { sheIpAntiSpoofingControlGracePeriod }
			STATUS current
			DESCRIPTION 
				"It notifies that GracePeriod of IpAnti-Spoofing is modified.  "
			::= { sheIpAntiSpoofingEvents 2 }

		
--   1.3.6.1.4.1.231.7.1.2.2.1.4.12.7.4.1.3
		sheDhcpSnoopingEntryDeleted NOTIFICATION-TYPE
			OBJECTS { sheDhcpSnoopControlTimeStamp, sheDhcpSnoopControlBridgePortIndex, sheDhcpSnoopControlIpAddress, sheDhcpSnoopControlVlanId }
			STATUS current
			DESCRIPTION 
				"It notifies that the requested DhcpSnooping Entry was deleted."
			::= { sheIpAntiSpoofingEvents 3 }

		
--   1.3.6.1.4.1.231.7.1.2.2.1.4.12.8
		sheArpVlanTable OBJECT-TYPE
			SYNTAX SEQUENCE OF SheArpVlanEntry
			MAX-ACCESS not-accessible
			STATUS current
			DESCRIPTION
				"Each entry in this table describe an arp flood policy based on vlan."
			::= { sheArp 8 }

		
--   1.3.6.1.4.1.231.7.1.2.2.1.4.12.8.1
		sheArpVlanEntry OBJECT-TYPE
			SYNTAX SheArpVlanEntry
			MAX-ACCESS not-accessible
			STATUS current
			DESCRIPTION
				"entry of the table"
			INDEX { sheVlanIndex }
			::= { sheArpVlanTable 1 }

		
		SheArpVlanEntry ::=
			SEQUENCE { 
				sheArpVlanFloodFlag
					SheArpVlanFloodType
			 }

--   1.3.6.1.4.1.231.7.1.2.2.1.4.12.8.1.1
		sheArpVlanFloodFlag OBJECT-TYPE
			SYNTAX SheArpVlanFloodType
			MAX-ACCESS read-only
			STATUS current
			DESCRIPTION
				"arp forward policy flag."
			::= { sheArpVlanEntry 1 }

		
--   1.3.6.1.4.1.231.7.1.2.2.1.4.12.9
		sheArpVlanControl OBJECT IDENTIFIER ::= { sheArp 9 }

		
--   1.3.6.1.4.1.231.7.1.2.2.1.4.12.9.1
		sheArpVlanControlRequest OBJECT-TYPE
			SYNTAX SheBridgeControlRequestType
			MAX-ACCESS read-write
			STATUS current
			DESCRIPTION
				"
				command to control the sheArpVlanTable.
				the valid command should be:
				
				modifyArpVlanFlood(901):
				sheArpVlanControlVlanId
				sheArpVlanControlFloodFlag
				   "
			::= { sheArpVlanControl 1 }

		
--   1.3.6.1.4.1.231.7.1.2.2.1.4.12.9.2
		sheArpVlanControlStatus OBJECT-TYPE
			SYNTAX SheControlStatusType
			MAX-ACCESS read-only
			STATUS current
			DESCRIPTION
				"The status of a control request."
			::= { sheArpVlanControl 2 }

		
--   1.3.6.1.4.1.231.7.1.2.2.1.4.12.9.3
		sheArpVlanControlTimer OBJECT-TYPE
			SYNTAX Unsigned32
			MAX-ACCESS read-only
			STATUS current
			DESCRIPTION
				"The maximum wait time for the manager for command ending.
				For long running commands.
				The manager reads this value from the SHE."
			::= { sheArpVlanControl 3 }

		
--   1.3.6.1.4.1.231.7.1.2.2.1.4.12.9.4
		sheArpVlanControlReqResult OBJECT-TYPE
			SYNTAX SheBridgeControlReqResultType
			MAX-ACCESS read-only
			STATUS current
			DESCRIPTION
				"The result of the last user command."
			::= { sheArpVlanControl 4 }

		
--   1.3.6.1.4.1.231.7.1.2.2.1.4.12.9.5
		sheArpVlanControlTimeStamp OBJECT-TYPE
			SYNTAX Unsigned32
			UNITS "sec"
			MAX-ACCESS read-only
			STATUS current
			DESCRIPTION
				"The time stamp of the last command (end of command)."
			::= { sheArpVlanControl 5 }

		
--   1.3.6.1.4.1.231.7.1.2.2.1.4.12.9.6
		sheArpVlanControlVlanId OBJECT-TYPE
			SYNTAX INTEGER (1..4093)
			MAX-ACCESS read-write
			STATUS current
			DESCRIPTION
				"VLAN ID which is controlled for ARP flooding."
			::= { sheArpVlanControl 6 }

		
--   1.3.6.1.4.1.231.7.1.2.2.1.4.12.9.7
		sheArpVlanControlFloodFlag OBJECT-TYPE
			SYNTAX SheArpVlanFloodType
			MAX-ACCESS read-write
			STATUS current
			DESCRIPTION
				"Arp foward policy. enable: flood ARP packets, disable: do not flood ARP packets"
			::= { sheArpVlanControl 7 }

		
--   1.3.6.1.4.1.231.7.1.2.2.1.4.12.10
		sheArpVlanNotifications OBJECT IDENTIFIER ::= { sheArp 10 }

		
--   1.3.6.1.4.1.231.7.1.2.2.1.4.12.10.1
		sheArpVlanFloodModified NOTIFICATION-TYPE
			OBJECTS { sheArpVlanControlTimeStamp, sheArpVlanControlVlanId, sheArpVlanControlFloodFlag }
			STATUS current
			DESCRIPTION 
				"ARP flooding policy for a VLAN has been modified."
			::= { sheArpVlanNotifications 1 }

		
--   1.3.6.1.4.1.231.7.1.2.2.1.4.12.4
		sheArpConformance OBJECT IDENTIFIER ::= { sheArp 100 }

		
--   1.3.6.1.4.1.231.7.1.2.2.1.4.12.4.1
		sheArpCompliances OBJECT IDENTIFIER ::= { sheArpConformance 1 }

		
--   1.3.6.1.4.1.231.7.1.2.2.1.4.12.4.1.1
-- this module
-- this module
		sheArpCompliance MODULE-COMPLIANCE
			STATUS current
			DESCRIPTION 
				"The compliance statement for the ARP MIB.
				"
			MODULE -- this module
				MANDATORY-GROUPS { sheArpBaseGroup, sheArpControlGroup, sheArpNotificationGroup, sheArpFixedIpAddressGroup, sheArpFixedIpAddressControlGroup, 
					sheDhcpSnoopingGroup, sheDhcpSnoopingControlGroup, sheDhcpSnoopingNotificationGroup }
			::= { sheArpCompliances 1 }

		
--   1.3.6.1.4.1.231.7.1.2.2.1.4.12.4.2
		sheArpGroups OBJECT IDENTIFIER ::= { sheArpConformance 2 }

		
--   1.3.6.1.4.1.231.7.1.2.2.1.4.12.4.2.1
		sheArpBaseGroup OBJECT-GROUP
			OBJECTS { sheArpBroadcastFloodPermission, sheArpVlanFloodFlag }
			STATUS current
			DESCRIPTION 
				"Description."
			::= { sheArpGroups 1 }

		
--   1.3.6.1.4.1.231.7.1.2.2.1.4.12.4.2.2
		sheArpControlGroup OBJECT-GROUP
			OBJECTS { sheArpControlRequest, sheArpControlStatus, sheArpControlTimestamp, sheArpControlReqResult, sheArpControlTimer, 
				sheArpControlBroadcastFloodPermission, sheArpVlanControlRequest, sheArpVlanControlStatus, sheArpVlanControlTimer, sheArpVlanControlReqResult, 
				sheArpVlanControlTimeStamp, sheArpVlanControlVlanId, sheArpVlanControlFloodFlag }
			STATUS current
			DESCRIPTION 
				"Description."
			::= { sheArpGroups 2 }

		
--   1.3.6.1.4.1.231.7.1.2.2.1.4.12.4.2.3
		sheArpNotificationGroup NOTIFICATION-GROUP
			NOTIFICATIONS { sheArpBroadcastFloodPermissionModified, sheArpFixedIpAddressTableEntryCreated, sheArpFixedIpAddressTableEntryModified, sheArpFixedIpAddressTableEntryDeleted, sheArpVlanFloodModified
				 }
			STATUS current
			DESCRIPTION 
				"Description."
			::= { sheArpGroups 3 }

		
--   1.3.6.1.4.1.231.7.1.2.2.1.4.12.4.2.4
		sheArpFixedIpAddressGroup OBJECT-GROUP
			OBJECTS { sheArpFixedIpAddressIndex, sheArpFixedIpAddressBridgePortIndex, sheArpFixedIpAddress, sheArpFixedIpAddressLearnedMac, sheArpFixedIpAntiSpoofingStatus, 
				sheArpFixedIpAddressInnerVlanTag, sheArpFixedIpAddressOuterVlanTag }
			STATUS current
			DESCRIPTION 
				"Description."
			::= { sheArpGroups 4 }

		
--   1.3.6.1.4.1.231.7.1.2.2.1.4.12.4.2.5
		sheArpFixedIpAddressControlGroup OBJECT-GROUP
			OBJECTS { sheArpFixedIpAddressControlRequest, sheArpFixedIpAddressControlIndex, sheArpFixedIpAddressControlStatus, sheArpFixedIpAddressControlTimestamp, sheArpFixedIpAddressControlReqResult, 
				sheArpFixedIpAddressControlTimer, sheArpFixedIpAddressControlBridgePortIndex, sheArpFixedIpAddressControlAddress, sheArpFixedIpAddressControlInnerVlanTag, sheArpFixedIpAddressControlOuterVlanTag
				 }
			STATUS current
			DESCRIPTION 
				"Description."
			::= { sheArpGroups 5 }

		
		sheDhcpSnoopingGroup OBJECT-GROUP
			OBJECTS { sheDhcpSnoopingBridgePortIndex, sheDhcpSnoopingIpAddress, sheDhcpSnoopingMacAddress, sheDhcpSnoopingRemainingTime, sheIpAntiSpoofingStatus, 
				sheIpAntiSpoofingEnable, sheIpAntiSpoofingGracePeriod, sheIpAntiSpoofingRemainingTime, sheDhcpSnoopingVlanId }
			STATUS current
			DESCRIPTION 
				"Description."
			::= { sheArpGroups 6 }

		
		sheDhcpSnoopingControlGroup OBJECT-GROUP
			OBJECTS { sheDhcpSnoopControlRequest, sheDhcpSnoopControlStatus, sheDhcpSnoopControlTimer, sheDhcpSnoopControlTimeStamp, sheDhcpSnoopControlReqResult, 
				sheDhcpSnoopControlBridgePortIndex, sheDhcpSnoopControlIpAddress, sheIpAntiSpoofingControlEnable, sheIpAntiSpoofingControlGracePeriod, sheDhcpSnoopControlVlanId
				 }
			STATUS current
			DESCRIPTION 
				"Description."
			::= { sheArpGroups 7 }

		
		sheDhcpSnoopingNotificationGroup NOTIFICATION-GROUP
			NOTIFICATIONS { sheIpAntiSpoofingChanged, sheIpAntiSpoofingGracePeriodChanged, sheDhcpSnoopingEntryDeleted }
			STATUS current
			DESCRIPTION 
				"Description."
			::= { sheArpGroups 8 }

		
--   1.3.6.1.4.1.231.7.1.2.2.1.4.13
		sheQoSPm OBJECT IDENTIFIER ::= { sheBridgeMib 13 }

		
--   1.3.6.1.4.1.231.7.1.2.2.1.4.13.1
		sheQoSPmCounterTable OBJECT-TYPE
			SYNTAX SEQUENCE OF SheQoSPmCounterEntry
			MAX-ACCESS not-accessible
			STATUS current
			DESCRIPTION
				"The QoS Performance counter table."
			::= { sheQoSPm 1 }

		
--   1.3.6.1.4.1.231.7.1.2.2.1.4.13.1.1
		sheQoSPmCounterEntry OBJECT-TYPE
			SYNTAX SheQoSPmCounterEntry
			MAX-ACCESS not-accessible
			STATUS current
			DESCRIPTION
				"The table provides set of hw-packet counters for egrees direction.
				The given values represent the current queue fill levels.
				These table will be indeced by the ifIndex of the GE uplink.
				To get usefull results, the NE should support a reasonable priority 
				to queue mapping."
			INDEX { ifIndex }
			::= { sheQoSPmCounterTable 1 }

		
		SheQoSPmCounterEntry ::=
			SEQUENCE { 
				sheQoSPacketCounterQueue1
					Counter64,
				sheQoSPacketCounterQueue2
					Counter64,
				sheQoSPacketCounterQueue3
					Counter64,
				sheQoSPacketCounterQueue4
					Counter64,
				sheQoSPacketCounterQueue5
					Counter64,
				sheQoSPacketCounterQueue6
					Counter64,
				sheQoSPacketCounterQueue7
					Counter64,
				sheQoSPacketCounterQueue8
					Counter64,
				sheQoSDroppedPacketCounter
					Counter64
			 }

--   1.3.6.1.4.1.231.7.1.2.2.1.4.13.1.1.1
		sheQoSPacketCounterQueue1 OBJECT-TYPE
			SYNTAX Counter64
			MAX-ACCESS read-only
			STATUS current
			DESCRIPTION
				"Current number of packets in the Queue."
			::= { sheQoSPmCounterEntry 1 }

		
--   1.3.6.1.4.1.231.7.1.2.2.1.4.13.1.1.2
		sheQoSPacketCounterQueue2 OBJECT-TYPE
			SYNTAX Counter64
			MAX-ACCESS read-only
			STATUS current
			DESCRIPTION
				"Current number of packets in the Queue."
			::= { sheQoSPmCounterEntry 2 }

		
--   1.3.6.1.4.1.231.7.1.2.2.1.4.13.1.1.3
		sheQoSPacketCounterQueue3 OBJECT-TYPE
			SYNTAX Counter64
			MAX-ACCESS read-only
			STATUS current
			DESCRIPTION
				"Current number of packets in the Queue."
			::= { sheQoSPmCounterEntry 3 }

		
--   1.3.6.1.4.1.231.7.1.2.2.1.4.13.1.1.4
		sheQoSPacketCounterQueue4 OBJECT-TYPE
			SYNTAX Counter64
			MAX-ACCESS read-only
			STATUS current
			DESCRIPTION
				"Current number of packets in the Queue."
			::= { sheQoSPmCounterEntry 4 }

		
--   1.3.6.1.4.1.231.7.1.2.2.1.4.13.1.1.5
		sheQoSPacketCounterQueue5 OBJECT-TYPE
			SYNTAX Counter64
			MAX-ACCESS read-only
			STATUS current
			DESCRIPTION
				"Current number of packets in the Queue."
			::= { sheQoSPmCounterEntry 5 }

		
--   1.3.6.1.4.1.231.7.1.2.2.1.4.13.1.1.6
		sheQoSPacketCounterQueue6 OBJECT-TYPE
			SYNTAX Counter64
			MAX-ACCESS read-only
			STATUS current
			DESCRIPTION
				"Current number of packets in the Queue."
			::= { sheQoSPmCounterEntry 6 }

		
--   1.3.6.1.4.1.231.7.1.2.2.1.4.13.1.1.7
		sheQoSPacketCounterQueue7 OBJECT-TYPE
			SYNTAX Counter64
			MAX-ACCESS read-only
			STATUS current
			DESCRIPTION
				"Current number of packets in the Queue."
			::= { sheQoSPmCounterEntry 7 }

		
--   1.3.6.1.4.1.231.7.1.2.2.1.4.13.1.1.8
		sheQoSPacketCounterQueue8 OBJECT-TYPE
			SYNTAX Counter64
			MAX-ACCESS read-only
			STATUS current
			DESCRIPTION
				"Current number of packets in the Queue."
			::= { sheQoSPmCounterEntry 8 }

		
--   1.3.6.1.4.1.231.7.1.2.2.1.4.13.1.1.9
		sheQoSDroppedPacketCounter OBJECT-TYPE
			SYNTAX Counter64
			MAX-ACCESS read-only
			STATUS current
			DESCRIPTION
				"Dropped packets per Interface."
			::= { sheQoSPmCounterEntry 9 }

		
--   1.3.6.1.4.1.231.7.1.2.2.1.4.13.2
		sheQoSPmControl OBJECT IDENTIFIER ::= { sheQoSPm 2 }

		
--   1.3.6.1.4.1.231.7.1.2.2.1.4.13.2.1
		sheQoSPmControlRequest OBJECT-TYPE
			SYNTAX SheBridgeControlRequestType
			MAX-ACCESS read-write
			STATUS current
			DESCRIPTION
				"clearQosPmCounters:
				sheQoSPmControlIndex
				
				
				
				"
			::= { sheQoSPmControl 1 }

		
--   1.3.6.1.4.1.231.7.1.2.2.1.4.13.2.2
		sheQoSPmControlIndex OBJECT-TYPE
			SYNTAX Integer32
			MAX-ACCESS read-write
			STATUS current
			DESCRIPTION
				"Value depends on the used ControlRequest."
			::= { sheQoSPmControl 2 }

		
--   1.3.6.1.4.1.231.7.1.2.2.1.4.13.2.3
		sheQoSPmControlStatus OBJECT-TYPE
			SYNTAX SheControlStatusType
			MAX-ACCESS read-only
			STATUS current
			DESCRIPTION
				"The status of a user command. 
				."
			::= { sheQoSPmControl 3 }

		
--   1.3.6.1.4.1.231.7.1.2.2.1.4.13.2.4
		sheQoSPmControlTimer OBJECT-TYPE
			SYNTAX Gauge32
			MAX-ACCESS read-only
			STATUS current
			DESCRIPTION
				"The maximum wait time for the manager for a long running user command. 
				"
			::= { sheQoSPmControl 4 }

		
--   1.3.6.1.4.1.231.7.1.2.2.1.4.13.2.5
		sheQoSPmControlReqResult OBJECT-TYPE
			SYNTAX SheBridgeControlReqResultType
			MAX-ACCESS read-only
			STATUS current
			DESCRIPTION
				"The result of the last user command."
			::= { sheQoSPmControl 5 }

		
--   1.3.6.1.4.1.231.7.1.2.2.1.4.13.2.6
		sheQoSPmControlTimeStamp OBJECT-TYPE
			SYNTAX Unsigned32
			UNITS "sec"
			MAX-ACCESS read-only
			STATUS current
			DESCRIPTION
				"The time stamp of the last command (end of command)."
			::= { sheQoSPmControl 6 }

		
--   1.3.6.1.4.1.231.7.1.2.2.1.4.13.3
		sheQoSPmNotifications OBJECT IDENTIFIER ::= { sheQoSPm 3 }

		
--   1.3.6.1.4.1.231.7.1.2.2.1.4.13.3.1
		sheQoSPmCountersCleared NOTIFICATION-TYPE
			OBJECTS { sheQoSPmControlIndex, sheQoSPmControlTimeStamp }
			STATUS current
			DESCRIPTION 
				"Counters cleared."
			::= { sheQoSPmNotifications 1 }

		
--   1.3.6.1.4.1.231.7.1.2.2.1.4.13.4
		sheQoSPmConformance OBJECT IDENTIFIER ::= { sheQoSPm 100 }

		
--   1.3.6.1.4.1.231.7.1.2.2.1.4.13.4.1
		sheQoSPmCompliances OBJECT IDENTIFIER ::= { sheQoSPmConformance 1 }

		
--   1.3.6.1.4.1.231.7.1.2.2.1.4.13.4.1.1
-- this module
-- this module
		sheQoSPmCompliance MODULE-COMPLIANCE
			STATUS current
			DESCRIPTION 
				"Description."
			MODULE -- this module
				MANDATORY-GROUPS { sheQoSPmGroup, sheQoSPmControlGroup, sheQoSPmNotificationsGroup }
			::= { sheQoSPmCompliances 1 }

		
--   1.3.6.1.4.1.231.7.1.2.2.1.4.13.4.2
		sheQoSPmGroups OBJECT IDENTIFIER ::= { sheQoSPmConformance 2 }

		
--   1.3.6.1.4.1.231.7.1.2.2.1.4.13.4.2.1
		sheQoSPmGroup OBJECT-GROUP
			OBJECTS { sheQoSPacketCounterQueue1, sheQoSPacketCounterQueue2, sheQoSPacketCounterQueue3, sheQoSPacketCounterQueue4, sheQoSPacketCounterQueue5, 
				sheQoSPacketCounterQueue6, sheQoSPacketCounterQueue7, sheQoSPacketCounterQueue8, sheQoSDroppedPacketCounter }
			STATUS current
			DESCRIPTION 
				"Description."
			::= { sheQoSPmGroups 1 }

		
--   1.3.6.1.4.1.231.7.1.2.2.1.4.13.4.2.2
		sheQoSPmControlGroup OBJECT-GROUP
			OBJECTS { sheQoSPmControlRequest, sheQoSPmControlIndex, sheQoSPmControlStatus, sheQoSPmControlTimer, sheQoSPmControlReqResult, 
				sheQoSPmControlTimeStamp }
			STATUS current
			DESCRIPTION 
				"Description."
			::= { sheQoSPmGroups 2 }

		
--   1.3.6.1.4.1.231.7.1.2.2.1.4.13.4.2.3
		sheQoSPmNotificationsGroup NOTIFICATION-GROUP
			NOTIFICATIONS { sheQoSPmCountersCleared }
			STATUS current
			DESCRIPTION 
				"Description."
			::= { sheQoSPmGroups 3 }

		
--   1.3.6.1.4.1.231.7.1.2.2.1.4.14
		sheUmas OBJECT IDENTIFIER ::= { sheBridgeMib 14 }

		
--  --------------------------------------------
-- Bridge UMAS(Uplink MAC AntiSpoofing) Group
-- --------------------------------------------
-- 1.3.6.1.4.1.231.7.1.2.2.1.4.14.1
		sheUmasBase OBJECT IDENTIFIER ::= { sheUmas 1 }

		
--   1.3.6.1.4.1.231.7.1.2.2.1.4.14.1.1
		sheUmasUseDhcpNextHop OBJECT-TYPE
			SYNTAX TruthValue
			MAX-ACCESS read-only
			STATUS current
			DESCRIPTION
				"Using the nexthop address of DHCP packet as a protected MAC address."
			::= { sheUmasBase 1 }

		
		sheUmasBaseUsePppoeNextHop OBJECT-TYPE
			SYNTAX TruthValue
			MAX-ACCESS read-only
			STATUS current
			DESCRIPTION
				"Indicates if umas keeps the uplink mac address through PADR (PPPoE Active Discovery Request)."
			::= { sheUmasBase 2 }

		
		sheUmasBasePppoeAgingTime OBJECT-TYPE
			SYNTAX Unsigned32 (600..4294967295)
			UNITS "sec"
			MAX-ACCESS read-only
			STATUS current
			DESCRIPTION
				"Indicates time until the next-hop address of pppoe is deleted from umas table."
			DEFVAL { 3600 }
			::= { sheUmasBase 3 }

		
--   1.3.6.1.4.1.231.7.1.2.2.1.4.14.2
		sheUmasTable OBJECT-TYPE
			SYNTAX SEQUENCE OF SheUmasEntry
			MAX-ACCESS not-accessible
			STATUS current
			DESCRIPTION
				"The Uplink MAC antispoofing table."
			::= { sheUmas 2 }

		
--   1.3.6.1.4.1.231.7.1.2.2.1.4.14.2.1
		sheUmasEntry OBJECT-TYPE
			SYNTAX SheUmasEntry
			MAX-ACCESS not-accessible
			STATUS current
			DESCRIPTION
				"Umas is an abbreviation for Uplink mac anti spoofing. 
				This table contains a few entries for Uplink (Gateway, DHCP server, etc) Mac anti-spoofing function. 
				2 ways for that: specifying a static Mac address and automatically collecting 
				Mac addresses to be protected."
			INDEX { sheUmasIndex }
			::= { sheUmasTable 1 }

		
		SheUmasEntry ::=
			SEQUENCE { 
				sheUmasIndex
					Integer32,
				sheUmasAddress
					OCTET STRING,
				sheUmasIsStatic
					TruthValue,
				sheUmasIsDhcpNextHop
					TruthValue,
				sheUmasIsPppoeNextHop
					TruthValue
			 }

--   1.3.6.1.4.1.231.7.1.2.2.1.4.14.2.1.1
		sheUmasIndex OBJECT-TYPE
			SYNTAX Integer32 (1..65535)
			MAX-ACCESS read-only
			STATUS current
			DESCRIPTION
				"The index of Umas table."
			::= { sheUmasEntry 1 }

		
--   1.3.6.1.4.1.231.7.1.2.2.1.4.14.2.1.2
		sheUmasAddress OBJECT-TYPE
			SYNTAX OCTET STRING (SIZE (6))
			MAX-ACCESS read-only
			STATUS current
			DESCRIPTION
				"The mac address which is proctected."
			::= { sheUmasEntry 2 }

		
--   1.3.6.1.4.1.231.7.1.2.2.1.4.14.2.1.3
		sheUmasIsStatic OBJECT-TYPE
			SYNTAX TruthValue
			MAX-ACCESS read-only
			STATUS current
			DESCRIPTION
				"Indicates if this entry is static or not."
			::= { sheUmasEntry 3 }

		
--   1.3.6.1.4.1.231.7.1.2.2.1.4.14.2.1.4
		sheUmasIsDhcpNextHop OBJECT-TYPE
			SYNTAX TruthValue
			MAX-ACCESS read-only
			STATUS current
			DESCRIPTION
				"Indicates if this address is the next hop address of DHCP packet."
			::= { sheUmasEntry 4 }

		
--   1.3.6.1.4.1.231.7.1.2.2.1.4.14.2.1.4
		sheUmasIsPppoeNextHop OBJECT-TYPE
			SYNTAX TruthValue
			MAX-ACCESS read-only
			STATUS current
			DESCRIPTION
				"Indicates if this address is the next hop address of PPPoE packet."
			::= { sheUmasEntry 5 }

		
--   1.3.6.1.4.1.231.7.1.2.2.1.4.14.3
		sheUmasControl OBJECT IDENTIFIER ::= { sheUmas 3 }

		
--   1.3.6.1.4.1.231.7.1.2.2.1.4.14.3.1
		sheUmasControlRequest OBJECT-TYPE
			SYNTAX SheUmasControlRequestType
			MAX-ACCESS read-write
			STATUS current
			DESCRIPTION
				"setUmasUseDhcpNextHop:
				sheUmasControlUseDhcpNextHop
				
				addUmasStaticAddr:
				sheUmasControlIndex
				sheUmasControlStaticAddr
				
				delUmasStaticAddr:
				sheUmasControlIndex
				sheUmasControlStaticAddr
				
				setUmasUsePppoeNextHop:
				sheUmasControlUsePppoeNextHop
				
				setUmasPppoeAgingTime:
				sheUmasControlPppoeAgingTime
				"
			::= { sheUmasControl 1 }

		
--   1.3.6.1.4.1.231.7.1.2.2.1.4.14.3.2
		sheUmasControlStatus OBJECT-TYPE
			SYNTAX SheControlStatusType
			MAX-ACCESS read-only
			STATUS current
			DESCRIPTION
				"Status of command. If requestBusy a command is still ongoing and another command will be rejected."
			::= { sheUmasControl 2 }

		
--   1.3.6.1.4.1.231.7.1.2.2.1.4.14.3.3
		sheUmasControlTimeStamp OBJECT-TYPE
			SYNTAX Unsigned32
			UNITS "sec"
			MAX-ACCESS read-only
			STATUS current
			DESCRIPTION
				"The time stamp of the last command (end of command)."
			::= { sheUmasControl 3 }

		
--   1.3.6.1.4.1.231.7.1.2.2.1.4.14.3.4
		sheUmasControlTimer OBJECT-TYPE
			SYNTAX Gauge32
			MAX-ACCESS read-only
			STATUS current
			DESCRIPTION
				"The maximum wait time for the manager for a long running user command. 
				"
			::= { sheUmasControl 4 }

		
--   1.3.6.1.4.1.231.7.1.2.2.1.4.14.3.5
		sheUmasControlReqResult OBJECT-TYPE
			SYNTAX SheUmasControlReqResultType
			MAX-ACCESS read-only
			STATUS current
			DESCRIPTION
				"The result of the last user command."
			::= { sheUmasControl 5 }

		
--   1.3.6.1.4.1.231.7.1.2.2.1.4.14.3.6
		sheUmasControlStaticAddr OBJECT-TYPE
			SYNTAX OCTET STRING (SIZE (6))
			MAX-ACCESS read-write
			STATUS current
			DESCRIPTION
				"The static MAC address which should be protected."
			::= { sheUmasControl 6 }

		
--   1.3.6.1.4.1.231.7.1.2.2.1.4.14.3.7
		sheUmasControlUseDhcpNextHop OBJECT-TYPE
			SYNTAX TruthValue
			MAX-ACCESS read-write
			STATUS current
			DESCRIPTION
				"Using the nexthop address of DHCP packet as a protected MAC address."
			::= { sheUmasControl 7 }

		
--  1.3.6.1.4.1.231.7.1.2.2.1.4.14.3.8
		sheUmasControlIndex OBJECT-TYPE
			SYNTAX Integer32
			MAX-ACCESS read-write
			STATUS current
			DESCRIPTION
				"Index for controlrequest to identify the table entry."
			::= { sheUmasControl 8 }

		
--   1.3.6.1.4.1.231.7.1.2.2.1.4.14.3.7
		sheUmasControlUsePppoeNextHop OBJECT-TYPE
			SYNTAX TruthValue
			MAX-ACCESS read-write
			STATUS current
			DESCRIPTION
				"Indicates if umas keeps the uplink mac address through PADR (PPPoE Active Discovery Request)."
			::= { sheUmasControl 9 }

		
		sheUmasControlPppoeAgingTime OBJECT-TYPE
			SYNTAX Unsigned32 (600..4294967295)
			UNITS "sec"
			MAX-ACCESS read-write
			STATUS current
			DESCRIPTION
				"Indicates time until the next-hop address of pppoe is deleted from umas table."
			::= { sheUmasControl 10 }

		
--   1.3.6.1.4.1.231.7.1.2.2.1.4.14.4
		sheUmasNotifications OBJECT IDENTIFIER ::= { sheUmas 4 }

		
--   1.3.6.1.4.1.231.7.1.2.2.1.4.14.4.1
		sheUmasStaticAddrChanged NOTIFICATION-TYPE
			OBJECTS { sheUmasControlRequest, sheUmasControlStaticAddr, sheUmasControlIndex }
			STATUS current
			DESCRIPTION 
				"Called after addUmasStaticAddr(102), delUmasStaticAddr(103) is requested for notification."
			::= { sheUmasNotifications 1 }

		
--   1.3.6.1.4.1.231.7.1.2.2.1.4.14.4.2
		sheUmasUseDhcpNextHopChanged NOTIFICATION-TYPE
			OBJECTS { sheUmasControlUseDhcpNextHop }
			STATUS current
			DESCRIPTION 
				"Called after setUmasUseDhcpNextHop (101) is requested for notification."
			::= { sheUmasNotifications 2 }

		
--   1.3.6.1.4.1.231.7.1.2.2.1.4.14.4.3
		sheUmasUsePppoeNextHopChanged NOTIFICATION-TYPE
			OBJECTS { sheUmasControlUsePppoeNextHop }
			STATUS current
			DESCRIPTION 
				"Called after setUmasUsePppoeNextHop (104) is requested for notification."
			::= { sheUmasNotifications 3 }

		
--   1.3.6.1.4.1.231.7.1.2.2.1.4.14.4.4
		sheUmasPppoeAgingTimeChanged NOTIFICATION-TYPE
			OBJECTS { sheUmasControlPppoeAgingTime }
			STATUS current
			DESCRIPTION 
				"Called after setUmasPppoeAgingTime (105) is requested for notification."
			::= { sheUmasNotifications 4 }

		
		sheUmasVlanEntryCreated NOTIFICATION-TYPE
			OBJECTS { sheUmasVlanControlTimestamp, sheUmasVlanControlVlanId }
			STATUS current
			DESCRIPTION 
				"Configuration notification."
			::= { sheUmasNotifications 5 }

		
		sheUmasVlanEntryDeleted NOTIFICATION-TYPE
			OBJECTS { sheUmasVlanControlTimestamp, sheUmasVlanControlVlanId }
			STATUS current
			DESCRIPTION 
				"Configuration notification."
			::= { sheUmasNotifications 6 }

		
		sheUmasAlarms OBJECT IDENTIFIER ::= { sheUmasNotifications 10 }

		
		sheUmasIUBlacklistOverflow NOTIFICATION-TYPE
			OBJECTS { sheAlarmTimeAndDate, sheAlarmReportingSource, sheAlarmReportingSourceType, sheAlarmSeverity }
			STATUS current
			DESCRIPTION 
				"UMAS blacklist overflow per card alarm.
				
				AlarmReportingSource -> entPhysicalIndex of card
				AlarmReportingSourceType -> physicalEntity
				
				New with R2.8 maintenance."
			::= { sheUmasAlarms 1 }

		
		sheUmasVlanTable OBJECT-TYPE
			SYNTAX SEQUENCE OF SheUmasVlanEntry
			MAX-ACCESS not-accessible
			STATUS current
			DESCRIPTION
				"CR#003659 - UMAS extension with R2.8
				
				New with R2.8 maintenance."
			::= { sheUmas 5 }

		
		sheUmasVlanEntry OBJECT-TYPE
			SYNTAX SheUmasVlanEntry
			MAX-ACCESS not-accessible
			STATUS current
			DESCRIPTION
				"The table contain all VLAN's for which dynamic UMAS should be supported. "
			INDEX { sheUmasVlanId }
			::= { sheUmasVlanTable 1 }

		
		SheUmasVlanEntry ::=
			SEQUENCE { 
				sheUmasVlanId
					INTEGER
			 }

		sheUmasVlanId OBJECT-TYPE
			SYNTAX INTEGER (1..4093)
			MAX-ACCESS read-only
			STATUS current
			DESCRIPTION
				"A vlanid of which dynamic UMAS should be supported.
				
				"
			::= { sheUmasVlanEntry 1 }

		
-- 1.3.6.1.4.1.231.7.1.2.2.1.4.14.6
		sheUmasVlanControl OBJECT IDENTIFIER ::= { sheUmas 6 }

		
-- 1.3.6.1.4.1.231.7.1.2.2.1.4.14.6.1
		sheUmasVlanControlRequest OBJECT-TYPE
			SYNTAX SheUmasControlRequestType
			MAX-ACCESS read-write
			STATUS current
			DESCRIPTION
				"
				createUmasVlanEntry (110):
				 sheUmasVlanControlVlanId
				
				deleteUmasVlanEntry (111):
				 sheUmasVlanControlVlanId
				"
			::= { sheUmasVlanControl 1 }

		
		sheUmasVlanControlStatus OBJECT-TYPE
			SYNTAX SheControlStatusType
			MAX-ACCESS read-only
			STATUS current
			DESCRIPTION
				"The status of a user command."
			::= { sheUmasVlanControl 2 }

		
		sheUmasVlanControlTimestamp OBJECT-TYPE
			SYNTAX Unsigned32
			MAX-ACCESS read-only
			STATUS current
			DESCRIPTION
				"The time stamp of the last command (end of command)."
			::= { sheUmasVlanControl 3 }

		
		sheUmasVlanControlTimer OBJECT-TYPE
			SYNTAX Gauge32
			MAX-ACCESS read-only
			STATUS current
			DESCRIPTION
				"Maximum command execution time (timeout) in seconds in case of a long running command."
			::= { sheUmasVlanControl 4 }

		
		sheUmasVlanControlReqResult OBJECT-TYPE
			SYNTAX SheUmasControlReqResultType
			MAX-ACCESS read-only
			STATUS current
			DESCRIPTION
				"The result of the last user command."
			::= { sheUmasVlanControl 5 }

		
		sheUmasVlanControlVlanId OBJECT-TYPE
			SYNTAX INTEGER (1..4093)
			MAX-ACCESS read-write
			STATUS current
			DESCRIPTION
				"Table index to create or delete."
			::= { sheUmasVlanControl 6 }

		
		sheUmasConformance OBJECT IDENTIFIER ::= { sheUmas 100 }

		
		sheUmasCompliances OBJECT IDENTIFIER ::= { sheUmasConformance 1 }

		
--  this module
		sheUmasCompliance MODULE-COMPLIANCE
			STATUS current
			DESCRIPTION 
				"Description."
			MODULE -- this module
				MANDATORY-GROUPS { sheUmasGroup, sheUmasControlGroup, sheUmasNotificationGroup }
			::= { sheUmasCompliances 1 }

		
		sheUmasGroups OBJECT IDENTIFIER ::= { sheUmasConformance 2 }

		
		sheUmasGroup OBJECT-GROUP
			OBJECTS { sheUmasUseDhcpNextHop, sheUmasIndex, sheUmasAddress, sheUmasIsStatic, sheUmasIsDhcpNextHop, 
				sheUmasIsPppoeNextHop, sheUmasBaseUsePppoeNextHop, sheUmasBasePppoeAgingTime, sheUmasVlanId }
			STATUS current
			DESCRIPTION 
				"Description."
			::= { sheUmasGroups 1 }

		
		sheUmasControlGroup OBJECT-GROUP
			OBJECTS { sheUmasControlRequest, sheUmasControlStatus, sheUmasControlTimeStamp, sheUmasControlTimer, sheUmasControlReqResult, 
				sheUmasControlStaticAddr, sheUmasControlUseDhcpNextHop, sheUmasControlIndex, sheUmasControlUsePppoeNextHop, sheUmasControlPppoeAgingTime, 
				sheUmasVlanControlRequest, sheUmasVlanControlStatus, sheUmasVlanControlTimestamp, sheUmasVlanControlTimer, sheUmasVlanControlReqResult, 
				sheUmasVlanControlVlanId }
			STATUS current
			DESCRIPTION 
				"Description."
			::= { sheUmasGroups 2 }

		
		sheUmasNotificationGroup NOTIFICATION-GROUP
			NOTIFICATIONS { sheUmasStaticAddrChanged, sheUmasUseDhcpNextHopChanged, sheUmasUsePppoeNextHopChanged, sheUmasPppoeAgingTimeChanged, sheUmasVlanEntryCreated, 
				sheUmasVlanEntryDeleted, sheUmasIUBlacklistOverflow }
			STATUS current
			DESCRIPTION 
				"Description."
			::= { sheUmasGroups 3 }

		
--  --------------------------------------------
-- CEBS(Carrier Ethernet Border Switch) Group
-- --------------------------------------------
-- 1.3.6.1.4.1.231.7.1.2.2.1.4.15
-- 
-- CEBS support by SHE system only if CXU types CXU_B, CXU_B1 or CXU_C are used!
		sheCebs OBJECT IDENTIFIER ::= { sheBridgeMib 15 }

		
--   1.3.6.1.4.1.231.7.1.2.2.1.4.15.1
		sheCebsPortTable OBJECT-TYPE
			SYNTAX SEQUENCE OF SheCebsPortEntry
			MAX-ACCESS not-accessible
			STATUS current
			DESCRIPTION
				"The CEBS port table"
			::= { sheCebs 1 }

		
--   1.3.6.1.4.1.231.7.1.2.2.1.4.15.1.1
		sheCebsPortEntry OBJECT-TYPE
			SYNTAX SheCebsPortEntry
			MAX-ACCESS not-accessible
			STATUS current
			DESCRIPTION
				"table entry"
			INDEX { sheCebsPortBridgePortIndex }
			::= { sheCebsPortTable 1 }

		
		SheCebsPortEntry ::=
			SEQUENCE { 
				sheCebsPortBridgePortIndex
					Integer32
			 }

--   1.3.6.1.4.1.231.7.1.2.2.1.4.15.1.1.1
		sheCebsPortBridgePortIndex OBJECT-TYPE
			SYNTAX Integer32 (1..65535)
			MAX-ACCESS read-only
			STATUS current
			DESCRIPTION
				"Index to the sheBridgePortTable. Points to the Bridgeport this configuration is made for. 
				If created, the CEBS state of this Bridgeport is enabled."
			::= { sheCebsPortEntry 1 }

		
--   1.3.6.1.4.1.231.7.1.2.2.1.4.15.2
		sheCebsPortControl OBJECT IDENTIFIER ::= { sheCebs 2 }

		
--   1.3.6.1.4.1.231.7.1.2.2.1.4.15.2.1
		sheCebsPortControlRequest OBJECT-TYPE
			SYNTAX SheBridgeControlRequestType
			MAX-ACCESS read-write
			STATUS current
			DESCRIPTION
				"950 - createCebsPortTableEntry 
				Parameters : 
				sheCebsControlBridgePortIndex
				951 - deleteCebsPotyTableEntry 
				Parameters : 
				sheCebsControlBridgePortIndex
					"
			::= { sheCebsPortControl 1 }

		
--   1.3.6.1.4.1.231.7.1.2.2.1.4.15.2.2
		sheCebsPortControlStatus OBJECT-TYPE
			SYNTAX SheControlStatusType
			MAX-ACCESS read-only
			STATUS current
			DESCRIPTION
				"configuration control status"
			::= { sheCebsPortControl 2 }

		
--   1.3.6.1.4.1.231.7.1.2.2.1.4.15.2.3
		sheCebsPortControlTimestamp OBJECT-TYPE
			SYNTAX Unsigned32
			MAX-ACCESS read-only
			STATUS current
			DESCRIPTION
				"Time stamp attribute set at the end of a command."
			::= { sheCebsPortControl 3 }

		
--   1.3.6.1.4.1.231.7.1.2.2.1.4.15.2.4
		sheCebsPortControlReqResult OBJECT-TYPE
			SYNTAX SheBridgeControlReqResultType
			MAX-ACCESS read-only
			STATUS current
			DESCRIPTION
				"Result of the last command"
			::= { sheCebsPortControl 4 }

		
--   1.3.6.1.4.1.231.7.1.2.2.1.4.15.2.5
		sheCebsPortControlTimer OBJECT-TYPE
			SYNTAX Gauge32
			MAX-ACCESS read-only
			STATUS current
			DESCRIPTION
				"Maximum command execution time (timeout) in seconds in case of a long running command"
			::= { sheCebsPortControl 5 }

		
--   1.3.6.1.4.1.231.7.1.2.2.1.4.15.2.6
		sheCebsPortControlBridgePortIndex OBJECT-TYPE
			SYNTAX Integer32
			MAX-ACCESS read-write
			STATUS current
			DESCRIPTION
				"Index to the sheBridgePortTable. Points to the Bridgeport were this configuration is made for.
				If configured, the cebs state of this Bridgeport is enabled."
			::= { sheCebsPortControl 6 }

		
--   1.3.6.1.4.1.231.7.1.2.2.1.4.15.3
		sheCebsSubscriberTable OBJECT-TYPE
			SYNTAX SEQUENCE OF SheCebsSubscriberEntry
			MAX-ACCESS not-accessible
			STATUS current
			DESCRIPTION
				"The CEBS subscriber table"
			::= { sheCebs 3 }

		
--   1.3.6.1.4.1.231.7.1.2.2.1.4.15.3.1
		sheCebsSubscriberEntry OBJECT-TYPE
			SYNTAX SheCebsSubscriberEntry
			MAX-ACCESS not-accessible
			STATUS current
			DESCRIPTION
				"table entry"
			INDEX { sheCebsSubscriberIpAddress }
			::= { sheCebsSubscriberTable 1 }

		
		SheCebsSubscriberEntry ::=
			SEQUENCE { 
				sheCebsSubscriberIpAddress
					IpAddress,
				sheCebsSubscriberBridePortIndex
					Integer32,
				sheCebsSubscriberVlan
					Integer32,
				sheCebsSubscriberIsStatic
					TruthValue,
				sheCebsSubscriberIsDynamic
					TruthValue,
				sheCebsSubscriberOperState
					Integer32
			 }

--   1.3.6.1.4.1.231.7.1.2.2.1.4.15.3.1.1
		sheCebsSubscriberIpAddress OBJECT-TYPE
			SYNTAX IpAddress
			MAX-ACCESS read-only
			STATUS current
			DESCRIPTION
				"The subscriber IP address configured by DHCP or operator."
			::= { sheCebsSubscriberEntry 1 }

		
--   1.3.6.1.4.1.231.7.1.2.2.1.4.15.3.1.2
		sheCebsSubscriberBridePortIndex OBJECT-TYPE
			SYNTAX Integer32
			MAX-ACCESS read-only
			STATUS current
			DESCRIPTION
				"Index to the sheBridgePortTable. Points to the Bridgeport this configuration is made for."
			::= { sheCebsSubscriberEntry 2 }

		
--   1.3.6.1.4.1.231.7.1.2.2.1.4.15.3.1.3
		sheCebsSubscriberVlan OBJECT-TYPE
			SYNTAX Integer32
			MAX-ACCESS read-only
			STATUS current
			DESCRIPTION
				"The vlan that subscriber uses."
			::= { sheCebsSubscriberEntry 3 }

		
--   1.3.6.1.4.1.231.7.1.2.2.1.4.15.3.1.4
		sheCebsSubscriberIsStatic OBJECT-TYPE
			SYNTAX TruthValue
			MAX-ACCESS read-only
			STATUS current
			DESCRIPTION
				"Indicates if this subscriber is created by operator command, sheArpFixedIpAddressControlRequest."
			::= { sheCebsSubscriberEntry 4 }

		
--   1.3.6.1.4.1.231.7.1.2.2.1.4.15.3.1.5
		sheCebsSubscriberIsDynamic OBJECT-TYPE
			SYNTAX TruthValue
			MAX-ACCESS read-only
			STATUS current
			DESCRIPTION
				"Indicates if this subscriber is created by DHCP."
			::= { sheCebsSubscriberEntry 5 }

		
--   1.3.6.1.4.1.231.7.1.2.2.1.4.15.3.1.6
		sheCebsSubscriberOperState OBJECT-TYPE
			SYNTAX Integer32
			MAX-ACCESS read-only
			STATUS current
			DESCRIPTION
				"The operating state specifying whether the subscriber is able to get CEBS service.
				1 : Down
				2 : Up
				"
			::= { sheCebsSubscriberEntry 6 }

		
--   1.3.6.1.4.1.231.7.1.2.2.1.4.15.4
		sheCebsDhcpGatewayTable OBJECT-TYPE
			SYNTAX SEQUENCE OF SheCebsDhcpGatewayEntry
			MAX-ACCESS not-accessible
			STATUS current
			DESCRIPTION
				"The CEBS Dhcp gateway table."
			::= { sheCebs 4 }

		
--   1.3.6.1.4.1.231.7.1.2.2.1.4.15.4.1
		sheCebsDhcpGatewayEntry OBJECT-TYPE
			SYNTAX SheCebsDhcpGatewayEntry
			MAX-ACCESS not-accessible
			STATUS current
			DESCRIPTION
				"table entry"
			INDEX { sheCebsDhcpGatewayUserVlan }
			::= { sheCebsDhcpGatewayTable 1 }

		
		SheCebsDhcpGatewayEntry ::=
			SEQUENCE { 
				sheCebsDhcpGatewayUserVlan
					Integer32,
				sheCebsDhcpGatewayIpAddress
					IpAddress
			 }

--   1.3.6.1.4.1.231.7.1.2.2.1.4.15.4.1.1
		sheCebsDhcpGatewayUserVlan OBJECT-TYPE
			SYNTAX Integer32 (1..4093)
			MAX-ACCESS read-only
			STATUS current
			DESCRIPTION
				"Subscriver vlan"
			::= { sheCebsDhcpGatewayEntry 1 }

		
--   1.3.6.1.4.1.231.7.1.2.2.1.4.15.4.1.2
		sheCebsDhcpGatewayIpAddress OBJECT-TYPE
			SYNTAX IpAddress
			MAX-ACCESS read-only
			STATUS current
			DESCRIPTION
				"The dymamic IP address that a DHCP automatically sets as a gateway."
			::= { sheCebsDhcpGatewayEntry 2 }

		
--   1.3.6.1.4.1.231.7.1.2.2.1.4.15.5
		sheCebsStaticGatewayTable OBJECT-TYPE
			SYNTAX SEQUENCE OF SheCebsStaticGatewayEntry
			MAX-ACCESS not-accessible
			STATUS current
			DESCRIPTION
				"The CEBS static gateway table"
			::= { sheCebs 5 }

		
--   1.3.6.1.4.1.231.7.1.2.2.1.4.15.5.1
		sheCebsStaticGatewayEntry OBJECT-TYPE
			SYNTAX SheCebsStaticGatewayEntry
			MAX-ACCESS not-accessible
			STATUS current
			DESCRIPTION
				"table entry"
			INDEX { sheCebsStaticGatewayUserVlan }
			::= { sheCebsStaticGatewayTable 1 }

		
		SheCebsStaticGatewayEntry ::=
			SEQUENCE { 
				sheCebsStaticGatewayUserVlan
					Integer32,
				sheCebsStaticGatewayIpAddress
					IpAddress
			 }

--   1.3.6.1.4.1.231.7.1.2.2.1.4.15.5.1.1
		sheCebsStaticGatewayUserVlan OBJECT-TYPE
			SYNTAX Integer32 (1..4093)
			MAX-ACCESS read-only
			STATUS current
			DESCRIPTION
				"Subscriver vlan"
			::= { sheCebsStaticGatewayEntry 1 }

		
--   1.3.6.1.4.1.231.7.1.2.2.1.4.15.5.1.2
		sheCebsStaticGatewayIpAddress OBJECT-TYPE
			SYNTAX IpAddress
			MAX-ACCESS read-only
			STATUS current
			DESCRIPTION
				"The static IP address that a user vlan uses as a gateway. 
				If this value is not configured, follow the the value that DHCP sets automatically."
			::= { sheCebsStaticGatewayEntry 2 }

		
--   1.3.6.1.4.1.231.7.1.2.2.1.4.15.6
		sheCebsStaticGatewayControl OBJECT IDENTIFIER ::= { sheCebs 6 }

		
--   1.3.6.1.4.1.231.7.1.2.2.1.4.15.6.1
		sheCebsStaticGatewayControlRequest OBJECT-TYPE
			SYNTAX SheBridgeControlRequestType
			MAX-ACCESS read-write
			STATUS current
			DESCRIPTION
				"952 - createCebsStaticGatewayTableEntry 
				Parameters : 
				sheCebsStaticGatewayControlUserVlan 
				sheCebsStaticGatewayControlIpAddress
				953 - modifyCebsStaticGatewayTableEntry 
				Parameters : 
				sheCebsStaticGatewayControlUserVlan 
				sheCebsStaticGatewayControlIpAddress
				954 - deleteCebsStaticGatewayTableEntry 
				Parameters :  
				sheCebsStaticGatewayControlUserVlan
				"
			::= { sheCebsStaticGatewayControl 1 }

		
--   1.3.6.1.4.1.231.7.1.2.2.1.4.15.6.2
		sheCebsStaticGatewayControlStatus OBJECT-TYPE
			SYNTAX SheControlStatusType
			MAX-ACCESS read-only
			STATUS current
			DESCRIPTION
				"configuration control status"
			::= { sheCebsStaticGatewayControl 2 }

		
--   1.3.6.1.4.1.231.7.1.2.2.1.4.15.6.3
		sheCebsStaticGatewayControlTimestamp OBJECT-TYPE
			SYNTAX Unsigned32
			MAX-ACCESS read-only
			STATUS current
			DESCRIPTION
				"Time stamp attribute set at the end of a command"
			::= { sheCebsStaticGatewayControl 3 }

		
--   1.3.6.1.4.1.231.7.1.2.2.1.4.15.6.4
		sheCebsStaticGatewayControlReqResult OBJECT-TYPE
			SYNTAX SheBridgeControlReqResultType
			MAX-ACCESS read-only
			STATUS current
			DESCRIPTION
				"Result of the last command"
			::= { sheCebsStaticGatewayControl 4 }

		
--   1.3.6.1.4.1.231.7.1.2.2.1.4.15.6.5
		sheCebsStaticGatewayControlTimer OBJECT-TYPE
			SYNTAX Gauge32
			MAX-ACCESS read-only
			STATUS current
			DESCRIPTION
				"Maximum command execution time (timeout) in seconds in case of a long running command"
			::= { sheCebsStaticGatewayControl 5 }

		
--   1.3.6.1.4.1.231.7.1.2.2.1.4.15.6.6
		sheCebsStaticGatewayControlUserVlan OBJECT-TYPE
			SYNTAX Integer32 (1..4093)
			MAX-ACCESS read-write
			STATUS current
			DESCRIPTION
				"Subscriver vlan"
			::= { sheCebsStaticGatewayControl 6 }

		
--   1.3.6.1.4.1.231.7.1.2.2.1.4.15.6.7
		sheCebsStaticGatewayControlIpAddress OBJECT-TYPE
			SYNTAX IpAddress
			MAX-ACCESS read-write
			STATUS current
			DESCRIPTION
				"The static IP address that a user vlan uses as a gateway. 
				If this value is not configured, follow the the value that DHCP sets automatically."
			::= { sheCebsStaticGatewayControl 7 }

		
--   1.3.6.1.4.1.231.7.1.2.2.1.4.15.7
		sheCebsVirtualMacTable OBJECT-TYPE
			SYNTAX SEQUENCE OF SheCebsVirtualMacEntry
			MAX-ACCESS not-accessible
			STATUS current
			DESCRIPTION
				"cebs virtual mac table"
			::= { sheCebs 7 }

		
--   1.3.6.1.4.1.231.7.1.2.2.1.4.15.7.1
		sheCebsVirtualMacEntry OBJECT-TYPE
			SYNTAX SheCebsVirtualMacEntry
			MAX-ACCESS not-accessible
			STATUS current
			DESCRIPTION
				"table entry"
			INDEX { sheCebsVirtualMacEntPhysicalIndex }
			::= { sheCebsVirtualMacTable 1 }

		
		SheCebsVirtualMacEntry ::=
			SEQUENCE { 
				sheCebsVirtualMacAddress
					OCTET STRING,
				sheCebsVirtualMacType
					Integer32,
				sheCebsVirtualMacEntPhysicalIndex
					PhysicalIndex
			 }

--   1.3.6.1.4.1.231.7.1.2.2.1.4.15.7.1.1
		sheCebsVirtualMacAddress OBJECT-TYPE
			SYNTAX OCTET STRING (SIZE (6))
			MAX-ACCESS read-only
			STATUS current
			DESCRIPTION
				"Mac address"
			::= { sheCebsVirtualMacEntry 1 }

		
--   1.3.6.1.4.1.231.7.1.2.2.1.4.15.7.1.2
		sheCebsVirtualMacType OBJECT-TYPE
			SYNTAX Integer32
			MAX-ACCESS read-only
			STATUS current
			DESCRIPTION
				"The flag specifying what this mac address is used for.
				1 : IP(Internet Protocol), 
					This is a global mac address for IP. The number of mac is only one for the IP. In this case sheCebsVirtualMacEntPhysicalIndex indicates rack index.
				2 : PPPoE(Point to Point Protocol over Ethernet)
					This mac is assigned to a slot for PPPoE. The number of mac is one per slot. In this case sheCebsVirtualMacEntPhysicalIndex indicates the index of a slot.
				"
			::= { sheCebsVirtualMacEntry 2 }

		
--   1.3.6.1.4.1.231.7.1.2.2.1.4.15.7.1.3
		sheCebsVirtualMacEntPhysicalIndex OBJECT-TYPE
			SYNTAX PhysicalIndex
			MAX-ACCESS read-only
			STATUS current
			DESCRIPTION
				"The entPhysical index of the card/rack that this virtual mac will be used.
				This is table index also!!"
			::= { sheCebsVirtualMacEntry 3 }

		
--   1.3.6.1.4.1.231.7.1.2.2.1.4.15.8
		sheCebsVirtualMacControl OBJECT IDENTIFIER ::= { sheCebs 8 }

		
--   1.3.6.1.4.1.231.7.1.2.2.1.4.15.8.1
		sheCebsVirtualMacControlRequest OBJECT-TYPE
			SYNTAX SheBridgeControlRequestType
			MAX-ACCESS read-write
			STATUS current
			DESCRIPTION
				"955 - createCebsVirtualMacTableEntry 
				Parameters : 
				sheCebsVirtualMacControlAddress
				sheCebsVirtualMacControlType
				SheCebsVirtualMacControlEntPhysicalIndex 
				956 - deleteCebsVirtualMacTableEntry 
				Parameters :  
				sheCebsVirtualMacControlAddress
				"
			::= { sheCebsVirtualMacControl 1 }

		
--   1.3.6.1.4.1.231.7.1.2.2.1.4.15.8.2
		sheCebsVirtualMacControlStatus OBJECT-TYPE
			SYNTAX SheControlStatusType
			MAX-ACCESS read-only
			STATUS current
			DESCRIPTION
				"configuration control status"
			::= { sheCebsVirtualMacControl 2 }

		
--   1.3.6.1.4.1.231.7.1.2.2.1.4.15.8.3
		sheCebsVirtualMacControlTimestamp OBJECT-TYPE
			SYNTAX Unsigned32
			MAX-ACCESS read-only
			STATUS current
			DESCRIPTION
				"Time stamp attribute set at the end of a command."
			::= { sheCebsVirtualMacControl 3 }

		
--   1.3.6.1.4.1.231.7.1.2.2.1.4.15.8.4
		sheCebsVirtualMacControlReqResult OBJECT-TYPE
			SYNTAX SheBridgeControlReqResultType
			MAX-ACCESS read-only
			STATUS current
			DESCRIPTION
				"Result of the last command"
			::= { sheCebsVirtualMacControl 4 }

		
--   1.3.6.1.4.1.231.7.1.2.2.1.4.15.8.5
		sheCebsVirtualMacControlTimer OBJECT-TYPE
			SYNTAX Gauge32
			MAX-ACCESS read-only
			STATUS current
			DESCRIPTION
				"Maximum command execution time (timeout) in seconds in case of a long running command"
			::= { sheCebsVirtualMacControl 5 }

		
--   1.3.6.1.4.1.231.7.1.2.2.1.4.15.8.6
		sheCebsVirtualMacControlAddress OBJECT-TYPE
			SYNTAX OCTET STRING (SIZE (6))
			MAX-ACCESS read-write
			STATUS current
			DESCRIPTION
				"Virtual mac address used during CEBS service"
			::= { sheCebsVirtualMacControl 6 }

		
--   1.3.6.1.4.1.231.7.1.2.2.1.4.15.8.7
		sheCebsVirtualMacControlType OBJECT-TYPE
			SYNTAX Integer32
			MAX-ACCESS read-write
			STATUS current
			DESCRIPTION
				"The flag specifying what this mac address is used for.
				1 : IP(Internet Protocol), 
					This is global mac address for IP. The number of mac is only one for the IP. In this case sheCebsVirtualMacEntPhysicalIndex indicates rack index
				2 : PPPoE(Point to Point Protocol over Ethernet)
					This mac is assigned to a slot for PPPoE. The number of mac is one per slot. In this case sheCebsVirtualMacEntPhysicalIndex indicates the index of a slot.
				"
			::= { sheCebsVirtualMacControl 7 }

		
--   1.3.6.1.4.1.231.7.1.2.2.1.4.15.8.8
		sheCebsVirtualMacControlEntPhysicalIndex OBJECT-TYPE
			SYNTAX PhysicalIndex
			MAX-ACCESS read-write
			STATUS current
			DESCRIPTION
				"The entPhysical index of the card/rack that this virtual mac will be used.
				Index of the table entry which should be modified."
			::= { sheCebsVirtualMacControl 8 }

		
--   1.3.6.1.4.1.231.7.1.2.2.1.4.15.9
		sheCebsNotifications OBJECT IDENTIFIER ::= { sheCebs 9 }

		
--   1.3.6.1.4.1.231.7.1.2.2.1.4.15.9.1
		sheCebsPortTableEntryCreated NOTIFICATION-TYPE
			OBJECTS { sheCebsPortControlTimestamp, sheCebsPortControlBridgePortIndex, sheCebsPortControlStatus }
			STATUS current
			DESCRIPTION 
				"sheCebsPortTableEntry has been created."
			::= { sheCebsNotifications 1 }

		
--   1.3.6.1.4.1.231.7.1.2.2.1.4.15.9.2
		sheCebsPortTableEntryDeleted NOTIFICATION-TYPE
			OBJECTS { sheCebsPortControlBridgePortIndex, sheCebsPortControlTimestamp }
			STATUS current
			DESCRIPTION 
				"sheCebsPortTableEntry has been deleted."
			::= { sheCebsNotifications 2 }

		
--   1.3.6.1.4.1.231.7.1.2.2.1.4.15.9.3
		sheCebsStaticGatewayTableEntryCreated NOTIFICATION-TYPE
			OBJECTS { sheCebsStaticGatewayControlTimestamp, sheCebsStaticGatewayControlUserVlan, sheCebsStaticGatewayControlIpAddress }
			STATUS current
			DESCRIPTION 
				"sheCebsStaticGatewayTableEntry has been created."
			::= { sheCebsNotifications 3 }

		
--   1.3.6.1.4.1.231.7.1.2.2.1.4.15.9.4
		sheCebsStaticGatewayTableEntryModified NOTIFICATION-TYPE
			OBJECTS { sheCebsStaticGatewayControlTimestamp, sheCebsStaticGatewayControlUserVlan, sheCebsStaticGatewayControlIpAddress }
			STATUS current
			DESCRIPTION 
				"sheCebsStaticGatewayTableEntry has been modified."
			::= { sheCebsNotifications 4 }

		
--   1.3.6.1.4.1.231.7.1.2.2.1.4.15.9.5
		sheCebsStaticGatewayTableEntryDeleted NOTIFICATION-TYPE
			OBJECTS { sheCebsStaticGatewayControlTimestamp, sheCebsStaticGatewayControlUserVlan }
			STATUS current
			DESCRIPTION 
				"sheCebsStaticGatewayTableEntry has been deleted."
			::= { sheCebsNotifications 5 }

		
--   1.3.6.1.4.1.231.7.1.2.2.1.4.15.9.6
		sheCebsVirtualMacTableEntryCreated NOTIFICATION-TYPE
			OBJECTS { sheCebsVirtualMacControlTimestamp, sheCebsVirtualMacControlAddress, sheCebsVirtualMacControlEntPhysicalIndex }
			STATUS current
			DESCRIPTION 
				"sheCebsPortTableEntry has been created."
			::= { sheCebsNotifications 6 }

		
--   1.3.6.1.4.1.231.7.1.2.2.1.4.15.9.7
		sheCebsVirtualMacTableEntryDeleted NOTIFICATION-TYPE
			OBJECTS { sheCebsVirtualMacControlTimestamp, sheCebsVirtualMacControlEntPhysicalIndex }
			STATUS current
			DESCRIPTION 
				"sheCebsVirtualMacTableEntry has been deleted."
			::= { sheCebsNotifications 7 }

		
--   1.3.6.1.4.1.231.7.1.2.2.1.4.15.10
		sheCebsConformance OBJECT IDENTIFIER ::= { sheCebs 100 }

		
--   1.3.6.1.4.1.231.7.1.2.2.1.4.15.10.1
		sheCebsCompliances OBJECT IDENTIFIER ::= { sheCebsConformance 1 }

		
--   1.3.6.1.4.1.231.7.1.2.2.1.4.15.10.1.1
-- this module
-- this module
		sheCebsCompliance MODULE-COMPLIANCE
			STATUS current
			DESCRIPTION 
				"Description."
			MODULE -- this module
				MANDATORY-GROUPS { sheCebsGroup, sheCebsControlGroup, sheCebsNotificationsGroup }
			::= { sheCebsCompliances 1 }

		
--   1.3.6.1.4.1.231.7.1.2.2.1.4.15.10.2
		sheCebsGroups OBJECT IDENTIFIER ::= { sheCebsConformance 2 }

		
--   1.3.6.1.4.1.231.7.1.2.2.1.4.15.10.2.1
		sheCebsGroup OBJECT-GROUP
			OBJECTS { sheCebsPortBridgePortIndex, sheCebsSubscriberIpAddress, sheCebsSubscriberBridePortIndex, sheCebsSubscriberVlan, sheCebsSubscriberIsStatic, 
				sheCebsSubscriberIsDynamic, sheCebsSubscriberOperState, sheCebsDhcpGatewayUserVlan, sheCebsDhcpGatewayIpAddress, sheCebsStaticGatewayUserVlan, 
				sheCebsStaticGatewayIpAddress, sheCebsVirtualMacAddress, sheCebsVirtualMacType, sheCebsVirtualMacEntPhysicalIndex }
			STATUS current
			DESCRIPTION 
				"Description."
			::= { sheCebsGroups 1 }

		
--   1.3.6.1.4.1.231.7.1.2.2.1.4.15.10.2.2
		sheCebsControlGroup OBJECT-GROUP
			OBJECTS { sheCebsPortControlRequest, sheCebsPortControlStatus, sheCebsPortControlTimestamp, sheCebsPortControlReqResult, sheCebsPortControlTimer, 
				sheCebsPortControlBridgePortIndex, sheCebsStaticGatewayControlRequest, sheCebsStaticGatewayControlStatus, sheCebsStaticGatewayControlTimestamp, sheCebsStaticGatewayControlReqResult, 
				sheCebsStaticGatewayControlTimer, sheCebsStaticGatewayControlUserVlan, sheCebsStaticGatewayControlIpAddress, sheCebsVirtualMacControlRequest, sheCebsVirtualMacControlStatus, 
				sheCebsVirtualMacControlTimestamp, sheCebsVirtualMacControlReqResult, sheCebsVirtualMacControlTimer, sheCebsVirtualMacControlAddress, sheCebsVirtualMacControlType, 
				sheCebsVirtualMacControlEntPhysicalIndex }
			STATUS current
			DESCRIPTION 
				"Description."
			::= { sheCebsGroups 2 }

		
		sheCebsNotificationsGroup NOTIFICATION-GROUP
			NOTIFICATIONS { sheCebsPortTableEntryCreated, sheCebsPortTableEntryDeleted, sheCebsStaticGatewayTableEntryCreated, sheCebsStaticGatewayTableEntryModified, sheCebsStaticGatewayTableEntryDeleted, 
				sheCebsVirtualMacTableEntryCreated, sheCebsVirtualMacTableEntryDeleted }
			STATUS current
			DESCRIPTION 
				"Description."
			::= { sheCebsGroups 3 }

		
--  --------------------------------------------
-- MAT(Mac Address Translation) Group
-- --------------------------------------------
-- 1.3.6.1.4.1.231.7.1.2.2.1.4.16
		sheMat OBJECT IDENTIFIER ::= { sheBridgeMib 16 }

		
--   1.3.6.1.4.1.231.7.1.2.2.1.4.16.1
		sheMatBase OBJECT IDENTIFIER ::= { sheMat 1 }

		
--   1.3.6.1.4.1.231.7.1.2.2.1.4.16.1.1
		sheMatDslamId OBJECT-TYPE
			SYNTAX Integer32 (-1..524287)
			MAX-ACCESS read-only
			STATUS current
			DESCRIPTION
				"A DSLAM ID used for IU's MAC address translation. MAT is performed based on this DSLAM ID. 
				The DSLAM ID should be interpreted as a hex value. Depending on the used MatTranslationMode,
				the following restrictions should be made:
				TranslationMode:
				world - The DSLAM ID should be a value between 0..4095 (0..FFF, 12 bits are valid)! 
				        The not needed upper bits will be ignored.
				ths - The DSLAM ID should be a value between 0..524287 (0..7FFFF, 19 bits are valid)!
				      The not needed upper bits will be ignored.
				      
				Default value is -1, that means a DSLAM ID is not assigned. 
				
				NOTE: A modified DSLAM ID need an IU reset for activation!
				"
			::= { sheMatBase 1 }

		
		sheMatTranslationMode OBJECT-TYPE
			SYNTAX SheMatTranslationModeType
			MAX-ACCESS read-only
			STATUS current
			DESCRIPTION
				"The attribute describes, which format for MAC address translation will be used.
				general structure: byte5-byte4-byte3-byte2-byte1-byte0
				                   bit47 .........................bit0
				
				world(1) - 
				  byte 5 - DSLAM ID (bit 47-44, 4 bit) and identifier (0110)
				  byte 4 - DSLAM ID 
				  byte 3 - slot number
				  byte 2 - port number
				  byte 1 - VCC number
				  byte 0 - MAC address index
				
				ths(2) - 
				  byte 5 - control (bit 47 = 0, bit 46 always 1, bit 45-40 no change)
				  byte 4,3,2 - DSLAM ID (bit 39-21, 19 bit)
				  byte 2,1 - slot number (bit 20-15, 6 bit)
				  byte 1,0 - port number (bit 14-6, 9 bits)
				  byte 0 - MAC address index (bit 5-0, 6 bits)
				
				This translation mode will use an fix offset for selected MAC address indeces depending on the
				fact, if the orginal MAc address was learned from a tagged or an untagged userframe.
				
				thsNoIndexOffset(3) - 
				  byte 5 - control (bit 47 = 0, bit 46 always 1, bit 45-40 no change)
				  byte 4,3,2 - DSLAM ID (bit 39-21, 19 bit)
				  byte 2,1 - slot number (bit 20-15, 6 bit)
				  byte 1,0 - port number (bit 14-6, 9 bits)
				  byte 0 - MAC address index (bit 5-0, 6 bits)
				
				This translation mode will not use an offset for selected MAC address indeces depending on the
				fact, if the orginal MAc address was learned from a tagged or an untagged userframe.
				"
			::= { sheMatBase 2 }

		
--   1.3.6.1.4.1.231.7.1.2.2.1.4.16.2
-- This table will not longer supported with SHE R2.6.
		sheMatPortTable OBJECT-TYPE
			SYNTAX SEQUENCE OF SheMatPortEntry
			MAX-ACCESS not-accessible
			STATUS obsolete
			DESCRIPTION
				"The MAT port table for enable/disable this feature on bridgePort base.
				
				NOTE:
				This table will not longer supported with SHE R2.6. The enable/disable of this feature
				will be done on VLAN base starting with this release. 
				Use new parameters in sheVlanTable therefor!!
				With R2.8 the functionality is available in the NE again, but the configuration should directly
				be done via sheBridgePortTable.
				
				"
			::= { sheMat 2 }

		
--   1.3.6.1.4.1.231.7.1.2.2.1.4.16.2.1
		sheMatPortEntry OBJECT-TYPE
			SYNTAX SheMatPortEntry
			MAX-ACCESS not-accessible
			STATUS obsolete
			DESCRIPTION
				"table entry"
			INDEX { sheBridgePortIndex }
			::= { sheMatPortTable 1 }

		
		SheMatPortEntry ::=
			SEQUENCE { 
				sheMatPortEnable
					TruthValue
			 }

--   1.3.6.1.4.1.231.7.1.2.2.1.4.16.2.1.1
		sheMatPortEnable OBJECT-TYPE
			SYNTAX TruthValue
			MAX-ACCESS read-only
			STATUS obsolete
			DESCRIPTION
				"Enable or disable the MAC address translation feature on bridgePort base.
				
				NOTE:
				This parameter will not longer supported with SHE R2.6. The enable/disable of this feature
				will be done on VLAN base starting with this release. 
				Use new parameters in sheVlanTable therefor!!
				With R2.8 the functionality is available in the NE again, but the configuration should directly
				be done via sheBridgePortTable."
			::= { sheMatPortEntry 1 }

		
--   1.3.6.1.4.1.231.7.1.2.2.1.4.16.3
		sheMatTable OBJECT-TYPE
			SYNTAX SEQUENCE OF SheMatEntry
			MAX-ACCESS not-accessible
			STATUS current
			DESCRIPTION
				"The MAT table contain the translated MAT addresses and her original laerned value.
				
				New with R2.8 maintenance:
				This release introduces a new ControlRequest command for refresh of this table. 
				Without calling this command, the table content will be static and not longer automatically updated.
				The refresh command could be used together with the BridgePortIndex, which is the first table index here.
				If a valid BridgePortIndex value was used, only the tableEntries with this BridgePortIndex as first key will be
				refreshed. 
				If the BridgePortIndex is 0 or unknown the full table will be refreshed."
			::= { sheMat 3 }

		
--   1.3.6.1.4.1.231.7.1.2.2.1.4.16.3.1
		sheMatEntry OBJECT-TYPE
			SYNTAX SheMatEntry
			MAX-ACCESS not-accessible
			STATUS current
			DESCRIPTION
				"table entry"
			INDEX { sheBridgePortIndex, sheVlanIndex, sheMatIndex }
			::= { sheMatTable 1 }

		
		SheMatEntry ::=
			SEQUENCE { 
				sheMatTranslatedMacAddress
					OCTET STRING,
				sheMatOriginalMacAddress
					OCTET STRING,
				sheMatIndex
					Unsigned32
			 }

--   1.3.6.1.4.1.231.7.1.2.2.1.4.16.3.1.1
		sheMatTranslatedMacAddress OBJECT-TYPE
			SYNTAX OCTET STRING (SIZE (6))
			MAX-ACCESS read-only
			STATUS current
			DESCRIPTION
				"Translated MAC address"
			::= { sheMatEntry 1 }

		
--   1.3.6.1.4.1.231.7.1.2.2.1.4.16.3.1.2
		sheMatOriginalMacAddress OBJECT-TYPE
			SYNTAX OCTET STRING (SIZE (6))
			MAX-ACCESS read-only
			STATUS current
			DESCRIPTION
				"Original MAC address"
			::= { sheMatEntry 2 }

		
		sheMatIndex OBJECT-TYPE
			SYNTAX Unsigned32 (1..64)
			MAX-ACCESS read-only
			STATUS current
			DESCRIPTION
				"This index is the new third index value for this table. "
			::= { sheMatEntry 3 }

		
--   1.3.6.1.4.1.231.7.1.2.2.1.4.16.4
		sheMatControl OBJECT IDENTIFIER ::= { sheMat 4 }

		
--   1.3.6.1.4.1.231.7.1.2.2.1.4.16.4.1
		sheMatControlRequest OBJECT-TYPE
			SYNTAX SheMatControlRequestType
			MAX-ACCESS read-write
			STATUS current
			DESCRIPTION
				"setDslamId(100):
				sheMatControlDslamId
				
				setPortEnable(101):
				sheMatControlBridgePortIndex
				sheMatControlPortEnable
				
				setMatTranslationMode(102):
				sheMatControlTranslationMode
				
				NOTE:
				SheMatPortTable will not longer supported with SHE R2.6. The enable/disable of this feature
				will be done on VLAN base starting with this release. Use new parameters in sheVlanTable therefor!! 
				Usecase setPortEnable(101) is not longer supported!!
				Release R2.8 will support a new port specific enable command via sheBridgePortTable!
				
				
				New with R2.8 maintenance:
				refreshMatTable (105):
				sheMatControlBridgePortIndex"
			::= { sheMatControl 1 }

		
--   1.3.6.1.4.1.231.7.1.2.2.1.4.16.4.2
		sheMatControlStatus OBJECT-TYPE
			SYNTAX SheControlStatusType
			MAX-ACCESS read-only
			STATUS current
			DESCRIPTION
				"Describes the status of a user command group, used for block commands while a command execution is in process.
				- Values : idle, busy, passed, failed
				- idle: default, no command in process
				- busy: command execution in process, attempts to start another user command on this control block are rejected
				- passed/failed: status at the end of a command
				"
			::= { sheMatControl 2 }

		
--   1.3.6.1.4.1.231.7.1.2.2.1.4.16.4.3
		sheMatControlTimestamp OBJECT-TYPE
			SYNTAX Unsigned32
			MAX-ACCESS read-only
			STATUS current
			DESCRIPTION
				"Time stamp attribute set at the end of a command."
			::= { sheMatControl 3 }

		
--   1.3.6.1.4.1.231.7.1.2.2.1.4.16.4.4
		sheMatControlReqResult OBJECT-TYPE
			SYNTAX SheBridgeControlReqResultType
			MAX-ACCESS read-only
			STATUS current
			DESCRIPTION
				"Result of the last command"
			::= { sheMatControl 4 }

		
--   1.3.6.1.4.1.231.7.1.2.2.1.4.16.4.5
		sheMatControlTimer OBJECT-TYPE
			SYNTAX Unsigned32
			MAX-ACCESS read-only
			STATUS current
			DESCRIPTION
				"Maximum command execution time (timeout) in seconds in case of a long running command"
			::= { sheMatControl 5 }

		
--   1.3.6.1.4.1.231.7.1.2.2.1.4.16.4.6
		sheMatControlDslamId OBJECT-TYPE
			SYNTAX Integer32 (-1..524287)
			MAX-ACCESS read-write
			STATUS current
			DESCRIPTION
				"A DSLAM ID used for IU's MAC address translation. MAT is performed based on this DSLAM ID. 
				The DSLAM ID should be interpreted as a hex value. Depending on the used MatTranslationMode,
				the following restrictions should be made:
				TranslationMode:
				world - The DSLAM ID should be a value between 0..4095 (0..FFF, 12 bits are valid)! 
				        The not needed upper bits will be ignored.
				ths - The DSLAM ID should be a value between 0..524287 (0..7FFFF, 19 bits are valid)!
				      The not needed upper bits will be ignored.
				      
				Default value is -1, that means a DSLAM ID is not assigned."
			::= { sheMatControl 6 }

		
--   1.3.6.1.4.1.231.7.1.2.2.1.4.16.4.7
		sheMatControlBridgePortIndex OBJECT-TYPE
			SYNTAX Unsigned32
			MAX-ACCESS read-write
			STATUS current
			DESCRIPTION
				"A bridge port index identifier"
			::= { sheMatControl 7 }

		
--   1.3.6.1.4.1.231.7.1.2.2.1.4.16.4.8
		sheMatControlPortEnable OBJECT-TYPE
			SYNTAX TruthValue
			MAX-ACCESS read-write
			STATUS obsolete
			DESCRIPTION
				"Sets MAC address translation enable/disable.
				
				NOTE:
				This value will not longer supported with SHE R2.6. The enable/disable of this feature
				will be done on VLAN base starting with this release. 
				Use new parameters in sheVlanTable therefor!!"
			::= { sheMatControl 8 }

		
		sheMatControlTranslationMode OBJECT-TYPE
			SYNTAX SheMatTranslationModeType
			MAX-ACCESS read-write
			STATUS current
			DESCRIPTION
				"The attribute descripes, which format for MAC address translation will be used.
				world(1) - 
				  byte 5 - DSLAM ID (bit 47-44, 4 bit) and identifier (0110)
				  byte 4 - DSLAM ID 
				  byte 3 - slot number
				  byte 2 - port number
				  byte 1 - VCC number
				  byte 0 - MAC address index
				
				ths(2) - 
				  byte 5 - control (bit 47 = 0, bit 46 always 1, bit 45-40 no change)
				  byte 4,3,2 - DSLAM ID (bit 39-21, 19 bit)
				  byte 2,1 - slot number (bit 20-15, 6 bit)
				  byte 1,0 - port number (bit 14-6, 9 bits)
				  byte 0 - MAC address index (bit 5-0, 6 bits)
				
				This translation mode will use an fix offset for selected MAC address indeces depending on the
				fact, if the orginal MAc address was learned from a tagged or an untagged userframe.
				
				thsNoIndexOffset(3) - 
				  byte 5 - control (bit 47 = 0, bit 46 always 1, bit 45-40 no change)
				  byte 4,3,2 - DSLAM ID (bit 39-21, 19 bit)
				  byte 2,1 - slot number (bit 20-15, 6 bit)
				  byte 1,0 - port number (bit 14-6, 9 bits)
				  byte 0 - MAC address index (bit 5-0, 6 bits)
				
				This translation mode will not use an offset for selected MAC address indeces depending on the
				fact, if the orginal MAc address was learned from a tagged or an untagged userframe.
				"
			::= { sheMatControl 9 }

		
--   1.3.6.1.4.1.231.7.1.2.2.1.4.16.5
		sheMatNotifications OBJECT IDENTIFIER ::= { sheMat 5 }

		
--   1.3.6.1.4.1.231.7.1.2.2.1.4.16.5.1
		sheMatDslamIdChanged NOTIFICATION-TYPE
			OBJECTS { sheMatDslamId }
			STATUS current
			DESCRIPTION 
				"sheMatDslamId has been changed."
			::= { sheMatNotifications 1 }

		
--   1.3.6.1.4.1.231.7.1.2.2.1.4.16.5.2
		sheMatPortEnableChanged NOTIFICATION-TYPE
			OBJECTS { sheMatPortEnable }
			STATUS obsolete
			DESCRIPTION 
				"sheMatPortEnable has been changed."
			::= { sheMatNotifications 2 }

		
--   1.3.6.1.4.1.231.7.1.2.2.1.4.16.5.1
		sheMatTranslationModeChanged NOTIFICATION-TYPE
			OBJECTS { sheMatTranslationMode }
			STATUS current
			DESCRIPTION 
				"sheMatTranslationMode has been changed."
			::= { sheMatNotifications 3 }

		
--   1.3.6.1.4.1.231.7.1.2.2.1.4.16.5.4
		sheMatTableUpdated NOTIFICATION-TYPE
			OBJECTS { sheMatControlTimestamp, sheMatControlBridgePortIndex, sheMatControlReqResult }
			STATUS current
			DESCRIPTION 
				"MAT table update finished."
			::= { sheMatNotifications 4 }

		
--   1.3.6.1.4.1.231.7.1.2.2.1.4.16.6
		sheMatConformance OBJECT IDENTIFIER ::= { sheMat 100 }

		
--   1.3.6.1.4.1.231.7.1.2.2.1.4.16.6.1
		sheMatCompliances OBJECT IDENTIFIER ::= { sheMatConformance 1 }

		
--   1.3.6.1.4.1.231.7.1.2.2.1.4.16.6.1.1
-- this module
-- this module
		sheMatCompliance MODULE-COMPLIANCE
			STATUS current
			DESCRIPTION 
				"Description."
			MODULE -- this module
				MANDATORY-GROUPS { sheMatGroup, sheMatControlGroup, sheMatNotificationsGroup }
			::= { sheMatCompliances 1 }

		
--   1.3.6.1.4.1.231.7.1.2.2.1.4.16.6.2
		sheMatGroups OBJECT IDENTIFIER ::= { sheMatConformance 2 }

		
--   1.3.6.1.4.1.231.7.1.2.2.1.4.16.6.2.1
		sheMatGroup OBJECT-GROUP
			OBJECTS { sheMatDslamId, sheMatTranslatedMacAddress, sheMatIndex, sheMatOriginalMacAddress, sheMatTranslationMode
				 }
			STATUS current
			DESCRIPTION 
				"Description."
			::= { sheMatGroups 1 }

		
--   1.3.6.1.4.1.231.7.1.2.2.1.4.16.6.2.2
		sheMatControlGroup OBJECT-GROUP
			OBJECTS { sheMatControlRequest, sheMatControlStatus, sheMatControlTimestamp, sheMatControlReqResult, sheMatControlTimer, 
				sheMatControlDslamId, sheMatControlBridgePortIndex, sheMatControlTranslationMode }
			STATUS current
			DESCRIPTION 
				"Description."
			::= { sheMatGroups 2 }

		
		sheMatNotificationsGroup NOTIFICATION-GROUP
			NOTIFICATIONS { sheMatDslamIdChanged, sheMatTranslationModeChanged, sheMatTableUpdated }
			STATUS current
			DESCRIPTION 
				"Description."
			::= { sheMatGroups 3 }

		
		sheMatObsoleteGroup OBJECT-GROUP
			OBJECTS { sheMatPortEnable, sheMatControlPortEnable }
			STATUS obsolete
			DESCRIPTION 
				"Description."
			::= { sheMatGroups 4 }

		
		sheMatObsoleteNotificationGroup NOTIFICATION-GROUP
			NOTIFICATIONS { sheMatPortEnableChanged }
			STATUS obsolete
			DESCRIPTION 
				"Description."
			::= { sheMatGroups 5 }

		
	
	END

--
-- she-bridge-mib.mib
--
