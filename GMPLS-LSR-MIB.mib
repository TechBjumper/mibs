-- extracted from draft-ietf-ccamp-gmpls-lsr-mib-00.txt
-- at Sat Jun 29 06:09:50 2002

GMPLS-LSR-MIB DEFINITIONS ::= BEGIN

IMPORTS
   MODULE-IDENTITY, OBJECT-TYPE, NOTIFICATION-TYPE,
   experimental, Unsigned32
      FROM SNMPv2-SMI
   MODULE-COMPLIANCE, OBJECT-GROUP, NOTIFICATION-GROUP
      FROM SNMPv2-CONF
   GmplsSegmentDirection
      FROM GMPLS-TC-MIB
   ;

gmplsLsrMIB MODULE-IDENTITY
   LAST-UPDATED
      "200206240900Z "  -- 24 June 2002 9:00:00 GMT"
   ORGANIZATION "Common Control And Management Protocols
(CCAMP) Working Group"
   CONTACT-INFO
      "       Thomas D. Nadeau
      Postal: Cisco Systems, Inc.
              250 Apollo Drive
              Chelmsford, MA 01824
         Tel: +1-978-244-3051
       Email: tnadeau@cisco.com
              Cheenu Srinivasan
      Postal: Parama Networks, Inc.
              1030 Broad Street
              Shrewsbury, NJ 07702
         Tel: +1-732-544-9120 x731
       Email: cheenu@paramanet.com
         Tel: +1-732-544-9120x731
      
              Adrian Farrel
      Postal: Movaz Networks, Inc.
              7926 Jones Branch Drive
              McLean, VA 22102
         Tel: +1-703-847-1867
       Email: afarrel@movaz.com
      
              Edward Harrison
      Postal: Data Connection Ltd.
              100 Church Street
              Enfield, Middlesex
              EN2 6BQ, United Kingdom
         Tel: +44-20-8366-1177
       Email: eph@dataconnection.com
      
              Tim Hall
      Postal: Data Connection Ltd.
              100 Church Street
              Enfield, Middlesex
              EN2 6BQ, United Kingdom
         Tel: +44-20-8366-1177
       Email: timhall@dataconnection.com
      
      Email comments to the CCAMP WG Mailing List at
      ccamp@ops.ietf.org."
   DESCRIPTION
       "This MIB contains managed object
        definitions for the Generalized
        Multiprotocol Label Switching (GMPLS)
        Router."
   -- Revision history.
   REVISION
       "200206240900Z"  -- 24 June 2002 9:00:00 GMT
   DESCRIPTION
       "First revision draft version."
   -- Above revision history to be replaced as below
   --  REVISION "yyyymmddhhmmZ"
   --  DESCRIPTION "Initial version, published as RFC xxxx"
   -- xxxx to be assigned by RFC Editor
   ::= { experimental 1 } -- To Be Assigned by IANA

-- Tables, Scalars
gmplsLsrObjects       OBJECT IDENTIFIER ::= { gmplsLsrMIB 1
}
-- Notifications
-- Conformance
gmplsLsrConformance   OBJECT IDENTIFIER ::= { gmplsLsrMIB 2
}


-- GMPLS Interface Configuration Table.

gmplsInterfaceConfTable  OBJECT-TYPE
   SYNTAX        SEQUENCE OF GmplsInterfaceConfEntry
   MAX-ACCESS    not-accessible
   STATUS        current
   DESCRIPTION
       "This table specifies per-interface GMPLS
        capability and associated information.  It
        extends the information in
        mplsInterfaceConfTable."
   ::= { gmplsLsrObjects 1 }

gmplsInterfaceConfEntry OBJECT-TYPE
   SYNTAX        GmplsInterfaceConfEntry
   MAX-ACCESS    not-accessible
   STATUS        current
   DESCRIPTION
       "An entry in this table is created by an LSR
        for every interface capable of supporting
        GMPLS.  Each entry in this table will exist
        only if corresponding entries in
        mplsInterfaceConfTable and ifTable exists.
        If the associated entry in
        mplsInterfaceConfTabel or ifTable is
        deleted, the corresponding entry in this
        table must also be deleted shortly
        thereafter.
        The indexing is the same as that for
        mplsInterfaceConfTabel.  Thus, the entry
        with index 0 represents the per-platform
        label space and contains parameters that
        apply to all interfaces that participate in
        the per-platform label space."
   INDEX { mplsInterfaceConfIndex }
   ::= { gmplsInterfaceConfTable 1 }

GmplsInterfaceConfEntry ::= SEQUENCE {
      
      gmplsInterfaceConfSignalingCaps      BITS
   }

gmplsInterfaceConfSignalingCaps  OBJECT-TYPE
   SYNTAX       BITS {
      rsvp-gmpls (1),
      crldp-gmpls (2),
      other-gmpls (3)
   }
   MAX-ACCESS   read-create
   STATUS       current
   DESCRIPTION
       "Defines the signaling capabilities on this
        interface.  Multiple bits may legitimately
        be set at once.  Setting no bits implies
        that GMPLS signaling cannot be performed on
        this interface and all LSPs must be
        manually provisioned."
   ::= { gmplsInterfaceConfEntry 1 }

-- End of gmplsInterfaceConfTable

-- In-segment table.


gmplsInSegmentTable  OBJECT-TYPE
   SYNTAX        SEQUENCE OF GmplsInSegmentEntry
   MAX-ACCESS    not-accessible
   STATUS        current
   DESCRIPTION
       "This table extends the mplsInSegmentTable
        to provide GMPLS-specific information about
        incoming segments to an LSR."
   ::= { gmplsLsrObjects 2 }

gmplsInSegmentEntry  OBJECT-TYPE
   SYNTAX        GmplsInSegmentEntry
   MAX-ACCESS    not-accessible
   STATUS        current
   DESCRIPTION
       "An entry in this table extends the
        representation of an incoming segment
        represented by an entry in
        mplsInSegmentTable.  An entry can be
        created by a network administrator or an
        SNMP agent, or a GMPLS signaling protocol.
        "
   INDEX { mplsInSegmentIndex }
   ::= { gmplsInSegmentTable 1 }

GmplsInSegmentEntry ::= SEQUENCE {
      gmplsInSegmentDirection
      GmplsSegmentDirection
   }

gmplsInSegmentDirection OBJECT-TYPE
   SYNTAX        GmplsSegmentDirection
   MAX-ACCESS    read-create
   STATUS        current
   DESCRIPTION
       "This variable indicates the direction of
        data flow on this segment."
   DEFVAL        { forward }
   ::= { gmplsInSegmentEntry 1 }

-- End of gmplsInSegmentTable


-- Out-segment table.

gmplsOutSegmentTable  OBJECT-TYPE
   SYNTAX        SEQUENCE OF GmplsOutSegmentEntry
   MAX-ACCESS    not-accessible
   STATUS        current
   DESCRIPTION
       "This table extends the mplsOutSegmentTable
        to provide GMPLS-specific information about
        outgoing segments from an LSR."
   ::= { gmplsLsrObjects 3 }

gmplsOutSegmentEntry  OBJECT-TYPE
   SYNTAX        GmplsOutSegmentEntry
   MAX-ACCESS    not-accessible
   STATUS        current
   DESCRIPTION
       "An entry in this table extends the
        representation of an outgoin segment
        represented by an entry in
        mplsOutSegmentTable.  An entry can be
        created by a network administrator or an
        SNMP agent, or a GMPLS signaling protocol.
        "
   INDEX         { mplsOutSegmentIndex }
   ::= { gmplsOutSegmentTable 1 }

GmplsOutSegmentEntry ::= SEQUENCE {
      gmplsOutSegmentDirection
      GmplsSegmentDirection,
      gmplsOutSegmentTTLDecrement        Unsigned32
   }

gmplsOutSegmentDirection OBJECT-TYPE
   SYNTAX        GmplsSegmentDirection
   MAX-ACCESS    read-create
   STATUS        current
   DESCRIPTION
       "This variable indicates the direction of
        data flow on this segment.  This object
        cannot be modified if
        mplsOutSegmentRowStatus for the associated
        entry in the mplsOutSegmentTavle is
        active(1)."
   DEFVAL        { forward }
   ::= { gmplsOutSegmentEntry 1 }

gmplsOutSegmentTTLDecrement OBJECT-TYPE
   SYNTAX        Unsigned32 (0..255)
   MAX-ACCESS    read-create
   STATUS        current
   DESCRIPTION
       "This variable indicates the amount by which
        to decrement the TTL of any payload packets
        forwarded on this segment if per-hop
        decrementing is being done.
        A value of zero indicates that no decrement
        should be made or that per-hop decrementing
        is not in force.
        See the gmplsTunnelTTLDecrement object in
        the gmplsTunnelTable of [GMPLSTEMIB] for a
        value by which to decrement the TTL for the
        whole of a tunnel.
        This object cannot be modified if
        mplsOutSegmentRowStatus for the associated
        entry in the mplsOutSegmentTavle is
        active(1)."
   DEFVAL        { 0 }
   ::= { gmplsOutSegmentEntry 2 }

-- End of gmplsOutSegmentTable

-- Module compliance.

gmplsLsrGroups
   OBJECT IDENTIFIER ::= { gmplsLsrConformance 1 }

gmplsLsrCompliances
   OBJECT IDENTIFIER ::= { gmplsLsrConformance 2 }

gmplsLsrModuleCompliance MODULE-COMPLIANCE
   STATUS current
   DESCRIPTION
       "Compliance statement for agents that
        support the GMPLS LSR MIB."

   MODULE -- this module

   -- The mandatory groups have to be implemented
   -- by all LSRs that support GMPLS.  However, they
   -- may all be supported as read-only objects in
   -- the case where manual configuration is unsupported.

   MANDATORY-GROUPS    {
      gmplsInSegmentGroup,
      gmplsOutSegmentGroup,
      gmplsInterfaceGroup
   }

   -- gmplsInSegmentTable 

   OBJECT      gmplsInSegmentDirection
   SYNTAX      GmplsSegmentDirection
   MIN-ACCESS  read-only
   DESCRIPTION
       "Only forward(1) needs to be supported."


   -- gmplsOutSegmentTable

   OBJECT      gmplsOutSegmentDirection
   SYNTAX      GmplsSegmentDirection
   MIN-ACCESS  read-only
   DESCRIPTION
       "Only forward(1) needs to be supported."

   OBJECT      gmplsOutSegmentTTLDecrement
   SYNTAX      Unsigned32 (0..255)
   MIN-ACCESS  read-only
   DESCRIPTION
       "Write access is not required."



   ::= { gmplsLsrCompliances 1 }

-- Units of conformance.

gmplsInterfaceGroup OBJECT-GROUP
   OBJECTS {
      gmplsInterfaceConfSignalingCaps
   }
   STATUS  current
   DESCRIPTION
       "Collection of objects needed for GMPLS
        interface configuration and performance
        information."
   ::= { gmplsLsrGroups 1 }

gmplsInSegmentGroup  OBJECT-GROUP
   OBJECTS {
      gmplsInSegmentDirection
   }
   STATUS  current
   DESCRIPTION
       "Collection of objects needed to implement a
        GMPLS in-segment."
   ::= { gmplsLsrGroups 2 }

gmplsOutSegmentGroup  OBJECT-GROUP
   OBJECTS {
      gmplsOutSegmentDirection,
      gmplsOutSegmentTTLDecrement
   }
   STATUS  current
   DESCRIPTION
       "Collection of objects needed to implement a
        GMPLS out-segment."
   ::= { gmplsLsrGroups 3 }


END

--    Copyright (C) The Internet Society (2002). All Rights
--    Reserved.
--    
--    This document and translations of it may be copied and
--    furnished to others, and derivative works that comment on
--    or otherwise explain it or assist in its implementation
--    may be prepared, copied, published and distributed, in
--    whole or in part, without restriction of any kind,
--    provided that the above copyright notice and this
--    paragraph are included on all such copies and derivative
--    works.  However, this document itself may not be modified
--    in any way, such as by removing the copyright notice or
--    references to the Internet Society or other Internet
--    organizations, except as needed for the purpose of
--    developing Internet standards in which case the
--    procedures for copyrights defined in the Internet
--    Standards process must be followed, or as required to
--    translate it into languages other than English.
--    
--    The limited permissions granted above are perpetual and
--    will not be revoked by the Internet Society or its
--    successors or assigns. This document and the information
--    contained herein is provided on an "AS IS" basis and THE
--    INTERNET SOCIETY AND THE INTERNET ENGINEERING TASK FORCE
--    DISCLAIMS ALL WARRANTIES, EXPRESS OR IMPLIED, INCLUDING
--    BUT NOT LIMITED TO ANY WARRANTY THAT THE USE OF THE
--    INFORMATION HEREIN WILL NOT INFRINGE ANY RIGHTS OR ANY
--    IMPLIED WARRANTIES OF MERCHANTABILITY OR FITNESS FOR A
--    PARTICULAR PURPOSE.
