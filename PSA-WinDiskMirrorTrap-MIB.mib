PSA-WinDiskMirrorTrap-MIB DEFINITIONS ::= BEGIN

--PRIMEQUEST system management MIB for Partition
--
--
--$Copyright$
--Copyright Fujitsu Limited 2007 - 2008
--All rights reserved
--
--
--MIB Revision: 01160000
--

IMPORTS
	OBJECT-TYPE								FROM RFC-1212
	TRAP-TYPE								FROM RFC-1215
	mib-2, DisplayString					FROM RFC1213-MIB
	TimeTicks, Counter, Gauge, IpAddress	FROM RFC1155-SMI
	mgmt, enterprises						FROM RFC1155-SMI;

--enterprises	OBJECT IDENTIFIER ::={ iso org(3) dod(6) internet(1) private(4) 1 }
--
--PRIMEQUEST system management MIB nodes
--fujitsu:                    1.3.6.1.4.1.211
-- products:                  1.3.6.1.4.1.211.1
--  iaServer:                 1.3.6.1.4.1.211.1.31
--   primequest:              1.3.6.1.4.1.211.1.31.1
--    partition:	           1.3.6.1.4.1.211.1.31.1.2
--
--Trap enterprise is "psaWinDiskMirrorTrap"

--FUJITSU PRIMEQUEST system management MIB nodes for Partition
  fujitsu        OBJECT IDENTIFIER  ::={ enterprises 211 }
  products       OBJECT IDENTIFIER  ::={ fujitsu 1 }
  iaServer       OBJECT IDENTIFIER  ::={ products 31 }
  primequest     OBJECT IDENTIFIER  ::={ iaServer 1 }
   partition     OBJECT IDENTIFIER  ::={ primequest 2 }
    parititonVariables	OBJECT IDENTIFIER	::={ partition	200 }
    partitionEnterprise	OBJECT IDENTIFIER  ::={ partition 201 }
     psaComTrap			OBJECT IDENTIFIER  ::={ partitionEnterprise 1 }
     psaWinIntelE100Trap	OBJECT IDENTIFIER  ::={ partitionEnterprise 51 }
     psaWinIntelE1000Trap	OBJECT IDENTIFIER  ::={ partitionEnterprise 52 }
     psaWinBcm5700Trap		OBJECT IDENTIFIER  ::={ partitionEnterprise 53 }
     psaWinEmulexTrap		OBJECT IDENTIFIER  ::={ partitionEnterprise 54 }
     psaWinLsiLogicTrap	OBJECT IDENTIFIER  ::={ partitionEnterprise 55 }
     psaWinDiskTrap		OBJECT IDENTIFIER  ::={ partitionEnterprise 56 }
     psaWinGrmpdTrap		OBJECT IDENTIFIER  ::={ partitionEnterprise 57 }
     psaWinDiskMirrorTrap	OBJECT IDENTIFIER  ::={ partitionEnterprise 58 }
     psaWinXframe2Trap		OBJECT IDENTIFIER  ::={ partitionEnterprise 59 }

--***************************************************************************************
--
--FUJITSU PRIMEQUEST system management trap parameter variables for Partition
--	They aren't directly accessibles(can't use snmp get/set command), but sent with trap
--
--***************************************************************************************

     trapVarComInfo	OBJECT IDENTIFIER	::={ parititonVariables 1 }

trapPartitionName OBJECT-TYPE
   SYNTAX   DisplayString
   ACCESS   not-accessible
   STATUS   mandatory
   DESCRIPTION "Partition name which trap is generated."
   ::= { trapVarComInfo 1 }

trapPartitionId OBJECT-TYPE
   SYNTAX   INTEGER
   ACCESS   not-accessible
   STATUS   mandatory
   DESCRIPTION "Paritition identifier which trap is generated."
   ::= { trapVarComInfo 2 }

trapEventLevel OBJECT-TYPE
   SYNTAX   DisplayString
   ACCESS   not-accessible
   STATUS   mandatory
   DESCRIPTION "Event level"
   ::= { trapVarComInfo 3 }

trapEventId OBJECT-TYPE
   SYNTAX   INTEGER
   ACCESS   not-accessible
   STATUS   mandatory
   DESCRIPTION "Event Identifier"
   ::= { trapVarComInfo 4 }

trapUnitName OBJECT-TYPE
   SYNTAX   DisplayString
   ACCESS   not-accessible
   STATUS   mandatory
   DESCRIPTION "Unit name which trap is generated."
   ::= { trapVarComInfo 5 }

trapMmbVip OBJECT-TYPE
   SYNTAX   DisplayString
   ACCESS   not-accessible
   STATUS   mandatory
   DESCRIPTION "Management board vertual IP address."
   ::= { trapVarComInfo 6 }

     trapVarDivInfo	OBJECT IDENTIFIER	::={ parititonVariables 2 }

trapPartNo OBJECT-TYPE
   SYNTAX   DisplayString
   ACCESS   not-accessible
   STATUS   mandatory
   DESCRIPTION "Parts number of trap source."
   ::= { trapVarDivInfo 1 }

trapStepping OBJECT-TYPE
   SYNTAX   DisplayString
   ACCESS   not-accessible
   STATUS   mandatory
   DESCRIPTION " "
   ::= { trapVarDivInfo 2 }

trapSerialNo OBJECT-TYPE
   SYNTAX   DisplayString
   ACCESS   not-accessible
   STATUS   mandatory
   DESCRIPTION "Serial number of trap source. "
   ::= { trapVarDivInfo 3 }

trapModelNo OBJECT-TYPE
   SYNTAX   DisplayString
   ACCESS   not-accessible
   STATUS   mandatory
   DESCRIPTION "Model number of trap source."
   ::= { trapVarDivInfo 4 }

trapSuspect OBJECT-TYPE
   SYNTAX   DisplayString
   ACCESS   not-accessible
   STATUS   mandatory
   DESCRIPTION "Logical name or pci bus number of trap source."
   ::= { trapVarDivInfo 5 }

trapVendorId OBJECT-TYPE
   SYNTAX   DisplayString
   ACCESS   not-accessible
   STATUS   mandatory
   DESCRIPTION "Vendor identifier of trap source."
   ::= { trapVarDivInfo 6 }

trapDeviceId OBJECT-TYPE
   SYNTAX   DisplayString
   ACCESS   not-accessible
   STATUS   mandatory
   DESCRIPTION "Device identifier of trap source."
   ::= { trapVarDivInfo 7 }

trapRevision OBJECT-TYPE
   SYNTAX   DisplayString
   ACCESS   not-accessible
   STATUS   mandatory
   DESCRIPTION "Revision of trap source."
   ::= { trapVarDivInfo 8 }

trapCardName OBJECT-TYPE
   SYNTAX   DisplayString
   ACCESS   not-accessible
   STATUS   mandatory
   DESCRIPTION "Device name of trap source."
   ::= { trapVarDivInfo 9 }

trapErrDetail OBJECT-TYPE
   SYNTAX   DisplayString
   ACCESS   not-accessible
   STATUS   mandatory
   DESCRIPTION " "
   ::= { trapVarDivInfo 10 }

trapErrCode OBJECT-TYPE
   SYNTAX   DisplayString
   ACCESS   not-accessible
   STATUS   mandatory
   DESCRIPTION " "
   ::= { trapVarDivInfo 11 }

trapIrpCode OBJECT-TYPE
   SYNTAX   DisplayString
   ACCESS   not-accessible
   STATUS   mandatory
   DESCRIPTION " "
   ::= { trapVarDivInfo 12 }

trapHbaNo OBJECT-TYPE
   SYNTAX   INTEGER
   ACCESS   not-accessible
   STATUS   mandatory
   DESCRIPTION " "
   ::= { trapVarDivInfo 13 }

trapErrCause OBJECT-TYPE
   SYNTAX   DisplayString
   ACCESS   not-accessible
   STATUS   mandatory
   DESCRIPTION " "
   ::= { trapVarDivInfo 14 }

trapPathNo OBJECT-TYPE
   SYNTAX   INTEGER
   ACCESS   not-accessible
   STATUS   mandatory
   DESCRIPTION " "
   ::= { trapVarDivInfo 15 }

trapDiskId OBJECT-TYPE
   SYNTAX   DisplayString
   ACCESS   not-accessible
   STATUS   mandatory
   DESCRIPTION " "
   ::= { trapVarDivInfo 16 }

trapFmrDiskId OBJECT-TYPE
   SYNTAX   DisplayString
   ACCESS   not-accessible
   STATUS   mandatory
   DESCRIPTION " "
   ::= { trapVarDivInfo 17 }

trapCurDiskId OBJECT-TYPE
   SYNTAX   DisplayString
   ACCESS   not-accessible
   STATUS   mandatory
   DESCRIPTION " "
   ::= { trapVarDivInfo 18 }

trapPathId OBJECT-TYPE
   SYNTAX   DisplayString
   ACCESS   not-accessible
   STATUS   mandatory
   DESCRIPTION " "
   ::= { trapVarDivInfo 19 }

trapPhysIf OBJECT-TYPE
   SYNTAX   DisplayString
   ACCESS   not-accessible
   STATUS   mandatory
   DESCRIPTION " "
   ::= { trapVarDivInfo 20 }

trapVirtualIf OBJECT-TYPE
   SYNTAX   DisplayString
   ACCESS   not-accessible
   STATUS   mandatory
   DESCRIPTION " "
   ::= { trapVarDivInfo 21 }

trapLogicalIp OBJECT-TYPE
   SYNTAX   DisplayString
   ACCESS   not-accessible
   STATUS   mandatory
   DESCRIPTION " "
   ::= { trapVarDivInfo 22 }

trapWatchIp OBJECT-TYPE
   SYNTAX   DisplayString
   ACCESS   not-accessible
   STATUS   mandatory
   DESCRIPTION " "
   ::= { trapVarDivInfo 23 }

trapInterface OBJECT-TYPE
   SYNTAX   DisplayString
   ACCESS   not-accessible
   STATUS   mandatory
   DESCRIPTION " "
   ::= { trapVarDivInfo 24 }

trapSourceIp OBJECT-TYPE
   SYNTAX   DisplayString
   ACCESS   not-accessible
   STATUS   mandatory
   DESCRIPTION " "
   ::= { trapVarDivInfo 25 }

trapDestIp OBJECT-TYPE
   SYNTAX   DisplayString
   ACCESS   not-accessible
   STATUS   mandatory
   DESCRIPTION " "
   ::= { trapVarDivInfo 26 }

trapModelName OBJECT-TYPE
   SYNTAX   DisplayString
   ACCESS   not-accessible
   STATUS   mandatory
   DESCRIPTION "Model name of trap source."
   ::= { trapVarDivInfo 27 }

--***************************************************************************************
--
--FUJITSU PRIMEQUEST system management TRAP definition for Partition
--	Trap enterprise:	psaWinDiskMirrorTrap (.1.3.6.1.4.1.211.1.31.1.2.201.58)
--
--***************************************************************************************

diskMirrorWinEvent0 TRAP-TYPE
   ENTERPRISE   psaWinDiskMirrorTrap
   VARIABLES {
      trapPartitionName,
      trapPartitionId,
      trapEventLevel,
      trapEventId,
      trapUnitName,
      trapMmbVip
   }
   DESCRIPTION "Disk Mirror: Software error (Mirror driver was not able to start because of load error)"
   --#TYPE			"Disk Mirror Win Event 0"
   --#SUMMARY		"%s(PID=%d) %s %d %s Disk Mirror: Software error (Mirror driver was not able to start because of load error)"
   --#ARGUMENTS		{ 0, 1, 2, 3, 4 }
   --#SEVERITY		MAJOR
   ::= 26000

diskMirrorWinEvent1 TRAP-TYPE
   ENTERPRISE   psaWinDiskMirrorTrap
   VARIABLES {
      trapPartitionName,
      trapPartitionId,
      trapEventLevel,
      trapEventId,
      trapUnitName,
      trapMmbVip
   }
   DESCRIPTION "Disk Mirror: Software error (Mirror driver was not able to start 
                because of initializing process failure)"
   --#TYPE			"Disk Mirror Win Event 1"
   --#SUMMARY		"%s(PID=%d) %s %d %s Disk Mirror: Software error (Mirror driver was not able to start because of initializing process failure)"
   --#ARGUMENTS		{ 0, 1, 2, 3, 4 }
   --#SEVERITY		MAJOR
   ::= 26001

diskMirrorWinEvent2 TRAP-TYPE
   ENTERPRISE   psaWinDiskMirrorTrap
   VARIABLES {
      trapPartitionName,
      trapPartitionId,
      trapEventLevel,
      trapEventId,
      trapUnitName,
      trapMmbVip
   }
   DESCRIPTION "Disk Mirror: Software error (Mirror driver was not able to start 
                because of add device process failure)"
   --#TYPE			"Disk Mirror Win Event 2"
   --#SUMMARY		"%s(PID=%d) %s %d %s Disk Mirror: Software error (Mirror driver was not able to start because of add device process failure)"
   --#ARGUMENTS		{ 0, 1, 2, 3, 4 }
   --#SEVERITY		MAJOR
   ::= 26002

diskMirrorWinEvent3 TRAP-TYPE
   ENTERPRISE   psaWinDiskMirrorTrap
   VARIABLES {
      trapPartitionName,
      trapPartitionId,
      trapEventLevel,
      trapEventId,
      trapUnitName,
      trapMmbVip
   }
   DESCRIPTION "Disk Mirror: Software error (Mirror driver was not able to start 
                because of registry accessing error)"
   --#TYPE			"Disk Mirror Win Event 3"
   --#SUMMARY		"%s(PID=%d) %s %d %s Disk Mirror: Software error (Mirror driver was not able to start because of registry accessing error)"
   --#ARGUMENTS		{ 0, 1, 2, 3, 4 }
   --#SEVERITY		MAJOR
   ::= 26003

diskMirrorWinEvent4 TRAP-TYPE
   ENTERPRISE   psaWinDiskMirrorTrap
   VARIABLES {
      trapPartitionName,
      trapPartitionId,
      trapEventLevel,
      trapEventId,
      trapUnitName,
      trapMmbVip
   }
   DESCRIPTION "Disk Mirror: Software error (Mirror driver was not able to start 
                because of broken reserved data)"
   --#TYPE			"Disk Mirror Win Event 4"
   --#SUMMARY		"%s(PID=%d) %s %d %s Disk Mirror: Software error (Mirror driver was not able to start because of broken reserved data)"
   --#ARGUMENTS		{ 0, 1, 2, 3, 4 }
   --#SEVERITY		MAJOR
   ::= 26004

diskMirrorWinEvent5 TRAP-TYPE
   ENTERPRISE   psaWinDiskMirrorTrap
   VARIABLES {
      trapPartitionName,
      trapPartitionId,
      trapEventLevel,
      trapEventId,
      trapUnitName,
      trapMmbVip
   }
   DESCRIPTION "Disk Mirror: Device error (The error occurred on all disks in the mirror group)"
   --#TYPE			"Disk Mirror Win Event 5"
   --#SUMMARY		"%s(PID=%d) %s %d %s Disk Mirror: Device error (The error occurred on all disks in the mirror group)"
   --#ARGUMENTS		{ 0, 1, 2, 3, 4 }
   --#SEVERITY		MAJOR
   ::= 26005

diskMirrorWinEvent6 TRAP-TYPE
   ENTERPRISE   psaWinDiskMirrorTrap
   VARIABLES {
      trapPartitionName,
      trapPartitionId,
      trapEventLevel,
      trapEventId,
      trapUnitName,
      trapMmbVip
   }
   DESCRIPTION "Disk Mirror: Software error (JRM copy process was failed)"
   --#TYPE			"Disk Mirror Win Event 6"
   --#SUMMARY		"%s(PID=%d) %s %d %s Disk Mirror: Software error (JRM copy process was failed)"
   --#ARGUMENTS		{ 0, 1, 2, 3, 4 }
   --#SEVERITY		MINOR
   ::= 26006

diskMirrorWinEvent7 TRAP-TYPE
   ENTERPRISE   psaWinDiskMirrorTrap
   VARIABLES {
      trapPartitionName,
      trapPartitionId,
      trapEventLevel,
      trapEventId,
      trapUnitName,
      trapMmbVip
   }
   DESCRIPTION "Disk Mirror: Software error (Full disk copy for recovering equivalence process was failed)"
   --#TYPE			"Disk Mirror Win Event 7"
   --#SUMMARY		"%s(PID=%d) %s %d %s Disk Mirror: Software error (Full disk copy for recovering equivalence process was failed)"
   --#ARGUMENTS		{ 0, 1, 2, 3, 4 }
   --#SEVERITY		MINOR
   ::= 26007

diskMirrorWinEvent8 TRAP-TYPE
   ENTERPRISE   psaWinDiskMirrorTrap
   VARIABLES {
      trapPartitionName,
      trapPartitionId,
      trapEventLevel,
      trapEventId,
      trapUnitName,
      trapMmbVip
   }
   DESCRIPTION "Disk Mirror: Software error (Disk surprise removal occurred)"
   --#TYPE			"Disk Mirror Win Event 8"
   --#SUMMARY		"%s(PID=%d) %s %d %s Disk Mirror: Software error (Disk surprise removal occurred)"
   --#ARGUMENTS		{ 0, 1, 2, 3, 4 }
   --#SEVERITY		MINOR
   ::= 26008

diskMirrorWinEvent9 TRAP-TYPE
   ENTERPRISE   psaWinDiskMirrorTrap
   VARIABLES {
      trapPartitionName,
      trapPartitionId,
      trapEventLevel,
      trapEventId,
      trapUnitName,
      trapMmbVip
   }
   DESCRIPTION "Disk Mirror: Software error (The spare disk building in the mirror group was failed)"
   --#TYPE			"Disk Mirror Win Event 9"
   --#SUMMARY		"%s(PID=%d) %s %d %s Disk Mirror: Software error (The spare disk building in the mirror group was failed)"
   --#ARGUMENTS		{ 0, 1, 2, 3, 4 }
   --#SEVERITY		MINOR
   ::= 26009

diskMirrorWinEvent10 TRAP-TYPE
   ENTERPRISE   psaWinDiskMirrorTrap
   VARIABLES {
      trapPartitionName,
      trapPartitionId,
      trapEventLevel,
      trapEventId,
      trapUnitName,
      trapMmbVip
   }
   DESCRIPTION "Disk Mirror: Software error (Separating the spare disk from the mirror group was failed)"
   --#TYPE			"Disk Mirror Win Event 10"
   --#SUMMARY		"%s(PID=%d) %s %d %s Disk Mirror: Software error (Separating the spare disk from the mirror group was failed)"
   --#ARGUMENTS		{ 0, 1, 2, 3, 4 }
   --#SEVERITY		MINOR
   ::= 26010

diskMirrorWinEvent11 TRAP-TYPE
   ENTERPRISE   psaWinDiskMirrorTrap
   VARIABLES {
      trapPartitionName,
      trapPartitionId,
      trapEventLevel,
      trapEventId,
      trapUnitName,
      trapMmbVip
   }
   DESCRIPTION "Disk Mirror: Software error (Disk is not mirrored because only 1 disk remains 
                in the mirror group)"
   --#TYPE			"Disk Mirror Win Event 11"
   --#SUMMARY		"%s(PID=%d) %s %d %s Disk Mirror: Software error (Disk is not mirrored because only 1 disk remains in the mirror group)"
   --#ARGUMENTS		{ 0, 1, 2, 3, 4 }
   --#SEVERITY		MINOR
   ::= 26011

diskMirrorWinEvent12 TRAP-TYPE
   ENTERPRISE   psaWinDiskMirrorTrap
   VARIABLES {
      trapPartitionName,
      trapPartitionId,
      trapEventLevel,
      trapEventId,
      trapUnitName,
      trapSuspect,
      trapVendorId,
      trapCardName,
      trapSerialNo,
      trapMmbVip
   }
   DESCRIPTION "Disk Mirror:Disk Device error (Disk read error occurred)"
   --#TYPE			"Disk Mirror Win Event 12"
   --#SUMMARY		"%s(PID=%d) %s %d %s Disk Mirror:Disk%s Device error (Disk read error occurred) vendor=%s model=%s serial-no=%s"
   --#ARGUMENTS		{ 0, 1, 2, 3, 4, 5, 6, 7, 8 }
   --#SEVERITY		MINOR
   ::= 26012

diskMirrorWinEvent13 TRAP-TYPE
   ENTERPRISE   psaWinDiskMirrorTrap
   VARIABLES {
      trapPartitionName,
      trapPartitionId,
      trapEventLevel,
      trapEventId,
      trapUnitName,
      trapSuspect,
      trapVendorId,
      trapCardName,
      trapSerialNo,
      trapMmbVip
   }
   DESCRIPTION "Disk Mirror:Disk Device error (Disk read error occurred by time-out)"
   --#TYPE			"Disk Mirror Win Event 13"
   --#SUMMARY		"%s(PID=%d) %s %d %s Disk Mirror:Disk%s Device error (Disk read error occurred by time-out) vendor=%s model=%s serial-no=%s"
   --#ARGUMENTS		{ 0, 1, 2, 3, 4, 5, 6, 7, 8 }
   --#SEVERITY		MINOR
   ::= 26013

diskMirrorWinEvent14 TRAP-TYPE
   ENTERPRISE   psaWinDiskMirrorTrap
   VARIABLES {
      trapPartitionName,
      trapPartitionId,
      trapEventLevel,
      trapEventId,
      trapUnitName,
      trapSuspect,
      trapVendorId,
      trapCardName,
      trapSerialNo,
      trapMmbVip
   }
   DESCRIPTION "Disk Mirror:Disk Device error (Disk write error occurred)"
   --#TYPE			"Disk Mirror Win Event 14"
   --#SUMMARY		"%s(PID=%d) %s %d %s Disk Mirror:Disk%s Device error (Disk write error occurred) vendor=%s model=%s serial-no=%s"
   --#ARGUMENTS		{ 0, 1, 2, 3, 4, 5, 6, 7, 8 }
   --#SEVERITY		MINOR
   ::= 26014

diskMirrorWinEvent15 TRAP-TYPE
   ENTERPRISE   psaWinDiskMirrorTrap
   VARIABLES {
      trapPartitionName,
      trapPartitionId,
      trapEventLevel,
      trapEventId,
      trapUnitName,
      trapSuspect,
      trapVendorId,
      trapCardName,
      trapSerialNo,
      trapMmbVip
   }
   DESCRIPTION "Disk Mirror:Disk Device error (Disk write error by time-out occurred)"
   --#TYPE			"Disk Mirror Win Event 15"
   --#SUMMARY		"%s(PID=%d) %s %d %s Disk Mirror:Disk%s Device error (Disk write error by time-out occurred) vendor=%s model=%s serial-no=%s"
   --#ARGUMENTS		{ 0, 1, 2, 3, 4, 5, 6, 7, 8 }
   --#SEVERITY		MINOR
   ::= 26015

diskMirrorWinEvent16 TRAP-TYPE
   ENTERPRISE   psaWinDiskMirrorTrap
   VARIABLES {
      trapPartitionName,
      trapPartitionId,
      trapEventLevel,
      trapEventId,
      trapUnitName,
      trapSuspect,
      trapVendorId,
      trapCardName,
      trapSerialNo,
      trapMmbVip
   }
   DESCRIPTION "Disk Mirror:Disk Device error (Write-back process was failed)"
   --#TYPE			"Disk Mirror Win Event 16"
   --#SUMMARY		"%s(PID=%d) %s %d %s Disk Mirror:Disk%s Device error (Write-back process was failed) vendor=%s model=%s serial-no=%s"
   --#ARGUMENTS		{ 0, 1, 2, 3, 4, 5, 6, 7, 8 }
   --#SEVERITY		MINOR
   ::= 26016

diskMirrorWinEvent17 TRAP-TYPE
   ENTERPRISE   psaWinDiskMirrorTrap
   VARIABLES {
      trapPartitionName,
      trapPartitionId,
      trapEventLevel,
      trapEventId,
      trapUnitName,
      trapSuspect,
      trapVendorId,
      trapCardName,
      trapSerialNo,
      trapMmbVip
   }
   DESCRIPTION "Disk Mirror:Disk Device error (Write-back frequency reached a regulated value)"
   --#TYPE			"Disk Mirror Win Event 17"
   --#SUMMARY		"%s(PID=%d) %s %d %s Disk Mirror:Disk%s Device error (Write-back frequency reached a regulated value) vendor=%s model=%s serial-no=%s"
   --#ARGUMENTS		{ 0, 1, 2, 3, 4, 5, 6, 7, 8 }
   --#SEVERITY		MINOR
   ::= 26017

diskMirrorWinEvent18 TRAP-TYPE
   ENTERPRISE   psaWinDiskMirrorTrap
   VARIABLES {
      trapPartitionName,
      trapPartitionId,
      trapEventLevel,
      trapEventId,
      trapUnitName,
      trapSuspect,
      trapVendorId,
      trapCardName,
      trapSerialNo,
      trapMmbVip
   }
   DESCRIPTION "Disk Mirror:Disk Device error (JRM read error)"
   --#TYPE			"Disk Mirror Win Event 18"
   --#SUMMARY		"%s(PID=%d) %s %d %s Disk Mirror:Disk%s Device error (JRM read error) vendor=%s model=%s serial-no=%s"
   --#ARGUMENTS		{ 0, 1, 2, 3, 4, 5, 6, 7, 8 }
   --#SEVERITY		MINOR
   ::= 26018

diskMirrorWinEvent19 TRAP-TYPE
   ENTERPRISE   psaWinDiskMirrorTrap
   VARIABLES {
      trapPartitionName,
      trapPartitionId,
      trapEventLevel,
      trapEventId,
      trapUnitName,
      trapSuspect,
      trapVendorId,
      trapCardName,
      trapSerialNo,
      trapMmbVip
   }
   DESCRIPTION "Disk Mirror:Disk Device error (JRM read error by time-out)"
   --#TYPE			"Disk Mirror Win Event 19"
   --#SUMMARY		"%s(PID=%d) %s %d %s Disk Mirror:Disk%s Device error (JRM read error by time-out) vendor=%s model=%s serial-no=%s"
   --#ARGUMENTS		{ 0, 1, 2, 3, 4, 5, 6, 7, 8 }
   --#SEVERITY		MINOR
   ::= 26019

diskMirrorWinEvent20 TRAP-TYPE
   ENTERPRISE   psaWinDiskMirrorTrap
   VARIABLES {
      trapPartitionName,
      trapPartitionId,
      trapEventLevel,
      trapEventId,
      trapUnitName,
      trapSuspect,
      trapVendorId,
      trapCardName,
      trapSerialNo,
      trapMmbVip
   }
   DESCRIPTION "Disk Mirror:Disk Device error (JRM write error)"
   --#TYPE			"Disk Mirror Win Event 20"
   --#SUMMARY		"%s(PID=%d) %s %d %s Disk Mirror:Disk%s Device error (JRM write error) vendor=%s model=%s serial-no=%s"
   --#ARGUMENTS		{ 0, 1, 2, 3, 4, 5, 6, 7, 8 }
   --#SEVERITY		MINOR
   ::= 26020

diskMirrorWinEvent21 TRAP-TYPE
   ENTERPRISE   psaWinDiskMirrorTrap
   VARIABLES {
      trapPartitionName,
      trapPartitionId,
      trapEventLevel,
      trapEventId,
      trapUnitName,
      trapSuspect,
      trapVendorId,
      trapCardName,
      trapSerialNo,
      trapMmbVip
   }
   DESCRIPTION "Disk Mirror:Disk Device error (JRM write error by time-out)"
   --#TYPE			"Disk Mirror Win Event 21"
   --#SUMMARY		"%s(PID=%d) %s %d %s Disk Mirror:Disk%s Device error (JRM write error by time-out) vendor=%s model=%s serial-no=%s"
   --#ARGUMENTS		{ 0, 1, 2, 3, 4, 5, 6, 7, 8 }
   --#SEVERITY		MINOR
   ::= 26021

diskMirrorWinEvent22 TRAP-TYPE
   ENTERPRISE   psaWinDiskMirrorTrap
   VARIABLES {
      trapPartitionName,
      trapPartitionId,
      trapEventLevel,
      trapEventId,
      trapUnitName,
      trapSuspect,
      trapVendorId,
      trapCardName,
      trapSerialNo,
      trapMmbVip
   }
   DESCRIPTION "Disk Mirror:Disk Device error (Status of disk changed to ERROR 
                by disk access except for read and write process)"
   --#TYPE			"Disk Mirror Win Event 22"
   --#SUMMARY		"%s(PID=%d) %s %d %s Disk Mirror:Disk%s Device error (Status of disk changed to ERROR by disk access except for read and write process) vendor=%s model=%s serial-no=%s"
   --#ARGUMENTS		{ 0, 1, 2, 3, 4, 5, 6, 7, 8 }
   --#SEVERITY		MINOR
   ::= 26022

diskMirrorWinEvent23 TRAP-TYPE
   ENTERPRISE   psaWinDiskMirrorTrap
   VARIABLES {
      trapPartitionName,
      trapPartitionId,
      trapEventLevel,
      trapEventId,
      trapUnitName,
      trapMmbVip
   }
   DESCRIPTION "Disk Mirror: Information (System does not shutdown normally last time)"
   --#TYPE			"Disk Mirror Win Event 23"
   --#SUMMARY		"%s(PID=%d) %s %d %s Disk Mirror: Information (System does not shutdown normally last time)"
   --#ARGUMENTS		{ 0, 1, 2, 3, 4 }
   --#SEVERITY		INFORMATIONAL
   ::= 26023

diskMirrorWinEvent24 TRAP-TYPE
   ENTERPRISE   psaWinDiskMirrorTrap
   VARIABLES {
      trapPartitionName,
      trapPartitionId,
      trapEventLevel,
      trapEventId,
      trapUnitName,
      trapMmbVip
   }
   DESCRIPTION "Disk Mirror: Information (JRM copy process was completed successfully)"
   --#TYPE			"Disk Mirror Win Event 24"
   --#SUMMARY		"%s(PID=%d) %s %d %s Disk Mirror: Information (JRM copy process was completed successfully)"
   --#ARGUMENTS		{ 0, 1, 2, 3, 4 }
   --#SEVERITY		INFORMATIONAL
   ::= 26024

diskMirrorWinEvent25 TRAP-TYPE
   ENTERPRISE   psaWinDiskMirrorTrap
   VARIABLES {
      trapPartitionName,
      trapPartitionId,
      trapEventLevel,
      trapEventId,
      trapUnitName,
      trapMmbVip
   }
   DESCRIPTION "Disk Mirror: Information (Full disk copy for recovering equivalence process 
                was completed successfull)"
   --#TYPE			"Disk Mirror Win Event 25"
   --#SUMMARY		"%s(PID=%d) %s %d %s Disk Mirror: Information (Full disk copy for recovering equivalence process was completed successfull)"
   --#ARGUMENTS		{ 0, 1, 2, 3, 4 }
   --#SEVERITY		INFORMATIONAL
   ::= 26025

diskMirrorWinEvent26 TRAP-TYPE
   ENTERPRISE   psaWinDiskMirrorTrap
   VARIABLES {
      trapPartitionName,
      trapPartitionId,
      trapEventLevel,
      trapEventId,
      trapUnitName,
      trapMmbVip
   }
   DESCRIPTION "Disk Mirror: Information (The spare disk building in the mirror group 
                was completed successfully)"
   --#TYPE			"Disk Mirror Win Event 26"
   --#SUMMARY		"%s(PID=%d) %s %d %s Disk Mirror: Information (The spare disk building in the mirror group was completed successfully)"
   --#ARGUMENTS		{ 0, 1, 2, 3, 4 }
   --#SEVERITY		INFORMATIONAL
   ::= 26026

diskMirrorWinEvent27 TRAP-TYPE
   ENTERPRISE   psaWinDiskMirrorTrap
   VARIABLES {
      trapPartitionName,
      trapPartitionId,
      trapEventLevel,
      trapEventId,
      trapUnitName,
      trapMmbVip
   }
   DESCRIPTION "Disk Mirror: Information (Recovered mirror disk and removing the spare disk from 
                the mirror group was completed successfully)"
   --#TYPE			"Disk Mirror Win Event 27"
   --#SUMMARY		"%s(PID=%d) %s %d %s Disk Mirror: Information (Recovered mirror disk and removing the spare disk from the mirror group was completed successfully)"
   --#ARGUMENTS		{ 0, 1, 2, 3, 4 }
   --#SEVERITY		INFORMATIONAL
   ::= 26027

diskMirrorWinEvent28 TRAP-TYPE
   ENTERPRISE   psaWinDiskMirrorTrap
   VARIABLES {
      trapPartitionName,
      trapPartitionId,
      trapEventLevel,
      trapEventId,
      trapUnitName,
      trapMmbVip
   }
   DESCRIPTION "Disk Mirror: Information (Disk is removed from the mirror group)"
   --#TYPE			"Disk Mirror Win Event 28"
   --#SUMMARY		"%s(PID=%d) %s %d %s Disk Mirror: Information (Disk is removed from the mirror group)"
   --#ARGUMENTS		{ 0, 1, 2, 3, 4 }
   --#SEVERITY		INFORMATIONAL
   ::= 26028

diskMirrorWinEvent29 TRAP-TYPE
   ENTERPRISE   psaWinDiskMirrorTrap
   VARIABLES {
      trapPartitionName,
      trapPartitionId,
      trapEventLevel,
      trapEventId,
      trapUnitName,
      trapMmbVip
   }
   DESCRIPTION "Disk Mirror: Information (Write-back process was succeeded)"
   --#TYPE			"Disk Mirror Win Event 29"
   --#SUMMARY		"%s(PID=%d) %s %d %s Disk Mirror: Information (Write-back process was succeeded)"
   --#ARGUMENTS		{ 0, 1, 2, 3, 4 }
   --#SEVERITY		INFORMATIONAL
   ::= 26029

diskMirrorWinEvent30 TRAP-TYPE
   ENTERPRISE   psaWinDiskMirrorTrap
   VARIABLES {
      trapPartitionName,
      trapPartitionId,
      trapEventLevel,
      trapEventId,
      trapUnitName,
      trapMmbVip
   }
   DESCRIPTION "Disk Mirror: Information (Conflict has been found between 
                the configuration database and the actual)"
   --#TYPE			"Disk Mirror Win Event 30"
   --#SUMMARY		"%s(PID=%d) %s %d %s Disk Mirror: Information (Conflict has been found between the configuration database and the actual)"
   --#ARGUMENTS		{ 0, 1, 2, 3, 4 }
   --#SEVERITY		INFORMATIONAL
   ::= 26030

diskMirrorWinEvent31 TRAP-TYPE
   ENTERPRISE   psaWinDiskMirrorTrap
   VARIABLES {
      trapPartitionName,
      trapPartitionId,
      trapEventLevel,
      trapEventId,
      trapUnitName,
      trapMmbVip
   }
   DESCRIPTION "Disk Mirror: Software error (The following mirror group has been removed automatically)"
   --#TYPE			"Disk Mirror Win Event 31"
   --#SUMMARY		"%s(PID=%d) %s %d %s Disk Mirror: Software error (The following mirror group has been removed automatically)"
   --#ARGUMENTS		{ 0, 1, 2, 3, 4 }
   --#SEVERITY		MINOR
   ::= 26031

diskMirrorWinEvent32 TRAP-TYPE
   ENTERPRISE   psaWinDiskMirrorTrap
   VARIABLES {
      trapPartitionName,
      trapPartitionId,
      trapEventLevel,
      trapEventId,
      trapUnitName,
      trapMmbVip
   }
   DESCRIPTION "Disk Mirror: Software error (The reserved partition has been 
                removed automatically from the following disk)"
   --#TYPE			"Disk Mirror Win Event 32"
   --#SUMMARY		"%s(PID=%d) %s %d %s Disk Mirror: Software error (The reserved partition has been removed automatically from the following disk)"
   --#ARGUMENTS		{ 0, 1, 2, 3, 4 }
   --#SEVERITY		MINOR
   ::= 26032

diskMirrorWinEvent33 TRAP-TYPE
   ENTERPRISE   psaWinDiskMirrorTrap
   VARIABLES {
      trapPartitionName,
      trapPartitionId,
      trapEventLevel,
      trapEventId,
      trapUnitName,
      trapMmbVip
   }
   DESCRIPTION "Disk Mirror: Information (The following mirror group has been removed)"
   --#TYPE			"Disk Mirror Win Event 33"
   --#SUMMARY		"%s(PID=%d) %s %d %s Disk Mirror: Information (The following mirror group has been removed)"
   --#ARGUMENTS		{ 0, 1, 2, 3, 4 }
   --#SEVERITY		INFORMATIONAL
   ::= 26033

diskMirrorWinEvent34 TRAP-TYPE
   ENTERPRISE   psaWinDiskMirrorTrap
   VARIABLES {
      trapPartitionName,
      trapPartitionId,
      trapEventLevel,
      trapEventId,
      trapUnitName,
      trapMmbVip
   }
   DESCRIPTION "Disk Mirror: Information (Write caching of the following disk has been disabled)"
   --#TYPE			"Disk Mirror Win Event 34"
   --#SUMMARY		"%s(PID=%d) %s %d %s Disk Mirror: Information (Write caching of the following disk has been disabled)"
   --#ARGUMENTS		{ 0, 1, 2, 3, 4 }
   --#SEVERITY		INFORMATIONAL
   ::= 26034

END
