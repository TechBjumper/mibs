ACC-ATM DEFINITIONS ::= BEGIN

    IMPORTS
		OBJECT-TYPE, Counter FROM RFC1155-SMI
   	 accTrapLogSeqNum FROM ACC-SYSTEM
	accBRG, DisplayString, IfIndex, SmdsAddress
             FROM ACC-MIB
			RowStatus FROM SNMPv2-TC;

-- ACC ATM General Group
--
-- Alcatraz ACC proprietary ATM MIB
--
accAtm  OBJECT IDENTIFIER ::= { accBRG 77 }
-- ATM Layer and Call Statistics group
atmStatsGrp   OBJECT IDENTIFIER ::= { accAtm 1 }
-- OAM group
atmOamGrp	   OBJECT IDENTIFIER ::= { accAtm 5 }
-- ILMI group
atmIlmiGrp	   OBJECT IDENTIFIER ::= { accAtm 6 }
-- rfc1695 doesn't provide ifindex within tables; our client needs all
-- objects in a table to share the same instance. What this means is
-- that we will need to duplicate the standards tables using only the
-- instance objects as entries.
atmInstGrp    OBJECT IDENTIFIER ::= { accAtm 9 }
--
-- ATM Layer and Call Statistics Group
--
  	 -- ATM Layer Statistics Table
atmStatsAtmLayerTable	  OBJECT-TYPE
   SYNTAX   SEQUENCE OF AtmStatsAtmLayerEntry
   ACCESS   not-accessible
   STATUS   mandatory
   DESCRIPTION
      "The ATM Layer Statistics Table."
   ::= { atmStatsGrp 1 }
atmStatsAtmLayerEntry  OBJECT-TYPE
   SYNTAX  AtmStatsAtmLayerEntry
   ACCESS  not-accessible
   STATUS  mandatory
   DESCRIPTION
      "An entry in the ATM Layer Statistics Table"
   INDEX   { ifIndex } -- accAtmIfIndex
   ::= { atmStatsAtmLayerTable 1 }
AtmStatsAtmLayerEntry ::=
       SEQUENCE {
       atmStatsAtmLayerRxCells	  Counter,
       atmStatsAtmLayerTxCells    Counter,
       atmStatsAtmLayerDiscCells  Counter,
       atmStatsAtmLayerDropCells  Counter
}
      atmStatsAtmLayerRxCells	 OBJECT-TYPE
	  SYNTAX  Counter
	  ACCESS read-only
	  STATUS mandatory
	  DESCRIPTION
	    " Total number of received cells."
	  ::= { atmStatsAtmLayerEntry 1 }
       atmStatsAtmLayerTxCells    OBJECT-TYPE
          SYNTAX Counter
	  ACCESS read-only
	  STATUS mandatory
	  DESCRIPTION
	    " Total number of transmitted cells."
	  ::= { atmStatsAtmLayerEntry 2 }
       atmStatsAtmLayerDiscCells  OBJECT-TYPE
          SYNTAX  Counter
	  ACCESS read-only
	  STATUS mandatory
	  DESCRIPTION
	    " Total number of discarded cells."
	  ::= { atmStatsAtmLayerEntry 3 }
       atmStatsAtmLayerDropCells  OBJECT-TYPE
          SYNTAX  Counter
	  ACCESS read-only
	  STATUS mandatory
	  DESCRIPTION
	    " Total number of dropped cells."
	  ::= { atmStatsAtmLayerEntry 4 }
	  -- Call Statistics Table
atmStatsCallTable	  OBJECT-TYPE
   SYNTAX   SEQUENCE OF AtmStatsCallEntry
   ACCESS   not-accessible
   STATUS   mandatory
   DESCRIPTION
      "The Call Statistics Table."
   ::= { atmStatsGrp 2 }
atmStatsCallEntry  OBJECT-TYPE
   SYNTAX  AtmStatsCallEntry
   ACCESS  not-accessible
   STATUS  mandatory
   DESCRIPTION
      "An entry in the Call Statistics Table"
   INDEX   { ifIndex } -- accAtmIfIndex
   ::= { atmStatsCallTable 1 }
AtmStatsCallEntry ::=
       SEQUENCE {
       atmStatsCallOrigCalls  Counter,
       atmStatsCallOffCalls   Counter,
       atmStatsCallAccCalls   Counter,
       atmStatsCallCompCalls  Counter,
       atmStatsCallClrCalls   Counter
}
      atmStatsCallOrigCalls	 OBJECT-TYPE
	  SYNTAX  Counter
	  ACCESS read-only
	  STATUS mandatory
	  DESCRIPTION
	    " Number of calls originated from this interface"
	  ::= { atmStatsCallEntry 1 }
       atmStatsCallOffCalls    OBJECT-TYPE
          SYNTAX  Counter
	  ACCESS read-only
	  STATUS mandatory
	  DESCRIPTION
	    " Number of calls offered to this interface."
	  ::= { atmStatsCallEntry 2 }
       atmStatsCallAccCalls  OBJECT-TYPE
          SYNTAX  Counter
	  ACCESS read-only
	  STATUS mandatory
	  DESCRIPTION
	    " Number of calls accepted. "
	  ::= { atmStatsCallEntry 3 }
       atmStatsCallCompCalls   OBJECT-TYPE
          SYNTAX  Counter
	  ACCESS read-only
	  STATUS mandatory
	  DESCRIPTION
	    " Number of successfull/completed calls. "
	  ::= { atmStatsCallEntry 4 }
       atmStatsCallClrCalls   OBJECT-TYPE
	   SYNTAX  Counter
	   ACCESS read-only
	   STATUS mandatory
	   DESCRIPTION
	     " Number of calls cleared. "
	   ::= { atmStatsCallEntry 5 }
--
-- OAM group
--
	-- OAM configuration table
atmOamConfTable	  OBJECT-TYPE
   SYNTAX   SEQUENCE OF AtmOamConfEntry
   ACCESS   not-accessible
   STATUS   mandatory
   DESCRIPTION
      " The OAM configuration table. "
   ::= { atmOamGrp 1 }
atmOamConfEntry    OBJECT-TYPE
    SYNTAX	   AtmOamConfEntry	
    ACCESS	   not-accessible
    STATUS	   mandatory
    DESCRIPTION	   
       " An entry in the OAM configuration table. "
    INDEX	   { atmOamIndex }
    ::= { atmOamConfTable 1 }
AtmOamConfEntry ::=
     SEQUENCE {
	      atmOamIndex		IfIndex,
	      atmOamPhyFlowType		INTEGER,
	      atmOamFlowState		INTEGER
}
	atmOamIndex		OBJECT-TYPE
	  SYNTAX		IfIndex 
	  ACCESS		read-only
	  STATUS		mandatory
	  DESCRIPTION
	" Index into this table; must have same value as ifIndex. "
	::= { atmOamConfEntry 1 }
	atmOamPhyFlowType	OBJECT-TYPE
	  SYNTAX		INTEGER { f1(1), f2(2), f3(3) }
	  ACCESS		read-write
	  STATUS		mandatory
	  DESCRIPTION
	" The PHY level flows - f1, f2, or f3. "
	::= { atmOamConfEntry 2 }
	atmOamFlowState		OBJECT-TYPE
	  SYNTAX		INTEGER { on(1), off(2) }
	  ACCESS		read-write
	  STATUS		mandatory
	  DESCRIPTION
		" flow state on or off. "
	::= { atmOamConfEntry 3 }
	 -- OAM VPC config table
	atmOamVpcTable		OBJECT-TYPE
	SYNTAX		SEQUENCE OF AtmOamVpcEntry
	ACCESS		not-accessible
	STATUS			mandatory
	DESCRIPTION
	    " The OAM VPC table. "
	::= { atmOamGrp 2 }
	atmOamVpcEntry	OBJECT-TYPE
	SYNTAX		AtmOamVpcEntry
	ACCESS	not-accessible
	STATUS		mandatory
	DESCRIPTION
	    " An entry in the OAM VPC Table. "
	INDEX		{ atmOamVpcIndex, atmOamVpcVpi }
	::= { atmOamVpcTable 1 }
AtmOamVpcEntry		::=
	SEQUENCE {
		atmOamVpcIndex		IfIndex,
		atmOamVpcVpi		INTEGER,
		atmOamVpcFlowType	INTEGER,
		atmOamVpcRowStatus	RowStatus
}
	atmOamVpcIndex		OBJECT-TYPE
	SYNTAX		IfIndex 
	ACCESS		read-only
	STATUS		mandatory
	DESCRIPTION
	" The index into the OAM VPC table. Must have same value as ifIndex."
::= { atmOamVpcEntry 1 }
	atmOamVpcVpi		OBJECT-TYPE
	SYNTAX		INTEGER (0..255)
	ACCESS		read-only
	STATUS		mandatory
	DESCRIPTION
	" The VPI of the VPC."
	::= { atmOamVpcEntry 2 }
	atmOamVpcFlowType		OBJECT-TYPE
	SYNTAX		INTEGER { end2end(1), segment(2) }
	ACCESS		read-write
	STATUS		mandatory
	DESCRIPTION
	"The VPC flow type: end2end or segment."
	::= { atmOamVpcEntry 3 }
	atmOamVpcRowStatus		OBJECT-TYPE
	SYNTAX		RowStatus 
	ACCESS		read-write
	STATUS		mandatory
	DESCRIPTION
	"Rowstatus for an entry."
	::= { atmOamVpcEntry 4 }
	 -- OAM VCC config table
	atmOamVccTable		OBJECT-TYPE
	SYNTAX		SEQUENCE OF AtmOamVccEntry
	ACCESS		not-accessible
	STATUS		mandatory
	DESCRIPTION
	    " The OAM VCC table. "
	::= { atmOamGrp 3 }
	atmOamVccEntry	OBJECT-TYPE
	SYNTAX		AtmOamVccEntry
	ACCESS		not-accessible
	STATUS		mandatory
	DESCRIPTION
	    " An entry in the OAM VCC Table. "
	INDEX		{ atmOamVccIndex, atmOamVccVpi, atmOamVccVci }
	::= { atmOamVccTable 1 }
AtmOamVccEntry		::=
	SEQUENCE {
		atmOamVccIndex		IfIndex,
		atmOamVccVpi		INTEGER,
		atmOamVccVci		INTEGER,
		atmOamVccFlowType	INTEGER,
		atmOamVccRowStatus	RowStatus
}
	atmOamVccIndex		OBJECT-TYPE
	SYNTAX		IfIndex 
	ACCESS		read-only
	STATUS		mandatory
	DESCRIPTION
	" The index into the OAM VCC table. Must have same value as ifIndex."
	::= { atmOamVccEntry 1 }
	atmOamVccVpi		OBJECT-TYPE
	SYNTAX		INTEGER (0..255)
	ACCESS		read-only
	STATUS		mandatory
	DESCRIPTION
	" The VPI of the VCC."
	::= { atmOamVccEntry 2 }
	atmOamVccVci		OBJECT-TYPE
	SYNTAX		INTEGER (0..65535)
	ACCESS	read-only
	STATUS		mandatory
	DESCRIPTION
	" The VCI of the VCC."
	::= { atmOamVccEntry 3 }
	atmOamVccFlowType		OBJECT-TYPE
	SYNTAX		INTEGER { end2end(1), segment(2) }
	ACCESS		read-write
	STATUS		mandatory
	DESCRIPTION
	"The VCC flow type: end2end or segment."
	::= { atmOamVccEntry 4 }
	atmOamVccRowStatus		OBJECT-TYPE
	SYNTAX		RowStatus 
	ACCESS		read-write
	STATUS		mandatory
	DESCRIPTION
	"Rowstatus for an entry."
	::= { atmOamVccEntry 5 }
--
-- ILMI group
--
	-- ILMI configuration table 
	atmIlmiConfTable	  OBJECT-TYPE
	   SYNTAX   SEQUENCE OF AtmIlmiConfEntry
	   ACCESS   not-accessible
	   STATUS   mandatory
	   DESCRIPTION
	      "The Ilmi Configuration Table."
	   ::= { atmIlmiGrp 1 }
	atmIlmiConfEntry  OBJECT-TYPE
	   SYNTAX  AtmIlmiConfEntry
	   ACCESS  not-accessible
	   STATUS  mandatory
	   DESCRIPTION
	      "An entry in the Ilmi Configuration Table"
	   INDEX   { ifIndex } -- accAtmIfIndex
	   ::= { atmIlmiConfTable 1 }
AtmIlmiConfEntry ::=
       SEQUENCE {
       atmIlmiImeType		INTEGER,
       atmIlmiUniType		INTEGER
}
       atmIlmiImeType		OBJECT-TYPE
	   SYNTAX		INTEGER { network(1), user(2),
					   symmetric(3) }
	   ACCESS		read-write
	   STATUS		mandatory
	   DESCRIPTION
	      " IME type: user/network/symmetric. In user mode, the
	   ILMI will be configured to initiate the connection. In
	   network mode, the ILMI listens for an ILMI connection. In
	   symmetric mode, it decides on whether to act as network or
	   user by talking to the peer. The default is user. "
	   DEFVAL { user }
	   ::= { atmIlmiConfEntry 1 }
	atmIlmiUniType           OBJECT-TYPE
	       SYNTAX	       INTEGER { public(1), private(2) }
	       ACCESS	       read-write
	       STATUS	       mandatory
	        DESCRIPTION
		  " The UNI type. This object maps to atmfAtmLayerUniType. If
		  private, then autoconfiguration procedures may be used to 
		  automatically determine the interface type as described in
		  the ILMI4.0 specification. Procedures for interface type 
		  determination for public devices is unspecified."
		 DEFVAL { private }
		 ::= { atmIlmiConfEntry 2 }
	 atmIlmiCommStrTable	OBJECT-TYPE
	      SYNTAX		SEQUENCE OF AtmIlmiCommStrEntry
	      ACCESS		not-accessible
	      STATUS		mandatory
	      DESCRIPTION
	       " The community string table for an interface. "
	      ::= { atmIlmiGrp 2 } 
	 atmIlmiCommStrEntry	 OBJECT-TYPE
	    SYNTAX		 AtmIlmiCommStrEntry
	    ACCESS		 not-accessible
	    STATUS		 mandatory
	    DESCRIPTION
	     " An entry in the atmIlmiCommStrTable. "
	    INDEX		 { atmIlmiCommStrIndex, atmIlmiCommStr }
	    ::= { atmIlmiCommStrTable 1 }
AtmIlmiCommStrEntry ::= SEQUENCE {
	   atmIlmiCommStrIndex	 IfIndex,
	   atmIlmiCommStr	 OCTET STRING,
	   atmIlmiCommStrStatus	 RowStatus
}
       atmIlmiCommStrIndex   OBJECT-TYPE
           SYNTAX	     IfIndex
	   ACCESS	     read-only
	   STATUS	     mandatory
	   DESCRIPTION
	     "ifIndex of an ATM interface to which a set of community
	      strings is associated. "
	   ::= { atmIlmiCommStrEntry 1 }
       atmIlmiCommStr     OBJECT-TYPE
            SYNTAX	  OCTET STRING(SIZE(0..255))
	    ACCESS	  read-write
	    STATUS	  mandatory
	    DESCRIPTION
	      " A community string for an interface. "
	    ::= { atmIlmiCommStrEntry 2 }
-- add: CREATE_AND_GO(4)
-- del: DESTROY(6)
       atmIlmiCommStrStatus   OBJECT-TYPE
            SYNTAX	  RowStatus
	    ACCESS	  read-write
	    STATUS	  mandatory
	    DESCRIPTION
	        " Modification status of this entry; setting the
            status to add causes a new entry to be added. Setting it
            to delete causes an existing entry to be deleted. "
            ::= { atmIlmiCommStrEntry 3 } 
--
-- AtmInst group
--
-- The ATM interface table (holds just ifIndex). Use in tables which
-- are indexed by ifIndex only
 accAtmIfTable     OBJECT-TYPE
     SYNTAX	SEQUENCE OF AccAtmIfEntry
     ACCESS	not-accessible
     STATUS	mandatory
     DESCRIPTION
         " Atm interface table, holds just the ifIndex to get around
	   ifIndex not being specifically included in rfc1695. Any
           place that ifIndex (pertaining to ATM is desired), this
	   object should be used."
     ::= { atmInstGrp 1 }
     accAtmIfEntry	OBJECT-TYPE
        SYNTAX		AccAtmIfEntry
	ACCESS		not-accessible
	STATUS		mandatory
	DESCRIPTION
	   " An entry in the atm interface tbl. Holds just ifIndex."
	INDEX		{ accAtmIfIndex }
	::= { accAtmIfTable 1 }
     AccAtmIfEntry ::= SEQUENCE {
		accAtmIfIndex   IfIndex
		}
     accAtmIfIndex  OBJECT-TYPE
        SYNTAX	    IfIndex
	ACCESS	    read-only
	STATUS	    mandatory
	DESCRIPTION
	   "Ifindex for ATM interfaces. Must have the same value as
	    the SNMP ifIndex object for this interface. "
        ::= { accAtmIfEntry 1 }
-- Duplicated VPL table. Use for tables which are instanced by ifIndex,vpi
   accAtmVplTable    OBJECT-TYPE
      SYNTAX         SEQUENCE OF AccAtmVplEntry
      ACCESS	     not-accessible
      STATUS	     mandatory
      DESCRIPTION
         " The ACC atm vpl table; provides ifIndex and vpi to be used
           as instance ids. "
      ::= { atmInstGrp 2 }
   accAtmVplEntry      OBJECT-TYPE	
       SYNTAX	       AccAtmVplEntry
       ACCESS	       not-accessible
       STATUS	       mandatory
       DESCRIPTION
         " An entry in the accAtmVplTable. "
       INDEX	       { accAtmVplIndex,accAtmVplVpi }
       ::= { accAtmVplTable 1 }
   AccAtmVplEntry ::= SEQUENCE {
		  accAtmVplIndex      IfIndex,
		  accAtmVplVpi	      INTEGER
   }
   accAtmVplIndex	OBJECT-TYPE
       SYNTAX		IfIndex
       ACCESS		read-only
       STATUS		mandatory
       DESCRIPTION
         " IfIndex of the VPL table. Must have same value as the
           ifIndex object. "
       ::= { accAtmVplEntry 1 }
    accAtmVplVpi        OBJECT-TYPE
        SYNTAX		INTEGER  (1..4095)
        ACCESS		read-only 
        STATUS		mandatory
        DESCRIPTION
           "The VPI value of the VPL. Note that the VPI=0 is not used
            VPL not associated with a VCL. The maximum VPI value cannot
            exceed the value allowable by the atmInterfaceMaxVpiBits."
        ::= { accAtmVplEntry 2 }
-- The Acc ATM VCL table; use for tables indexed by ifIndex,vpi,vci       
   accAtmVclTable    OBJECT-TYPE
      SYNTAX         SEQUENCE OF AccAtmVclEntry
      ACCESS	     not-accessible
      STATUS	     mandatory
      DESCRIPTION
         " The ACC atm VCL table; provides ifIndex, vpi and vci to be used
           as instance ids. "
      ::= { atmInstGrp 3 }
   accAtmVclEntry      OBJECT-TYPE	
       SYNTAX	       AccAtmVclEntry
       ACCESS	       not-accessible
       STATUS	       mandatory
       DESCRIPTION
         " An entry in the accAtmVclTable. "
       INDEX	       { accAtmVclIndex, accAtmVclVpi, accAtmVclVci }
       ::= { accAtmVclTable 1 }
   AccAtmVclEntry ::= SEQUENCE {
		  accAtmVclIndex      IfIndex,
		  accAtmVclVpi	      INTEGER,
		  accAtmVclVci	      INTEGER
   }
   accAtmVclIndex	OBJECT-TYPE
       SYNTAX		IfIndex
       ACCESS		read-only
       STATUS		mandatory
       DESCRIPTION
         " IfIndex of the VCL table. Must have same value as the
           ifIndex object. "
       ::= { accAtmVclEntry 1 }
      accAtmVclVpi    OBJECT-TYPE
            SYNTAX    INTEGER  (0..4095)
       ACCESS	      read-only
       STATUS         mandatory
       DESCRIPTION
           "The VPI value of the VCL.
            The maximum VPI value cannot
            exceed the value allowable by the
            atmInterfaceMaxVpiBits."
      ::= { accAtmVclEntry 2 }
      accAtmVclVci    OBJECT-TYPE
       SYNTAX	      INTEGER  (0..65535)
       ACCESS	      read-only
       STATUS         mandatory
       DESCRIPTION
         "The VCI value of the VCL.
          The maximum VCI value cannot
          exceed the value allowable by the
          atmInterfaceMaxVciBits."
       ::= { accAtmVclEntry 3 }
-- The Acc ATM CLOCK table; use for tables indexed by ifIndex, clockType      
   accAtmClockTable    OBJECT-TYPE
      SYNTAX         SEQUENCE OF AccAtmClockEntry
      ACCESS	     not-accessible
      STATUS	     mandatory
      DESCRIPTION
         " The ACC atm CLOCK table; provides ifIndex and clockType to be used
           as instance ids. "
      ::= { atmInstGrp 4 }
   accAtmClockEntry      OBJECT-TYPE	
       SYNTAX	       AccAtmClockEntry
       ACCESS	       not-accessible
       STATUS	       mandatory
       DESCRIPTION
         " An entry in the accAtmClockTable. "
       INDEX	       { accAtmClockIndex, accAtmClockType }
       ::= { accAtmClockTable 1 }
   AccAtmClockEntry ::= SEQUENCE {
		  accAtmClockIndex      IfIndex,
		  accAtmClockType	INTEGER
   }
   accAtmClockIndex	OBJECT-TYPE
       SYNTAX		IfIndex
       ACCESS		read-only
       STATUS		mandatory
       DESCRIPTION
         " IfIndex of the CLOCK table. Must have same value as the
           ifIndex object. "
       ::= { accAtmClockEntry 1 }
   accAtmClockType    OBJECT-TYPE
       SYNTAX	      INTEGER { external(1), internal(2) }
       ACCESS	      read-write
       STATUS         mandatory
       DESCRIPTION
           "The clock type of the Interface.
            The clock type is either external
	    or internal."
      ::= { accAtmClockEntry 2 }

END
