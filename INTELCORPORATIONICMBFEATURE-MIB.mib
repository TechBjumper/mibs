-- MIB generated by miftomib version 1.0a

INTELCORPORATIONICMBFEATURE-MIB DEFINITIONS ::= BEGIN

-- This component allows control and configuration of the ICMB feature.

IMPORTS
	TRAP-TYPE FROM RFC-1215
    OBJECT-TYPE
    FROM RFC-1212
    enterprises
    FROM RFC1155-SMI
    DisplayString
    FROM RFC1213-MIB;

DmiInteger			::= INTEGER
DmiOctetstring		::= OCTET STRING
DmiDisplaystring	::= DisplayString
DmiDateX			::= OCTET STRING (SIZE (28))
DmiComponentIndex	::= INTEGER

intel                   OBJECT IDENTIFIER ::= {enterprises 343}
products                OBJECT IDENTIFIER ::= {intel 2}
server-products         OBJECT IDENTIFIER ::= {products 6}
platforms               OBJECT IDENTIFIER ::= {server-products 2}
icmbFeature             OBJECT IDENTIFIER ::= {platforms 4}
dmtfGroups              OBJECT IDENTIFIER ::= {icmbFeature 1}

SComponentid ::= SEQUENCE {
	a1Manufacturer                          	DmiDisplaystring,
	a1Product                               	DmiDisplaystring,
	a1Version                               	DmiDisplaystring,
	a1SerialNumber                          	DmiDisplaystring,
	a1Installation                          	DmiDateX,
	a1Verify                                	DmiInteger
}

tComponentid OBJECT-TYPE
	SYNTAX		SEQUENCE OF SComponentid
	ACCESS		not-accessible
	STATUS		mandatory
	DESCRIPTION	"This group defines the attributes common to all components.This
group is required."
	::= {dmtfGroups 1}

eComponentid OBJECT-TYPE
	SYNTAX		SComponentid
	ACCESS		not-accessible
	STATUS		mandatory
	DESCRIPTION	""
	--INDEX		{DmiComponentIndex}
	::= {tComponentid 1}

a1Manufacturer OBJECT-TYPE
	SYNTAX		DmiDisplaystring
	ACCESS		read-only
	STATUS		mandatory
	DESCRIPTION	"Manufacturer of this software."
	::= {eComponentid 1}

a1Product OBJECT-TYPE
	SYNTAX		DmiDisplaystring
	ACCESS		read-only
	STATUS		mandatory
	DESCRIPTION	"Product name for this software."
	::= {eComponentid 2}

a1Version OBJECT-TYPE
	SYNTAX		DmiDisplaystring
	ACCESS		read-only
	STATUS		mandatory
	DESCRIPTION	"Version number of this system."
	::= {eComponentid 3}

a1SerialNumber OBJECT-TYPE
	SYNTAX		DmiDisplaystring
	ACCESS		read-only
	STATUS		mandatory
	DESCRIPTION	"Serial number for this system."
	::= {eComponentid 4}

a1Installation OBJECT-TYPE
	SYNTAX		DmiDateX
	ACCESS		read-only
	STATUS		mandatory
	DESCRIPTION	"The time and date when this component was installed."
	::= {eComponentid 5}

a1Verify OBJECT-TYPE
	SYNTAX		INTEGER {
		vAnErrorOccurredCheckStatusCode         	(0),
		vThisComponentDoesNotExist              	(1),
		vVerificationIsNotSupported             	(2),
		vReserved                               	(3),
		vThisComponentExistsButTheFunctionalityI	(4),
		vThisComponentExistsButTheFunctionality1	(5),
		vThisComponentExistsAndIsNotFunctioningC	(6),
		vThisComponentExistsAndIsFunctioningCorr	(7)
	}
	ACCESS		read-only
	STATUS		mandatory
	DESCRIPTION	"A code that provides a level of verification that the component
is still installed and working."
	::= {eComponentid 6}

SIcmbChassisTable ::= SEQUENCE {
	a11ChassisIndex                         	DmiInteger,
	a11ComponentId                          	DmiInteger,
	a11ChassisAvailable                     	DmiInteger
}

tIcmbChassisTable OBJECT-TYPE
	SYNTAX		SEQUENCE OF SIcmbChassisTable
	ACCESS		not-accessible
	STATUS		mandatory
	DESCRIPTION	"This table contains a row per ICMB remote chassis component."
	::= {dmtfGroups 11}

eIcmbChassisTable OBJECT-TYPE
	SYNTAX		SIcmbChassisTable
	ACCESS		not-accessible
	STATUS		mandatory
	DESCRIPTION	""
	--INDEX		{DmiComponentIndex, a11ChassisIndex}
	::= {tIcmbChassisTable 1}

a11ChassisIndex OBJECT-TYPE
	SYNTAX		DmiInteger
	ACCESS		read-only
	STATUS		mandatory
	DESCRIPTION	"This is the index into the table"
	::= {eIcmbChassisTable 1}

a11ComponentId OBJECT-TYPE
	SYNTAX		DmiInteger
	ACCESS		read-only
	STATUS		mandatory
	DESCRIPTION	"This is the DMI component ID of a remote chassis component."
	::= {eIcmbChassisTable 2}

a11ChassisAvailable OBJECT-TYPE
	SYNTAX		INTEGER {
		vAvailable                              	(0),
		vShuttingDown                           	(1),
		vUnavailable                            	(2),
		vInitializing                           	(3)
	}
	ACCESS		read-write
	STATUS		mandatory
	DESCRIPTION	"This attribute indicates whether the chassis represented
by this row is currently visible on the ICMB."
	::= {eIcmbChassisTable 3}

SIcmbControl ::= SEQUENCE {
	a12State                                	DmiInteger,
	a12DiscoveryPeriod                      	DmiInteger,
	a12SdrReadState                         	DmiInteger,
	a12AcceptIcmbCommands                   	DmiInteger,
	a12ReclaimResources                     	DmiInteger
}

tIcmbControl OBJECT-TYPE
	SYNTAX		SEQUENCE OF SIcmbControl
	ACCESS		not-accessible
	STATUS		mandatory
	DESCRIPTION	"Control of the ICMB feature"
	::= {dmtfGroups 12}

eIcmbControl OBJECT-TYPE
	SYNTAX		SIcmbControl
	ACCESS		not-accessible
	STATUS		mandatory
	DESCRIPTION	""
	--INDEX		{DmiComponentIndex}
	::= {tIcmbControl 1}

a12State OBJECT-TYPE
	SYNTAX		INTEGER {
		vFalse                                  	(0),
		vTrue                                   	(1)
	}
	ACCESS		read-write
	STATUS		mandatory
	DESCRIPTION	"This attribute indicates whether the ICMB feature is enabled
or not"
	::= {eIcmbControl 1}

a12DiscoveryPeriod OBJECT-TYPE
	SYNTAX		DmiInteger
	ACCESS		read-write
	STATUS		mandatory
	DESCRIPTION	"This is the period of ICMB discovery cycles, in seconds"
	::= {eIcmbControl 2}

a12SdrReadState OBJECT-TYPE
	SYNTAX		INTEGER {
		vFalse                                  	(0),
		vTrue                                   	(1)
	}
	ACCESS		read-write
	STATUS		mandatory
	DESCRIPTION	"This attribute indicates whether the chassis SDR is used
to populate the sensor tables"
	::= {eIcmbControl 3}

a12AcceptIcmbCommands OBJECT-TYPE
	SYNTAX		INTEGER {
		vFalse                                  	(0),
		vTrue                                   	(1)
	}
	ACCESS		read-write
	STATUS		mandatory
	DESCRIPTION	"This attribute indicates whether this server will accept
and execute incoming commands over the ICMB"
	::= {eIcmbControl 4}

a12ReclaimResources OBJECT-TYPE
	SYNTAX		DmiInteger
	ACCESS		read-write
	STATUS		mandatory
	DESCRIPTION	"This attribute is used to reclaim resources for remote chassis
that cannot be seen on theICMB bus."
	::= {eIcmbControl 5}

SIcmbMifMappingTable ::= SEQUENCE {
	a13MapIndex                             	DmiInteger,
	a13Manufacturer                         	DmiDisplaystring,
	a13ProductName                          	DmiDisplaystring,
	a13ModelNumber                          	DmiDisplaystring,
	a13MifFilename                          	DmiDisplaystring
}

tIcmbMifMappingTable OBJECT-TYPE
	SYNTAX		SEQUENCE OF SIcmbMifMappingTable
	ACCESS		not-accessible
	STATUS		mandatory
	DESCRIPTION	"This table contains a row per ICMB remote chassis MIF file"
	::= {dmtfGroups 13}

eIcmbMifMappingTable OBJECT-TYPE
	SYNTAX		SIcmbMifMappingTable
	ACCESS		not-accessible
	STATUS		mandatory
	DESCRIPTION	""
	--INDEX		{DmiComponentIndex, a13MapIndex}
	::= {tIcmbMifMappingTable 1}

a13MapIndex OBJECT-TYPE
	SYNTAX		DmiInteger
	ACCESS		read-only
	STATUS		mandatory
	DESCRIPTION	"This is the indes into the table"
	::= {eIcmbMifMappingTable 1}

a13Manufacturer OBJECT-TYPE
	SYNTAX		DmiDisplaystring
	ACCESS		read-write
	STATUS		mandatory
	DESCRIPTION	"This is the manufacturer of the chassis this MIF file instrument
"
	::= {eIcmbMifMappingTable 2}

a13ProductName OBJECT-TYPE
	SYNTAX		DmiDisplaystring
	ACCESS		read-write
	STATUS		mandatory
	DESCRIPTION	"This is the Product Name of the chassis this MIF file instrument
"
	::= {eIcmbMifMappingTable 3}

a13ModelNumber OBJECT-TYPE
	SYNTAX		DmiDisplaystring
	ACCESS		read-write
	STATUS		mandatory
	DESCRIPTION	"This is the Model Number of the chassis this MIF file instrument
"
	::= {eIcmbMifMappingTable 4}

a13MifFilename OBJECT-TYPE
	SYNTAX		DmiDisplaystring
	ACCESS		read-write
	STATUS		mandatory
	DESCRIPTION	"This is the filename path of the MIF file this row represents"
	::= {eIcmbMifMappingTable 5}

SMiftomib ::= SEQUENCE {
	a1001MibName                            	DmiDisplaystring,
	a1001MibOid                             	DmiDisplaystring,
	a1001DisableTrap                        	DmiInteger
}

tMiftomib OBJECT-TYPE
	SYNTAX		SEQUENCE OF SMiftomib
	ACCESS		not-accessible
	STATUS		mandatory
	DESCRIPTION	"This group defines attributes required for DMI to
SNMP translati
n."
	::= {dmtfGroups 1001}

eMiftomib OBJECT-TYPE
	SYNTAX		SMiftomib
	ACCESS		not-accessible
	STATUS		mandatory
	DESCRIPTION	""
	--INDEX		{DmiComponentIndex}
	::= {tMiftomib 1}

a1001MibName OBJECT-TYPE
	SYNTAX		DmiDisplaystring
	ACCESS		read-only
	STATUS		mandatory
	DESCRIPTION	"The MIB name that defines this MIF"
	::= {eMiftomib 1}

a1001MibOid OBJECT-TYPE
	SYNTAX		DmiDisplaystring
	ACCESS		read-only
	STATUS		mandatory
	DESCRIPTION	"The MIB Object Identifier that corresponds to this MIF"
	::= {eMiftomib 2}

a1001DisableTrap OBJECT-TYPE
	SYNTAX		DmiInteger
	ACCESS		read-write
	STATUS		mandatory
	DESCRIPTION	"This attribute can be changed to disable sending oftraps
from this component"
	::= {eMiftomib 3}

SEifControl ::= SEQUENCE {
	a2000Status                             	DmiInteger,
	a2000DimContext                         	DmiOctetstring,
	a2000PersistentDataWriteDelay           	DmiInteger,
	a2000EifInterfaceName                   	DmiDisplaystring
}

tEifControl OBJECT-TYPE
	SYNTAX		SEQUENCE OF SEifControl
	ACCESS		not-accessible
	STATUS		mandatory
	DESCRIPTION	"Special control group for use with EIF"
	::= {dmtfGroups 2000}

eEifControl OBJECT-TYPE
	SYNTAX		SEifControl
	ACCESS		not-accessible
	STATUS		mandatory
	DESCRIPTION	""
	--INDEX		{DmiComponentIndex}
	::= {tEifControl 1}

a2000Status OBJECT-TYPE
	SYNTAX		INTEGER {
		vOther                                  	(1),
		vUnknown                                	(2),
		vCreatedOnly                            	(3),
		vConstructedOnly                        	(4),
		vFullyOperational                       	(5),
		vIdle                                   	(6)
	}
	ACCESS		read-write
	STATUS		mandatory
	DESCRIPTION	"Current status of this component as set by EIF"
	::= {eEifControl 1}

a2000DimContext OBJECT-TYPE
	SYNTAX		DmiOctetstring
	ACCESS		read-write
	STATUS		mandatory
	DESCRIPTION	"Opaque data used by DIM objects to obtain their context informat
on from some invocating source. It is assumed that the DIMs will be able
to usefully parse the information in this attribute, as the 'mainline' DMI
code in the CI makes no attempt to understand it."
	::= {eEifControl 2}

a2000PersistentDataWriteDelay OBJECT-TYPE
	SYNTAX		DmiInteger
	ACCESS		read-write
	STATUS		mandatory
	DESCRIPTION	"Defines the timeout from an attribute set operation until
the presistent write operation is invoked. If another set operation takes
place during this period, the timeout timer is reset back to this value,
so a persistent write operation will only take place after the specified
period has elasped with no set operations. Timeout is specified in 1/10 second
quantity. If set to zero, no persistent write operation will occur."
	::= {eEifControl 3}

a2000EifInterfaceName OBJECT-TYPE
	SYNTAX		DmiDisplaystring
	ACCESS		read-only
	STATUS		mandatory
	DESCRIPTION	"EIF Interface Name used to distinguish the component type
this MIF file represents."
	::= {eEifControl 4}

SEifExtensionList ::= SEQUENCE {
	a2001Index                              	DmiInteger,
	a2001Filename                           	DmiDisplaystring
}

tEifExtensionList OBJECT-TYPE
	SYNTAX		SEQUENCE OF SEifExtensionList
	ACCESS		not-accessible
	STATUS		mandatory
	DESCRIPTION	"A specific extension library specification"
	::= {dmtfGroups 2001}

eEifExtensionList OBJECT-TYPE
	SYNTAX		SEifExtensionList
	ACCESS		not-accessible
	STATUS		mandatory
	DESCRIPTION	""
	--INDEX		{DmiComponentIndex, a2001Index}
	::= {tEifExtensionList 1}

a2001Index OBJECT-TYPE
	SYNTAX		DmiInteger
	ACCESS		read-only
	STATUS		mandatory
	DESCRIPTION	"row index"
	::= {eEifExtensionList 1}

a2001Filename OBJECT-TYPE
	SYNTAX		DmiDisplaystring
	ACCESS		read-only
	STATUS		mandatory
	DESCRIPTION	"name of extension library"
	::= {eEifExtensionList 2}

SEventGenerationForEifControl ::= SEQUENCE {
	a2002EventType                          	DmiInteger,
	a2002EventSeverity                      	DmiInteger,
	a2002IsEventState-based                 	DmiInteger,
	a2002EventStateKey                      	DmiInteger,
	a2002AssociatedGroup                    	DmiDisplaystring,
	a2002EventSystem                        	DmiInteger,
	a2002EventSubsystem                     	DmiInteger
}

tEventGenerationForEifControl OBJECT-TYPE
	SYNTAX		SEQUENCE OF SEventGenerationForEifControl
	ACCESS		not-accessible
	STATUS		mandatory
	DESCRIPTION	""
	::= {dmtfGroups 2002}

eEventGenerationForEifControl OBJECT-TYPE
	SYNTAX		SEventGenerationForEifControl
	ACCESS		not-accessible
	STATUS		mandatory
	DESCRIPTION	""
	--INDEX		{DmiComponentIndex, a2002AssociatedGroup}
	::= {tEventGenerationForEifControl 1}

a2002EventType OBJECT-TYPE
	SYNTAX		INTEGER {
		vNoDimContextsCreated                   	(1)
	}
	ACCESS		read-only
	STATUS		mandatory
	DESCRIPTION	"The type of event that has occurred."
	::= {eEventGenerationForEifControl 1}

a2002EventSeverity OBJECT-TYPE
	SYNTAX		INTEGER {
		vMonitor                                	(1),
		vInformation                            	(2),
		vOk                                     	(4),
		vNon-critical                           	(8),
		vCritical                               	(16),
		vNon-recoverable                        	(32)
	}
	ACCESS		read-only
	STATUS		mandatory
	DESCRIPTION	"The severity of this event."
	::= {eEventGenerationForEifControl 2}

a2002IsEventState-based OBJECT-TYPE
	SYNTAX		INTEGER {
		vFalse                                  	(0),
		vTrue                                   	(1)
	}
	ACCESS		read-only
	STATUS		mandatory
	DESCRIPTION	"The value of this attribute determines whether the Event
being reported is a state-based Event or not. If the value of this attribute
is TRUE then the Event is state-based. Otherwise the Event is not state-based."
	::= {eEventGenerationForEifControl 3}

a2002EventStateKey OBJECT-TYPE
	SYNTAX		DmiInteger
	ACCESS		read-only
	STATUS		mandatory
	DESCRIPTION	"A unique, single integer key into the Event State group if
this is a state-based Event. If this is not a state-based Event then this
attribute's value is not defined."
	::= {eEventGenerationForEifControl 4}

a2002AssociatedGroup OBJECT-TYPE
	SYNTAX		DmiDisplaystring
	ACCESS		read-only
	STATUS		mandatory
	DESCRIPTION	"The class name of the group that is associated with the events
defined in this Event Generation group."
	::= {eEventGenerationForEifControl 5}

a2002EventSystem OBJECT-TYPE
	SYNTAX		INTEGER {
		vOther1                                 	(0),
		vUnknown1                               	(1)
	}
	ACCESS		read-only
	STATUS		mandatory
	DESCRIPTION	"The major functional aspect of the product causing the fault."
	::= {eEventGenerationForEifControl 6}

a2002EventSubsystem OBJECT-TYPE
	SYNTAX		INTEGER {
		vOther                                  	(0),
		vUnknown                                	(1)
	}
	ACCESS		read-only
	STATUS		mandatory
	DESCRIPTION	"The minor functional aspect of the product causing the fault."
	::= {eEventGenerationForEifControl 7}

trap1ForEifControl TRAP-TYPE
    ENTERPRISE eEventGenerationForEifControl
    VARIABLES  {
	a2002EventType,
	a2002EventSeverity,
	a2002IsEventState-based,
	a2002EventStateKey,
	a2002AssociatedGroup,
	a2002EventSystem,
	a2002EventSubsystem
       }

    DESCRIPTION "No DIM Context created"

    ::= 1

END
