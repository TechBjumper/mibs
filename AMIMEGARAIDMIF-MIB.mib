-- MIB generated by miftomib version 1.0a

AMIMEGARAIDMIF-MIB DEFINITIONS ::= BEGIN

-- This is the MIF for the Megaraid

IMPORTS
    OBJECT-TYPE
    FROM RFC-1212
    enterprises
    FROM RFC1155-SMI
    DisplayString
    FROM RFC1213-MIB;

DmiInteger			::= INTEGER
DmiOctetstring		::= OCTET STRING
DmiDisplaystring	::= DisplayString
DmiDateX			::= OCTET STRING (SIZE (28))
DmiComponentIndex	::= INTEGER

ami                   	OBJECT IDENTIFIER ::= {enterprises 16}
megaraid             	OBJECT IDENTIFIER ::= {ami 1}
mifmib			      	OBJECT IDENTIFIER ::= {megaraid 2}
dmtfGroups          	OBJECT IDENTIFIER ::= {mifmib 1}

SComponentid ::= SEQUENCE {
	a1Manufacturer                          	DmiDisplaystring,
	a1Product                               	DmiDisplaystring,
	a1Version                               	DmiDisplaystring,
	a1SerialNumber                          	DmiDisplaystring,
	a1Installation                          	DmiDateX,
	a1Verify                                	DmiInteger
}

tComponentid OBJECT-TYPE
	SYNTAX		SEQUENCE OF SComponentid
	ACCESS		not-accessible
	STATUS		mandatory
	DESCRIPTION	"This group defines attributes common to all components."
	::= {dmtfGroups 1}

eComponentid OBJECT-TYPE
	SYNTAX		SComponentid
	ACCESS		not-accessible
	STATUS		mandatory
	DESCRIPTION	""
--	INDEX		{DmiComponentIndex}
	::= {tComponentid 1}

a1Manufacturer OBJECT-TYPE
	SYNTAX		DmiDisplaystring
	ACCESS		read-only
	STATUS		mandatory
	DESCRIPTION	"The name of the manufacturer that produced this component."
	::= {eComponentid 1}

a1Product OBJECT-TYPE
	SYNTAX		DmiDisplaystring
	ACCESS		read-only
	STATUS		mandatory
	DESCRIPTION	"The name of the component."
	::= {eComponentid 2}

a1Version OBJECT-TYPE
	SYNTAX		DmiDisplaystring
	ACCESS		read-only
	STATUS		mandatory
	DESCRIPTION	"The version for the component."
	::= {eComponentid 3}

a1SerialNumber OBJECT-TYPE
	SYNTAX		DmiDisplaystring
	ACCESS		read-only
	STATUS		mandatory
	DESCRIPTION	"The serial number for this instance of this component."
	::= {eComponentid 4}

a1Installation OBJECT-TYPE
	SYNTAX		DmiDateX
	ACCESS		read-only
	STATUS		mandatory
	DESCRIPTION	"The time & date of the lastest installation of this component."
	::= {eComponentid 5}

a1Verify OBJECT-TYPE
	SYNTAX		INTEGER {
		vAnErrorOccurredCheckStatusCode         	(0),
		vThisComponentDoesNotExist              	(1),
		vTheVerifyIsNotSupported                	(2),
		vReserved                               	(3),
		vThisComponentExistsButTheFunctionalityI	(4),
		vThisComponentExistsButTheFunctionality1	(5),
		vThisComponentExistsAndIsNotFunctioningC	(6),
		vThisComponentExistsAndIsFunctioningCorr	(7)
	}
	ACCESS		read-only
	STATUS		mandatory
	DESCRIPTION	"A code that provides a level of verification that the component
is still installed and working."
	::= {eComponentid 6}

SControllerInformation ::= SEQUENCE {
	a2Adpadapternumber                      	DmiInteger,
	a2Firmwareversion                       	DmiDisplaystring,
	a2Biosversion                           	DmiDisplaystring,
	a2Numlogicaldrives                      	DmiInteger,
	a2Dramsizeinmb                          	DmiInteger,
	a2Chipsettype                           	DmiInteger,
	a2Rebuildrateinpercent                  	DmiInteger,
	a2Flushinterval                         	DmiInteger,
	a2Maxconcurrentcmds                     	DmiInteger,
	a2Spinupdelay                           	DmiInteger,
	a2Spinupcount                           	DmiInteger,
	a2Adpioreadspersec                      	DmiInteger,
	a2Adpiowritespersec                     	DmiInteger,
	a2Adpreadkbspersec                      	DmiInteger,
	a2Adpwritekbspersec                     	DmiInteger,
	a2Adpreadfailurespersec                 	DmiInteger,
	a2Adpwritefailurespersec                	DmiInteger,
	a2Scanchannels                          	DmiInteger,
	a2Logicalview                           	DmiOctetstring,
	a2Physicalview                          	DmiOctetstring
}

tControllerInformation OBJECT-TYPE
	SYNTAX		SEQUENCE OF SControllerInformation
	ACCESS		not-accessible
	STATUS		mandatory
	DESCRIPTION	"This group contains Megaraid common information"
	::= {dmtfGroups 2}

eControllerInformation OBJECT-TYPE
	SYNTAX		SControllerInformation
	ACCESS		not-accessible
	STATUS		mandatory
	DESCRIPTION	""
--	INDEX		{DmiComponentIndex, a2Adpadapternumber}
	::= {tControllerInformation 1}

a2Adpadapternumber OBJECT-TYPE
	SYNTAX		DmiInteger
	ACCESS		read-only
	STATUS		mandatory
	DESCRIPTION	"The adapter number for this instance of adapter object"
	::= {eControllerInformation 1}

a2Firmwareversion OBJECT-TYPE
	SYNTAX		DmiDisplaystring
	ACCESS		read-only
	STATUS		mandatory
	DESCRIPTION	"The firmware version of this adapter."
	::= {eControllerInformation 2}

a2Biosversion OBJECT-TYPE
	SYNTAX		DmiDisplaystring
	ACCESS		read-only
	STATUS		mandatory
	DESCRIPTION	"The bios version of this adapter."
	::= {eControllerInformation 3}

a2Numlogicaldrives OBJECT-TYPE
	SYNTAX		DmiInteger
	ACCESS		read-only
	STATUS		mandatory
	DESCRIPTION	"The number of logical drives attatched to this controller."
	::= {eControllerInformation 4}

a2Dramsizeinmb OBJECT-TYPE
	SYNTAX		DmiInteger
	ACCESS		read-only
	STATUS		mandatory
	DESCRIPTION	"Amount of DRAM in MB present on this adapter"
	::= {eControllerInformation 5}

a2Chipsettype OBJECT-TYPE
	SYNTAX		INTEGER {
		vIntelneptuneormercury                  	(225),
		vTriton                                 	(226),
		vOthers                                 	(97)
	}
	ACCESS		read-only
	STATUS		mandatory
	DESCRIPTION	"Motherboard Chipset Type for which the Adapter ASIC is Configure
."
	::= {eControllerInformation 6}

a2Rebuildrateinpercent OBJECT-TYPE
	SYNTAX		DmiInteger
	ACCESS		read-write
	STATUS		mandatory
	DESCRIPTION	"Rebuild Rate for this Adapter. This determines the Priority
of Rebuild/Check-Consistency/Reconstruct Operations versus the Read-Write
Operations."
	::= {eControllerInformation 7}

a2Flushinterval OBJECT-TYPE
	SYNTAX		INTEGER {
		vTwosec                                 	(2),
		vFoursec                                	(4),
		vSixsec                                 	(6),
		vEightsec                               	(8),
		vTensec                                 	(10)
	}
	ACCESS		read-write
	STATUS		mandatory
	DESCRIPTION	"Internal Cache Flush Interval for Logical Drives in WriteBack
Mode."
	::= {eControllerInformation 8}

a2Maxconcurrentcmds OBJECT-TYPE
	SYNTAX		DmiInteger
	ACCESS		read-only
	STATUS		mandatory
	DESCRIPTION	"Maximum Concurrent Commands Supported by the Adapter."
	::= {eControllerInformation 9}

a2Spinupdelay OBJECT-TYPE
	SYNTAX		DmiInteger
	ACCESS		read-only
	STATUS		mandatory
	DESCRIPTION	"This is the Spinup Delay for Spinning Up Physical Drives
at Firmware Initialization Time. The Physical Drives are divided into Groups,
each containing the number of drives indicated by the spinupCount variable.
spinupDelay variable is the amount of delay used before the drives in the
next group are issued a SPINUP Command."
	::= {eControllerInformation 10}

a2Spinupcount OBJECT-TYPE
	SYNTAX		DmiInteger
	ACCESS		read-only
	STATUS		mandatory
	DESCRIPTION	"This is the Spinup Count for Spinning up Physical Drives
at Firmware Initialization Time. The Physical Drives are divided into Groups,
each containing the number of drives indicated by this variable. All the
drives in a group are issued SPINUP Command without any delay. Next group
is given SPINUP Commands after a delay indicated by the spinupDelay variable."
	::= {eControllerInformation 11}

a2Adpioreadspersec OBJECT-TYPE
	SYNTAX		DmiInteger
	ACCESS		read-only
	STATUS		mandatory
	DESCRIPTION	"Number of IO Reads/sec statistics for this adapter."
	::= {eControllerInformation 12}

a2Adpiowritespersec OBJECT-TYPE
	SYNTAX		DmiInteger
	ACCESS		read-only
	STATUS		mandatory
	DESCRIPTION	"Number of IO writes/sec statistics for this adapter."
	::= {eControllerInformation 13}

a2Adpreadkbspersec OBJECT-TYPE
	SYNTAX		DmiInteger
	ACCESS		read-only
	STATUS		mandatory
	DESCRIPTION	"Amount of Data Transferred in KBs/sec due to READ Transfers."
	::= {eControllerInformation 14}

a2Adpwritekbspersec OBJECT-TYPE
	SYNTAX		DmiInteger
	ACCESS		read-only
	STATUS		mandatory
	DESCRIPTION	"Amount of Data Transferred in KBs/sec due to Write Transfers."
	::= {eControllerInformation 15}

a2Adpreadfailurespersec OBJECT-TYPE
	SYNTAX		DmiInteger
	ACCESS		read-only
	STATUS		mandatory
	DESCRIPTION	"Number of Read-Failures/sec statistics for this adapter."
	::= {eControllerInformation 16}

a2Adpwritefailurespersec OBJECT-TYPE
	SYNTAX		DmiInteger
	ACCESS		read-only
	STATUS		mandatory
	DESCRIPTION	"Number of write-Failures/sec statistics for this adapter."
	::= {eControllerInformation 17}

a2Scanchannels OBJECT-TYPE
	SYNTAX		INTEGER {
		vScanover                               	(1),
		vStartscan                              	(2),
		vScaninprog                             	(3)
	}
	ACCESS		read-write
	STATUS		mandatory
	DESCRIPTION	"Use this Variable to Discover the Non-Disk Devices attached
to the Adapter. Set this Variable to startscan (an integer value of 2) to
start the Channel Scanning."
	::= {eControllerInformation 18}

a2Logicalview OBJECT-TYPE
	SYNTAX		DmiOctetstring
	ACCESS		read-only
	STATUS		mandatory
	DESCRIPTION	"logical drive status for this adpater"
	::= {eControllerInformation 19}

a2Physicalview OBJECT-TYPE
	SYNTAX		DmiOctetstring
	ACCESS		read-only
	STATUS		mandatory
	DESCRIPTION	"logical drive status for this adpater"
	::= {eControllerInformation 20}

SLogicalDriveInformation ::= SEQUENCE {
	a3Ldadapternumber                       	DmiInteger,
	a3Logicaldrivenumber                    	DmiInteger,
	a3Raidlevel                             	DmiInteger,
	a3Status                                	DmiInteger,
	a3Sizeinmb                              	DmiInteger,
	a3Stripesize                            	DmiInteger,
	a3Readpolicy                            	DmiInteger,
	a3Writepolicy                           	DmiInteger,
	a3Cachepolicy                           	DmiInteger,
	a3Numberofspans                         	DmiInteger,
	a3Numberofstripes                       	DmiInteger,
	a3Ldioreadspersec                       	DmiInteger,
	a3Ldiowritespersec                      	DmiInteger,
	a3Ldreadskbspersec                      	DmiInteger,
	a3Ldwritekbspersec                      	DmiInteger,
	a3Ldioreadfailurespersec                	DmiInteger,
	a3Ldwritefailurespersec                 	DmiInteger,
	a3Progress                              	DmiInteger,
	a3Allattributes                         	DmiOctetstring
}

tLogicalDriveInformation OBJECT-TYPE
	SYNTAX		SEQUENCE OF SLogicalDriveInformation
	ACCESS		not-accessible
	STATUS		mandatory
	DESCRIPTION	"This group contains Logical Drive common information"
	::= {dmtfGroups 3}

eLogicalDriveInformation OBJECT-TYPE
	SYNTAX		SLogicalDriveInformation
	ACCESS		not-accessible
	STATUS		mandatory
	DESCRIPTION	""
--	INDEX		{DmiComponentIndex, a3Ldadapternumber, a3Logicaldrivenumber}
	::= {tLogicalDriveInformation 1}

a3Ldadapternumber OBJECT-TYPE
	SYNTAX		DmiInteger
	ACCESS		read-only
	STATUS		mandatory
	DESCRIPTION	"The adapter number for this instance of adpter/logical drive."
	::= {eLogicalDriveInformation 1}

a3Logicaldrivenumber OBJECT-TYPE
	SYNTAX		DmiInteger
	ACCESS		read-only
	STATUS		mandatory
	DESCRIPTION	"The logical drive number."
	::= {eLogicalDriveInformation 2}

a3Raidlevel OBJECT-TYPE
	SYNTAX		INTEGER {
		vRaid0                                  	(0),
		vRaid1                                  	(1),
		vRaid3                                  	(3),
		vRaid5                                  	(5)
	}
	ACCESS		read-only
	STATUS		mandatory
	DESCRIPTION	"The Raid level of this logical drive."
	::= {eLogicalDriveInformation 3}

a3Status OBJECT-TYPE
	SYNTAX		INTEGER {
		vOffline                                	(0),
		vDegraded                               	(1),
		vOptimal                                	(2),
		vInitialize                             	(3),
		vCheckconsistency                       	(4)
	}
	ACCESS		read-write
	STATUS		mandatory
	DESCRIPTION	"The current status of this Logical drive."
	::= {eLogicalDriveInformation 4}

a3Sizeinmb OBJECT-TYPE
	SYNTAX		DmiInteger
	ACCESS		read-only
	STATUS		mandatory
	DESCRIPTION	"The Configured size of this logical drive(in MB)."
	::= {eLogicalDriveInformation 5}

a3Stripesize OBJECT-TYPE
	SYNTAX		INTEGER {
		vOnekb                                  	(2),
		vTwokb                                  	(4),
		vFourkb                                 	(8),
		vEightkb                                	(16),
		vSixteenkb                              	(32),
		vThirtytwokb                            	(64),
		vSixtyfourkb                            	(128),
		vOnetwentyeightkb                       	(256)
	}
	ACCESS		read-only
	STATUS		mandatory
	DESCRIPTION	"The Configured stripe size of this logical drive(in MB)."
	::= {eLogicalDriveInformation 6}

a3Readpolicy OBJECT-TYPE
	SYNTAX		INTEGER {
		vNormal                                 	(0),
		vReadahead                              	(1),
		vAdaptive                               	(2)
	}
	ACCESS		read-write
	STATUS		mandatory
	DESCRIPTION	"The readpolicy logical drive(in MB)."
	::= {eLogicalDriveInformation 7}

a3Writepolicy OBJECT-TYPE
	SYNTAX		INTEGER {
		vWritethru                              	(0),
		vWriteback                              	(1)
	}
	ACCESS		read-write
	STATUS		mandatory
	DESCRIPTION	"The write policy logical drive(in MB)."
	::= {eLogicalDriveInformation 8}

a3Cachepolicy OBJECT-TYPE
	SYNTAX		INTEGER {
		vCachedio                               	(0),
		vDirectio                               	(1)
	}
	ACCESS		read-write
	STATUS		mandatory
	DESCRIPTION	"The cache policy logical drive(in MB)."
	::= {eLogicalDriveInformation 9}

a3Numberofspans OBJECT-TYPE
	SYNTAX		DmiInteger
	ACCESS		read-only
	STATUS		mandatory
	DESCRIPTION	""
	::= {eLogicalDriveInformation 10}

a3Numberofstripes OBJECT-TYPE
	SYNTAX		DmiInteger
	ACCESS		read-only
	STATUS		mandatory
	DESCRIPTION	""
	::= {eLogicalDriveInformation 11}

a3Ldioreadspersec OBJECT-TYPE
	SYNTAX		DmiInteger
	ACCESS		read-only
	STATUS		mandatory
	DESCRIPTION	""
	::= {eLogicalDriveInformation 12}

a3Ldiowritespersec OBJECT-TYPE
	SYNTAX		DmiInteger
	ACCESS		read-only
	STATUS		mandatory
	DESCRIPTION	""
	::= {eLogicalDriveInformation 13}

a3Ldreadskbspersec OBJECT-TYPE
	SYNTAX		DmiInteger
	ACCESS		read-only
	STATUS		mandatory
	DESCRIPTION	""
	::= {eLogicalDriveInformation 14}

a3Ldwritekbspersec OBJECT-TYPE
	SYNTAX		DmiInteger
	ACCESS		read-only
	STATUS		mandatory
	DESCRIPTION	""
	::= {eLogicalDriveInformation 15}

a3Ldioreadfailurespersec OBJECT-TYPE
	SYNTAX		DmiInteger
	ACCESS		read-only
	STATUS		mandatory
	DESCRIPTION	""
	::= {eLogicalDriveInformation 16}

a3Ldwritefailurespersec OBJECT-TYPE
	SYNTAX		DmiInteger
	ACCESS		read-only
	STATUS		mandatory
	DESCRIPTION	""
	::= {eLogicalDriveInformation 17}

a3Progress OBJECT-TYPE
	SYNTAX		DmiInteger
	ACCESS		read-write
	STATUS		mandatory
	DESCRIPTION	"Shows the Initialization or Check Consistency Progress inPercent
ge"
	::= {eLogicalDriveInformation 18}

a3Allattributes OBJECT-TYPE
	SYNTAX		DmiOctetstring
	ACCESS		read-only
	STATUS		mandatory
	DESCRIPTION	"Shows All Attributes Of this logical Drive As Octet String"
	::= {eLogicalDriveInformation 19}

SPhysicalDeviceInformation ::= SEQUENCE {
	a4Physadapternumber                     	DmiInteger,
	a4Physchannel                           	DmiInteger,
	a4Targetid                              	DmiInteger,
	a4State                                 	DmiInteger,
	a4Arrayposition                         	DmiDisplaystring,
	a4Sizemb                                	DmiInteger,
	a4Devicetype                            	DmiInteger,
	a4Inquirystring                         	DmiDisplaystring,
	a4Scsilevel                             	DmiInteger,
	a4Syncnegotiation                       	DmiInteger,
	a4Qtags                                 	DmiInteger,
	a4Rebuildprogress                       	DmiInteger,
	a4Mediumerrors                          	DmiInteger,
	a4Othererrors                           	DmiInteger,
	a4Allattributes                         	DmiOctetstring
}

tPhysicalDeviceInformation OBJECT-TYPE
	SYNTAX		SEQUENCE OF SPhysicalDeviceInformation
	ACCESS		not-accessible
	STATUS		mandatory
	DESCRIPTION	"SCSI physical device information."
	::= {dmtfGroups 4}

ePhysicalDeviceInformation OBJECT-TYPE
	SYNTAX		SPhysicalDeviceInformation
	ACCESS		not-accessible
	STATUS		mandatory
	DESCRIPTION	""
--	INDEX		{DmiComponentIndex, a4Physadapternumber, a4Physchannel, a4Targetid}
	::= {tPhysicalDeviceInformation 1}

a4Physadapternumber OBJECT-TYPE
	SYNTAX		DmiInteger
	ACCESS		read-only
	STATUS		mandatory
	DESCRIPTION	"The controller number this drive is connected to. (0-based)"
	::= {ePhysicalDeviceInformation 1}

a4Physchannel OBJECT-TYPE
	SYNTAX		DmiInteger
	ACCESS		read-only
	STATUS		mandatory
	DESCRIPTION	"channel number on adapter"
	::= {ePhysicalDeviceInformation 2}

a4Targetid OBJECT-TYPE
	SYNTAX		DmiInteger
	ACCESS		read-only
	STATUS		mandatory
	DESCRIPTION	"SCSI Target ID of this device"
	::= {ePhysicalDeviceInformation 3}

a4State OBJECT-TYPE
	SYNTAX		INTEGER {
		vReady                                  	(1),
		vOnline                                 	(3),
		vFailed                                 	(4),
		vRebuild                                	(5),
		vHotspare                               	(6),
		vNotResponding                          	(7)
	}
	ACCESS		read-write
	STATUS		mandatory
	DESCRIPTION	"Current State of this physical drive"
	::= {ePhysicalDeviceInformation 4}

a4Arrayposition OBJECT-TYPE
	SYNTAX		DmiDisplaystring
	ACCESS		read-only
	STATUS		mandatory
	DESCRIPTION	"array position of this disk"
	::= {ePhysicalDeviceInformation 5}

a4Sizemb OBJECT-TYPE
	SYNTAX		DmiInteger
	ACCESS		read-only
	STATUS		mandatory
	DESCRIPTION	"Actual size of this physical drive"
	::= {ePhysicalDeviceInformation 6}

a4Devicetype OBJECT-TYPE
	SYNTAX		INTEGER {
		vDisk                                   	(0),
		vTape                                   	(1),
		vPrinter                                	(2),
		vProcessor                              	(3),
		vWorm                                   	(4),
		vScanner                                	(6),
		vOptical                                	(7),
		vChanger                                	(8),
		vCommunication                          	(9),
		vAsynchronouslow                        	(10),
		vAsynchronoushigh                       	(11),
		vReservedlow                            	(12),
		vNotResponding                          	(13)
	}
	ACCESS		read-only
	STATUS		mandatory
	DESCRIPTION	"The type of physical device (cdrom, tape, disk, etc)."
	::= {ePhysicalDeviceInformation 7}

a4Inquirystring OBJECT-TYPE
	SYNTAX		DmiDisplaystring
	ACCESS		read-only
	STATUS		mandatory
	DESCRIPTION	"SCSI Inquiry String of this device"
	::= {ePhysicalDeviceInformation 8}

a4Scsilevel OBJECT-TYPE
	SYNTAX		INTEGER {
		vScsi1                                  	(1),
		vScsi2                                  	(2),
		vUnknown                                	(3)
	}
	ACCESS		read-only
	STATUS		mandatory
	DESCRIPTION	"ANSI SCSI Level Conformance of this device"
	::= {ePhysicalDeviceInformation 9}

a4Syncnegotiation OBJECT-TYPE
	SYNTAX		INTEGER {
		vEnable                                 	(1),
		vDisable                                	(2),
		vUnknown                                	(3)
	}
	ACCESS		read-only
	STATUS		mandatory
	DESCRIPTION	"This indicates whether firmware has been enabled to perform
Synchrous negotiation"
	::= {ePhysicalDeviceInformation 10}

a4Qtags OBJECT-TYPE
	SYNTAX		INTEGER {
		vOne                                    	(1),
		vTwo                                    	(2),
		vThree                                  	(3),
		vFour                                   	(4),
		vEnhancedqtagscheduling                 	(5),
		vUnknown                                	(6)
	}
	ACCESS		read-only
	STATUS		mandatory
	DESCRIPTION	"This indicates maximum number of concurrent commands that
can be issued to thisdevice"
	::= {ePhysicalDeviceInformation 11}

a4Rebuildprogress OBJECT-TYPE
	SYNTAX		DmiInteger
	ACCESS		read-write
	STATUS		mandatory
	DESCRIPTION	"This Field Shows the Rebuild Progress In Percent. If There
Is No Rebuild Started Then The Rebuild Progress Shown Will Be Zero Percent."
	::= {ePhysicalDeviceInformation 12}

a4Mediumerrors OBJECT-TYPE
	SYNTAX		DmiInteger
	ACCESS		read-only
	STATUS		mandatory
	DESCRIPTION	"Medium error occured"
	::= {ePhysicalDeviceInformation 13}

a4Othererrors OBJECT-TYPE
	SYNTAX		DmiInteger
	ACCESS		read-only
	STATUS		mandatory
	DESCRIPTION	"Other errors occured"
	::= {ePhysicalDeviceInformation 14}

a4Allattributes OBJECT-TYPE
	SYNTAX		DmiOctetstring
	ACCESS		read-only
	STATUS		mandatory
	DESCRIPTION	"logical drive status for this adpater"
	::= {ePhysicalDeviceInformation 15}

SChannels ::= SEQUENCE {
	a5Chanadapternumber                     	DmiInteger,
	a5Channel                               	DmiInteger,
	a5Terminations                          	DmiInteger,
	a5Channelstatus                         	DmiInteger
}

tChannels OBJECT-TYPE
	SYNTAX		SEQUENCE OF SChannels
	ACCESS		not-accessible
	STATUS		mandatory
	DESCRIPTION	"A list of channel Entries containing properties about scsi
channels"
	::= {dmtfGroups 5}

eChannels OBJECT-TYPE
	SYNTAX		SChannels
	ACCESS		not-accessible
	STATUS		mandatory
	DESCRIPTION	""
--	INDEX		{DmiComponentIndex, a5Chanadapternumber, a5Channel}
	::= {tChannels 1}

a5Chanadapternumber OBJECT-TYPE
	SYNTAX		DmiInteger
	ACCESS		read-only
	STATUS		mandatory
	DESCRIPTION	"The Adapter Number"
	::= {eChannels 1}

a5Channel OBJECT-TYPE
	SYNTAX		DmiInteger
	ACCESS		read-only
	STATUS		mandatory
	DESCRIPTION	"Channel Number"
	::= {eChannels 2}

a5Terminations OBJECT-TYPE
	SYNTAX		INTEGER {
		vDisabled                               	(0),
		vHigher8bits                            	(1),
		vWideterminations                       	(2)
	}
	ACCESS		read-only
	STATUS		mandatory
	DESCRIPTION	"Current Terminations effective on this channel"
	::= {eChannels 3}

a5Channelstatus OBJECT-TYPE
	SYNTAX		INTEGER {
		vQuit                                   	(0),
		vActive                                 	(1)
	}
	ACCESS		read-only
	STATUS		mandatory
	DESCRIPTION	"Current Activity status"
	::= {eChannels 4}

SAlertManagementInformation ::= SEQUENCE {
	a6Dmiindication                         	DmiInteger,
	a6Ams2alerts                            	DmiInteger,
	a6Eventlog                              	DmiInteger
}

tAlertManagementInformation OBJECT-TYPE
	SYNTAX		SEQUENCE OF SAlertManagementInformation
	ACCESS		not-accessible
	STATUS		mandatory
	DESCRIPTION	"Alert Management Information"
	::= {dmtfGroups 6}

eAlertManagementInformation OBJECT-TYPE
	SYNTAX		SAlertManagementInformation
	ACCESS		not-accessible
	STATUS		mandatory
	DESCRIPTION	""
--	INDEX		{DmiComponentIndex}
	::= {tAlertManagementInformation 1}

a6Dmiindication OBJECT-TYPE
	SYNTAX		INTEGER {
		vDisabled                               	(0),
		vEnabled                                	(1)
	}
	ACCESS		read-write
	STATUS		mandatory
	DESCRIPTION	"Indicates whether error reporting using dmiindication has
been enabled "
	::= {eAlertManagementInformation 1}

a6Ams2alerts OBJECT-TYPE
	SYNTAX		INTEGER {
		vDisabled                               	(0),
		vEnabled                                	(1)
	}
	ACCESS		read-write
	STATUS		mandatory
	DESCRIPTION	"Indicates whether error reporting using AMS2 alerts has been
enabled "
	::= {eAlertManagementInformation 2}

a6Eventlog OBJECT-TYPE
	SYNTAX		INTEGER {
		vDisabled                               	(0),
		vEnabled                                	(1)
	}
	ACCESS		read-write
	STATUS		mandatory
	DESCRIPTION	"Indicates whether error reporting using NT event log has
been enabled "
	::= {eAlertManagementInformation 3}

SGlobalinfo ::= SEQUENCE {
	a7Globalcltrinfo                        	DmiOctetstring
}

tGlobalinfo OBJECT-TYPE
	SYNTAX		SEQUENCE OF SGlobalinfo
	ACCESS		not-accessible
	STATUS		mandatory
	DESCRIPTION	"Global Controller and logical drive information"
	::= {dmtfGroups 7}

eGlobalinfo OBJECT-TYPE
	SYNTAX		SGlobalinfo
	ACCESS		not-accessible
	STATUS		mandatory
	DESCRIPTION	""
--	INDEX		{DmiComponentIndex}
	::= {tGlobalinfo 1}

a7Globalcltrinfo OBJECT-TYPE
	SYNTAX		DmiOctetstring
	ACCESS		read-only
	STATUS		mandatory
	DESCRIPTION	"global controller information"
	::= {eGlobalinfo 1}

SMiftomib ::= SEQUENCE {
	a99AmiMegaraidMib                       	DmiDisplaystring,
	a99MibOid                               	DmiDisplaystring,
	a99DisableTraps                         	DmiInteger
}

tMiftomib OBJECT-TYPE
	SYNTAX		SEQUENCE OF SMiftomib
	ACCESS		not-accessible
	STATUS		mandatory
	DESCRIPTION	"This group maps the DMI attributes to SNMP."
	::= {dmtfGroups 99}

eMiftomib OBJECT-TYPE
	SYNTAX		SMiftomib
	ACCESS		not-accessible
	STATUS		mandatory
	DESCRIPTION	""
--	INDEX		{DmiComponentIndex}
	::= {tMiftomib 1}

a99AmiMegaraidMib OBJECT-TYPE
	SYNTAX		DmiDisplaystring
	ACCESS		read-only
	STATUS		mandatory
	DESCRIPTION	"The MIB name that defines this MIF"
	::= {eMiftomib 1}

a99MibOid OBJECT-TYPE
	SYNTAX		DmiDisplaystring
	ACCESS		read-only
	STATUS		mandatory
	DESCRIPTION	"The MIB OID that corresponds to this MIF"
	::= {eMiftomib 2}

a99DisableTraps OBJECT-TYPE
	SYNTAX		DmiInteger
	ACCESS		read-only
	STATUS		mandatory
	DESCRIPTION	"Setting this value to 1 disables trap generation."
	::= {eMiftomib 3}

SCompositeDriveAlerts ::= SEQUENCE {
	a103EventType                           	DmiInteger,
	a103EventSeverity                       	DmiInteger,
	a103IsEventStateBased                   	DmiInteger,
	a103EventStateKey                       	DmiInteger,
	a103AssociatedGroup                     	DmiDisplaystring,
	a103EventSystem                         	DmiInteger,
	a103EventSubsystem                      	DmiInteger,
	a103EventSolution                       	DmiInteger,
	a103InstanceDataPresent                 	DmiInteger,
	a103VendorSpecificMessage               	DmiOctetstring,
	a103VendorSpecificData                  	DmiOctetstring,
	a103VendorTrapNumber                    	DmiInteger
}

tCompositeDriveAlerts OBJECT-TYPE
	SYNTAX		SEQUENCE OF SCompositeDriveAlerts
	ACCESS		not-accessible
	STATUS		mandatory
	DESCRIPTION	""
	::= {dmtfGroups 103}

eCompositeDriveAlerts OBJECT-TYPE
	SYNTAX		SCompositeDriveAlerts
	ACCESS		not-accessible
	STATUS		mandatory
	DESCRIPTION	""
--	INDEX		{DmiComponentIndex, a103AssociatedGroup}
	::= {tCompositeDriveAlerts 1}

a103EventType OBJECT-TYPE
	SYNTAX		INTEGER {
		vCompositeDriveStatusChange             	(1),
		vCompositeDriveRecoveryStarted          	(2),
		vCompositeDriveRecoveryCompleted        	(3)
	}
	ACCESS		read-only
	STATUS		mandatory
	DESCRIPTION	"The type of event that has occurred."
	::= {eCompositeDriveAlerts 1}

a103EventSeverity OBJECT-TYPE
	SYNTAX		INTEGER {
		vMonitor                                	(1),
		vInformation                            	(2),
		vOk                                     	(4),
		vNon-critical                           	(8),
		vCritical                               	(10),
		vNon-recoverable                        	(12)
	}
	ACCESS		read-only
	STATUS		mandatory
	DESCRIPTION	"The severity of this event."
	::= {eCompositeDriveAlerts 2}

a103IsEventStateBased OBJECT-TYPE
	SYNTAX		INTEGER {
		vFalse                                  	(0),
		vTrue                                   	(1)
	}
	ACCESS		read-only
	STATUS		mandatory
	DESCRIPTION	""
	::= {eCompositeDriveAlerts 3}

a103EventStateKey OBJECT-TYPE
	SYNTAX		DmiInteger
	ACCESS		read-only
	STATUS		mandatory
	DESCRIPTION	""
	::= {eCompositeDriveAlerts 4}

a103AssociatedGroup OBJECT-TYPE
	SYNTAX		DmiDisplaystring
	ACCESS		read-only
	STATUS		mandatory
	DESCRIPTION	""
	::= {eCompositeDriveAlerts 5}

a103EventSystem OBJECT-TYPE
	SYNTAX		DmiInteger
	ACCESS		read-only
	STATUS		mandatory
	DESCRIPTION	""
	::= {eCompositeDriveAlerts 6}

a103EventSubsystem OBJECT-TYPE
	SYNTAX		DmiInteger
	ACCESS		read-only
	STATUS		mandatory
	DESCRIPTION	""
	::= {eCompositeDriveAlerts 7}

a103EventSolution OBJECT-TYPE
	SYNTAX		INTEGER {
		vOther                                  	(1),
		vUnknown                                	(2)
	}
	ACCESS		read-only
	STATUS		mandatory
	DESCRIPTION	""
	::= {eCompositeDriveAlerts 8}

a103InstanceDataPresent OBJECT-TYPE
	SYNTAX		INTEGER {
		vFalse                                  	(0),
		vTrue                                   	(1)
	}
	ACCESS		read-only
	STATUS		mandatory
	DESCRIPTION	""
	::= {eCompositeDriveAlerts 9}

a103VendorSpecificMessage OBJECT-TYPE
	SYNTAX		DmiOctetstring
	ACCESS		read-only
	STATUS		mandatory
	DESCRIPTION	""
	::= {eCompositeDriveAlerts 10}

a103VendorSpecificData OBJECT-TYPE
	SYNTAX		DmiOctetstring
	ACCESS		read-only
	STATUS		mandatory
	DESCRIPTION	""
	::= {eCompositeDriveAlerts 11}

a103VendorTrapNumber OBJECT-TYPE
	SYNTAX		DmiInteger
	ACCESS		read-only
	STATUS		mandatory
	DESCRIPTION	""
	::= {eCompositeDriveAlerts 12}

SPhysicalDriveAlerts ::= SEQUENCE {
	a104EventType                           	DmiInteger,
	a104EventSeverity                       	DmiInteger,
	a104IsEventStateBased                   	DmiInteger,
	a104EventStateKey                       	DmiInteger,
	a104AssociatedGroup                     	DmiDisplaystring,
	a104EventSystem                         	DmiInteger,
	a104EventSubsystem                      	DmiInteger,
	a104EventSolution                       	DmiInteger,
	a104InstanceDataPresent                 	DmiInteger,
	a104VendorSpecificMessage               	DmiOctetstring,
	a104VendorSpecificData                  	DmiOctetstring,
	a104VendorTrapNumber                    	DmiInteger
}

tPhysicalDriveAlerts OBJECT-TYPE
	SYNTAX		SEQUENCE OF SPhysicalDriveAlerts
	ACCESS		not-accessible
	STATUS		mandatory
	DESCRIPTION	""
	::= {dmtfGroups 104}

ePhysicalDriveAlerts OBJECT-TYPE
	SYNTAX		SPhysicalDriveAlerts
	ACCESS		not-accessible
	STATUS		mandatory
	DESCRIPTION	""
--	INDEX		{DmiComponentIndex, a104AssociatedGroup}
	::= {tPhysicalDriveAlerts 1}

a104EventType OBJECT-TYPE
	SYNTAX		INTEGER {
		vPhysicalDriveStatusChange              	(1),
		vPhysicalDriveRemoved                   	(2),
		vPhysicalDriveAppeared                  	(3),
		vHotSpareCreated                        	(4)
	}
	ACCESS		read-only
	STATUS		mandatory
	DESCRIPTION	"The type of event that has occurred."
	::= {ePhysicalDriveAlerts 1}

a104EventSeverity OBJECT-TYPE
	SYNTAX		INTEGER {
		vMonitor                                	(1),
		vInformation                            	(2),
		vOk                                     	(4),
		vNon-critical                           	(8),
		vCritical                               	(10),
		vNon-recoverable                        	(12)
	}
	ACCESS		read-only
	STATUS		mandatory
	DESCRIPTION	"The severity of this event."
	::= {ePhysicalDriveAlerts 2}

a104IsEventStateBased OBJECT-TYPE
	SYNTAX		INTEGER {
		vFalse                                  	(0),
		vTrue                                   	(1)
	}
	ACCESS		read-only
	STATUS		mandatory
	DESCRIPTION	""
	::= {ePhysicalDriveAlerts 3}

a104EventStateKey OBJECT-TYPE
	SYNTAX		DmiInteger
	ACCESS		read-only
	STATUS		mandatory
	DESCRIPTION	""
	::= {ePhysicalDriveAlerts 4}

a104AssociatedGroup OBJECT-TYPE
	SYNTAX		DmiDisplaystring
	ACCESS		read-only
	STATUS		mandatory
	DESCRIPTION	""
	::= {ePhysicalDriveAlerts 5}

a104EventSystem OBJECT-TYPE
	SYNTAX		DmiInteger
	ACCESS		read-only
	STATUS		mandatory
	DESCRIPTION	""
	::= {ePhysicalDriveAlerts 6}

a104EventSubsystem OBJECT-TYPE
	SYNTAX		DmiInteger
	ACCESS		read-only
	STATUS		mandatory
	DESCRIPTION	""
	::= {ePhysicalDriveAlerts 7}

a104EventSolution OBJECT-TYPE
	SYNTAX		INTEGER {
		vOther                                  	(1),
		vUnknown                                	(2)
	}
	ACCESS		read-only
	STATUS		mandatory
	DESCRIPTION	""
	::= {ePhysicalDriveAlerts 8}

a104InstanceDataPresent OBJECT-TYPE
	SYNTAX		INTEGER {
		vFalse                                  	(0),
		vTrue                                   	(1)
	}
	ACCESS		read-only
	STATUS		mandatory
	DESCRIPTION	""
	::= {ePhysicalDriveAlerts 9}

a104VendorSpecificMessage OBJECT-TYPE
	SYNTAX		DmiOctetstring
	ACCESS		read-only
	STATUS		mandatory
	DESCRIPTION	""
	::= {ePhysicalDriveAlerts 10}

a104VendorSpecificData OBJECT-TYPE
	SYNTAX		DmiOctetstring
	ACCESS		read-only
	STATUS		mandatory
	DESCRIPTION	""
	::= {ePhysicalDriveAlerts 11}

a104VendorTrapNumber OBJECT-TYPE
	SYNTAX		DmiInteger
	ACCESS		read-only
	STATUS		mandatory
	DESCRIPTION	""
	::= {ePhysicalDriveAlerts 12}

END
