-- file automatically created


TELDAT-TRAP-RIP-MIB DEFINITIONS ::= BEGIN


IMPORTS
	MODULE-IDENTITY,OBJECT-TYPE,OBJECT-IDENTITY,NOTIFICATION-TYPE,Integer32,IpAddress
		FROM SNMPv2-SMI
	DisplayString
		FROM SNMPv2-TC
	telEventTraps
		FROM TELDAT-MIB;


ripTrapsMIB MODULE-IDENTITY
    LAST-UPDATED "201401200930Z"
    ORGANIZATION "Teldat, S.A."
    CONTACT-INFO 
        "Teldat, S.A.
        Customer Service

        Postal: Parque Tecnologico de Madrid
                Tres Cantos 28760
                Madrid, SPAIN

        Tel.: +34 918 076 565

        http://www.teldat.com"
    DESCRIPTION
        "This Module Information Base file is defined for managing received
        SNMP notifications generated by the RIP event subsystem."
    REVISION "201401200930Z"
    DESCRIPTION "Initial implementation"
        ::= { telEventTraps 219 }


ripEventsGroup	OBJECT IDENTIFIER	::= { ripTrapsMIB 1 }

ripNotifications	OBJECT IDENTIFIER	::= { ripTrapsMIB 2 }
ripNotificationsPrefix	OBJECT IDENTIFIER	::= { ripNotifications 0 }

ripEventObjects1 OBJECT-IDENTITY
    STATUS current
    DESCRIPTION
        "Event RIP.1
        The version field in the RIP header did not match the current
        version."
    ::= { ripEventsGroup 1 }

rip1-version-number OBJECT-TYPE
    SYNTAX Integer32
    MAX-ACCESS accessible-for-notify
    STATUS current
    DESCRIPTION
        "Parameter 'version-number' in event RIP.1"
    ::= { ripEventObjects1 1 }

rip1-source-IP-address OBJECT-TYPE
    SYNTAX IpAddress
    MAX-ACCESS accessible-for-notify
    STATUS current
    DESCRIPTION
        "Parameter 'source-IP-address' in event RIP.1"
    ::= { ripEventObjects1 2 }

ripEventObjects2 OBJECT-IDENTITY
    STATUS current
    DESCRIPTION
        "Event RIP.2
        A RIP routing table request was received from another host. A routing
        table update will be sent to it."
    ::= { ripEventsGroup 2 }

rip2-source-IP-address OBJECT-TYPE
    SYNTAX IpAddress
    MAX-ACCESS accessible-for-notify
    STATUS current
    DESCRIPTION
        "Parameter 'source-IP-address' in event RIP.2"
    ::= { ripEventObjects2 1 }

ripEventObjects3 OBJECT-IDENTITY
    STATUS current
    DESCRIPTION
        "Event RIP.3
        A request from a host to turn RIP tracing on to a given log
        file was received. The router ignores this request."
    ::= { ripEventsGroup 3 }

rip3-source-IP-address OBJECT-TYPE
    SYNTAX IpAddress
    MAX-ACCESS accessible-for-notify
    STATUS current
    DESCRIPTION
        "Parameter 'source-IP-address' in event RIP.3"
    ::= { ripEventObjects3 1 }

ripEventObjects4 OBJECT-IDENTITY
    STATUS current
    DESCRIPTION
        "Event RIP.4
        A request from a host to turn RIP tracing off was received.
        The router ignores this request."
    ::= { ripEventsGroup 4 }

rip4-source-IP-address OBJECT-TYPE
    SYNTAX IpAddress
    MAX-ACCESS accessible-for-notify
    STATUS current
    DESCRIPTION
        "Parameter 'source-IP-address' in event RIP.4"
    ::= { ripEventObjects4 1 }

ripEventObjects5 OBJECT-IDENTITY
    STATUS current
    DESCRIPTION
        "Event RIP.5
        A RIP routing table update was received. Note that it may take
        more than one response packet to transmit the entire routing
        table, especially if the routing table is large."
    ::= { ripEventsGroup 5 }

rip5-source-IP-address OBJECT-TYPE
    SYNTAX IpAddress
    MAX-ACCESS accessible-for-notify
    STATUS current
    DESCRIPTION
        "Parameter 'source-IP-address' in event RIP.5"
    ::= { ripEventObjects5 1 }

ripEventObjects6 OBJECT-IDENTITY
    STATUS current
    DESCRIPTION
        "Event RIP.6
        A RIP message was received with an unrecognized command code."
    ::= { ripEventsGroup 6 }

rip6-command-code OBJECT-TYPE
    SYNTAX Integer32
    MAX-ACCESS accessible-for-notify
    STATUS current
    DESCRIPTION
        "Parameter 'command-code' in event RIP.6"
    ::= { ripEventObjects6 1 }

rip6-source-IP-address OBJECT-TYPE
    SYNTAX IpAddress
    MAX-ACCESS accessible-for-notify
    STATUS current
    DESCRIPTION
        "Parameter 'source-IP-address' in event RIP.6"
    ::= { ripEventObjects6 2 }

ripEventObjects7 OBJECT-IDENTITY
    STATUS current
    DESCRIPTION
        "Event RIP.7
        A RIP routing update response was received from a machine which
        was not directly attached to the network the response came in on.
        The packet is discarded."
    ::= { ripEventsGroup 7 }

rip7-source-IP-address OBJECT-TYPE
    SYNTAX IpAddress
    MAX-ACCESS accessible-for-notify
    STATUS current
    DESCRIPTION
        "Parameter 'source-IP-address' in event RIP.7"
    ::= { ripEventObjects7 1 }

ripEventObjects8 OBJECT-IDENTITY
    STATUS current
    DESCRIPTION
        "Event RIP.8
        An apparent subnet route (i.e. the 'rest' field of the Internet
        address contained non-zero data) was received over an interface
        that is not marked as subnetted in the router."
    ::= { ripEventsGroup 8 }

rip8-destination-IP-network OBJECT-TYPE
    SYNTAX IpAddress
    MAX-ACCESS accessible-for-notify
    STATUS current
    DESCRIPTION
        "Parameter 'destination-IP-network' in event RIP.8"
    ::= { ripEventObjects8 1 }

rip8-next-hop-IP-address OBJECT-TYPE
    SYNTAX IpAddress
    MAX-ACCESS accessible-for-notify
    STATUS current
    DESCRIPTION
        "Parameter 'next-hop-IP-address' in event RIP.8"
    ::= { ripEventObjects8 2 }

ripEventObjects9 OBJECT-IDENTITY
    STATUS current
    DESCRIPTION
        "Event RIP.9
        A dynamic route was received but is being ignored because the
        configuration of RIP on the router does not allow dynamic routes
        except for those in a table, and this route was not in that table."
    ::= { ripEventsGroup 9 }

rip9-destination-IP-network OBJECT-TYPE
    SYNTAX IpAddress
    MAX-ACCESS accessible-for-notify
    STATUS current
    DESCRIPTION
        "Parameter 'destination-IP-network' in event RIP.9"
    ::= { ripEventObjects9 1 }

rip9-next-hop-IP-address OBJECT-TYPE
    SYNTAX IpAddress
    MAX-ACCESS accessible-for-notify
    STATUS current
    DESCRIPTION
        "Parameter 'next-hop-IP-address' in event RIP.9"
    ::= { ripEventObjects9 2 }

ripEventObjects10 OBJECT-IDENTITY
    STATUS current
    DESCRIPTION
        "Event RIP.10
        An incoming RIP update from the router that was previously
        listed as the next hop to the destination network has announced
        that the destination is unreachable (i.e. at metric 'infinity').
        The RIP route to that destination is being deleted."
    ::= { ripEventsGroup 10 }

rip10-destination-IP-address OBJECT-TYPE
    SYNTAX IpAddress
    MAX-ACCESS accessible-for-notify
    STATUS current
    DESCRIPTION
        "Parameter 'destination-IP-address' in event RIP.10"
    ::= { ripEventObjects10 1 }

rip10-next-hop-IP-address OBJECT-TYPE
    SYNTAX IpAddress
    MAX-ACCESS accessible-for-notify
    STATUS current
    DESCRIPTION
        "Parameter 'next-hop-IP-address' in event RIP.10"
    ::= { ripEventObjects10 2 }

ripEventObjects11 OBJECT-IDENTITY
    STATUS current
    DESCRIPTION
        "Event RIP.11
        A new (better) route to the given destination has been learned
        via RIP and has been installed."
    ::= { ripEventsGroup 11 }

rip11-destination-IP-network OBJECT-TYPE
    SYNTAX IpAddress
    MAX-ACCESS accessible-for-notify
    STATUS current
    DESCRIPTION
        "Parameter 'destination-IP-network' in event RIP.11"
    ::= { ripEventObjects11 1 }

rip11-metric OBJECT-TYPE
    SYNTAX Integer32
    MAX-ACCESS accessible-for-notify
    STATUS current
    DESCRIPTION
        "Parameter 'metric' in event RIP.11"
    ::= { ripEventObjects11 2 }

rip11-next-hop-IP-address OBJECT-TYPE
    SYNTAX IpAddress
    MAX-ACCESS accessible-for-notify
    STATUS current
    DESCRIPTION
        "Parameter 'next-hop-IP-address' in event RIP.11"
    ::= { ripEventObjects11 3 }

ripEventObjects12 OBJECT-IDENTITY
    STATUS current
    DESCRIPTION
        "Event RIP.12
        The router is sending a RIP broadcast/multicast request from each of
        the addresses associated with an interface which has just come up."
    ::= { ripEventsGroup 12 }

rip12-source-IP-address OBJECT-TYPE
    SYNTAX IpAddress
    MAX-ACCESS accessible-for-notify
    STATUS current
    DESCRIPTION
        "Parameter 'source-IP-address' in event RIP.12"
    ::= { ripEventObjects12 1 }

rip12-destination-IP-address OBJECT-TYPE
    SYNTAX IpAddress
    MAX-ACCESS accessible-for-notify
    STATUS current
    DESCRIPTION
        "Parameter 'destination-IP-address' in event RIP.12"
    ::= { ripEventObjects12 2 }

ripEventObjects13 OBJECT-IDENTITY
    STATUS current
    DESCRIPTION
        "Event RIP.13
        The router is sending a RIP broadcast/multicast request from
        the addresses associated with a dlci has just come up."
    ::= { ripEventsGroup 13 }

rip13-source-IP-address OBJECT-TYPE
    SYNTAX IpAddress
    MAX-ACCESS accessible-for-notify
    STATUS current
    DESCRIPTION
        "Parameter 'source-IP-address' in event RIP.13"
    ::= { ripEventObjects13 1 }

rip13-destination-IP-address OBJECT-TYPE
    SYNTAX IpAddress
    MAX-ACCESS accessible-for-notify
    STATUS current
    DESCRIPTION
        "Parameter 'destination-IP-address' in event RIP.13"
    ::= { ripEventObjects13 2 }

ripEventObjects14 OBJECT-IDENTITY
    STATUS current
    DESCRIPTION
        "Event RIP.14
        The router is sending a RIP update (triggered by a request
        from another host) to the specified address."
    ::= { ripEventsGroup 14 }

rip14-source-IP-address OBJECT-TYPE
    SYNTAX IpAddress
    MAX-ACCESS accessible-for-notify
    STATUS current
    DESCRIPTION
        "Parameter 'source-IP-address' in event RIP.14"
    ::= { ripEventObjects14 1 }

rip14-destination-IP-address OBJECT-TYPE
    SYNTAX IpAddress
    MAX-ACCESS accessible-for-notify
    STATUS current
    DESCRIPTION
        "Parameter 'destination-IP-address' in event RIP.14"
    ::= { ripEventObjects14 2 }

rip14-packet-count OBJECT-TYPE
    SYNTAX Integer32
    MAX-ACCESS accessible-for-notify
    STATUS current
    DESCRIPTION
        "Parameter 'packet-count' in event RIP.14"
    ::= { ripEventObjects14 3 }

rip14-number-of-routes OBJECT-TYPE
    SYNTAX Integer32
    MAX-ACCESS accessible-for-notify
    STATUS current
    DESCRIPTION
        "Parameter 'number-of-routes' in event RIP.14"
    ::= { ripEventObjects14 4 }

ripEventObjects16 OBJECT-IDENTITY
    STATUS current
    DESCRIPTION
        "Event RIP.16
        A RIP packet (either a routing table update, or when an interface
        first comes up, a request) was sent."
    ::= { ripEventsGroup 16 }

rip16-source-IP-address OBJECT-TYPE
    SYNTAX IpAddress
    MAX-ACCESS accessible-for-notify
    STATUS current
    DESCRIPTION
        "Parameter 'source-IP-address' in event RIP.16"
    ::= { ripEventObjects16 1 }

rip16-destination-IP-address OBJECT-TYPE
    SYNTAX IpAddress
    MAX-ACCESS accessible-for-notify
    STATUS current
    DESCRIPTION
        "Parameter 'destination-IP-address' in event RIP.16"
    ::= { ripEventObjects16 2 }

ripEventObjects17 OBJECT-IDENTITY
    STATUS current
    DESCRIPTION
        "Event RIP.17
        An outgoing reply packet was dropped as the result of some
        problem in the router."
    ::= { ripEventsGroup 17 }

rip17-output-error-code OBJECT-TYPE
    SYNTAX Integer32
    MAX-ACCESS accessible-for-notify
    STATUS current
    DESCRIPTION
        "Parameter 'output-error-code' in event RIP.17"
    ::= { ripEventObjects17 1 }

rip17-interface OBJECT-TYPE
    SYNTAX DisplayString
    MAX-ACCESS accessible-for-notify
    STATUS current
    DESCRIPTION
        "Parameter 'interface' in event RIP.17"
    ::= { ripEventObjects17 2 }

ripEventObjects18 OBJECT-IDENTITY
    STATUS current
    DESCRIPTION
        "Event RIP.18
        A route to a destination via some other router in the routing
        database has not been heard from for a while and is now being
        marked as unreachable."
    ::= { ripEventsGroup 18 }

rip18-destination-IP-address OBJECT-TYPE
    SYNTAX IpAddress
    MAX-ACCESS accessible-for-notify
    STATUS current
    DESCRIPTION
        "Parameter 'destination-IP-address' in event RIP.18"
    ::= { ripEventObjects18 1 }

ripEventObjects19 OBJECT-IDENTITY
    STATUS current
    DESCRIPTION
        "Event RIP.19
        A route to a destination via some other router in the routing
        database has not been heard from for a while, has been marked
        unreachable, and is now being deleted."
    ::= { ripEventsGroup 19 }

rip19-destination-IP-address OBJECT-TYPE
    SYNTAX IpAddress
    MAX-ACCESS accessible-for-notify
    STATUS current
    DESCRIPTION
        "Parameter 'destination-IP-address' in event RIP.19"
    ::= { ripEventObjects19 1 }

ripEventObjects20 OBJECT-IDENTITY
    STATUS current
    DESCRIPTION
        "Event RIP.20
        A RIP packet was received by a local interface but is being ignored
        because the configuration of RIP on that interface does not allow
        its version."
    ::= { ripEventsGroup 20 }

rip20-source-IP-address OBJECT-TYPE
    SYNTAX IpAddress
    MAX-ACCESS accessible-for-notify
    STATUS current
    DESCRIPTION
        "Parameter 'source-IP-address' in event RIP.20"
    ::= { ripEventObjects20 1 }

rip20-local-IP-address OBJECT-TYPE
    SYNTAX IpAddress
    MAX-ACCESS accessible-for-notify
    STATUS current
    DESCRIPTION
        "Parameter 'local-IP-address' in event RIP.20"
    ::= { ripEventObjects20 2 }

rip20-version-number OBJECT-TYPE
    SYNTAX Integer32
    MAX-ACCESS accessible-for-notify
    STATUS current
    DESCRIPTION
        "Parameter 'version-number' in event RIP.20"
    ::= { ripEventObjects20 3 }

ripEventObjects21 OBJECT-IDENTITY
    STATUS current
    DESCRIPTION
        "Event RIP.21
        Parsing error in that packet. Some must be zero field is not zero.
        The packet is being ignored."
    ::= { ripEventsGroup 21 }

rip21-source-IP-address OBJECT-TYPE
    SYNTAX IpAddress
    MAX-ACCESS accessible-for-notify
    STATUS current
    DESCRIPTION
        "Parameter 'source-IP-address' in event RIP.21"
    ::= { ripEventObjects21 1 }

ripEventObjects22 OBJECT-IDENTITY
    STATUS current
    DESCRIPTION
        "Event RIP.22
        A packet is being ignored because authentication process disallow it."
    ::= { ripEventsGroup 22 }

rip22-source-IP-address OBJECT-TYPE
    SYNTAX IpAddress
    MAX-ACCESS accessible-for-notify
    STATUS current
    DESCRIPTION
        "Parameter 'source-IP-address' in event RIP.22"
    ::= { ripEventObjects22 1 }

rip22-local-IP-address OBJECT-TYPE
    SYNTAX IpAddress
    MAX-ACCESS accessible-for-notify
    STATUS current
    DESCRIPTION
        "Parameter 'local-IP-address' in event RIP.22"
    ::= { ripEventObjects22 2 }

rip22-authentication-version OBJECT-TYPE
    SYNTAX Integer32
    MAX-ACCESS accessible-for-notify
    STATUS current
    DESCRIPTION
        "Parameter 'authentication-version' in event RIP.22"
    ::= { ripEventObjects22 3 }

ripEventObjects23 OBJECT-IDENTITY
    STATUS current
    DESCRIPTION
        "Event RIP.23
        A paket is not to be send because local interface compatibility sending
        configuration disallows it."
    ::= { ripEventsGroup 23 }

rip23-local-IP-address OBJECT-TYPE
    SYNTAX IpAddress
    MAX-ACCESS accessible-for-notify
    STATUS current
    DESCRIPTION
        "Parameter 'local-IP-address' in event RIP.23"
    ::= { ripEventObjects23 1 }

rip23-destination-IP-address OBJECT-TYPE
    SYNTAX IpAddress
    MAX-ACCESS accessible-for-notify
    STATUS current
    DESCRIPTION
        "Parameter 'destination-IP-address' in event RIP.23"
    ::= { ripEventObjects23 2 }

rip23-version-number OBJECT-TYPE
    SYNTAX Integer32
    MAX-ACCESS accessible-for-notify
    STATUS current
    DESCRIPTION
        "Parameter 'version-number' in event RIP.23"
    ::= { ripEventObjects23 3 }

ripEventObjects24 OBJECT-IDENTITY
    STATUS current
    DESCRIPTION
        "Event RIP.24
        The router is sending a normal RIP broadcast/multicast update
        (triggered either by a timer or a change in the routing table)
        to the specified address."
    ::= { ripEventsGroup 24 }

rip24-source-IP-address OBJECT-TYPE
    SYNTAX IpAddress
    MAX-ACCESS accessible-for-notify
    STATUS current
    DESCRIPTION
        "Parameter 'source-IP-address' in event RIP.24"
    ::= { ripEventObjects24 1 }

rip24-destination-IP-address OBJECT-TYPE
    SYNTAX IpAddress
    MAX-ACCESS accessible-for-notify
    STATUS current
    DESCRIPTION
        "Parameter 'destination-IP-address' in event RIP.24"
    ::= { ripEventObjects24 2 }

rip24-packet-count OBJECT-TYPE
    SYNTAX Integer32
    MAX-ACCESS accessible-for-notify
    STATUS current
    DESCRIPTION
        "Parameter 'packet-count' in event RIP.24"
    ::= { ripEventObjects24 3 }

rip24-number-of-routes OBJECT-TYPE
    SYNTAX Integer32
    MAX-ACCESS accessible-for-notify
    STATUS current
    DESCRIPTION
        "Parameter 'number-of-routes' in event RIP.24"
    ::= { ripEventObjects24 4 }

ripEventObjects25 OBJECT-IDENTITY
    STATUS current
    DESCRIPTION
        "Event RIP.25
        The router is responding with routes that a host previosly asked for."
    ::= { ripEventsGroup 25 }

rip25-source-IP-address OBJECT-TYPE
    SYNTAX IpAddress
    MAX-ACCESS accessible-for-notify
    STATUS current
    DESCRIPTION
        "Parameter 'source-IP-address' in event RIP.25"
    ::= { ripEventObjects25 1 }

rip25-destination-IP-address OBJECT-TYPE
    SYNTAX IpAddress
    MAX-ACCESS accessible-for-notify
    STATUS current
    DESCRIPTION
        "Parameter 'destination-IP-address' in event RIP.25"
    ::= { ripEventObjects25 2 }

rip25-packet-count OBJECT-TYPE
    SYNTAX Integer32
    MAX-ACCESS accessible-for-notify
    STATUS current
    DESCRIPTION
        "Parameter 'packet-count' in event RIP.25"
    ::= { ripEventObjects25 3 }

rip25-number-of-routes OBJECT-TYPE
    SYNTAX Integer32
    MAX-ACCESS accessible-for-notify
    STATUS current
    DESCRIPTION
        "Parameter 'number-of-routes' in event RIP.25"
    ::= { ripEventObjects25 4 }

ripEventObjects26 OBJECT-IDENTITY
    STATUS current
    DESCRIPTION
        "Event RIP.26
        A host is asking for some routes."
    ::= { ripEventsGroup 26 }

rip26-source-IP-address OBJECT-TYPE
    SYNTAX IpAddress
    MAX-ACCESS accessible-for-notify
    STATUS current
    DESCRIPTION
        "Parameter 'source-IP-address' in event RIP.26"
    ::= { ripEventObjects26 1 }

ripEventObjects27 OBJECT-IDENTITY
    STATUS current
    DESCRIPTION
        "Event RIP.27
        The router has read (in) or write (out) this route from or to
        a RIP packet."
    ::= { ripEventsGroup 27 }

rip27-In-Out OBJECT-TYPE
    SYNTAX DisplayString
    MAX-ACCESS accessible-for-notify
    STATUS current
    DESCRIPTION
        "Parameter 'In-Out' in event RIP.27"
    ::= { ripEventObjects27 1 }

rip27-destination-IP-route OBJECT-TYPE
    SYNTAX IpAddress
    MAX-ACCESS accessible-for-notify
    STATUS current
    DESCRIPTION
        "Parameter 'destination-IP-route' in event RIP.27"
    ::= { ripEventObjects27 2 }

rip27-mask-IP-route OBJECT-TYPE
    SYNTAX Integer32
    MAX-ACCESS accessible-for-notify
    STATUS current
    DESCRIPTION
        "Parameter 'mask-IP-route' in event RIP.27"
    ::= { ripEventObjects27 3 }

rip27-gw-IP-address OBJECT-TYPE
    SYNTAX IpAddress
    MAX-ACCESS accessible-for-notify
    STATUS current
    DESCRIPTION
        "Parameter 'gw-IP-address' in event RIP.27"
    ::= { ripEventObjects27 4 }

rip27-cost OBJECT-TYPE
    SYNTAX Integer32
    MAX-ACCESS accessible-for-notify
    STATUS current
    DESCRIPTION
        "Parameter 'cost' in event RIP.27"
    ::= { ripEventObjects27 5 }

ripEventObjects29 OBJECT-IDENTITY
    STATUS current
    DESCRIPTION
        "Event RIP.29
        There are no routes through this tunnel so the tunnel is released."
    ::= { ripEventsGroup 29 }

rip29-interface OBJECT-TYPE
    SYNTAX DisplayString
    MAX-ACCESS accessible-for-notify
    STATUS current
    DESCRIPTION
        "Parameter 'interface' in event RIP.29"
    ::= { ripEventObjects29 1 }

ripEventObjects30 OBJECT-IDENTITY
    STATUS current
    DESCRIPTION
        "Event RIP.30
        A route was received but is being ignored after missing the configured
        access list for RIP routes filtering."
    ::= { ripEventsGroup 30 }

rip30-destination-IP-network OBJECT-TYPE
    SYNTAX IpAddress
    MAX-ACCESS accessible-for-notify
    STATUS current
    DESCRIPTION
        "Parameter 'destination-IP-network' in event RIP.30"
    ::= { ripEventObjects30 1 }

rip30-destination-IP-mask OBJECT-TYPE
    SYNTAX IpAddress
    MAX-ACCESS accessible-for-notify
    STATUS current
    DESCRIPTION
        "Parameter 'destination-IP-mask' in event RIP.30"
    ::= { ripEventObjects30 2 }

rip30-next-hop-IP-address OBJECT-TYPE
    SYNTAX IpAddress
    MAX-ACCESS accessible-for-notify
    STATUS current
    DESCRIPTION
        "Parameter 'next-hop-IP-address' in event RIP.30"
    ::= { ripEventObjects30 3 }

ripEventObjects31 OBJECT-IDENTITY
    STATUS current
    DESCRIPTION
        "Event RIP.31
        The router is sending a RIP update (triggered by a request
        from another host) to the specified address."
    ::= { ripEventsGroup 31 }

rip31-source-interface OBJECT-TYPE
    SYNTAX DisplayString
    MAX-ACCESS accessible-for-notify
    STATUS current
    DESCRIPTION
        "Parameter 'source-interface' in event RIP.31"
    ::= { ripEventObjects31 1 }

rip31-source-IP-address OBJECT-TYPE
    SYNTAX IpAddress
    MAX-ACCESS accessible-for-notify
    STATUS current
    DESCRIPTION
        "Parameter 'source-IP-address' in event RIP.31"
    ::= { ripEventObjects31 2 }

rip31-destination-IP-address OBJECT-TYPE
    SYNTAX IpAddress
    MAX-ACCESS accessible-for-notify
    STATUS current
    DESCRIPTION
        "Parameter 'destination-IP-address' in event RIP.31"
    ::= { ripEventObjects31 3 }

rip31-packet-count OBJECT-TYPE
    SYNTAX Integer32
    MAX-ACCESS accessible-for-notify
    STATUS current
    DESCRIPTION
        "Parameter 'packet-count' in event RIP.31"
    ::= { ripEventObjects31 4 }

rip31-number-of-routes OBJECT-TYPE
    SYNTAX Integer32
    MAX-ACCESS accessible-for-notify
    STATUS current
    DESCRIPTION
        "Parameter 'number-of-routes' in event RIP.31"
    ::= { ripEventObjects31 5 }

ripEventObjects32 OBJECT-IDENTITY
    STATUS current
    DESCRIPTION
        "Event RIP.32
        A packet is not to be send because local interface compatibility sending
        configuration disallows it."
    ::= { ripEventsGroup 32 }

rip32-source-interface OBJECT-TYPE
    SYNTAX DisplayString
    MAX-ACCESS accessible-for-notify
    STATUS current
    DESCRIPTION
        "Parameter 'source-interface' in event RIP.32"
    ::= { ripEventObjects32 1 }

rip32-local-IP-address OBJECT-TYPE
    SYNTAX IpAddress
    MAX-ACCESS accessible-for-notify
    STATUS current
    DESCRIPTION
        "Parameter 'local-IP-address' in event RIP.32"
    ::= { ripEventObjects32 2 }

rip32-destination-IP-address OBJECT-TYPE
    SYNTAX IpAddress
    MAX-ACCESS accessible-for-notify
    STATUS current
    DESCRIPTION
        "Parameter 'destination-IP-address' in event RIP.32"
    ::= { ripEventObjects32 3 }

rip32-version-number OBJECT-TYPE
    SYNTAX Integer32
    MAX-ACCESS accessible-for-notify
    STATUS current
    DESCRIPTION
        "Parameter 'version-number' in event RIP.32"
    ::= { ripEventObjects32 4 }

ripEventObjects33 OBJECT-IDENTITY
    STATUS current
    DESCRIPTION
        "Event RIP.33
        The router is sending a normal RIP broadcast/multicast update
        (triggered either by a timer or a change in the routing table)
        to the specified address."
    ::= { ripEventsGroup 33 }

rip33-source-interface OBJECT-TYPE
    SYNTAX DisplayString
    MAX-ACCESS accessible-for-notify
    STATUS current
    DESCRIPTION
        "Parameter 'source-interface' in event RIP.33"
    ::= { ripEventObjects33 1 }

rip33-source-IP-address OBJECT-TYPE
    SYNTAX IpAddress
    MAX-ACCESS accessible-for-notify
    STATUS current
    DESCRIPTION
        "Parameter 'source-IP-address' in event RIP.33"
    ::= { ripEventObjects33 2 }

rip33-destination-IP-address OBJECT-TYPE
    SYNTAX IpAddress
    MAX-ACCESS accessible-for-notify
    STATUS current
    DESCRIPTION
        "Parameter 'destination-IP-address' in event RIP.33"
    ::= { ripEventObjects33 3 }

rip33-packet-count OBJECT-TYPE
    SYNTAX Integer32
    MAX-ACCESS accessible-for-notify
    STATUS current
    DESCRIPTION
        "Parameter 'packet-count' in event RIP.33"
    ::= { ripEventObjects33 4 }

rip33-number-of-routes OBJECT-TYPE
    SYNTAX Integer32
    MAX-ACCESS accessible-for-notify
    STATUS current
    DESCRIPTION
        "Parameter 'number-of-routes' in event RIP.33"
    ::= { ripEventObjects33 5 }

ripEventObjects34 OBJECT-IDENTITY
    STATUS current
    DESCRIPTION
        "Event RIP.34
        The router is responding with routes that a host previosly asked for."
    ::= { ripEventsGroup 34 }

rip34-source-interface OBJECT-TYPE
    SYNTAX DisplayString
    MAX-ACCESS accessible-for-notify
    STATUS current
    DESCRIPTION
        "Parameter 'source-interface' in event RIP.34"
    ::= { ripEventObjects34 1 }

rip34-source-IP-address OBJECT-TYPE
    SYNTAX IpAddress
    MAX-ACCESS accessible-for-notify
    STATUS current
    DESCRIPTION
        "Parameter 'source-IP-address' in event RIP.34"
    ::= { ripEventObjects34 2 }

rip34-destination-IP-address OBJECT-TYPE
    SYNTAX IpAddress
    MAX-ACCESS accessible-for-notify
    STATUS current
    DESCRIPTION
        "Parameter 'destination-IP-address' in event RIP.34"
    ::= { ripEventObjects34 3 }

rip34-packet-count OBJECT-TYPE
    SYNTAX Integer32
    MAX-ACCESS accessible-for-notify
    STATUS current
    DESCRIPTION
        "Parameter 'packet-count' in event RIP.34"
    ::= { ripEventObjects34 4 }

rip34-number-of-routes OBJECT-TYPE
    SYNTAX Integer32
    MAX-ACCESS accessible-for-notify
    STATUS current
    DESCRIPTION
        "Parameter 'number-of-routes' in event RIP.34"
    ::= { ripEventObjects34 5 }

ripEventObjects35 OBJECT-IDENTITY
    STATUS current
    DESCRIPTION
        "Event RIP.35
        A packet is being ignored because the sequence number is higher than it expect ."
    ::= { ripEventsGroup 35 }

rip35-source-IP-address OBJECT-TYPE
    SYNTAX IpAddress
    MAX-ACCESS accessible-for-notify
    STATUS current
    DESCRIPTION
        "Parameter 'source-IP-address' in event RIP.35"
    ::= { ripEventObjects35 1 }

rip35-local-IP-address OBJECT-TYPE
    SYNTAX IpAddress
    MAX-ACCESS accessible-for-notify
    STATUS current
    DESCRIPTION
        "Parameter 'local-IP-address' in event RIP.35"
    ::= { ripEventObjects35 2 }

rip35-sequence-number OBJECT-TYPE
    SYNTAX Integer32
    MAX-ACCESS accessible-for-notify
    STATUS current
    DESCRIPTION
        "Parameter 'sequence-number' in event RIP.35"
    ::= { ripEventObjects35 3 }


ripNotification1 NOTIFICATION-TYPE
    OBJECTS { 
              rip1-version-number, 
              rip1-source-IP-address 
            }
    STATUS current
    DESCRIPTION
        "Notification of Event RIP.1

        Message: 'bad version $1 received from host $2'

        Parameters list:
              $1: rip1-version-number
              $2: rip1-source-IP-address

        The version field in the RIP header did not match the current
        version."
    ::= { ripNotificationsPrefix 1 }

ripNotification2 NOTIFICATION-TYPE
    OBJECTS { 
              rip2-source-IP-address 
            }
    STATUS current
    DESCRIPTION
        "Notification of Event RIP.2

        Message: 'update request received from host $1'

        Parameters list:
              $1: rip2-source-IP-address

        A RIP routing table request was received from another host. A routing
        table update will be sent to it."
    ::= { ripNotificationsPrefix 2 }

ripNotification3 NOTIFICATION-TYPE
    OBJECTS { 
              rip3-source-IP-address 
            }
    STATUS current
    DESCRIPTION
        "Notification of Event RIP.3

        Message: 'trace on received from host $1'

        Parameters list:
              $1: rip3-source-IP-address

        A request from a host to turn RIP tracing on to a given log
        file was received. The router ignores this request."
    ::= { ripNotificationsPrefix 3 }

ripNotification4 NOTIFICATION-TYPE
    OBJECTS { 
              rip4-source-IP-address 
            }
    STATUS current
    DESCRIPTION
        "Notification of Event RIP.4

        Message: 'trace off received from host $1'

        Parameters list:
              $1: rip4-source-IP-address

        A request from a host to turn RIP tracing off was received.
        The router ignores this request."
    ::= { ripNotificationsPrefix 4 }

ripNotification5 NOTIFICATION-TYPE
    OBJECTS { 
              rip5-source-IP-address 
            }
    STATUS current
    DESCRIPTION
        "Notification of Event RIP.5

        Message: 'response received from host $1'

        Parameters list:
              $1: rip5-source-IP-address

        A RIP routing table update was received. Note that it may take
        more than one response packet to transmit the entire routing
        table, especially if the routing table is large."
    ::= { ripNotificationsPrefix 5 }

ripNotification6 NOTIFICATION-TYPE
    OBJECTS { 
              rip6-command-code, 
              rip6-source-IP-address 
            }
    STATUS current
    DESCRIPTION
        "Notification of Event RIP.6

        Message: 'bad command code $1 received from host $2'

        Parameters list:
              $1: rip6-command-code
              $2: rip6-source-IP-address

        A RIP message was received with an unrecognized command code."
    ::= { ripNotificationsPrefix 6 }

ripNotification7 NOTIFICATION-TYPE
    OBJECTS { 
              rip7-source-IP-address 
            }
    STATUS current
    DESCRIPTION
        "Notification of Event RIP.7

        Message: 'response received from off network host $1'

        Parameters list:
              $1: rip7-source-IP-address

        A RIP routing update response was received from a machine which
        was not directly attached to the network the response came in on.
        The packet is discarded."
    ::= { ripNotificationsPrefix 7 }

ripNotification8 NOTIFICATION-TYPE
    OBJECTS { 
              rip8-destination-IP-network, 
              rip8-next-hop-IP-address 
            }
    STATUS current
    DESCRIPTION
        "Notification of Event RIP.8

        Message: 'subnet route $1 on non-subnetted interface from host $2'

        Parameters list:
              $1: rip8-destination-IP-network
              $2: rip8-next-hop-IP-address

        An apparent subnet route (i.e. the 'rest' field of the Internet
        address contained non-zero data) was received over an interface
        that is not marked as subnetted in the router."
    ::= { ripNotificationsPrefix 8 }

ripNotification9 NOTIFICATION-TYPE
    OBJECTS { 
              rip9-destination-IP-network, 
              rip9-next-hop-IP-address 
            }
    STATUS current
    DESCRIPTION
        "Notification of Event RIP.9

        Message: 'dynamic route to $1 from $2 disallowed in configuration'

        Parameters list:
              $1: rip9-destination-IP-network
              $2: rip9-next-hop-IP-address

        A dynamic route was received but is being ignored because the
        configuration of RIP on the router does not allow dynamic routes
        except for those in a table, and this route was not in that table."
    ::= { ripNotificationsPrefix 9 }

ripNotification10 NOTIFICATION-TYPE
    OBJECTS { 
              rip10-destination-IP-address, 
              rip10-next-hop-IP-address 
            }
    STATUS current
    DESCRIPTION
        "Notification of Event RIP.10

        Message: 'network $1 now unreachable via router $2, deleted'

        Parameters list:
              $1: rip10-destination-IP-address
              $2: rip10-next-hop-IP-address

        An incoming RIP update from the router that was previously
        listed as the next hop to the destination network has announced
        that the destination is unreachable (i.e. at metric 'infinity').
        The RIP route to that destination is being deleted."
    ::= { ripNotificationsPrefix 10 }

ripNotification11 NOTIFICATION-TYPE
    OBJECTS { 
              rip11-destination-IP-network, 
              rip11-metric,
              rip11-next-hop-IP-address 
            }
    STATUS current
    DESCRIPTION
        "Notification of Event RIP.11

        Message: 'update route to net $1 at metric $2 hops via router $3'

        Parameters list:
              $1: rip11-destination-IP-network
              $2: rip11-metric
              $3: rip11-next-hop-IP-address

        A new (better) route to the given destination has been learned
        via RIP and has been installed."
    ::= { ripNotificationsPrefix 11 }

ripNotification12 NOTIFICATION-TYPE
    OBJECTS { 
              rip12-source-IP-address, 
              rip12-destination-IP-address 
            }
    STATUS current
    DESCRIPTION
        "Notification of Event RIP.12

        Message: 'send broadcast/multicast request from address $1 to address $2'

        Parameters list:
              $1: rip12-source-IP-address
              $2: rip12-destination-IP-address

        The router is sending a RIP broadcast/multicast request from each of
        the addresses associated with an interface which has just come up."
    ::= { ripNotificationsPrefix 12 }

ripNotification13 NOTIFICATION-TYPE
    OBJECTS { 
              rip13-source-IP-address, 
              rip13-destination-IP-address 
            }
    STATUS current
    DESCRIPTION
        "Notification of Event RIP.13

        Message: 'send request by dlci from address $1 to address $2'

        Parameters list:
              $1: rip13-source-IP-address
              $2: rip13-destination-IP-address

        The router is sending a RIP broadcast/multicast request from
        the addresses associated with a dlci has just come up."
    ::= { ripNotificationsPrefix 13 }

ripNotification14 NOTIFICATION-TYPE
    OBJECTS { 
              rip14-source-IP-address, 
              rip14-destination-IP-address,
              rip14-packet-count,
              rip14-number-of-routes 
            }
    STATUS current
    DESCRIPTION
        "Notification of Event RIP.14

        Message: 'sending unicast response from address $1 to address $2 in $3 packets with $4 routes'

        Parameters list:
              $1: rip14-source-IP-address
              $2: rip14-destination-IP-address
              $3: rip14-packet-count
              $4: rip14-number-of-routes

        The router is sending a RIP update (triggered by a request
        from another host) to the specified address."
    ::= { ripNotificationsPrefix 14 }

ripNotification15 NOTIFICATION-TYPE
    STATUS current
    DESCRIPTION
        "Notification of Event RIP.15

        Message: 'cannot allocate packet for transmission'

        When RIP went to allocate a packet for transmission (either for
        a request or reply), none was available."
    ::= { ripNotificationsPrefix 15 }

ripNotification16 NOTIFICATION-TYPE
    OBJECTS { 
              rip16-source-IP-address, 
              rip16-destination-IP-address 
            }
    STATUS current
    DESCRIPTION
        "Notification of Event RIP.16

        Message: 'sending packet from $1 to $2'

        Parameters list:
              $1: rip16-source-IP-address
              $2: rip16-destination-IP-address

        A RIP packet (either a routing table update, or when an interface
        first comes up, a request) was sent."
    ::= { ripNotificationsPrefix 16 }

ripNotification17 NOTIFICATION-TYPE
    OBJECTS { 
              rip17-output-error-code, 
              rip17-interface 
            }
    STATUS current
    DESCRIPTION
        "Notification of Event RIP.17

        Message: 'error code $1 when sending packet out interface $2'

        Parameters list:
              $1: rip17-output-error-code
              $2: rip17-interface

        An outgoing reply packet was dropped as the result of some
        problem in the router."
    ::= { ripNotificationsPrefix 17 }

ripNotification18 NOTIFICATION-TYPE
    OBJECTS { 
              rip18-destination-IP-address 
            }
    STATUS current
    DESCRIPTION
        "Notification of Event RIP.18

        Message: 'network route to $1 timed out'

        Parameters list:
              $1: rip18-destination-IP-address

        A route to a destination via some other router in the routing
        database has not been heard from for a while and is now being
        marked as unreachable."
    ::= { ripNotificationsPrefix 18 }

ripNotification19 NOTIFICATION-TYPE
    OBJECTS { 
              rip19-destination-IP-address 
            }
    STATUS current
    DESCRIPTION
        "Notification of Event RIP.19

        Message: 'network route to $1 deleted'

        Parameters list:
              $1: rip19-destination-IP-address

        A route to a destination via some other router in the routing
        database has not been heard from for a while, has been marked
        unreachable, and is now being deleted."
    ::= { ripNotificationsPrefix 19 }

ripNotification20 NOTIFICATION-TYPE
    OBJECTS { 
              rip20-source-IP-address, 
              rip20-local-IP-address,
              rip20-version-number 
            }
    STATUS current
    DESCRIPTION
        "Notification of Event RIP.20

        Message: 'packet received from host $1 by local interface $2 with version $3 disallowed in configuration'

        Parameters list:
              $1: rip20-source-IP-address
              $2: rip20-local-IP-address
              $3: rip20-version-number

        A RIP packet was received by a local interface but is being ignored
        because the configuration of RIP on that interface does not allow
        its version."
    ::= { ripNotificationsPrefix 20 }

ripNotification21 NOTIFICATION-TYPE
    OBJECTS { 
              rip21-source-IP-address 
            }
    STATUS current
    DESCRIPTION
        "Notification of Event RIP.21

        Message: 'error in packet from host $1 because a must be zero field is not zero'

        Parameters list:
              $1: rip21-source-IP-address

        Parsing error in that packet. Some must be zero field is not zero.
        The packet is being ignored."
    ::= { ripNotificationsPrefix 21 }

ripNotification22 NOTIFICATION-TYPE
    OBJECTS { 
              rip22-source-IP-address, 
              rip22-local-IP-address,
              rip22-authentication-version 
            }
    STATUS current
    DESCRIPTION
        "Notification of Event RIP.22

        Message: 'authentication error in packet received from $1 by interface $2, authentication type $3'

        Parameters list:
              $1: rip22-source-IP-address
              $2: rip22-local-IP-address
              $3: rip22-authentication-version

        A packet is being ignored because authentication process disallow it."
    ::= { ripNotificationsPrefix 22 }

ripNotification23 NOTIFICATION-TYPE
    OBJECTS { 
              rip23-local-IP-address, 
              rip23-destination-IP-address,
              rip23-version-number 
            }
    STATUS current
    DESCRIPTION
        "Notification of Event RIP.23

        Message: 'Response is not sent from $1 to $2 because its version $3 is disallowed in sending configuration'

        Parameters list:
              $1: rip23-local-IP-address
              $2: rip23-destination-IP-address
              $3: rip23-version-number

        A paket is not to be send because local interface compatibility sending
        configuration disallows it."
    ::= { ripNotificationsPrefix 23 }

ripNotification24 NOTIFICATION-TYPE
    OBJECTS { 
              rip24-source-IP-address, 
              rip24-destination-IP-address,
              rip24-packet-count,
              rip24-number-of-routes 
            }
    STATUS current
    DESCRIPTION
        "Notification of Event RIP.24

        Message: 'sending broadcast/multicast response all table from address $1 to address $2 in $3 packets with $4 routes'

        Parameters list:
              $1: rip24-source-IP-address
              $2: rip24-destination-IP-address
              $3: rip24-packet-count
              $4: rip24-number-of-routes

        The router is sending a normal RIP broadcast/multicast update
        (triggered either by a timer or a change in the routing table)
        to the specified address."
    ::= { ripNotificationsPrefix 24 }

ripNotification25 NOTIFICATION-TYPE
    OBJECTS { 
              rip25-source-IP-address, 
              rip25-destination-IP-address,
              rip25-packet-count,
              rip25-number-of-routes 
            }
    STATUS current
    DESCRIPTION
        "Notification of Event RIP.25

        Message: 'sending unicast response partial table from address $1 to address $2 in $3 packets with $4 routes'

        Parameters list:
              $1: rip25-source-IP-address
              $2: rip25-destination-IP-address
              $3: rip25-packet-count
              $4: rip25-number-of-routes

        The router is responding with routes that a host previosly asked for."
    ::= { ripNotificationsPrefix 25 }

ripNotification26 NOTIFICATION-TYPE
    OBJECTS { 
              rip26-source-IP-address 
            }
    STATUS current
    DESCRIPTION
        "Notification of Event RIP.26

        Message: 'partial request from host $1'

        Parameters list:
              $1: rip26-source-IP-address

        A host is asking for some routes."
    ::= { ripNotificationsPrefix 26 }

ripNotification27 NOTIFICATION-TYPE
    OBJECTS { 
              rip27-In-Out, 
              rip27-destination-IP-route,
              rip27-mask-IP-route,
              rip27-gw-IP-address,
              rip27-cost 
            }
    STATUS current
    DESCRIPTION
        "Notification of Event RIP.27

        Message: '$1 $2/$3 via $4 in $5 hops'

        Parameters list:
              $1: rip27-In-Out
              $2: rip27-destination-IP-route
              $3: rip27-mask-IP-route
              $4: rip27-gw-IP-address
              $5: rip27-cost

        The router has read (in) or write (out) this route from or to
        a RIP packet."
    ::= { ripNotificationsPrefix 27 }

ripNotification28 NOTIFICATION-TYPE
    STATUS current
    DESCRIPTION
        "Notification of Event RIP.28

        Message: 'RIP not enabled, packet is discarted'

        The router has protocol RIP dissabled, received packets are discarted."
    ::= { ripNotificationsPrefix 28 }

ripNotification29 NOTIFICATION-TYPE
    OBJECTS { 
              rip29-interface 
            }
    STATUS current
    DESCRIPTION
        "Notification of Event RIP.29

        Message: 'Tunnel interface $1 released, no routes'

        Parameters list:
              $1: rip29-interface

        There are no routes through this tunnel so the tunnel is released."
    ::= { ripNotificationsPrefix 29 }

ripNotification30 NOTIFICATION-TYPE
    OBJECTS { 
              rip30-destination-IP-network, 
              rip30-destination-IP-mask,
              rip30-next-hop-IP-address 
            }
    STATUS current
    DESCRIPTION
        "Notification of Event RIP.30

        Message: 'route to $1 mask $2 from $3 disallowed in configuration'

        Parameters list:
              $1: rip30-destination-IP-network
              $2: rip30-destination-IP-mask
              $3: rip30-next-hop-IP-address

        A route was received but is being ignored after missing the configured
        access list for RIP routes filtering."
    ::= { ripNotificationsPrefix 30 }

ripNotification31 NOTIFICATION-TYPE
    OBJECTS { 
              rip31-source-interface, 
              rip31-source-IP-address,
              rip31-destination-IP-address,
              rip31-packet-count,
              rip31-number-of-routes 
            }
    STATUS current
    DESCRIPTION
        "Notification of Event RIP.31

        Message: 'sending unicast response from unnumbered address $1 $2 to address $3 in $4 packets with $5 routes'

        Parameters list:
              $1: rip31-source-interface
              $2: rip31-source-IP-address
              $3: rip31-destination-IP-address
              $4: rip31-packet-count
              $5: rip31-number-of-routes

        The router is sending a RIP update (triggered by a request
        from another host) to the specified address."
    ::= { ripNotificationsPrefix 31 }

ripNotification32 NOTIFICATION-TYPE
    OBJECTS { 
              rip32-source-interface, 
              rip32-local-IP-address,
              rip32-destination-IP-address,
              rip32-version-number 
            }
    STATUS current
    DESCRIPTION
        "Notification of Event RIP.32

        Message: 'Response is not sent from $1 $2 to $3 because its version $4 is disallowed in sending configuration'

        Parameters list:
              $1: rip32-source-interface
              $2: rip32-local-IP-address
              $3: rip32-destination-IP-address
              $4: rip32-version-number

        A packet is not to be send because local interface compatibility sending
        configuration disallows it."
    ::= { ripNotificationsPrefix 32 }

ripNotification33 NOTIFICATION-TYPE
    OBJECTS { 
              rip33-source-interface, 
              rip33-source-IP-address,
              rip33-destination-IP-address,
              rip33-packet-count,
              rip33-number-of-routes 
            }
    STATUS current
    DESCRIPTION
        "Notification of Event RIP.33

        Message: 'sending broadcast/multicast response all table from address $1 $2 to address $3 in $4 packets with $5 routes'

        Parameters list:
              $1: rip33-source-interface
              $2: rip33-source-IP-address
              $3: rip33-destination-IP-address
              $4: rip33-packet-count
              $5: rip33-number-of-routes

        The router is sending a normal RIP broadcast/multicast update
        (triggered either by a timer or a change in the routing table)
        to the specified address."
    ::= { ripNotificationsPrefix 33 }

ripNotification34 NOTIFICATION-TYPE
    OBJECTS { 
              rip34-source-interface, 
              rip34-source-IP-address,
              rip34-destination-IP-address,
              rip34-packet-count,
              rip34-number-of-routes 
            }
    STATUS current
    DESCRIPTION
        "Notification of Event RIP.34

        Message: 'sending unicast response partial table from unnumbered address $1 $2 to address $3 in $4 packets with $5 routes'

        Parameters list:
              $1: rip34-source-interface
              $2: rip34-source-IP-address
              $3: rip34-destination-IP-address
              $4: rip34-packet-count
              $5: rip34-number-of-routes

        The router is responding with routes that a host previosly asked for."
    ::= { ripNotificationsPrefix 34 }

ripNotification35 NOTIFICATION-TYPE
    OBJECTS { 
              rip35-source-IP-address, 
              rip35-local-IP-address,
              rip35-sequence-number 
            }
    STATUS current
    DESCRIPTION
        "Notification of Event RIP.35

        Message: 'error in sequence number received from $1 by interface $2, seq num $3'

        Parameters list:
              $1: rip35-source-IP-address
              $2: rip35-local-IP-address
              $3: rip35-sequence-number

        A packet is being ignored because the sequence number is higher than it expect ."
    ::= { ripNotificationsPrefix 35 }

ripNotification36 NOTIFICATION-TYPE
    STATUS current
    DESCRIPTION
        "Notification of Event RIP.36

        Message: 'The time to live of the key have expired'

        A packet is being sent with a non valid key authetication ."
    ::= { ripNotificationsPrefix 36 }


END
