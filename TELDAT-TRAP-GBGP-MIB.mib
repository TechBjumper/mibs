-- file automatically created


TELDAT-TRAP-GBGP-MIB DEFINITIONS ::= BEGIN


IMPORTS
	MODULE-IDENTITY,OBJECT-TYPE,OBJECT-IDENTITY,NOTIFICATION-TYPE,Integer32,IpAddress
		FROM SNMPv2-SMI
	DisplayString
		FROM SNMPv2-TC
	telEventTraps
		FROM TELDAT-MIB;


gbgpTrapsMIB MODULE-IDENTITY
    LAST-UPDATED "201401200930Z"
    ORGANIZATION "Teldat, S.A."
    CONTACT-INFO 
        "Teldat, S.A.
        Customer Service

        Postal: Parque Tecnologico de Madrid
                Tres Cantos 28760
                Madrid, SPAIN

        Tel.: +34 918 076 565

        http://www.teldat.com"
    DESCRIPTION
        "This Module Information Base file is defined for managing received
        SNMP notifications generated by the GBGP event subsystem."
    REVISION "201401200930Z"
    DESCRIPTION "Initial implementation"
        ::= { telEventTraps 169 }


gbgpEventsGroup	OBJECT IDENTIFIER	::= { gbgpTrapsMIB 1 }

gbgpNotifications	OBJECT IDENTIFIER	::= { gbgpTrapsMIB 2 }
gbgpNotificationsPrefix	OBJECT IDENTIFIER	::= { gbgpNotifications 0 }

gbgpEventObjects2 OBJECT-IDENTITY
    STATUS current
    DESCRIPTION
        "Event GBGP.2
        A connection to a ESTABLISHED BGP peer has been lost. Possible causes
        are either a keepalive timer timeout or a TCP protocol error. The status
        of this peer is changed to ACTIVE."
    ::= { gbgpEventsGroup 2 }

gbgp2-RemotePeerAddress OBJECT-TYPE
    SYNTAX IpAddress
    MAX-ACCESS accessible-for-notify
    STATUS current
    DESCRIPTION
        "Parameter 'RemotePeerAddress' in event GBGP.2"
    ::= { gbgpEventObjects2 1 }

gbgp2-AutonomousSystem OBJECT-TYPE
    SYNTAX Integer32
    MAX-ACCESS accessible-for-notify
    STATUS current
    DESCRIPTION
        "Parameter 'AutonomousSystem' in event GBGP.2"
    ::= { gbgpEventObjects2 2 }

gbgpEventObjects3 OBJECT-IDENTITY
    STATUS current
    DESCRIPTION
        "Event GBGP.3
        Syntax errors found in configuration file."
    ::= { gbgpEventsGroup 3 }

gbgp3-ParserErrors OBJECT-TYPE
    SYNTAX Integer32
    MAX-ACCESS accessible-for-notify
    STATUS current
    DESCRIPTION
        "Parameter 'ParserErrors' in event GBGP.3"
    ::= { gbgpEventObjects3 1 }

gbgpEventObjects4 OBJECT-IDENTITY
    STATUS current
    DESCRIPTION
        "Event GBGP.4
        A valid incoming BGP message has been received from a peer.
        The type of message is shown, as well as the remote peer address and
        autonomous system."
    ::= { gbgpEventsGroup 4 }

gbgp4-PacketType OBJECT-TYPE
    SYNTAX DisplayString
    MAX-ACCESS accessible-for-notify
    STATUS current
    DESCRIPTION
        "Parameter 'PacketType' in event GBGP.4"
    ::= { gbgpEventObjects4 1 }

gbgp4-RemotePeerAddress OBJECT-TYPE
    SYNTAX IpAddress
    MAX-ACCESS accessible-for-notify
    STATUS current
    DESCRIPTION
        "Parameter 'RemotePeerAddress' in event GBGP.4"
    ::= { gbgpEventObjects4 2 }

gbgp4-AutonomousSystem OBJECT-TYPE
    SYNTAX Integer32
    MAX-ACCESS accessible-for-notify
    STATUS current
    DESCRIPTION
        "Parameter 'AutonomousSystem' in event GBGP.4"
    ::= { gbgpEventObjects4 3 }

gbgpEventObjects5 OBJECT-IDENTITY
    STATUS current
    DESCRIPTION
        "Event GBGP.5
        A message is been sent to a remote peer.
        The type of message is shown, as well as the remote peer address and
        autonomous system."
    ::= { gbgpEventsGroup 5 }

gbgp5-PacketType OBJECT-TYPE
    SYNTAX DisplayString
    MAX-ACCESS accessible-for-notify
    STATUS current
    DESCRIPTION
        "Parameter 'PacketType' in event GBGP.5"
    ::= { gbgpEventObjects5 1 }

gbgp5-RemotePeerAddress OBJECT-TYPE
    SYNTAX IpAddress
    MAX-ACCESS accessible-for-notify
    STATUS current
    DESCRIPTION
        "Parameter 'RemotePeerAddress' in event GBGP.5"
    ::= { gbgpEventObjects5 2 }

gbgp5-AutonomousSystem OBJECT-TYPE
    SYNTAX Integer32
    MAX-ACCESS accessible-for-notify
    STATUS current
    DESCRIPTION
        "Parameter 'AutonomousSystem' in event GBGP.5"
    ::= { gbgpEventObjects5 3 }

gbgpEventObjects6 OBJECT-IDENTITY
    STATUS current
    DESCRIPTION
        "Event GBGP.6
        An incoming BGP message has been rejected. The rejection cause is shown
        in the message."
    ::= { gbgpEventsGroup 6 }

gbgp6-RemotePeerName OBJECT-TYPE
    SYNTAX DisplayString
    MAX-ACCESS accessible-for-notify
    STATUS current
    DESCRIPTION
        "Parameter 'RemotePeerName' in event GBGP.6"
    ::= { gbgpEventObjects6 1 }

gbgp6-ErrorMessage OBJECT-TYPE
    SYNTAX DisplayString
    MAX-ACCESS accessible-for-notify
    STATUS current
    DESCRIPTION
        "Parameter 'ErrorMessage' in event GBGP.6"
    ::= { gbgpEventObjects6 2 }

gbgpEventObjects7 OBJECT-IDENTITY
    STATUS current
    DESCRIPTION
        "Event GBGP.7
        An active open from a remote system has been rejected. The address, AS
        and rejection cause are shown."
    ::= { gbgpEventsGroup 7 }

gbgp7-RemotePeerName OBJECT-TYPE
    SYNTAX DisplayString
    MAX-ACCESS accessible-for-notify
    STATUS current
    DESCRIPTION
        "Parameter 'RemotePeerName' in event GBGP.7"
    ::= { gbgpEventObjects7 1 }

gbgp7-ErrorMessage OBJECT-TYPE
    SYNTAX DisplayString
    MAX-ACCESS accessible-for-notify
    STATUS current
    DESCRIPTION
        "Parameter 'ErrorMessage' in event GBGP.7"
    ::= { gbgpEventObjects7 2 }

gbgpEventObjects8 OBJECT-IDENTITY
    STATUS current
    DESCRIPTION
        "Event GBGP.8
        A valid connection has been made to a configured BGP peer. Peer status
        is changed to ESTABLISHED."
    ::= { gbgpEventsGroup 8 }

gbgp8-RemotePeerAddress OBJECT-TYPE
    SYNTAX IpAddress
    MAX-ACCESS accessible-for-notify
    STATUS current
    DESCRIPTION
        "Parameter 'RemotePeerAddress' in event GBGP.8"
    ::= { gbgpEventObjects8 1 }

gbgp8-AutonomousSystem OBJECT-TYPE
    SYNTAX Integer32
    MAX-ACCESS accessible-for-notify
    STATUS current
    DESCRIPTION
        "Parameter 'AutonomousSystem' in event GBGP.8"
    ::= { gbgpEventObjects8 2 }

gbgpEventObjects10 OBJECT-IDENTITY
    STATUS current
    DESCRIPTION
        "Event GBGP.10
        An update message for the route shown has been received. This message
        does not mean that this route has been made active, it just means that
        the system has received information for this route from a BGP peer. This
        route will be processed, and, taking into account the
        configured preference rules, will be or not exported to the active
        routes table. To be able to see changes in the active RT, please
        use the IP subsystem events."
    ::= { gbgpEventsGroup 10 }

gbgp10-RouteDest OBJECT-TYPE
    SYNTAX IpAddress
    MAX-ACCESS accessible-for-notify
    STATUS current
    DESCRIPTION
        "Parameter 'RouteDest' in event GBGP.10"
    ::= { gbgpEventObjects10 1 }

gbgp10-RouteMask OBJECT-TYPE
    SYNTAX IpAddress
    MAX-ACCESS accessible-for-notify
    STATUS current
    DESCRIPTION
        "Parameter 'RouteMask' in event GBGP.10"
    ::= { gbgpEventObjects10 2 }

gbgp10-NextHop OBJECT-TYPE
    SYNTAX IpAddress
    MAX-ACCESS accessible-for-notify
    STATUS current
    DESCRIPTION
        "Parameter 'NextHop' in event GBGP.10"
    ::= { gbgpEventObjects10 3 }

gbgp10-Preference OBJECT-TYPE
    SYNTAX Integer32
    MAX-ACCESS accessible-for-notify
    STATUS current
    DESCRIPTION
        "Parameter 'Preference' in event GBGP.10"
    ::= { gbgpEventObjects10 4 }

gbgp10-Metric OBJECT-TYPE
    SYNTAX DisplayString
    MAX-ACCESS accessible-for-notify
    STATUS current
    DESCRIPTION
        "Parameter 'Metric' in event GBGP.10"
    ::= { gbgpEventObjects10 5 }

gbgp10-LocalPref OBJECT-TYPE
    SYNTAX DisplayString
    MAX-ACCESS accessible-for-notify
    STATUS current
    DESCRIPTION
        "Parameter 'LocalPref' in event GBGP.10"
    ::= { gbgpEventObjects10 6 }

gbgpEventObjects11 OBJECT-IDENTITY
    STATUS current
    DESCRIPTION
        "Event GBGP.11
        An unreach message has been received for this route. This message
        does not mean that this route will be deleted from the active RT
        (it is possible that the route was not even made active when it
        was received). To be able to see changes in the active RT, please
        use the IP subsystem events."
    ::= { gbgpEventsGroup 11 }

gbgp11-RouteDest OBJECT-TYPE
    SYNTAX IpAddress
    MAX-ACCESS accessible-for-notify
    STATUS current
    DESCRIPTION
        "Parameter 'RouteDest' in event GBGP.11"
    ::= { gbgpEventObjects11 1 }

gbgp11-RouteMask OBJECT-TYPE
    SYNTAX IpAddress
    MAX-ACCESS accessible-for-notify
    STATUS current
    DESCRIPTION
        "Parameter 'RouteMask' in event GBGP.11"
    ::= { gbgpEventObjects11 2 }

gbgp11-BGPPeer OBJECT-TYPE
    SYNTAX DisplayString
    MAX-ACCESS accessible-for-notify
    STATUS current
    DESCRIPTION
        "Parameter 'BGPPeer' in event GBGP.11"
    ::= { gbgpEventObjects11 3 }

gbgpEventObjects12 OBJECT-IDENTITY
    STATUS current
    DESCRIPTION
        "Event GBGP.12
        The holdtime for a given BGP peer has expired."
    ::= { gbgpEventsGroup 12 }

gbgp12-RemotePeerAddress OBJECT-TYPE
    SYNTAX IpAddress
    MAX-ACCESS accessible-for-notify
    STATUS current
    DESCRIPTION
        "Parameter 'RemotePeerAddress' in event GBGP.12"
    ::= { gbgpEventObjects12 1 }

gbgp12-AutonomousSystem OBJECT-TYPE
    SYNTAX Integer32
    MAX-ACCESS accessible-for-notify
    STATUS current
    DESCRIPTION
        "Parameter 'AutonomousSystem' in event GBGP.12"
    ::= { gbgpEventObjects12 2 }

gbgpEventObjects14 OBJECT-IDENTITY
    STATUS current
    DESCRIPTION
        "Event GBGP.14
        Deleting route from BGP routing Database."
    ::= { gbgpEventsGroup 14 }

gbgp14-Dest OBJECT-TYPE
    SYNTAX IpAddress
    MAX-ACCESS accessible-for-notify
    STATUS current
    DESCRIPTION
        "Parameter 'Dest' in event GBGP.14"
    ::= { gbgpEventObjects14 1 }

gbgp14-Mask OBJECT-TYPE
    SYNTAX IpAddress
    MAX-ACCESS accessible-for-notify
    STATUS current
    DESCRIPTION
        "Parameter 'Mask' in event GBGP.14"
    ::= { gbgpEventObjects14 2 }

gbgp14-BGPPeer OBJECT-TYPE
    SYNTAX DisplayString
    MAX-ACCESS accessible-for-notify
    STATUS current
    DESCRIPTION
        "Parameter 'BGPPeer' in event GBGP.14"
    ::= { gbgpEventObjects14 3 }

gbgpEventObjects15 OBJECT-IDENTITY
    STATUS current
    DESCRIPTION
        "Event GBGP.15
        Adding route to BGP routing Database."
    ::= { gbgpEventsGroup 15 }

gbgp15-Dest OBJECT-TYPE
    SYNTAX IpAddress
    MAX-ACCESS accessible-for-notify
    STATUS current
    DESCRIPTION
        "Parameter 'Dest' in event GBGP.15"
    ::= { gbgpEventObjects15 1 }

gbgp15-Mask OBJECT-TYPE
    SYNTAX IpAddress
    MAX-ACCESS accessible-for-notify
    STATUS current
    DESCRIPTION
        "Parameter 'Mask' in event GBGP.15"
    ::= { gbgpEventObjects15 2 }

gbgp15-NextHop OBJECT-TYPE
    SYNTAX IpAddress
    MAX-ACCESS accessible-for-notify
    STATUS current
    DESCRIPTION
        "Parameter 'NextHop' in event GBGP.15"
    ::= { gbgpEventObjects15 3 }

gbgpEventObjects16 OBJECT-IDENTITY
    STATUS current
    DESCRIPTION
        "Event GBGP.16
        Adding direct route to BGP routing Database."
    ::= { gbgpEventsGroup 16 }

gbgp16-Dest OBJECT-TYPE
    SYNTAX IpAddress
    MAX-ACCESS accessible-for-notify
    STATUS current
    DESCRIPTION
        "Parameter 'Dest' in event GBGP.16"
    ::= { gbgpEventObjects16 1 }

gbgp16-Mask OBJECT-TYPE
    SYNTAX IpAddress
    MAX-ACCESS accessible-for-notify
    STATUS current
    DESCRIPTION
        "Parameter 'Mask' in event GBGP.16"
    ::= { gbgpEventObjects16 2 }

gbgpEventObjects18 OBJECT-IDENTITY
    STATUS current
    DESCRIPTION
        "Event GBGP.18
        BGP subsystem is trying to connect to a remote peer."
    ::= { gbgpEventsGroup 18 }

gbgp18-RemotePeer OBJECT-TYPE
    SYNTAX DisplayString
    MAX-ACCESS accessible-for-notify
    STATUS current
    DESCRIPTION
        "Parameter 'RemotePeer' in event GBGP.18"
    ::= { gbgpEventObjects18 1 }

gbgpEventObjects19 OBJECT-IDENTITY
    STATUS current
    DESCRIPTION
        "Event GBGP.19
        A notification message has been sent or received."
    ::= { gbgpEventsGroup 19 }

gbgp19-fromto OBJECT-TYPE
    SYNTAX DisplayString
    MAX-ACCESS accessible-for-notify
    STATUS current
    DESCRIPTION
        "Parameter 'fromto' in event GBGP.19"
    ::= { gbgpEventObjects19 1 }

gbgp19-RemoteAS OBJECT-TYPE
    SYNTAX DisplayString
    MAX-ACCESS accessible-for-notify
    STATUS current
    DESCRIPTION
        "Parameter 'RemoteAS' in event GBGP.19"
    ::= { gbgpEventObjects19 2 }

gbgp19-code OBJECT-TYPE
    SYNTAX DisplayString
    MAX-ACCESS accessible-for-notify
    STATUS current
    DESCRIPTION
        "Parameter 'code' in event GBGP.19"
    ::= { gbgpEventObjects19 3 }

gbgp19-subcode OBJECT-TYPE
    SYNTAX Integer32
    MAX-ACCESS accessible-for-notify
    STATUS current
    DESCRIPTION
        "Parameter 'subcode' in event GBGP.19"
    ::= { gbgpEventObjects19 4 }

gbgpEventObjects20 OBJECT-IDENTITY
    STATUS current
    DESCRIPTION
        "Event GBGP.20
        Changing state of peer to idled. The cause is printed at the end of
        the message."
    ::= { gbgpEventsGroup 20 }

gbgp20-RemotePeer OBJECT-TYPE
    SYNTAX DisplayString
    MAX-ACCESS accessible-for-notify
    STATUS current
    DESCRIPTION
        "Parameter 'RemotePeer' in event GBGP.20"
    ::= { gbgpEventObjects20 1 }

gbgp20-cause OBJECT-TYPE
    SYNTAX DisplayString
    MAX-ACCESS accessible-for-notify
    STATUS current
    DESCRIPTION
        "Parameter 'cause' in event GBGP.20"
    ::= { gbgpEventObjects20 2 }

gbgpEventObjects22 OBJECT-IDENTITY
    STATUS current
    DESCRIPTION
        "Event GBGP.22
        The error printed occurred while reading the configuration."
    ::= { gbgpEventsGroup 22 }

gbgp22-DiagnosticMessage OBJECT-TYPE
    SYNTAX DisplayString
    MAX-ACCESS accessible-for-notify
    STATUS current
    DESCRIPTION
        "Parameter 'DiagnosticMessage' in event GBGP.22"
    ::= { gbgpEventObjects22 1 }

gbgpEventObjects23 OBJECT-IDENTITY
    STATUS current
    DESCRIPTION
        "Event GBGP.23
        An update packet has been received with community attributes."
    ::= { gbgpEventsGroup 23 }

gbgp23-NumberOfComms OBJECT-TYPE
    SYNTAX Integer32
    MAX-ACCESS accessible-for-notify
    STATUS current
    DESCRIPTION
        "Parameter 'NumberOfComms' in event GBGP.23"
    ::= { gbgpEventObjects23 1 }

gbgp23-Communities OBJECT-TYPE
    SYNTAX DisplayString
    MAX-ACCESS accessible-for-notify
    STATUS current
    DESCRIPTION
        "Parameter 'Communities' in event GBGP.23"
    ::= { gbgpEventObjects23 2 }

gbgpEventObjects24 OBJECT-IDENTITY
    STATUS current
    DESCRIPTION
        "Event GBGP.24
        A route received in an update packet has been discarded due to
        preconfigured route-map in/out policy for this neighbor."
    ::= { gbgpEventsGroup 24 }

gbgp24-RouteDest OBJECT-TYPE
    SYNTAX IpAddress
    MAX-ACCESS accessible-for-notify
    STATUS current
    DESCRIPTION
        "Parameter 'RouteDest' in event GBGP.24"
    ::= { gbgpEventObjects24 1 }

gbgp24-RouteMask OBJECT-TYPE
    SYNTAX IpAddress
    MAX-ACCESS accessible-for-notify
    STATUS current
    DESCRIPTION
        "Parameter 'RouteMask' in event GBGP.24"
    ::= { gbgpEventObjects24 2 }

gbgp24-Route-MapName OBJECT-TYPE
    SYNTAX DisplayString
    MAX-ACCESS accessible-for-notify
    STATUS current
    DESCRIPTION
        "Parameter 'Route-MapName' in event GBGP.24"
    ::= { gbgpEventObjects24 3 }

gbgpEventObjects25 OBJECT-IDENTITY
    STATUS current
    DESCRIPTION
        "Event GBGP.25
        The local pref value of a route received in an update packet
        has been changed due to a preconfigured route-map in/out policy
        for this neighbor."
    ::= { gbgpEventsGroup 25 }

gbgp25-RouteDest OBJECT-TYPE
    SYNTAX IpAddress
    MAX-ACCESS accessible-for-notify
    STATUS current
    DESCRIPTION
        "Parameter 'RouteDest' in event GBGP.25"
    ::= { gbgpEventObjects25 1 }

gbgp25-RouteMask OBJECT-TYPE
    SYNTAX IpAddress
    MAX-ACCESS accessible-for-notify
    STATUS current
    DESCRIPTION
        "Parameter 'RouteMask' in event GBGP.25"
    ::= { gbgpEventObjects25 2 }

gbgp25-OldLocalPref OBJECT-TYPE
    SYNTAX DisplayString
    MAX-ACCESS accessible-for-notify
    STATUS current
    DESCRIPTION
        "Parameter 'OldLocalPref' in event GBGP.25"
    ::= { gbgpEventObjects25 3 }

gbgp25-NewLocalPref OBJECT-TYPE
    SYNTAX DisplayString
    MAX-ACCESS accessible-for-notify
    STATUS current
    DESCRIPTION
        "Parameter 'NewLocalPref' in event GBGP.25"
    ::= { gbgpEventObjects25 4 }

gbgpEventObjects26 OBJECT-IDENTITY
    STATUS current
    DESCRIPTION
        "Event GBGP.26
        Could not apply the route-map policy: max number of communities per
        route exceeded."
    ::= { gbgpEventsGroup 26 }

gbgp26-RouteMapName OBJECT-TYPE
    SYNTAX DisplayString
    MAX-ACCESS accessible-for-notify
    STATUS current
    DESCRIPTION
        "Parameter 'RouteMapName' in event GBGP.26"
    ::= { gbgpEventObjects26 1 }

gbgpEventObjects27 OBJECT-IDENTITY
    STATUS current
    DESCRIPTION
        "Event GBGP.27
        The metric value of a route received in an update packet
        has been changed due to a preconfigured route-map in/out policy
        for this neighbor."
    ::= { gbgpEventsGroup 27 }

gbgp27-RouteDest OBJECT-TYPE
    SYNTAX IpAddress
    MAX-ACCESS accessible-for-notify
    STATUS current
    DESCRIPTION
        "Parameter 'RouteDest' in event GBGP.27"
    ::= { gbgpEventObjects27 1 }

gbgp27-RouteMask OBJECT-TYPE
    SYNTAX IpAddress
    MAX-ACCESS accessible-for-notify
    STATUS current
    DESCRIPTION
        "Parameter 'RouteMask' in event GBGP.27"
    ::= { gbgpEventObjects27 2 }

gbgp27-OldMetric OBJECT-TYPE
    SYNTAX DisplayString
    MAX-ACCESS accessible-for-notify
    STATUS current
    DESCRIPTION
        "Parameter 'OldMetric' in event GBGP.27"
    ::= { gbgpEventObjects27 3 }

gbgp27-NewMetric OBJECT-TYPE
    SYNTAX DisplayString
    MAX-ACCESS accessible-for-notify
    STATUS current
    DESCRIPTION
        "Parameter 'NewMetric' in event GBGP.27"
    ::= { gbgpEventObjects27 4 }

gbgpEventObjects28 OBJECT-IDENTITY
    STATUS current
    DESCRIPTION
        "Event GBGP.28
        The status of the specified peer has changed from a higher
        numbered status to a lower numbered status."
    ::= { gbgpEventsGroup 28 }

gbgp28-RemotePeerAddress OBJECT-TYPE
    SYNTAX IpAddress
    MAX-ACCESS accessible-for-notify
    STATUS current
    DESCRIPTION
        "Parameter 'RemotePeerAddress' in event GBGP.28"
    ::= { gbgpEventObjects28 1 }

gbgp28-AutonomousSystem OBJECT-TYPE
    SYNTAX Integer32
    MAX-ACCESS accessible-for-notify
    STATUS current
    DESCRIPTION
        "Parameter 'AutonomousSystem' in event GBGP.28"
    ::= { gbgpEventObjects28 2 }

gbgpEventObjects29 OBJECT-IDENTITY
    STATUS current
    DESCRIPTION
        "Event GBGP.29
        A connection to a ESTABLISHED BGP peer has been lost. Possible causes
        are either a keepalive timer timeout or a TCP protocol error. The status
        of this peer is changed to ACTIVE."
    ::= { gbgpEventsGroup 29 }

gbgp29-RemotePeerAddress OBJECT-TYPE
    SYNTAX DisplayString
    MAX-ACCESS accessible-for-notify
    STATUS current
    DESCRIPTION
        "Parameter 'RemotePeerAddress' in event GBGP.29"
    ::= { gbgpEventObjects29 1 }

gbgp29-AutonomousSystem OBJECT-TYPE
    SYNTAX Integer32
    MAX-ACCESS accessible-for-notify
    STATUS current
    DESCRIPTION
        "Parameter 'AutonomousSystem' in event GBGP.29"
    ::= { gbgpEventObjects29 2 }

gbgpEventObjects30 OBJECT-IDENTITY
    STATUS current
    DESCRIPTION
        "Event GBGP.30
        A valid incoming BGP message has been received from a peer.
        The type of message is shown, as well as the remote peer address and
        autonomous system."
    ::= { gbgpEventsGroup 30 }

gbgp30-PacketType OBJECT-TYPE
    SYNTAX DisplayString
    MAX-ACCESS accessible-for-notify
    STATUS current
    DESCRIPTION
        "Parameter 'PacketType' in event GBGP.30"
    ::= { gbgpEventObjects30 1 }

gbgp30-RemotePeerAddress OBJECT-TYPE
    SYNTAX DisplayString
    MAX-ACCESS accessible-for-notify
    STATUS current
    DESCRIPTION
        "Parameter 'RemotePeerAddress' in event GBGP.30"
    ::= { gbgpEventObjects30 2 }

gbgp30-AutonomousSystem OBJECT-TYPE
    SYNTAX Integer32
    MAX-ACCESS accessible-for-notify
    STATUS current
    DESCRIPTION
        "Parameter 'AutonomousSystem' in event GBGP.30"
    ::= { gbgpEventObjects30 3 }

gbgpEventObjects31 OBJECT-IDENTITY
    STATUS current
    DESCRIPTION
        "Event GBGP.31
        A message is been sent to a remote peer.
        The type of message is shown, as well as the remote peer address and
        autonomous system."
    ::= { gbgpEventsGroup 31 }

gbgp31-PacketType OBJECT-TYPE
    SYNTAX DisplayString
    MAX-ACCESS accessible-for-notify
    STATUS current
    DESCRIPTION
        "Parameter 'PacketType' in event GBGP.31"
    ::= { gbgpEventObjects31 1 }

gbgp31-RemotePeerAddress OBJECT-TYPE
    SYNTAX DisplayString
    MAX-ACCESS accessible-for-notify
    STATUS current
    DESCRIPTION
        "Parameter 'RemotePeerAddress' in event GBGP.31"
    ::= { gbgpEventObjects31 2 }

gbgp31-AutonomousSystem OBJECT-TYPE
    SYNTAX Integer32
    MAX-ACCESS accessible-for-notify
    STATUS current
    DESCRIPTION
        "Parameter 'AutonomousSystem' in event GBGP.31"
    ::= { gbgpEventObjects31 3 }

gbgpEventObjects32 OBJECT-IDENTITY
    STATUS current
    DESCRIPTION
        "Event GBGP.32
        A valid connection has been made to a configured BGP peer. Peer status
        is changed to ESTABLISHED."
    ::= { gbgpEventsGroup 32 }

gbgp32-RemotePeerAddress OBJECT-TYPE
    SYNTAX DisplayString
    MAX-ACCESS accessible-for-notify
    STATUS current
    DESCRIPTION
        "Parameter 'RemotePeerAddress' in event GBGP.32"
    ::= { gbgpEventObjects32 1 }

gbgp32-AutonomousSystem OBJECT-TYPE
    SYNTAX Integer32
    MAX-ACCESS accessible-for-notify
    STATUS current
    DESCRIPTION
        "Parameter 'AutonomousSystem' in event GBGP.32"
    ::= { gbgpEventObjects32 2 }

gbgpEventObjects33 OBJECT-IDENTITY
    STATUS current
    DESCRIPTION
        "Event GBGP.33
        An update message for the route shown has been received. This message
        does not mean that this route has been made active, it just means that
        the system has received information for this route from a BGP peer. This
        route will be processed, and, taking into account the
        configured preference rules, will be or not exported to the active
        routes table. To be able to see changes in the active RT, please
        use the IPv6 subsystem events."
    ::= { gbgpEventsGroup 33 }

gbgp33-RouteDest OBJECT-TYPE
    SYNTAX DisplayString
    MAX-ACCESS accessible-for-notify
    STATUS current
    DESCRIPTION
        "Parameter 'RouteDest' in event GBGP.33"
    ::= { gbgpEventObjects33 1 }

gbgp33-RoutePrefixLen OBJECT-TYPE
    SYNTAX Integer32
    MAX-ACCESS accessible-for-notify
    STATUS current
    DESCRIPTION
        "Parameter 'RoutePrefixLen' in event GBGP.33"
    ::= { gbgpEventObjects33 2 }

gbgp33-NextHop OBJECT-TYPE
    SYNTAX DisplayString
    MAX-ACCESS accessible-for-notify
    STATUS current
    DESCRIPTION
        "Parameter 'NextHop' in event GBGP.33"
    ::= { gbgpEventObjects33 3 }

gbgp33-Preference OBJECT-TYPE
    SYNTAX Integer32
    MAX-ACCESS accessible-for-notify
    STATUS current
    DESCRIPTION
        "Parameter 'Preference' in event GBGP.33"
    ::= { gbgpEventObjects33 4 }

gbgp33-Metric OBJECT-TYPE
    SYNTAX DisplayString
    MAX-ACCESS accessible-for-notify
    STATUS current
    DESCRIPTION
        "Parameter 'Metric' in event GBGP.33"
    ::= { gbgpEventObjects33 5 }

gbgp33-LocalPref OBJECT-TYPE
    SYNTAX DisplayString
    MAX-ACCESS accessible-for-notify
    STATUS current
    DESCRIPTION
        "Parameter 'LocalPref' in event GBGP.33"
    ::= { gbgpEventObjects33 6 }

gbgpEventObjects34 OBJECT-IDENTITY
    STATUS current
    DESCRIPTION
        "Event GBGP.34
        An update message for the route shown has been received. This message
        does not mean that this route has been made active, it just means that
        the system has received information for this route from a BGP peer. This
        route will be processed, and, taking into account the
        configured preference rules, will be or not exported to the active
        routes table. To be able to see changes in the active RT, please
        use the IPv6 subsystem events."
    ::= { gbgpEventsGroup 34 }

gbgp34-RouteDest OBJECT-TYPE
    SYNTAX DisplayString
    MAX-ACCESS accessible-for-notify
    STATUS current
    DESCRIPTION
        "Parameter 'RouteDest' in event GBGP.34"
    ::= { gbgpEventObjects34 1 }

gbgp34-RoutePrefixLen OBJECT-TYPE
    SYNTAX Integer32
    MAX-ACCESS accessible-for-notify
    STATUS current
    DESCRIPTION
        "Parameter 'RoutePrefixLen' in event GBGP.34"
    ::= { gbgpEventObjects34 2 }

gbgp34-NextHop OBJECT-TYPE
    SYNTAX DisplayString
    MAX-ACCESS accessible-for-notify
    STATUS current
    DESCRIPTION
        "Parameter 'NextHop' in event GBGP.34"
    ::= { gbgpEventObjects34 3 }

gbgp34-NextHopLocal OBJECT-TYPE
    SYNTAX DisplayString
    MAX-ACCESS accessible-for-notify
    STATUS current
    DESCRIPTION
        "Parameter 'NextHopLocal' in event GBGP.34"
    ::= { gbgpEventObjects34 4 }

gbgp34-Preference OBJECT-TYPE
    SYNTAX Integer32
    MAX-ACCESS accessible-for-notify
    STATUS current
    DESCRIPTION
        "Parameter 'Preference' in event GBGP.34"
    ::= { gbgpEventObjects34 5 }

gbgp34-Metric OBJECT-TYPE
    SYNTAX DisplayString
    MAX-ACCESS accessible-for-notify
    STATUS current
    DESCRIPTION
        "Parameter 'Metric' in event GBGP.34"
    ::= { gbgpEventObjects34 6 }

gbgp34-LocalPref OBJECT-TYPE
    SYNTAX DisplayString
    MAX-ACCESS accessible-for-notify
    STATUS current
    DESCRIPTION
        "Parameter 'LocalPref' in event GBGP.34"
    ::= { gbgpEventObjects34 7 }

gbgpEventObjects35 OBJECT-IDENTITY
    STATUS current
    DESCRIPTION
        "Event GBGP.35
        An unreach message has been received for this route. This message
        does not mean that this route will be deleted from the active RT
        (it is possible that the route was not even made active when it
        was received). To be able to see changes in the active RT, please
        use the IPv6 subsystem events."
    ::= { gbgpEventsGroup 35 }

gbgp35-RouteDest OBJECT-TYPE
    SYNTAX DisplayString
    MAX-ACCESS accessible-for-notify
    STATUS current
    DESCRIPTION
        "Parameter 'RouteDest' in event GBGP.35"
    ::= { gbgpEventObjects35 1 }

gbgp35-RoutePrefixLen OBJECT-TYPE
    SYNTAX Integer32
    MAX-ACCESS accessible-for-notify
    STATUS current
    DESCRIPTION
        "Parameter 'RoutePrefixLen' in event GBGP.35"
    ::= { gbgpEventObjects35 2 }

gbgp35-BGPPeer OBJECT-TYPE
    SYNTAX DisplayString
    MAX-ACCESS accessible-for-notify
    STATUS current
    DESCRIPTION
        "Parameter 'BGPPeer' in event GBGP.35"
    ::= { gbgpEventObjects35 3 }

gbgpEventObjects36 OBJECT-IDENTITY
    STATUS current
    DESCRIPTION
        "Event GBGP.36
        The holdtime for a given BGP peer has expired."
    ::= { gbgpEventsGroup 36 }

gbgp36-RemotePeerAddress OBJECT-TYPE
    SYNTAX DisplayString
    MAX-ACCESS accessible-for-notify
    STATUS current
    DESCRIPTION
        "Parameter 'RemotePeerAddress' in event GBGP.36"
    ::= { gbgpEventObjects36 1 }

gbgp36-AutonomousSystem OBJECT-TYPE
    SYNTAX Integer32
    MAX-ACCESS accessible-for-notify
    STATUS current
    DESCRIPTION
        "Parameter 'AutonomousSystem' in event GBGP.36"
    ::= { gbgpEventObjects36 2 }

gbgpEventObjects37 OBJECT-IDENTITY
    STATUS current
    DESCRIPTION
        "Event GBGP.37
        Adding route into BGP routing Database."
    ::= { gbgpEventsGroup 37 }

gbgp37-Dest OBJECT-TYPE
    SYNTAX DisplayString
    MAX-ACCESS accessible-for-notify
    STATUS current
    DESCRIPTION
        "Parameter 'Dest' in event GBGP.37"
    ::= { gbgpEventObjects37 1 }

gbgp37-PrefixLen OBJECT-TYPE
    SYNTAX Integer32
    MAX-ACCESS accessible-for-notify
    STATUS current
    DESCRIPTION
        "Parameter 'PrefixLen' in event GBGP.37"
    ::= { gbgpEventObjects37 2 }

gbgp37-NextHop OBJECT-TYPE
    SYNTAX DisplayString
    MAX-ACCESS accessible-for-notify
    STATUS current
    DESCRIPTION
        "Parameter 'NextHop' in event GBGP.37"
    ::= { gbgpEventObjects37 3 }

gbgpEventObjects38 OBJECT-IDENTITY
    STATUS current
    DESCRIPTION
        "Event GBGP.38
        Adding direct route to BGP routing Database."
    ::= { gbgpEventsGroup 38 }

gbgp38-Dest OBJECT-TYPE
    SYNTAX DisplayString
    MAX-ACCESS accessible-for-notify
    STATUS current
    DESCRIPTION
        "Parameter 'Dest' in event GBGP.38"
    ::= { gbgpEventObjects38 1 }

gbgp38-PrefixLen OBJECT-TYPE
    SYNTAX Integer32
    MAX-ACCESS accessible-for-notify
    STATUS current
    DESCRIPTION
        "Parameter 'PrefixLen' in event GBGP.38"
    ::= { gbgpEventObjects38 2 }

gbgpEventObjects39 OBJECT-IDENTITY
    STATUS current
    DESCRIPTION
        "Event GBGP.39
        A route received in an update packet has been discarded due to
        preconfigured route-map in/out policy for this neighbor."
    ::= { gbgpEventsGroup 39 }

gbgp39-RouteDest OBJECT-TYPE
    SYNTAX DisplayString
    MAX-ACCESS accessible-for-notify
    STATUS current
    DESCRIPTION
        "Parameter 'RouteDest' in event GBGP.39"
    ::= { gbgpEventObjects39 1 }

gbgp39-RoutePrefixLen OBJECT-TYPE
    SYNTAX Integer32
    MAX-ACCESS accessible-for-notify
    STATUS current
    DESCRIPTION
        "Parameter 'RoutePrefixLen' in event GBGP.39"
    ::= { gbgpEventObjects39 2 }

gbgp39-Route-MapName OBJECT-TYPE
    SYNTAX DisplayString
    MAX-ACCESS accessible-for-notify
    STATUS current
    DESCRIPTION
        "Parameter 'Route-MapName' in event GBGP.39"
    ::= { gbgpEventObjects39 3 }

gbgpEventObjects40 OBJECT-IDENTITY
    STATUS current
    DESCRIPTION
        "Event GBGP.40
        The local pref value of a route received in an update packet
        has been changed due to a preconfigured route-map in/out policy
        for this neighbor."
    ::= { gbgpEventsGroup 40 }

gbgp40-RouteDest OBJECT-TYPE
    SYNTAX DisplayString
    MAX-ACCESS accessible-for-notify
    STATUS current
    DESCRIPTION
        "Parameter 'RouteDest' in event GBGP.40"
    ::= { gbgpEventObjects40 1 }

gbgp40-RoutePrefixLen OBJECT-TYPE
    SYNTAX Integer32
    MAX-ACCESS accessible-for-notify
    STATUS current
    DESCRIPTION
        "Parameter 'RoutePrefixLen' in event GBGP.40"
    ::= { gbgpEventObjects40 2 }

gbgp40-OldLocalPref OBJECT-TYPE
    SYNTAX DisplayString
    MAX-ACCESS accessible-for-notify
    STATUS current
    DESCRIPTION
        "Parameter 'OldLocalPref' in event GBGP.40"
    ::= { gbgpEventObjects40 3 }

gbgp40-NewLocalPref OBJECT-TYPE
    SYNTAX DisplayString
    MAX-ACCESS accessible-for-notify
    STATUS current
    DESCRIPTION
        "Parameter 'NewLocalPref' in event GBGP.40"
    ::= { gbgpEventObjects40 4 }

gbgpEventObjects41 OBJECT-IDENTITY
    STATUS current
    DESCRIPTION
        "Event GBGP.41
        The metric value of a route received in an update packet
        has been changed due to a preconfigured route-map in/out policy
        for this neighbor."
    ::= { gbgpEventsGroup 41 }

gbgp41-RouteDest OBJECT-TYPE
    SYNTAX DisplayString
    MAX-ACCESS accessible-for-notify
    STATUS current
    DESCRIPTION
        "Parameter 'RouteDest' in event GBGP.41"
    ::= { gbgpEventObjects41 1 }

gbgp41-RoutePrefixLen OBJECT-TYPE
    SYNTAX Integer32
    MAX-ACCESS accessible-for-notify
    STATUS current
    DESCRIPTION
        "Parameter 'RoutePrefixLen' in event GBGP.41"
    ::= { gbgpEventObjects41 2 }

gbgp41-OldMetric OBJECT-TYPE
    SYNTAX DisplayString
    MAX-ACCESS accessible-for-notify
    STATUS current
    DESCRIPTION
        "Parameter 'OldMetric' in event GBGP.41"
    ::= { gbgpEventObjects41 3 }

gbgp41-NewMetric OBJECT-TYPE
    SYNTAX DisplayString
    MAX-ACCESS accessible-for-notify
    STATUS current
    DESCRIPTION
        "Parameter 'NewMetric' in event GBGP.41"
    ::= { gbgpEventObjects41 4 }

gbgpEventObjects42 OBJECT-IDENTITY
    STATUS current
    DESCRIPTION
        "Event GBGP.42
        The nexthop value of a route received in an update packet
        has been changed due to a preconfigured route-map in/out policy
        for this neighbor."
    ::= { gbgpEventsGroup 42 }

gbgp42-RouteDest OBJECT-TYPE
    SYNTAX DisplayString
    MAX-ACCESS accessible-for-notify
    STATUS current
    DESCRIPTION
        "Parameter 'RouteDest' in event GBGP.42"
    ::= { gbgpEventObjects42 1 }

gbgp42-RoutePrefixLen OBJECT-TYPE
    SYNTAX Integer32
    MAX-ACCESS accessible-for-notify
    STATUS current
    DESCRIPTION
        "Parameter 'RoutePrefixLen' in event GBGP.42"
    ::= { gbgpEventObjects42 2 }

gbgp42-OldNexthop OBJECT-TYPE
    SYNTAX DisplayString
    MAX-ACCESS accessible-for-notify
    STATUS current
    DESCRIPTION
        "Parameter 'OldNexthop' in event GBGP.42"
    ::= { gbgpEventObjects42 3 }

gbgp42-NewNexthop OBJECT-TYPE
    SYNTAX DisplayString
    MAX-ACCESS accessible-for-notify
    STATUS current
    DESCRIPTION
        "Parameter 'NewNexthop' in event GBGP.42"
    ::= { gbgpEventObjects42 4 }

gbgp42-rtmapinout OBJECT-TYPE
    SYNTAX DisplayString
    MAX-ACCESS accessible-for-notify
    STATUS current
    DESCRIPTION
        "Parameter 'rtmapinout' in event GBGP.42"
    ::= { gbgpEventObjects42 5 }

gbgpEventObjects43 OBJECT-IDENTITY
    STATUS current
    DESCRIPTION
        "Event GBGP.43
        The nexthop value of a route transmitted in an update packet
        has been set due to a preconfigured route-map in/out policy
        for this neighbor."
    ::= { gbgpEventsGroup 43 }

gbgp43-RouteDest OBJECT-TYPE
    SYNTAX DisplayString
    MAX-ACCESS accessible-for-notify
    STATUS current
    DESCRIPTION
        "Parameter 'RouteDest' in event GBGP.43"
    ::= { gbgpEventObjects43 1 }

gbgp43-RoutePrefixLen OBJECT-TYPE
    SYNTAX Integer32
    MAX-ACCESS accessible-for-notify
    STATUS current
    DESCRIPTION
        "Parameter 'RoutePrefixLen' in event GBGP.43"
    ::= { gbgpEventObjects43 2 }

gbgp43-NewNexthop OBJECT-TYPE
    SYNTAX DisplayString
    MAX-ACCESS accessible-for-notify
    STATUS current
    DESCRIPTION
        "Parameter 'NewNexthop' in event GBGP.43"
    ::= { gbgpEventObjects43 3 }

gbgp43-rtmapinout OBJECT-TYPE
    SYNTAX DisplayString
    MAX-ACCESS accessible-for-notify
    STATUS current
    DESCRIPTION
        "Parameter 'rtmapinout' in event GBGP.43"
    ::= { gbgpEventObjects43 4 }

gbgpEventObjects44 OBJECT-IDENTITY
    STATUS current
    DESCRIPTION
        "Event GBGP.44
        The nexthop value of a route received in an update packet
        has been changed due to a preconfigured route-map in/out policy
        for this neighbor."
    ::= { gbgpEventsGroup 44 }

gbgp44-RouteDest OBJECT-TYPE
    SYNTAX DisplayString
    MAX-ACCESS accessible-for-notify
    STATUS current
    DESCRIPTION
        "Parameter 'RouteDest' in event GBGP.44"
    ::= { gbgpEventObjects44 1 }

gbgp44-RouteMask OBJECT-TYPE
    SYNTAX DisplayString
    MAX-ACCESS accessible-for-notify
    STATUS current
    DESCRIPTION
        "Parameter 'RouteMask' in event GBGP.44"
    ::= { gbgpEventObjects44 2 }

gbgp44-OldNexthop OBJECT-TYPE
    SYNTAX DisplayString
    MAX-ACCESS accessible-for-notify
    STATUS current
    DESCRIPTION
        "Parameter 'OldNexthop' in event GBGP.44"
    ::= { gbgpEventObjects44 3 }

gbgp44-NewNexthop OBJECT-TYPE
    SYNTAX DisplayString
    MAX-ACCESS accessible-for-notify
    STATUS current
    DESCRIPTION
        "Parameter 'NewNexthop' in event GBGP.44"
    ::= { gbgpEventObjects44 4 }

gbgp44-rtmapinout OBJECT-TYPE
    SYNTAX DisplayString
    MAX-ACCESS accessible-for-notify
    STATUS current
    DESCRIPTION
        "Parameter 'rtmapinout' in event GBGP.44"
    ::= { gbgpEventObjects44 5 }

gbgpEventObjects45 OBJECT-IDENTITY
    STATUS current
    DESCRIPTION
        "Event GBGP.45
        The nexthop value of a route transmitted in an update packet
        has been set due to a preconfigured route-map in/out policy
        for this neighbor."
    ::= { gbgpEventsGroup 45 }

gbgp45-RouteDest OBJECT-TYPE
    SYNTAX DisplayString
    MAX-ACCESS accessible-for-notify
    STATUS current
    DESCRIPTION
        "Parameter 'RouteDest' in event GBGP.45"
    ::= { gbgpEventObjects45 1 }

gbgp45-RouteMask OBJECT-TYPE
    SYNTAX DisplayString
    MAX-ACCESS accessible-for-notify
    STATUS current
    DESCRIPTION
        "Parameter 'RouteMask' in event GBGP.45"
    ::= { gbgpEventObjects45 2 }

gbgp45-NewNexthop OBJECT-TYPE
    SYNTAX DisplayString
    MAX-ACCESS accessible-for-notify
    STATUS current
    DESCRIPTION
        "Parameter 'NewNexthop' in event GBGP.45"
    ::= { gbgpEventObjects45 3 }

gbgp45-rtmapinout OBJECT-TYPE
    SYNTAX DisplayString
    MAX-ACCESS accessible-for-notify
    STATUS current
    DESCRIPTION
        "Parameter 'rtmapinout' in event GBGP.45"
    ::= { gbgpEventObjects45 4 }

gbgpEventObjects46 OBJECT-IDENTITY
    STATUS current
    DESCRIPTION
        "Event GBGP.46
        The status of the specified peer has changed from a higher
        numbered status to a lower numbered status."
    ::= { gbgpEventsGroup 46 }

gbgp46-RemotePeerAddress OBJECT-TYPE
    SYNTAX DisplayString
    MAX-ACCESS accessible-for-notify
    STATUS current
    DESCRIPTION
        "Parameter 'RemotePeerAddress' in event GBGP.46"
    ::= { gbgpEventObjects46 1 }

gbgp46-AutonomousSystem OBJECT-TYPE
    SYNTAX Integer32
    MAX-ACCESS accessible-for-notify
    STATUS current
    DESCRIPTION
        "Parameter 'AutonomousSystem' in event GBGP.46"
    ::= { gbgpEventObjects46 2 }

gbgpEventObjects47 OBJECT-IDENTITY
    STATUS current
    DESCRIPTION
        "Event GBGP.47
        The update received contains an invalid field."
    ::= { gbgpEventsGroup 47 }

gbgp47-Error-msg OBJECT-TYPE
    SYNTAX DisplayString
    MAX-ACCESS accessible-for-notify
    STATUS current
    DESCRIPTION
        "Parameter 'Error-msg' in event GBGP.47"
    ::= { gbgpEventObjects47 1 }

gbgp47-RemotePeerAddress OBJECT-TYPE
    SYNTAX DisplayString
    MAX-ACCESS accessible-for-notify
    STATUS current
    DESCRIPTION
        "Parameter 'RemotePeerAddress' in event GBGP.47"
    ::= { gbgpEventObjects47 2 }

gbgp47-AutonomousSystem OBJECT-TYPE
    SYNTAX Integer32
    MAX-ACCESS accessible-for-notify
    STATUS current
    DESCRIPTION
        "Parameter 'AutonomousSystem' in event GBGP.47"
    ::= { gbgpEventObjects47 3 }

gbgpEventObjects48 OBJECT-IDENTITY
    STATUS current
    DESCRIPTION
        "Event GBGP.48
        Received an open msg with an optional parameter."
    ::= { gbgpEventsGroup 48 }

gbgp48-opt-param OBJECT-TYPE
    SYNTAX Integer32
    MAX-ACCESS accessible-for-notify
    STATUS current
    DESCRIPTION
        "Parameter 'opt-param' in event GBGP.48"
    ::= { gbgpEventObjects48 1 }

gbgp48-opt-param-str OBJECT-TYPE
    SYNTAX DisplayString
    MAX-ACCESS accessible-for-notify
    STATUS current
    DESCRIPTION
        "Parameter 'opt-param-str' in event GBGP.48"
    ::= { gbgpEventObjects48 2 }

gbgp48-RemotePeerAddress OBJECT-TYPE
    SYNTAX DisplayString
    MAX-ACCESS accessible-for-notify
    STATUS current
    DESCRIPTION
        "Parameter 'RemotePeerAddress' in event GBGP.48"
    ::= { gbgpEventObjects48 3 }

gbgpEventObjects49 OBJECT-IDENTITY
    STATUS current
    DESCRIPTION
        "Event GBGP.49
        Received an open msg with capability in the optional paramater."
    ::= { gbgpEventsGroup 49 }

gbgp49-capab-code OBJECT-TYPE
    SYNTAX Integer32
    MAX-ACCESS accessible-for-notify
    STATUS current
    DESCRIPTION
        "Parameter 'capab-code' in event GBGP.49"
    ::= { gbgpEventObjects49 1 }

gbgp49-capab-len OBJECT-TYPE
    SYNTAX Integer32
    MAX-ACCESS accessible-for-notify
    STATUS current
    DESCRIPTION
        "Parameter 'capab-len' in event GBGP.49"
    ::= { gbgpEventObjects49 2 }

gbgp49-RemotePeerAddress OBJECT-TYPE
    SYNTAX DisplayString
    MAX-ACCESS accessible-for-notify
    STATUS current
    DESCRIPTION
        "Parameter 'RemotePeerAddress' in event GBGP.49"
    ::= { gbgpEventObjects49 3 }

gbgpEventObjects50 OBJECT-IDENTITY
    STATUS current
    DESCRIPTION
        "Event GBGP.50
        Received an open msg with MP-EXT capability."
    ::= { gbgpEventsGroup 50 }

gbgp50-afi OBJECT-TYPE
    SYNTAX Integer32
    MAX-ACCESS accessible-for-notify
    STATUS current
    DESCRIPTION
        "Parameter 'afi' in event GBGP.50"
    ::= { gbgpEventObjects50 1 }

gbgp50-safi OBJECT-TYPE
    SYNTAX Integer32
    MAX-ACCESS accessible-for-notify
    STATUS current
    DESCRIPTION
        "Parameter 'safi' in event GBGP.50"
    ::= { gbgpEventObjects50 2 }

gbgp50-RemotePeerAddress OBJECT-TYPE
    SYNTAX DisplayString
    MAX-ACCESS accessible-for-notify
    STATUS current
    DESCRIPTION
        "Parameter 'RemotePeerAddress' in event GBGP.50"
    ::= { gbgpEventObjects50 3 }

gbgpEventObjects51 OBJECT-IDENTITY
    STATUS current
    DESCRIPTION
        "Event GBGP.51
        Received an open msg with an unsupported capability (ignoring)."
    ::= { gbgpEventsGroup 51 }

gbgp51-capab-code OBJECT-TYPE
    SYNTAX Integer32
    MAX-ACCESS accessible-for-notify
    STATUS current
    DESCRIPTION
        "Parameter 'capab-code' in event GBGP.51"
    ::= { gbgpEventObjects51 1 }

gbgp51-RemotePeerAddress OBJECT-TYPE
    SYNTAX DisplayString
    MAX-ACCESS accessible-for-notify
    STATUS current
    DESCRIPTION
        "Parameter 'RemotePeerAddress' in event GBGP.51"
    ::= { gbgpEventObjects51 2 }

gbgpEventObjects52 OBJECT-IDENTITY
    STATUS current
    DESCRIPTION
        "Event GBGP.52
        When a route is received, there are four posible actions: install (ins),
        remove (rem), discard (dis) or idle (idl).
        - install : the route is installed in the BGP table and marked as usable
        (the preference is a positive integer).
        - remove : the route will be removed from the BGP table if already exists.
        - discard : the route won't be installed in the BGP table.
        - idle : the route will never be usable (the preference is a negative
        integer).
        Along with each action, an informative message is shown. If everything
        goes well, the message is 'ok'. Otherwise, a descriptive message will
        explain the cause of the error."
    ::= { gbgpEventsGroup 52 }

gbgp52-Action OBJECT-TYPE
    SYNTAX DisplayString
    MAX-ACCESS accessible-for-notify
    STATUS current
    DESCRIPTION
        "Parameter 'Action' in event GBGP.52"
    ::= { gbgpEventObjects52 1 }

gbgp52-Prefix OBJECT-TYPE
    SYNTAX DisplayString
    MAX-ACCESS accessible-for-notify
    STATUS current
    DESCRIPTION
        "Parameter 'Prefix' in event GBGP.52"
    ::= { gbgpEventObjects52 2 }

gbgp52-PrefixLen OBJECT-TYPE
    SYNTAX Integer32
    MAX-ACCESS accessible-for-notify
    STATUS current
    DESCRIPTION
        "Parameter 'PrefixLen' in event GBGP.52"
    ::= { gbgpEventObjects52 3 }

gbgp52-Information OBJECT-TYPE
    SYNTAX DisplayString
    MAX-ACCESS accessible-for-notify
    STATUS current
    DESCRIPTION
        "Parameter 'Information' in event GBGP.52"
    ::= { gbgpEventObjects52 4 }

gbgp52-Origin OBJECT-TYPE
    SYNTAX DisplayString
    MAX-ACCESS accessible-for-notify
    STATUS current
    DESCRIPTION
        "Parameter 'Origin' in event GBGP.52"
    ::= { gbgpEventObjects52 5 }

gbgpEventObjects53 OBJECT-IDENTITY
    STATUS current
    DESCRIPTION
        "Event GBGP.53
        Data has been received from the specified peer. The received data is
        shown in hexadecimal."
    ::= { gbgpEventsGroup 53 }

gbgp53-RemotePeerName OBJECT-TYPE
    SYNTAX DisplayString
    MAX-ACCESS accessible-for-notify
    STATUS current
    DESCRIPTION
        "Parameter 'RemotePeerName' in event GBGP.53"
    ::= { gbgpEventObjects53 1 }

gbgp53-DataHexDump OBJECT-TYPE
    SYNTAX DisplayString
    MAX-ACCESS accessible-for-notify
    STATUS current
    DESCRIPTION
        "Parameter 'DataHexDump' in event GBGP.53"
    ::= { gbgpEventObjects53 2 }

gbgpEventObjects54 OBJECT-IDENTITY
    STATUS current
    DESCRIPTION
        "Event GBGP.54
        An invalid message has been received from the specified peer. The
        received message data is shown in hexadecimal."
    ::= { gbgpEventsGroup 54 }

gbgp54-RemotePeerName OBJECT-TYPE
    SYNTAX DisplayString
    MAX-ACCESS accessible-for-notify
    STATUS current
    DESCRIPTION
        "Parameter 'RemotePeerName' in event GBGP.54"
    ::= { gbgpEventObjects54 1 }

gbgp54-DataHexDump OBJECT-TYPE
    SYNTAX DisplayString
    MAX-ACCESS accessible-for-notify
    STATUS current
    DESCRIPTION
        "Parameter 'DataHexDump' in event GBGP.54"
    ::= { gbgpEventObjects54 2 }

gbgpEventObjects55 OBJECT-IDENTITY
    STATUS current
    DESCRIPTION
        "Event GBGP.55
        A message has been received from the specified peer. The received
        message data is shown in hexadecimal."
    ::= { gbgpEventsGroup 55 }

gbgp55-RemotePeerName OBJECT-TYPE
    SYNTAX DisplayString
    MAX-ACCESS accessible-for-notify
    STATUS current
    DESCRIPTION
        "Parameter 'RemotePeerName' in event GBGP.55"
    ::= { gbgpEventObjects55 1 }

gbgp55-DataHexDump OBJECT-TYPE
    SYNTAX DisplayString
    MAX-ACCESS accessible-for-notify
    STATUS current
    DESCRIPTION
        "Parameter 'DataHexDump' in event GBGP.55"
    ::= { gbgpEventObjects55 2 }

gbgpEventObjects56 OBJECT-IDENTITY
    STATUS current
    DESCRIPTION
        "Event GBGP.56
        A message is sent to the specified peer. The message data is shown in
        hexadecimal."
    ::= { gbgpEventsGroup 56 }

gbgp56-RemotePeerName OBJECT-TYPE
    SYNTAX DisplayString
    MAX-ACCESS accessible-for-notify
    STATUS current
    DESCRIPTION
        "Parameter 'RemotePeerName' in event GBGP.56"
    ::= { gbgpEventObjects56 1 }

gbgp56-DataHexDump OBJECT-TYPE
    SYNTAX DisplayString
    MAX-ACCESS accessible-for-notify
    STATUS current
    DESCRIPTION
        "Parameter 'DataHexDump' in event GBGP.56"
    ::= { gbgpEventObjects56 2 }

gbgpEventObjects57 OBJECT-IDENTITY
    STATUS current
    DESCRIPTION
        "Event GBGP.57
        Data has been sent to the specified peer. The data is shown in
        hexadecimal."
    ::= { gbgpEventsGroup 57 }

gbgp57-RemotePeerName OBJECT-TYPE
    SYNTAX DisplayString
    MAX-ACCESS accessible-for-notify
    STATUS current
    DESCRIPTION
        "Parameter 'RemotePeerName' in event GBGP.57"
    ::= { gbgpEventObjects57 1 }

gbgp57-DataHexDump OBJECT-TYPE
    SYNTAX DisplayString
    MAX-ACCESS accessible-for-notify
    STATUS current
    DESCRIPTION
        "Parameter 'DataHexDump' in event GBGP.57"
    ::= { gbgpEventObjects57 2 }

gbgpEventObjects58 OBJECT-IDENTITY
    STATUS current
    DESCRIPTION
        "Event GBGP.58
        Received an open message without Multiprotocol Extensions Capability for
        an AFI/SAFI which is needed to operate."
    ::= { gbgpEventsGroup 58 }

gbgp58-afi OBJECT-TYPE
    SYNTAX DisplayString
    MAX-ACCESS accessible-for-notify
    STATUS current
    DESCRIPTION
        "Parameter 'afi' in event GBGP.58"
    ::= { gbgpEventObjects58 1 }

gbgp58-safi OBJECT-TYPE
    SYNTAX DisplayString
    MAX-ACCESS accessible-for-notify
    STATUS current
    DESCRIPTION
        "Parameter 'safi' in event GBGP.58"
    ::= { gbgpEventObjects58 2 }

gbgp58-RemotePeerAddress OBJECT-TYPE
    SYNTAX DisplayString
    MAX-ACCESS accessible-for-notify
    STATUS current
    DESCRIPTION
        "Parameter 'RemotePeerAddress' in event GBGP.58"
    ::= { gbgpEventObjects58 3 }

gbgpEventObjects59 OBJECT-IDENTITY
    STATUS current
    DESCRIPTION
        "Event GBGP.59
        Received an open message with Graceful Restart Capability. The Restart
        Flags and Restart Time values are shown."
    ::= { gbgpEventsGroup 59 }

gbgp59-restart-flags OBJECT-TYPE
    SYNTAX Integer32
    MAX-ACCESS accessible-for-notify
    STATUS current
    DESCRIPTION
        "Parameter 'restart-flags' in event GBGP.59"
    ::= { gbgpEventObjects59 1 }

gbgp59-restart-time OBJECT-TYPE
    SYNTAX Integer32
    MAX-ACCESS accessible-for-notify
    STATUS current
    DESCRIPTION
        "Parameter 'restart-time' in event GBGP.59"
    ::= { gbgpEventObjects59 2 }

gbgp59-RemotePeerAddress OBJECT-TYPE
    SYNTAX DisplayString
    MAX-ACCESS accessible-for-notify
    STATUS current
    DESCRIPTION
        "Parameter 'RemotePeerAddress' in event GBGP.59"
    ::= { gbgpEventObjects59 3 }

gbgpEventObjects60 OBJECT-IDENTITY
    STATUS current
    DESCRIPTION
        "Event GBGP.60
        Received an open message with Graceful Restart Capability, with the
        Address Family specified by the afi/safi pair. The Address Family Flags
        are shown."
    ::= { gbgpEventsGroup 60 }

gbgp60-afi OBJECT-TYPE
    SYNTAX DisplayString
    MAX-ACCESS accessible-for-notify
    STATUS current
    DESCRIPTION
        "Parameter 'afi' in event GBGP.60"
    ::= { gbgpEventObjects60 1 }

gbgp60-safi OBJECT-TYPE
    SYNTAX DisplayString
    MAX-ACCESS accessible-for-notify
    STATUS current
    DESCRIPTION
        "Parameter 'safi' in event GBGP.60"
    ::= { gbgpEventObjects60 2 }

gbgp60-flags OBJECT-TYPE
    SYNTAX Integer32
    MAX-ACCESS accessible-for-notify
    STATUS current
    DESCRIPTION
        "Parameter 'flags' in event GBGP.60"
    ::= { gbgpEventObjects60 3 }

gbgp60-RemotePeerAddress OBJECT-TYPE
    SYNTAX DisplayString
    MAX-ACCESS accessible-for-notify
    STATUS current
    DESCRIPTION
        "Parameter 'RemotePeerAddress' in event GBGP.60"
    ::= { gbgpEventObjects60 4 }

gbgpEventObjects61 OBJECT-IDENTITY
    STATUS current
    DESCRIPTION
        "Event GBGP.61
        An Update message conforming to the End-Of-RIB marker specification is
        sent for the Address Family specified by the afi/safi pair."
    ::= { gbgpEventsGroup 61 }

gbgp61-afi OBJECT-TYPE
    SYNTAX DisplayString
    MAX-ACCESS accessible-for-notify
    STATUS current
    DESCRIPTION
        "Parameter 'afi' in event GBGP.61"
    ::= { gbgpEventObjects61 1 }

gbgp61-safi OBJECT-TYPE
    SYNTAX DisplayString
    MAX-ACCESS accessible-for-notify
    STATUS current
    DESCRIPTION
        "Parameter 'safi' in event GBGP.61"
    ::= { gbgpEventObjects61 2 }

gbgp61-RemotePeerAddress OBJECT-TYPE
    SYNTAX DisplayString
    MAX-ACCESS accessible-for-notify
    STATUS current
    DESCRIPTION
        "Parameter 'RemotePeerAddress' in event GBGP.61"
    ::= { gbgpEventObjects61 3 }

gbgpEventObjects62 OBJECT-IDENTITY
    STATUS current
    DESCRIPTION
        "Event GBGP.62
        An Update message conforming to the End-Of-RIB marker specification has
        been received for the Address Family specified by the afi/safi pair."
    ::= { gbgpEventsGroup 62 }

gbgp62-afi OBJECT-TYPE
    SYNTAX DisplayString
    MAX-ACCESS accessible-for-notify
    STATUS current
    DESCRIPTION
        "Parameter 'afi' in event GBGP.62"
    ::= { gbgpEventObjects62 1 }

gbgp62-safi OBJECT-TYPE
    SYNTAX DisplayString
    MAX-ACCESS accessible-for-notify
    STATUS current
    DESCRIPTION
        "Parameter 'safi' in event GBGP.62"
    ::= { gbgpEventObjects62 2 }

gbgp62-RemotePeerAddress OBJECT-TYPE
    SYNTAX DisplayString
    MAX-ACCESS accessible-for-notify
    STATUS current
    DESCRIPTION
        "Parameter 'RemotePeerAddress' in event GBGP.62"
    ::= { gbgpEventObjects62 3 }

gbgpEventObjects64 OBJECT-IDENTITY
    STATUS current
    DESCRIPTION
        "Event GBGP.64
        Send an open message with Graceful Restart Capability. The Restart
        Flags and Restart Time values are shown."
    ::= { gbgpEventsGroup 64 }

gbgp64-restart-flags OBJECT-TYPE
    SYNTAX Integer32
    MAX-ACCESS accessible-for-notify
    STATUS current
    DESCRIPTION
        "Parameter 'restart-flags' in event GBGP.64"
    ::= { gbgpEventObjects64 1 }

gbgp64-restart-time OBJECT-TYPE
    SYNTAX Integer32
    MAX-ACCESS accessible-for-notify
    STATUS current
    DESCRIPTION
        "Parameter 'restart-time' in event GBGP.64"
    ::= { gbgpEventObjects64 2 }

gbgp64-RemotePeerAddress OBJECT-TYPE
    SYNTAX DisplayString
    MAX-ACCESS accessible-for-notify
    STATUS current
    DESCRIPTION
        "Parameter 'RemotePeerAddress' in event GBGP.64"
    ::= { gbgpEventObjects64 3 }

gbgpEventObjects65 OBJECT-IDENTITY
    STATUS current
    DESCRIPTION
        "Event GBGP.65
        Send an open message with Graceful Restart Capability, with the
        Address Family specified by the afi/safi pair. The Address Family Flags
        are shown."
    ::= { gbgpEventsGroup 65 }

gbgp65-afi OBJECT-TYPE
    SYNTAX DisplayString
    MAX-ACCESS accessible-for-notify
    STATUS current
    DESCRIPTION
        "Parameter 'afi' in event GBGP.65"
    ::= { gbgpEventObjects65 1 }

gbgp65-safi OBJECT-TYPE
    SYNTAX DisplayString
    MAX-ACCESS accessible-for-notify
    STATUS current
    DESCRIPTION
        "Parameter 'safi' in event GBGP.65"
    ::= { gbgpEventObjects65 2 }

gbgp65-flags OBJECT-TYPE
    SYNTAX Integer32
    MAX-ACCESS accessible-for-notify
    STATUS current
    DESCRIPTION
        "Parameter 'flags' in event GBGP.65"
    ::= { gbgpEventObjects65 3 }

gbgp65-RemotePeerAddress OBJECT-TYPE
    SYNTAX DisplayString
    MAX-ACCESS accessible-for-notify
    STATUS current
    DESCRIPTION
        "Parameter 'RemotePeerAddress' in event GBGP.65"
    ::= { gbgpEventObjects65 4 }

gbgpEventObjects66 OBJECT-IDENTITY
    STATUS current
    DESCRIPTION
        "Event GBGP.66
        A peer session is being closed, and a backup for Graceful Restart has
        been triggered. Stale information is discarded because Graceful Restart
        is disabled."
    ::= { gbgpEventsGroup 66 }

gbgp66-RemotePeerAddress OBJECT-TYPE
    SYNTAX DisplayString
    MAX-ACCESS accessible-for-notify
    STATUS current
    DESCRIPTION
        "Parameter 'RemotePeerAddress' in event GBGP.66"
    ::= { gbgpEventObjects66 1 }

gbgpEventObjects67 OBJECT-IDENTITY
    STATUS current
    DESCRIPTION
        "Event GBGP.67
        A peer session is being closed, and a backup for Graceful Restart has
        been triggered. New stale information is generated from scratch or
        reinitializing old stale information as specified in stale-type."
    ::= { gbgpEventsGroup 67 }

gbgp67-stale-type OBJECT-TYPE
    SYNTAX DisplayString
    MAX-ACCESS accessible-for-notify
    STATUS current
    DESCRIPTION
        "Parameter 'stale-type' in event GBGP.67"
    ::= { gbgpEventObjects67 1 }

gbgp67-RemotePeerAddress OBJECT-TYPE
    SYNTAX DisplayString
    MAX-ACCESS accessible-for-notify
    STATUS current
    DESCRIPTION
        "Parameter 'RemotePeerAddress' in event GBGP.67"
    ::= { gbgpEventObjects67 2 }

gbgpEventObjects68 OBJECT-IDENTITY
    STATUS current
    DESCRIPTION
        "Event GBGP.68
        Graceful Restart has created a stale route to the specified destination
        network."
    ::= { gbgpEventsGroup 68 }

gbgp68-dest-addr OBJECT-TYPE
    SYNTAX DisplayString
    MAX-ACCESS accessible-for-notify
    STATUS current
    DESCRIPTION
        "Parameter 'dest-addr' in event GBGP.68"
    ::= { gbgpEventObjects68 1 }

gbgp68-dest-len OBJECT-TYPE
    SYNTAX Integer32
    MAX-ACCESS accessible-for-notify
    STATUS current
    DESCRIPTION
        "Parameter 'dest-len' in event GBGP.68"
    ::= { gbgpEventObjects68 2 }

gbgp68-RemotePeerAddress OBJECT-TYPE
    SYNTAX DisplayString
    MAX-ACCESS accessible-for-notify
    STATUS current
    DESCRIPTION
        "Parameter 'RemotePeerAddress' in event GBGP.68"
    ::= { gbgpEventObjects68 3 }

gbgpEventObjects69 OBJECT-IDENTITY
    STATUS current
    DESCRIPTION
        "Event GBGP.69
        Graceful Restart made a backup generating stale information for a
        receiving or restarting speaker (as specified in speaker-type) with the
        specified number of address families and routes."
    ::= { gbgpEventsGroup 69 }

gbgp69-speaker-type OBJECT-TYPE
    SYNTAX DisplayString
    MAX-ACCESS accessible-for-notify
    STATUS current
    DESCRIPTION
        "Parameter 'speaker-type' in event GBGP.69"
    ::= { gbgpEventObjects69 1 }

gbgp69-family-count OBJECT-TYPE
    SYNTAX Integer32
    MAX-ACCESS accessible-for-notify
    STATUS current
    DESCRIPTION
        "Parameter 'family-count' in event GBGP.69"
    ::= { gbgpEventObjects69 2 }

gbgp69-route-count OBJECT-TYPE
    SYNTAX Integer32
    MAX-ACCESS accessible-for-notify
    STATUS current
    DESCRIPTION
        "Parameter 'route-count' in event GBGP.69"
    ::= { gbgpEventObjects69 3 }

gbgp69-RemotePeerAddress OBJECT-TYPE
    SYNTAX DisplayString
    MAX-ACCESS accessible-for-notify
    STATUS current
    DESCRIPTION
        "Parameter 'RemotePeerAddress' in event GBGP.69"
    ::= { gbgpEventObjects69 4 }

gbgpEventObjects70 OBJECT-IDENTITY
    STATUS current
    DESCRIPTION
        "Event GBGP.70
        Graceful Restart detected the session establishment for a receiving or
        restarting speaker as specified in speaker-type."
    ::= { gbgpEventsGroup 70 }

gbgp70-speaker-type OBJECT-TYPE
    SYNTAX DisplayString
    MAX-ACCESS accessible-for-notify
    STATUS current
    DESCRIPTION
        "Parameter 'speaker-type' in event GBGP.70"
    ::= { gbgpEventObjects70 1 }

gbgp70-RemotePeerAddress OBJECT-TYPE
    SYNTAX DisplayString
    MAX-ACCESS accessible-for-notify
    STATUS current
    DESCRIPTION
        "Parameter 'RemotePeerAddress' in event GBGP.70"
    ::= { gbgpEventObjects70 2 }

gbgpEventObjects71 OBJECT-IDENTITY
    STATUS current
    DESCRIPTION
        "Event GBGP.71
        Graceful Restart detected the session establishment for a restarting
        speaker, but no graceful restart capability was received or it was
        received with the 'Restart State' bit set. This peer will not be waited
        for to stop deferring."
    ::= { gbgpEventsGroup 71 }

gbgp71-afi OBJECT-TYPE
    SYNTAX DisplayString
    MAX-ACCESS accessible-for-notify
    STATUS current
    DESCRIPTION
        "Parameter 'afi' in event GBGP.71"
    ::= { gbgpEventObjects71 1 }

gbgp71-safi OBJECT-TYPE
    SYNTAX DisplayString
    MAX-ACCESS accessible-for-notify
    STATUS current
    DESCRIPTION
        "Parameter 'safi' in event GBGP.71"
    ::= { gbgpEventObjects71 2 }

gbgp71-RemotePeerAddress OBJECT-TYPE
    SYNTAX DisplayString
    MAX-ACCESS accessible-for-notify
    STATUS current
    DESCRIPTION
        "Parameter 'RemotePeerAddress' in event GBGP.71"
    ::= { gbgpEventObjects71 3 }

gbgpEventObjects72 OBJECT-IDENTITY
    STATUS current
    DESCRIPTION
        "Event GBGP.72
        Graceful Restart has deferred a restarting speaker route received in an
        update message. The route destination network is specified."
    ::= { gbgpEventsGroup 72 }

gbgp72-dest-addr OBJECT-TYPE
    SYNTAX DisplayString
    MAX-ACCESS accessible-for-notify
    STATUS current
    DESCRIPTION
        "Parameter 'dest-addr' in event GBGP.72"
    ::= { gbgpEventObjects72 1 }

gbgp72-dest-len OBJECT-TYPE
    SYNTAX Integer32
    MAX-ACCESS accessible-for-notify
    STATUS current
    DESCRIPTION
        "Parameter 'dest-len' in event GBGP.72"
    ::= { gbgpEventObjects72 2 }

gbgp72-RemotePeerAddress OBJECT-TYPE
    SYNTAX DisplayString
    MAX-ACCESS accessible-for-notify
    STATUS current
    DESCRIPTION
        "Parameter 'RemotePeerAddress' in event GBGP.72"
    ::= { gbgpEventObjects72 3 }

gbgpEventObjects73 OBJECT-IDENTITY
    STATUS current
    DESCRIPTION
        "Event GBGP.73
        Graceful Restart has deleted a stale route. The route destination
        network is specified. Possible causes are: 'rx nlri' when
        the receiving speaker stale route is superseded by a nlri received on an
        update message; 'term' when the BGP process is terminating; 'rx eor'
        when the End-of-RIB marker has been received by a receiving speaker;
        'estab' when the receiving speaker BGP session has been established and
        no 'Forwarding State' bit has been received for an address family;
        'stop defer' when the restarting speaker stops deferring an address
        family."
    ::= { gbgpEventsGroup 73 }

gbgp73-dest-addr OBJECT-TYPE
    SYNTAX DisplayString
    MAX-ACCESS accessible-for-notify
    STATUS current
    DESCRIPTION
        "Parameter 'dest-addr' in event GBGP.73"
    ::= { gbgpEventObjects73 1 }

gbgp73-dest-len OBJECT-TYPE
    SYNTAX Integer32
    MAX-ACCESS accessible-for-notify
    STATUS current
    DESCRIPTION
        "Parameter 'dest-len' in event GBGP.73"
    ::= { gbgpEventObjects73 2 }

gbgp73-cause OBJECT-TYPE
    SYNTAX DisplayString
    MAX-ACCESS accessible-for-notify
    STATUS current
    DESCRIPTION
        "Parameter 'cause' in event GBGP.73"
    ::= { gbgpEventObjects73 3 }

gbgp73-RemotePeerAddress OBJECT-TYPE
    SYNTAX DisplayString
    MAX-ACCESS accessible-for-notify
    STATUS current
    DESCRIPTION
        "Parameter 'RemotePeerAddress' in event GBGP.73"
    ::= { gbgpEventObjects73 4 }

gbgpEventObjects74 OBJECT-IDENTITY
    STATUS current
    DESCRIPTION
        "Event GBGP.74
        Graceful Restart stale information has timed out for the specified peer."
    ::= { gbgpEventsGroup 74 }

gbgp74-RemotePeerAddress OBJECT-TYPE
    SYNTAX DisplayString
    MAX-ACCESS accessible-for-notify
    STATUS current
    DESCRIPTION
        "Parameter 'RemotePeerAddress' in event GBGP.74"
    ::= { gbgpEventObjects74 1 }

gbgpEventObjects75 OBJECT-IDENTITY
    STATUS current
    DESCRIPTION
        "Event GBGP.75
        Graceful Restart stale information is deleted. The cause is specified."
    ::= { gbgpEventsGroup 75 }

gbgp75-cause OBJECT-TYPE
    SYNTAX DisplayString
    MAX-ACCESS accessible-for-notify
    STATUS current
    DESCRIPTION
        "Parameter 'cause' in event GBGP.75"
    ::= { gbgpEventObjects75 1 }

gbgp75-RemotePeerAddress OBJECT-TYPE
    SYNTAX DisplayString
    MAX-ACCESS accessible-for-notify
    STATUS current
    DESCRIPTION
        "Parameter 'RemotePeerAddress' in event GBGP.75"
    ::= { gbgpEventObjects75 2 }

gbgpEventObjects76 OBJECT-IDENTITY
    STATUS current
    DESCRIPTION
        "Event GBGP.76
        Graceful Restart stale peer is deleted. This is an idle unconfigured
        peer which lost the stale iformation. The cause is specified."
    ::= { gbgpEventsGroup 76 }

gbgp76-cause OBJECT-TYPE
    SYNTAX DisplayString
    MAX-ACCESS accessible-for-notify
    STATUS current
    DESCRIPTION
        "Parameter 'cause' in event GBGP.76"
    ::= { gbgpEventObjects76 1 }

gbgp76-RemotePeerAddress OBJECT-TYPE
    SYNTAX DisplayString
    MAX-ACCESS accessible-for-notify
    STATUS current
    DESCRIPTION
        "Parameter 'RemotePeerAddress' in event GBGP.76"
    ::= { gbgpEventObjects76 2 }

gbgpEventObjects77 OBJECT-IDENTITY
    STATUS current
    DESCRIPTION
        "Event GBGP.77
        Graceful Restart initial update has been deferred for the specified
        address family."
    ::= { gbgpEventsGroup 77 }

gbgp77-afi OBJECT-TYPE
    SYNTAX DisplayString
    MAX-ACCESS accessible-for-notify
    STATUS current
    DESCRIPTION
        "Parameter 'afi' in event GBGP.77"
    ::= { gbgpEventObjects77 1 }

gbgp77-safi OBJECT-TYPE
    SYNTAX DisplayString
    MAX-ACCESS accessible-for-notify
    STATUS current
    DESCRIPTION
        "Parameter 'safi' in event GBGP.77"
    ::= { gbgpEventObjects77 2 }

gbgp77-RemotePeerAddress OBJECT-TYPE
    SYNTAX DisplayString
    MAX-ACCESS accessible-for-notify
    STATUS current
    DESCRIPTION
        "Parameter 'RemotePeerAddress' in event GBGP.77"
    ::= { gbgpEventObjects77 3 }

gbgpEventObjects78 OBJECT-IDENTITY
    STATUS current
    DESCRIPTION
        "Event GBGP.78
        Graceful Restart initial update with End-of-RIB marker has been started
        for the specified address family."
    ::= { gbgpEventsGroup 78 }

gbgp78-afi OBJECT-TYPE
    SYNTAX DisplayString
    MAX-ACCESS accessible-for-notify
    STATUS current
    DESCRIPTION
        "Parameter 'afi' in event GBGP.78"
    ::= { gbgpEventObjects78 1 }

gbgp78-safi OBJECT-TYPE
    SYNTAX DisplayString
    MAX-ACCESS accessible-for-notify
    STATUS current
    DESCRIPTION
        "Parameter 'safi' in event GBGP.78"
    ::= { gbgpEventObjects78 2 }

gbgp78-RemotePeerAddress OBJECT-TYPE
    SYNTAX DisplayString
    MAX-ACCESS accessible-for-notify
    STATUS current
    DESCRIPTION
        "Parameter 'RemotePeerAddress' in event GBGP.78"
    ::= { gbgpEventObjects78 3 }

gbgpEventObjects79 OBJECT-IDENTITY
    STATUS current
    DESCRIPTION
        "Event GBGP.79
        Graceful Restart selection deferral started for all address families.
        The selection deferral timer has been started with the specified
        timeout."
    ::= { gbgpEventsGroup 79 }

gbgp79-timeout-seconds OBJECT-TYPE
    SYNTAX Integer32
    MAX-ACCESS accessible-for-notify
    STATUS current
    DESCRIPTION
        "Parameter 'timeout-seconds' in event GBGP.79"
    ::= { gbgpEventObjects79 1 }

gbgpEventObjects83 OBJECT-IDENTITY
    STATUS current
    DESCRIPTION
        "Event GBGP.83
        Graceful Restart selection deferral ended for the specified address
        family."
    ::= { gbgpEventsGroup 83 }

gbgp83-afi OBJECT-TYPE
    SYNTAX DisplayString
    MAX-ACCESS accessible-for-notify
    STATUS current
    DESCRIPTION
        "Parameter 'afi' in event GBGP.83"
    ::= { gbgpEventObjects83 1 }

gbgp83-safi OBJECT-TYPE
    SYNTAX DisplayString
    MAX-ACCESS accessible-for-notify
    STATUS current
    DESCRIPTION
        "Parameter 'safi' in event GBGP.83"
    ::= { gbgpEventObjects83 2 }

gbgpEventObjects84 OBJECT-IDENTITY
    STATUS current
    DESCRIPTION
        "Event GBGP.84
        Graceful Restart has stopped deferring a restarting speaker route. The
        route destination network is specified."
    ::= { gbgpEventsGroup 84 }

gbgp84-dest-addr OBJECT-TYPE
    SYNTAX DisplayString
    MAX-ACCESS accessible-for-notify
    STATUS current
    DESCRIPTION
        "Parameter 'dest-addr' in event GBGP.84"
    ::= { gbgpEventObjects84 1 }

gbgp84-dest-len OBJECT-TYPE
    SYNTAX Integer32
    MAX-ACCESS accessible-for-notify
    STATUS current
    DESCRIPTION
        "Parameter 'dest-len' in event GBGP.84"
    ::= { gbgpEventObjects84 2 }

gbgp84-RemotePeerAddress OBJECT-TYPE
    SYNTAX DisplayString
    MAX-ACCESS accessible-for-notify
    STATUS current
    DESCRIPTION
        "Parameter 'RemotePeerAddress' in event GBGP.84"
    ::= { gbgpEventObjects84 3 }

gbgpEventObjects85 OBJECT-IDENTITY
    STATUS current
    DESCRIPTION
        "Event GBGP.85
        Graceful Restart peer has started address family deferral."
    ::= { gbgpEventsGroup 85 }

gbgp85-RemotePeerAddress OBJECT-TYPE
    SYNTAX DisplayString
    MAX-ACCESS accessible-for-notify
    STATUS current
    DESCRIPTION
        "Parameter 'RemotePeerAddress' in event GBGP.85"
    ::= { gbgpEventObjects85 1 }

gbgpEventObjects86 OBJECT-IDENTITY
    STATUS current
    DESCRIPTION
        "Event GBGP.86
        Graceful Restart peer has stopped address family deferral."
    ::= { gbgpEventsGroup 86 }

gbgp86-RemotePeerAddress OBJECT-TYPE
    SYNTAX DisplayString
    MAX-ACCESS accessible-for-notify
    STATUS current
    DESCRIPTION
        "Parameter 'RemotePeerAddress' in event GBGP.86"
    ::= { gbgpEventObjects86 1 }

gbgpEventObjects87 OBJECT-IDENTITY
    STATUS current
    DESCRIPTION
        "Event GBGP.87
        The local origin value of a route received in an update packet
        has been changed due to a preconfigured route-map in/out policy
        for this neighbor."
    ::= { gbgpEventsGroup 87 }

gbgp87-RouteDest OBJECT-TYPE
    SYNTAX DisplayString
    MAX-ACCESS accessible-for-notify
    STATUS current
    DESCRIPTION
        "Parameter 'RouteDest' in event GBGP.87"
    ::= { gbgpEventObjects87 1 }

gbgp87-MaskLenght OBJECT-TYPE
    SYNTAX Integer32
    MAX-ACCESS accessible-for-notify
    STATUS current
    DESCRIPTION
        "Parameter 'MaskLenght' in event GBGP.87"
    ::= { gbgpEventObjects87 2 }

gbgp87-NewOrigin OBJECT-TYPE
    SYNTAX DisplayString
    MAX-ACCESS accessible-for-notify
    STATUS current
    DESCRIPTION
        "Parameter 'NewOrigin' in event GBGP.87"
    ::= { gbgpEventObjects87 3 }

gbgpEventObjects88 OBJECT-IDENTITY
    STATUS current
    DESCRIPTION
        "Event GBGP.88
        The peer prefix database is above the maximum-prefix configured limit.
        Both this limit and the current prefix count are shown."
    ::= { gbgpEventsGroup 88 }

gbgp88-maximum-prefixes OBJECT-TYPE
    SYNTAX Integer32
    MAX-ACCESS accessible-for-notify
    STATUS current
    DESCRIPTION
        "Parameter 'maximum-prefixes' in event GBGP.88"
    ::= { gbgpEventObjects88 1 }

gbgp88-current-prefixes OBJECT-TYPE
    SYNTAX Integer32
    MAX-ACCESS accessible-for-notify
    STATUS current
    DESCRIPTION
        "Parameter 'current-prefixes' in event GBGP.88"
    ::= { gbgpEventObjects88 2 }

gbgp88-RemotePeerAddress OBJECT-TYPE
    SYNTAX DisplayString
    MAX-ACCESS accessible-for-notify
    STATUS current
    DESCRIPTION
        "Parameter 'RemotePeerAddress' in event GBGP.88"
    ::= { gbgpEventObjects88 3 }

gbgp88-AutonomousSystem OBJECT-TYPE
    SYNTAX Integer32
    MAX-ACCESS accessible-for-notify
    STATUS current
    DESCRIPTION
        "Parameter 'AutonomousSystem' in event GBGP.88"
    ::= { gbgpEventObjects88 4 }


gbgpNotification1 NOTIFICATION-TYPE
    STATUS current
    DESCRIPTION
        "Notification of Event GBGP.1

        Message: 'BGP subsystem started succesfully.'

        The BGP subsystem initialization process was started successfully."
    ::= { gbgpNotificationsPrefix 1 }

gbgpNotification2 NOTIFICATION-TYPE
    OBJECTS { 
              gbgp2-RemotePeerAddress, 
              gbgp2-AutonomousSystem 
            }
    STATUS current
    DESCRIPTION
        "Notification of Event GBGP.2

        Message: 'The system disconnected from a configured BGP peer. Remote address is $1 AS $2'

        Parameters list:
              $1: gbgp2-RemotePeerAddress
              $2: gbgp2-AutonomousSystem

        A connection to a ESTABLISHED BGP peer has been lost. Possible causes
        are either a keepalive timer timeout or a TCP protocol error. The status
        of this peer is changed to ACTIVE."
    ::= { gbgpNotificationsPrefix 2 }

gbgpNotification3 NOTIFICATION-TYPE
    OBJECTS { 
              gbgp3-ParserErrors 
            }
    STATUS current
    DESCRIPTION
        "Notification of Event GBGP.3

        Message: '$1 errors were found in the configuration'

        Parameters list:
              $1: gbgp3-ParserErrors

        Syntax errors found in configuration file."
    ::= { gbgpNotificationsPrefix 3 }

gbgpNotification4 NOTIFICATION-TYPE
    OBJECTS { 
              gbgp4-PacketType, 
              gbgp4-RemotePeerAddress,
              gbgp4-AutonomousSystem 
            }
    STATUS current
    DESCRIPTION
        "Notification of Event GBGP.4

        Message: 'Received $1 message from peer $2/AS $3'

        Parameters list:
              $1: gbgp4-PacketType
              $2: gbgp4-RemotePeerAddress
              $3: gbgp4-AutonomousSystem

        A valid incoming BGP message has been received from a peer.
        The type of message is shown, as well as the remote peer address and
        autonomous system."
    ::= { gbgpNotificationsPrefix 4 }

gbgpNotification5 NOTIFICATION-TYPE
    OBJECTS { 
              gbgp5-PacketType, 
              gbgp5-RemotePeerAddress,
              gbgp5-AutonomousSystem 
            }
    STATUS current
    DESCRIPTION
        "Notification of Event GBGP.5

        Message: 'Sending $1 message to peer $2/AS $3'

        Parameters list:
              $1: gbgp5-PacketType
              $2: gbgp5-RemotePeerAddress
              $3: gbgp5-AutonomousSystem

        A message is been sent to a remote peer.
        The type of message is shown, as well as the remote peer address and
        autonomous system."
    ::= { gbgpNotificationsPrefix 5 }

gbgpNotification6 NOTIFICATION-TYPE
    OBJECTS { 
              gbgp6-RemotePeerName, 
              gbgp6-ErrorMessage 
            }
    STATUS current
    DESCRIPTION
        "Notification of Event GBGP.6

        Message: 'Packet from peer $1 has been rejected. Cause is $2'

        Parameters list:
              $1: gbgp6-RemotePeerName
              $2: gbgp6-ErrorMessage

        An incoming BGP message has been rejected. The rejection cause is shown
        in the message."
    ::= { gbgpNotificationsPrefix 6 }

gbgpNotification7 NOTIFICATION-TYPE
    OBJECTS { 
              gbgp7-RemotePeerName, 
              gbgp7-ErrorMessage 
            }
    STATUS current
    DESCRIPTION
        "Notification of Event GBGP.7

        Message: 'Rejected incoming connection from $1. Cause: $2'

        Parameters list:
              $1: gbgp7-RemotePeerName
              $2: gbgp7-ErrorMessage

        An active open from a remote system has been rejected. The address, AS
        and rejection cause are shown."
    ::= { gbgpNotificationsPrefix 7 }

gbgpNotification8 NOTIFICATION-TYPE
    OBJECTS { 
              gbgp8-RemotePeerAddress, 
              gbgp8-AutonomousSystem 
            }
    STATUS current
    DESCRIPTION
        "Notification of Event GBGP.8

        Message: 'The system connected to BGP peer. Address is $1, AS is $2.'

        Parameters list:
              $1: gbgp8-RemotePeerAddress
              $2: gbgp8-AutonomousSystem

        A valid connection has been made to a configured BGP peer. Peer status
        is changed to ESTABLISHED."
    ::= { gbgpNotificationsPrefix 8 }

gbgpNotification9 NOTIFICATION-TYPE
    STATUS current
    DESCRIPTION
        "Notification of Event GBGP.9

        Message: 'BGP subsystem stopped: normal stop.'

        The BGP subsystem was stopped due to an user request."
    ::= { gbgpNotificationsPrefix 9 }

gbgpNotification10 NOTIFICATION-TYPE
    OBJECTS { 
              gbgp10-RouteDest, 
              gbgp10-RouteMask,
              gbgp10-NextHop,
              gbgp10-Preference,
              gbgp10-Metric,
              gbgp10-LocalPref 
            }
    STATUS current
    DESCRIPTION
        "Notification of Event GBGP.10

        Message: 'received route update $1/$2 $3 pref $4 metric $5 localpref $6'

        Parameters list:
              $1: gbgp10-RouteDest
              $2: gbgp10-RouteMask
              $3: gbgp10-NextHop
              $4: gbgp10-Preference
              $5: gbgp10-Metric
              $6: gbgp10-LocalPref

        An update message for the route shown has been received. This message
        does not mean that this route has been made active, it just means that
        the system has received information for this route from a BGP peer. This
        route will be processed, and, taking into account the
        configured preference rules, will be or not exported to the active
        routes table. To be able to see changes in the active RT, please
        use the IP subsystem events."
    ::= { gbgpNotificationsPrefix 10 }

gbgpNotification11 NOTIFICATION-TYPE
    OBJECTS { 
              gbgp11-RouteDest, 
              gbgp11-RouteMask,
              gbgp11-BGPPeer 
            }
    STATUS current
    DESCRIPTION
        "Notification of Event GBGP.11

        Message: 'route $1/$2 from $3 is now unreachable'

        Parameters list:
              $1: gbgp11-RouteDest
              $2: gbgp11-RouteMask
              $3: gbgp11-BGPPeer

        An unreach message has been received for this route. This message
        does not mean that this route will be deleted from the active RT
        (it is possible that the route was not even made active when it
        was received). To be able to see changes in the active RT, please
        use the IP subsystem events."
    ::= { gbgpNotificationsPrefix 11 }

gbgpNotification12 NOTIFICATION-TYPE
    OBJECTS { 
              gbgp12-RemotePeerAddress, 
              gbgp12-AutonomousSystem 
            }
    STATUS current
    DESCRIPTION
        "Notification of Event GBGP.12

        Message: 'The holdtime for peer $1/AS $2 has expired'

        Parameters list:
              $1: gbgp12-RemotePeerAddress
              $2: gbgp12-AutonomousSystem

        The holdtime for a given BGP peer has expired."
    ::= { gbgpNotificationsPrefix 12 }

gbgpNotification13 NOTIFICATION-TYPE
    STATUS current
    DESCRIPTION
        "Notification of Event GBGP.13

        Message: 'BGP subsystem aborted'

        BGP subsystem was killed due to an unexpected error."
    ::= { gbgpNotificationsPrefix 13 }

gbgpNotification14 NOTIFICATION-TYPE
    OBJECTS { 
              gbgp14-Dest, 
              gbgp14-Mask,
              gbgp14-BGPPeer 
            }
    STATUS current
    DESCRIPTION
        "Notification of Event GBGP.14

        Message: 'Del route $1/$2 $3 from RT DB'

        Parameters list:
              $1: gbgp14-Dest
              $2: gbgp14-Mask
              $3: gbgp14-BGPPeer

        Deleting route from BGP routing Database."
    ::= { gbgpNotificationsPrefix 14 }

gbgpNotification15 NOTIFICATION-TYPE
    OBJECTS { 
              gbgp15-Dest, 
              gbgp15-Mask,
              gbgp15-NextHop 
            }
    STATUS current
    DESCRIPTION
        "Notification of Event GBGP.15

        Message: 'Add route $1/$2 $3'

        Parameters list:
              $1: gbgp15-Dest
              $2: gbgp15-Mask
              $3: gbgp15-NextHop

        Adding route to BGP routing Database."
    ::= { gbgpNotificationsPrefix 15 }

gbgpNotification16 NOTIFICATION-TYPE
    OBJECTS { 
              gbgp16-Dest, 
              gbgp16-Mask 
            }
    STATUS current
    DESCRIPTION
        "Notification of Event GBGP.16

        Message: 'Add direct rte $1/$2'

        Parameters list:
              $1: gbgp16-Dest
              $2: gbgp16-Mask

        Adding direct route to BGP routing Database."
    ::= { gbgpNotificationsPrefix 16 }

gbgpNotification17 NOTIFICATION-TYPE
    STATUS current
    DESCRIPTION
        "Notification of Event GBGP.17

        Message: 'BGP restart command issued'

        A restart BGP command has been issued from the system console."
    ::= { gbgpNotificationsPrefix 17 }

gbgpNotification18 NOTIFICATION-TYPE
    OBJECTS { 
              gbgp18-RemotePeer 
            }
    STATUS current
    DESCRIPTION
        "Notification of Event GBGP.18

        Message: 'Trying to connect to $1'

        Parameters list:
              $1: gbgp18-RemotePeer

        BGP subsystem is trying to connect to a remote peer."
    ::= { gbgpNotificationsPrefix 18 }

gbgpNotification19 NOTIFICATION-TYPE
    OBJECTS { 
              gbgp19-fromto, 
              gbgp19-RemoteAS,
              gbgp19-code,
              gbgp19-subcode 
            }
    STATUS current
    DESCRIPTION
        "Notification of Event GBGP.19

        Message: 'notification message $1 $2: $3/$4'

        Parameters list:
              $1: gbgp19-fromto
              $2: gbgp19-RemoteAS
              $3: gbgp19-code
              $4: gbgp19-subcode

        A notification message has been sent or received."
    ::= { gbgpNotificationsPrefix 19 }

gbgpNotification20 NOTIFICATION-TYPE
    OBJECTS { 
              gbgp20-RemotePeer, 
              gbgp20-cause 
            }
    STATUS current
    DESCRIPTION
        "Notification of Event GBGP.20

        Message: 'Peer $1 is idle. Cause $2'

        Parameters list:
              $1: gbgp20-RemotePeer
              $2: gbgp20-cause

        Changing state of peer to idled. The cause is printed at the end of
        the message."
    ::= { gbgpNotificationsPrefix 20 }

gbgpNotification21 NOTIFICATION-TYPE
    STATUS current
    DESCRIPTION
        "Notification of Event GBGP.21

        Message: 'Could not read config'

        Could not read BGP configuration."
    ::= { gbgpNotificationsPrefix 21 }

gbgpNotification22 NOTIFICATION-TYPE
    OBJECTS { 
              gbgp22-DiagnosticMessage 
            }
    STATUS current
    DESCRIPTION
        "Notification of Event GBGP.22

        Message: 'Error reading config: $1'

        Parameters list:
              $1: gbgp22-DiagnosticMessage

        The error printed occurred while reading the configuration."
    ::= { gbgpNotificationsPrefix 22 }

gbgpNotification23 NOTIFICATION-TYPE
    OBJECTS { 
              gbgp23-NumberOfComms, 
              gbgp23-Communities 
            }
    STATUS current
    DESCRIPTION
        "Notification of Event GBGP.23

        Message: 'Received update packet with $1 communitites: $2'

        Parameters list:
              $1: gbgp23-NumberOfComms
              $2: gbgp23-Communities

        An update packet has been received with community attributes."
    ::= { gbgpNotificationsPrefix 23 }

gbgpNotification24 NOTIFICATION-TYPE
    OBJECTS { 
              gbgp24-RouteDest, 
              gbgp24-RouteMask,
              gbgp24-Route-MapName 
            }
    STATUS current
    DESCRIPTION
        "Notification of Event GBGP.24

        Message: 'Discarded $1/$2 due to route-map with name $3'

        Parameters list:
              $1: gbgp24-RouteDest
              $2: gbgp24-RouteMask
              $3: gbgp24-Route-MapName

        A route received in an update packet has been discarded due to
        preconfigured route-map in/out policy for this neighbor."
    ::= { gbgpNotificationsPrefix 24 }

gbgpNotification25 NOTIFICATION-TYPE
    OBJECTS { 
              gbgp25-RouteDest, 
              gbgp25-RouteMask,
              gbgp25-OldLocalPref,
              gbgp25-NewLocalPref 
            }
    STATUS current
    DESCRIPTION
        "Notification of Event GBGP.25

        Message: 'Changed localpref of route $1/$2 from $3 to $4'

        Parameters list:
              $1: gbgp25-RouteDest
              $2: gbgp25-RouteMask
              $3: gbgp25-OldLocalPref
              $4: gbgp25-NewLocalPref

        The local pref value of a route received in an update packet
        has been changed due to a preconfigured route-map in/out policy
        for this neighbor."
    ::= { gbgpNotificationsPrefix 25 }

gbgpNotification26 NOTIFICATION-TYPE
    OBJECTS { 
              gbgp26-RouteMapName 
            }
    STATUS current
    DESCRIPTION
        "Notification of Event GBGP.26

        Message: 'Maximum number of communities exceeded applying route-map $1'

        Parameters list:
              $1: gbgp26-RouteMapName

        Could not apply the route-map policy: max number of communities per
        route exceeded."
    ::= { gbgpNotificationsPrefix 26 }

gbgpNotification27 NOTIFICATION-TYPE
    OBJECTS { 
              gbgp27-RouteDest, 
              gbgp27-RouteMask,
              gbgp27-OldMetric,
              gbgp27-NewMetric 
            }
    STATUS current
    DESCRIPTION
        "Notification of Event GBGP.27

        Message: 'Changed metric of route $1/$2 from $3 to $4'

        Parameters list:
              $1: gbgp27-RouteDest
              $2: gbgp27-RouteMask
              $3: gbgp27-OldMetric
              $4: gbgp27-NewMetric

        The metric value of a route received in an update packet
        has been changed due to a preconfigured route-map in/out policy
        for this neighbor."
    ::= { gbgpNotificationsPrefix 27 }

gbgpNotification28 NOTIFICATION-TYPE
    OBJECTS { 
              gbgp28-RemotePeerAddress, 
              gbgp28-AutonomousSystem 
            }
    STATUS current
    DESCRIPTION
        "Notification of Event GBGP.28

        Message: 'Backward status transition. Peer $1/AS $2'

        Parameters list:
              $1: gbgp28-RemotePeerAddress
              $2: gbgp28-AutonomousSystem

        The status of the specified peer has changed from a higher
        numbered status to a lower numbered status."
    ::= { gbgpNotificationsPrefix 28 }

gbgpNotification29 NOTIFICATION-TYPE
    OBJECTS { 
              gbgp29-RemotePeerAddress, 
              gbgp29-AutonomousSystem 
            }
    STATUS current
    DESCRIPTION
        "Notification of Event GBGP.29

        Message: 'The system disconnected from a configured BGP peer. Remote address is $1 AS $2'

        Parameters list:
              $1: gbgp29-RemotePeerAddress
              $2: gbgp29-AutonomousSystem

        A connection to a ESTABLISHED BGP peer has been lost. Possible causes
        are either a keepalive timer timeout or a TCP protocol error. The status
        of this peer is changed to ACTIVE."
    ::= { gbgpNotificationsPrefix 29 }

gbgpNotification30 NOTIFICATION-TYPE
    OBJECTS { 
              gbgp30-PacketType, 
              gbgp30-RemotePeerAddress,
              gbgp30-AutonomousSystem 
            }
    STATUS current
    DESCRIPTION
        "Notification of Event GBGP.30

        Message: 'Received $1 message from peer $2/AS $3'

        Parameters list:
              $1: gbgp30-PacketType
              $2: gbgp30-RemotePeerAddress
              $3: gbgp30-AutonomousSystem

        A valid incoming BGP message has been received from a peer.
        The type of message is shown, as well as the remote peer address and
        autonomous system."
    ::= { gbgpNotificationsPrefix 30 }

gbgpNotification31 NOTIFICATION-TYPE
    OBJECTS { 
              gbgp31-PacketType, 
              gbgp31-RemotePeerAddress,
              gbgp31-AutonomousSystem 
            }
    STATUS current
    DESCRIPTION
        "Notification of Event GBGP.31

        Message: 'Sending $1 message to peer $2/AS $3'

        Parameters list:
              $1: gbgp31-PacketType
              $2: gbgp31-RemotePeerAddress
              $3: gbgp31-AutonomousSystem

        A message is been sent to a remote peer.
        The type of message is shown, as well as the remote peer address and
        autonomous system."
    ::= { gbgpNotificationsPrefix 31 }

gbgpNotification32 NOTIFICATION-TYPE
    OBJECTS { 
              gbgp32-RemotePeerAddress, 
              gbgp32-AutonomousSystem 
            }
    STATUS current
    DESCRIPTION
        "Notification of Event GBGP.32

        Message: 'The system connected to BGP peer. Address is $1, AS is $2.'

        Parameters list:
              $1: gbgp32-RemotePeerAddress
              $2: gbgp32-AutonomousSystem

        A valid connection has been made to a configured BGP peer. Peer status
        is changed to ESTABLISHED."
    ::= { gbgpNotificationsPrefix 32 }

gbgpNotification33 NOTIFICATION-TYPE
    OBJECTS { 
              gbgp33-RouteDest, 
              gbgp33-RoutePrefixLen,
              gbgp33-NextHop,
              gbgp33-Preference,
              gbgp33-Metric,
              gbgp33-LocalPref 
            }
    STATUS current
    DESCRIPTION
        "Notification of Event GBGP.33

        Message: 'received route update $1/$2 $3 pref $4 metric $5 localpref $6'

        Parameters list:
              $1: gbgp33-RouteDest
              $2: gbgp33-RoutePrefixLen
              $3: gbgp33-NextHop
              $4: gbgp33-Preference
              $5: gbgp33-Metric
              $6: gbgp33-LocalPref

        An update message for the route shown has been received. This message
        does not mean that this route has been made active, it just means that
        the system has received information for this route from a BGP peer. This
        route will be processed, and, taking into account the
        configured preference rules, will be or not exported to the active
        routes table. To be able to see changes in the active RT, please
        use the IPv6 subsystem events."
    ::= { gbgpNotificationsPrefix 33 }

gbgpNotification34 NOTIFICATION-TYPE
    OBJECTS { 
              gbgp34-RouteDest, 
              gbgp34-RoutePrefixLen,
              gbgp34-NextHop,
              gbgp34-NextHopLocal,
              gbgp34-Preference,
              gbgp34-Metric,
              gbgp34-LocalPref 
            }
    STATUS current
    DESCRIPTION
        "Notification of Event GBGP.34

        Message: 'received route update $1/$2 $3 ($4) pref $5 metric $6 localpref $7'

        Parameters list:
              $1: gbgp34-RouteDest
              $2: gbgp34-RoutePrefixLen
              $3: gbgp34-NextHop
              $4: gbgp34-NextHopLocal
              $5: gbgp34-Preference
              $6: gbgp34-Metric
              $7: gbgp34-LocalPref

        An update message for the route shown has been received. This message
        does not mean that this route has been made active, it just means that
        the system has received information for this route from a BGP peer. This
        route will be processed, and, taking into account the
        configured preference rules, will be or not exported to the active
        routes table. To be able to see changes in the active RT, please
        use the IPv6 subsystem events."
    ::= { gbgpNotificationsPrefix 34 }

gbgpNotification35 NOTIFICATION-TYPE
    OBJECTS { 
              gbgp35-RouteDest, 
              gbgp35-RoutePrefixLen,
              gbgp35-BGPPeer 
            }
    STATUS current
    DESCRIPTION
        "Notification of Event GBGP.35

        Message: 'route $1/$2 from $3 is now unreachable'

        Parameters list:
              $1: gbgp35-RouteDest
              $2: gbgp35-RoutePrefixLen
              $3: gbgp35-BGPPeer

        An unreach message has been received for this route. This message
        does not mean that this route will be deleted from the active RT
        (it is possible that the route was not even made active when it
        was received). To be able to see changes in the active RT, please
        use the IPv6 subsystem events."
    ::= { gbgpNotificationsPrefix 35 }

gbgpNotification36 NOTIFICATION-TYPE
    OBJECTS { 
              gbgp36-RemotePeerAddress, 
              gbgp36-AutonomousSystem 
            }
    STATUS current
    DESCRIPTION
        "Notification of Event GBGP.36

        Message: 'The holdtime for peer $1/AS $2 has expired'

        Parameters list:
              $1: gbgp36-RemotePeerAddress
              $2: gbgp36-AutonomousSystem

        The holdtime for a given BGP peer has expired."
    ::= { gbgpNotificationsPrefix 36 }

gbgpNotification37 NOTIFICATION-TYPE
    OBJECTS { 
              gbgp37-Dest, 
              gbgp37-PrefixLen,
              gbgp37-NextHop 
            }
    STATUS current
    DESCRIPTION
        "Notification of Event GBGP.37

        Message: 'Add route $1/$2 $3'

        Parameters list:
              $1: gbgp37-Dest
              $2: gbgp37-PrefixLen
              $3: gbgp37-NextHop

        Adding route into BGP routing Database."
    ::= { gbgpNotificationsPrefix 37 }

gbgpNotification38 NOTIFICATION-TYPE
    OBJECTS { 
              gbgp38-Dest, 
              gbgp38-PrefixLen 
            }
    STATUS current
    DESCRIPTION
        "Notification of Event GBGP.38

        Message: 'Add direct rte $1/$2'

        Parameters list:
              $1: gbgp38-Dest
              $2: gbgp38-PrefixLen

        Adding direct route to BGP routing Database."
    ::= { gbgpNotificationsPrefix 38 }

gbgpNotification39 NOTIFICATION-TYPE
    OBJECTS { 
              gbgp39-RouteDest, 
              gbgp39-RoutePrefixLen,
              gbgp39-Route-MapName 
            }
    STATUS current
    DESCRIPTION
        "Notification of Event GBGP.39

        Message: 'Discarded $1/$2 due to route-map with name $3'

        Parameters list:
              $1: gbgp39-RouteDest
              $2: gbgp39-RoutePrefixLen
              $3: gbgp39-Route-MapName

        A route received in an update packet has been discarded due to
        preconfigured route-map in/out policy for this neighbor."
    ::= { gbgpNotificationsPrefix 39 }

gbgpNotification40 NOTIFICATION-TYPE
    OBJECTS { 
              gbgp40-RouteDest, 
              gbgp40-RoutePrefixLen,
              gbgp40-OldLocalPref,
              gbgp40-NewLocalPref 
            }
    STATUS current
    DESCRIPTION
        "Notification of Event GBGP.40

        Message: 'Changed localpref of route $1/$2 from $3 to $4'

        Parameters list:
              $1: gbgp40-RouteDest
              $2: gbgp40-RoutePrefixLen
              $3: gbgp40-OldLocalPref
              $4: gbgp40-NewLocalPref

        The local pref value of a route received in an update packet
        has been changed due to a preconfigured route-map in/out policy
        for this neighbor."
    ::= { gbgpNotificationsPrefix 40 }

gbgpNotification41 NOTIFICATION-TYPE
    OBJECTS { 
              gbgp41-RouteDest, 
              gbgp41-RoutePrefixLen,
              gbgp41-OldMetric,
              gbgp41-NewMetric 
            }
    STATUS current
    DESCRIPTION
        "Notification of Event GBGP.41

        Message: 'Changed metric of route $1/$2 from $3 to $4'

        Parameters list:
              $1: gbgp41-RouteDest
              $2: gbgp41-RoutePrefixLen
              $3: gbgp41-OldMetric
              $4: gbgp41-NewMetric

        The metric value of a route received in an update packet
        has been changed due to a preconfigured route-map in/out policy
        for this neighbor."
    ::= { gbgpNotificationsPrefix 41 }

gbgpNotification42 NOTIFICATION-TYPE
    OBJECTS { 
              gbgp42-RouteDest, 
              gbgp42-RoutePrefixLen,
              gbgp42-OldNexthop,
              gbgp42-NewNexthop,
              gbgp42-rtmapinout 
            }
    STATUS current
    DESCRIPTION
        "Notification of Event GBGP.42

        Message: 'Changed nexthop of route $1/$2 from $3 to $4 ($5)'

        Parameters list:
              $1: gbgp42-RouteDest
              $2: gbgp42-RoutePrefixLen
              $3: gbgp42-OldNexthop
              $4: gbgp42-NewNexthop
              $5: gbgp42-rtmapinout

        The nexthop value of a route received in an update packet
        has been changed due to a preconfigured route-map in/out policy
        for this neighbor."
    ::= { gbgpNotificationsPrefix 42 }

gbgpNotification43 NOTIFICATION-TYPE
    OBJECTS { 
              gbgp43-RouteDest, 
              gbgp43-RoutePrefixLen,
              gbgp43-NewNexthop,
              gbgp43-rtmapinout 
            }
    STATUS current
    DESCRIPTION
        "Notification of Event GBGP.43

        Message: 'Set nexthop of route $1/$2 to $3 ($4)'

        Parameters list:
              $1: gbgp43-RouteDest
              $2: gbgp43-RoutePrefixLen
              $3: gbgp43-NewNexthop
              $4: gbgp43-rtmapinout

        The nexthop value of a route transmitted in an update packet
        has been set due to a preconfigured route-map in/out policy
        for this neighbor."
    ::= { gbgpNotificationsPrefix 43 }

gbgpNotification44 NOTIFICATION-TYPE
    OBJECTS { 
              gbgp44-RouteDest, 
              gbgp44-RouteMask,
              gbgp44-OldNexthop,
              gbgp44-NewNexthop,
              gbgp44-rtmapinout 
            }
    STATUS current
    DESCRIPTION
        "Notification of Event GBGP.44

        Message: 'Changed nexthop of route $1/$2 from $3 to $4 ($5)'

        Parameters list:
              $1: gbgp44-RouteDest
              $2: gbgp44-RouteMask
              $3: gbgp44-OldNexthop
              $4: gbgp44-NewNexthop
              $5: gbgp44-rtmapinout

        The nexthop value of a route received in an update packet
        has been changed due to a preconfigured route-map in/out policy
        for this neighbor."
    ::= { gbgpNotificationsPrefix 44 }

gbgpNotification45 NOTIFICATION-TYPE
    OBJECTS { 
              gbgp45-RouteDest, 
              gbgp45-RouteMask,
              gbgp45-NewNexthop,
              gbgp45-rtmapinout 
            }
    STATUS current
    DESCRIPTION
        "Notification of Event GBGP.45

        Message: 'Set nexthop of route $1/$2 to $3 ($4)'

        Parameters list:
              $1: gbgp45-RouteDest
              $2: gbgp45-RouteMask
              $3: gbgp45-NewNexthop
              $4: gbgp45-rtmapinout

        The nexthop value of a route transmitted in an update packet
        has been set due to a preconfigured route-map in/out policy
        for this neighbor."
    ::= { gbgpNotificationsPrefix 45 }

gbgpNotification46 NOTIFICATION-TYPE
    OBJECTS { 
              gbgp46-RemotePeerAddress, 
              gbgp46-AutonomousSystem 
            }
    STATUS current
    DESCRIPTION
        "Notification of Event GBGP.46

        Message: 'Backward status transition. Peer $1/AS $2'

        Parameters list:
              $1: gbgp46-RemotePeerAddress
              $2: gbgp46-AutonomousSystem

        The status of the specified peer has changed from a higher
        numbered status to a lower numbered status."
    ::= { gbgpNotificationsPrefix 46 }

gbgpNotification47 NOTIFICATION-TYPE
    OBJECTS { 
              gbgp47-Error-msg, 
              gbgp47-RemotePeerAddress,
              gbgp47-AutonomousSystem 
            }
    STATUS current
    DESCRIPTION
        "Notification of Event GBGP.47

        Message: 'Received Update Error: $1 (Peer $2/AS $3)'

        Parameters list:
              $1: gbgp47-Error-msg
              $2: gbgp47-RemotePeerAddress
              $3: gbgp47-AutonomousSystem

        The update received contains an invalid field."
    ::= { gbgpNotificationsPrefix 47 }

gbgpNotification48 NOTIFICATION-TYPE
    OBJECTS { 
              gbgp48-opt-param, 
              gbgp48-opt-param-str,
              gbgp48-RemotePeerAddress 
            }
    STATUS current
    DESCRIPTION
        "Notification of Event GBGP.48

        Message: 'Received Open with optional parameter $1 ($2) (Peer $3)'

        Parameters list:
              $1: gbgp48-opt-param
              $2: gbgp48-opt-param-str
              $3: gbgp48-RemotePeerAddress

        Received an open msg with an optional parameter."
    ::= { gbgpNotificationsPrefix 48 }

gbgpNotification49 NOTIFICATION-TYPE
    OBJECTS { 
              gbgp49-capab-code, 
              gbgp49-capab-len,
              gbgp49-RemotePeerAddress 
            }
    STATUS current
    DESCRIPTION
        "Notification of Event GBGP.49

        Message: 'Received Open with Capability code $1 lenght $2 (Peer $3)'

        Parameters list:
              $1: gbgp49-capab-code
              $2: gbgp49-capab-len
              $3: gbgp49-RemotePeerAddress

        Received an open msg with capability in the optional paramater."
    ::= { gbgpNotificationsPrefix 49 }

gbgpNotification50 NOTIFICATION-TYPE
    OBJECTS { 
              gbgp50-afi, 
              gbgp50-safi,
              gbgp50-RemotePeerAddress 
            }
    STATUS current
    DESCRIPTION
        "Notification of Event GBGP.50

        Message: 'Received Open with MultiProtocol Extension Capability for afi/safi: $1/$2 (Peer $3)'

        Parameters list:
              $1: gbgp50-afi
              $2: gbgp50-safi
              $3: gbgp50-RemotePeerAddress

        Received an open msg with MP-EXT capability."
    ::= { gbgpNotificationsPrefix 50 }

gbgpNotification51 NOTIFICATION-TYPE
    OBJECTS { 
              gbgp51-capab-code, 
              gbgp51-RemotePeerAddress 
            }
    STATUS current
    DESCRIPTION
        "Notification of Event GBGP.51

        Message: 'Received Open with no supported Capability code $1, ignoring capability (Peer $2)'

        Parameters list:
              $1: gbgp51-capab-code
              $2: gbgp51-RemotePeerAddress

        Received an open msg with an unsupported capability (ignoring)."
    ::= { gbgpNotificationsPrefix 51 }

gbgpNotification52 NOTIFICATION-TYPE
    OBJECTS { 
              gbgp52-Action, 
              gbgp52-Prefix,
              gbgp52-PrefixLen,
              gbgp52-Information,
              gbgp52-Origin 
            }
    STATUS current
    DESCRIPTION
        "Notification of Event GBGP.52

        Message: 'Receive route $1 $2/$3 ($4) from $5'

        Parameters list:
              $1: gbgp52-Action
              $2: gbgp52-Prefix
              $3: gbgp52-PrefixLen
              $4: gbgp52-Information
              $5: gbgp52-Origin

        When a route is received, there are four posible actions: install (ins),
        remove (rem), discard (dis) or idle (idl).
        - install : the route is installed in the BGP table and marked as usable
        (the preference is a positive integer).
        - remove : the route will be removed from the BGP table if already exists.
        - discard : the route won't be installed in the BGP table.
        - idle : the route will never be usable (the preference is a negative
        integer).
        Along with each action, an informative message is shown. If everything
        goes well, the message is 'ok'. Otherwise, a descriptive message will
        explain the cause of the error."
    ::= { gbgpNotificationsPrefix 52 }

gbgpNotification53 NOTIFICATION-TYPE
    OBJECTS { 
              gbgp53-RemotePeerName, 
              gbgp53-DataHexDump 
            }
    STATUS current
    DESCRIPTION
        "Notification of Event GBGP.53

        Message: 'Received raw data from peer $1: hex dump is $2'

        Parameters list:
              $1: gbgp53-RemotePeerName
              $2: gbgp53-DataHexDump

        Data has been received from the specified peer. The received data is
        shown in hexadecimal."
    ::= { gbgpNotificationsPrefix 53 }

gbgpNotification54 NOTIFICATION-TYPE
    OBJECTS { 
              gbgp54-RemotePeerName, 
              gbgp54-DataHexDump 
            }
    STATUS current
    DESCRIPTION
        "Notification of Event GBGP.54

        Message: 'Received invalid message from peer $1: hex dump is $2'

        Parameters list:
              $1: gbgp54-RemotePeerName
              $2: gbgp54-DataHexDump

        An invalid message has been received from the specified peer. The
        received message data is shown in hexadecimal."
    ::= { gbgpNotificationsPrefix 54 }

gbgpNotification55 NOTIFICATION-TYPE
    OBJECTS { 
              gbgp55-RemotePeerName, 
              gbgp55-DataHexDump 
            }
    STATUS current
    DESCRIPTION
        "Notification of Event GBGP.55

        Message: 'Received message from peer $1: hex dump is $2'

        Parameters list:
              $1: gbgp55-RemotePeerName
              $2: gbgp55-DataHexDump

        A message has been received from the specified peer. The received
        message data is shown in hexadecimal."
    ::= { gbgpNotificationsPrefix 55 }

gbgpNotification56 NOTIFICATION-TYPE
    OBJECTS { 
              gbgp56-RemotePeerName, 
              gbgp56-DataHexDump 
            }
    STATUS current
    DESCRIPTION
        "Notification of Event GBGP.56

        Message: 'Send message to peer $1: hex dump is $2'

        Parameters list:
              $1: gbgp56-RemotePeerName
              $2: gbgp56-DataHexDump

        A message is sent to the specified peer. The message data is shown in
        hexadecimal."
    ::= { gbgpNotificationsPrefix 56 }

gbgpNotification57 NOTIFICATION-TYPE
    OBJECTS { 
              gbgp57-RemotePeerName, 
              gbgp57-DataHexDump 
            }
    STATUS current
    DESCRIPTION
        "Notification of Event GBGP.57

        Message: 'Send raw data to peer $1: hex dump is $2'

        Parameters list:
              $1: gbgp57-RemotePeerName
              $2: gbgp57-DataHexDump

        Data has been sent to the specified peer. The data is shown in
        hexadecimal."
    ::= { gbgpNotificationsPrefix 57 }

gbgpNotification58 NOTIFICATION-TYPE
    OBJECTS { 
              gbgp58-afi, 
              gbgp58-safi,
              gbgp58-RemotePeerAddress 
            }
    STATUS current
    DESCRIPTION
        "Notification of Event GBGP.58

        Message: 'Received Open without Multiprotocol Extensions Capability for afi/safi $1/$2 (Peer $3)'

        Parameters list:
              $1: gbgp58-afi
              $2: gbgp58-safi
              $3: gbgp58-RemotePeerAddress

        Received an open message without Multiprotocol Extensions Capability for
        an AFI/SAFI which is needed to operate."
    ::= { gbgpNotificationsPrefix 58 }

gbgpNotification59 NOTIFICATION-TYPE
    OBJECTS { 
              gbgp59-restart-flags, 
              gbgp59-restart-time,
              gbgp59-RemotePeerAddress 
            }
    STATUS current
    DESCRIPTION
        "Notification of Event GBGP.59

        Message: 'Received Open with Graceful Restart Capability with Restart Flags $1 Time $2 (Peer $3)'

        Parameters list:
              $1: gbgp59-restart-flags
              $2: gbgp59-restart-time
              $3: gbgp59-RemotePeerAddress

        Received an open message with Graceful Restart Capability. The Restart
        Flags and Restart Time values are shown."
    ::= { gbgpNotificationsPrefix 59 }

gbgpNotification60 NOTIFICATION-TYPE
    OBJECTS { 
              gbgp60-afi, 
              gbgp60-safi,
              gbgp60-flags,
              gbgp60-RemotePeerAddress 
            }
    STATUS current
    DESCRIPTION
        "Notification of Event GBGP.60

        Message: 'Received Open with Graceful Restart Capability with afi/safi $1/$2 Flags 0x$3 (Peer $4)'

        Parameters list:
              $1: gbgp60-afi
              $2: gbgp60-safi
              $3: gbgp60-flags
              $4: gbgp60-RemotePeerAddress

        Received an open message with Graceful Restart Capability, with the
        Address Family specified by the afi/safi pair. The Address Family Flags
        are shown."
    ::= { gbgpNotificationsPrefix 60 }

gbgpNotification61 NOTIFICATION-TYPE
    OBJECTS { 
              gbgp61-afi, 
              gbgp61-safi,
              gbgp61-RemotePeerAddress 
            }
    STATUS current
    DESCRIPTION
        "Notification of Event GBGP.61

        Message: 'Send Update End-of-RIB marker for afi/safi $1/$2 (Peer $3)'

        Parameters list:
              $1: gbgp61-afi
              $2: gbgp61-safi
              $3: gbgp61-RemotePeerAddress

        An Update message conforming to the End-Of-RIB marker specification is
        sent for the Address Family specified by the afi/safi pair."
    ::= { gbgpNotificationsPrefix 61 }

gbgpNotification62 NOTIFICATION-TYPE
    OBJECTS { 
              gbgp62-afi, 
              gbgp62-safi,
              gbgp62-RemotePeerAddress 
            }
    STATUS current
    DESCRIPTION
        "Notification of Event GBGP.62

        Message: 'Received Update End-of-RIB marker for afi/safi $1/$2 (Peer $3)'

        Parameters list:
              $1: gbgp62-afi
              $2: gbgp62-safi
              $3: gbgp62-RemotePeerAddress

        An Update message conforming to the End-Of-RIB marker specification has
        been received for the Address Family specified by the afi/safi pair."
    ::= { gbgpNotificationsPrefix 62 }

gbgpNotification63 NOTIFICATION-TYPE
    STATUS current
    DESCRIPTION
        "Notification of Event GBGP.63

        Message: 'Out of memory error'

        The system is out of memory."
    ::= { gbgpNotificationsPrefix 63 }

gbgpNotification64 NOTIFICATION-TYPE
    OBJECTS { 
              gbgp64-restart-flags, 
              gbgp64-restart-time,
              gbgp64-RemotePeerAddress 
            }
    STATUS current
    DESCRIPTION
        "Notification of Event GBGP.64

        Message: 'Send Open with Graceful Restart Capability with Restart Flags $1 Time $2 (Peer $3)'

        Parameters list:
              $1: gbgp64-restart-flags
              $2: gbgp64-restart-time
              $3: gbgp64-RemotePeerAddress

        Send an open message with Graceful Restart Capability. The Restart
        Flags and Restart Time values are shown."
    ::= { gbgpNotificationsPrefix 64 }

gbgpNotification65 NOTIFICATION-TYPE
    OBJECTS { 
              gbgp65-afi, 
              gbgp65-safi,
              gbgp65-flags,
              gbgp65-RemotePeerAddress 
            }
    STATUS current
    DESCRIPTION
        "Notification of Event GBGP.65

        Message: 'Send Open with Graceful Restart Capability with afi/safi $1/$2 Flags 0x$3 (Peer $4)'

        Parameters list:
              $1: gbgp65-afi
              $2: gbgp65-safi
              $3: gbgp65-flags
              $4: gbgp65-RemotePeerAddress

        Send an open message with Graceful Restart Capability, with the
        Address Family specified by the afi/safi pair. The Address Family Flags
        are shown."
    ::= { gbgpNotificationsPrefix 65 }

gbgpNotification66 NOTIFICATION-TYPE
    OBJECTS { 
              gbgp66-RemotePeerAddress 
            }
    STATUS current
    DESCRIPTION
        "Notification of Event GBGP.66

        Message: 'Graceful Restart on close triggers backup and discards stale information (Peer $1)'

        Parameters list:
              $1: gbgp66-RemotePeerAddress

        A peer session is being closed, and a backup for Graceful Restart has
        been triggered. Stale information is discarded because Graceful Restart
        is disabled."
    ::= { gbgpNotificationsPrefix 66 }

gbgpNotification67 NOTIFICATION-TYPE
    OBJECTS { 
              gbgp67-stale-type, 
              gbgp67-RemotePeerAddress 
            }
    STATUS current
    DESCRIPTION
        "Notification of Event GBGP.67

        Message: 'Graceful Restart on close triggers backup with $1 stale information (Peer $2)'

        Parameters list:
              $1: gbgp67-stale-type
              $2: gbgp67-RemotePeerAddress

        A peer session is being closed, and a backup for Graceful Restart has
        been triggered. New stale information is generated from scratch or
        reinitializing old stale information as specified in stale-type."
    ::= { gbgpNotificationsPrefix 67 }

gbgpNotification68 NOTIFICATION-TYPE
    OBJECTS { 
              gbgp68-dest-addr, 
              gbgp68-dest-len,
              gbgp68-RemotePeerAddress 
            }
    STATUS current
    DESCRIPTION
        "Notification of Event GBGP.68

        Message: 'Graceful Restart stale route create $1/$2 (Peer $3)'

        Parameters list:
              $1: gbgp68-dest-addr
              $2: gbgp68-dest-len
              $3: gbgp68-RemotePeerAddress

        Graceful Restart has created a stale route to the specified destination
        network."
    ::= { gbgpNotificationsPrefix 68 }

gbgpNotification69 NOTIFICATION-TYPE
    OBJECTS { 
              gbgp69-speaker-type, 
              gbgp69-family-count,
              gbgp69-route-count,
              gbgp69-RemotePeerAddress 
            }
    STATUS current
    DESCRIPTION
        "Notification of Event GBGP.69

        Message: 'Graceful Restart backup stale information for $1 speaker with $2 address families and $3 routes (Peer $4)'

        Parameters list:
              $1: gbgp69-speaker-type
              $2: gbgp69-family-count
              $3: gbgp69-route-count
              $4: gbgp69-RemotePeerAddress

        Graceful Restart made a backup generating stale information for a
        receiving or restarting speaker (as specified in speaker-type) with the
        specified number of address families and routes."
    ::= { gbgpNotificationsPrefix 69 }

gbgpNotification70 NOTIFICATION-TYPE
    OBJECTS { 
              gbgp70-speaker-type, 
              gbgp70-RemotePeerAddress 
            }
    STATUS current
    DESCRIPTION
        "Notification of Event GBGP.70

        Message: 'Graceful Restart established session for $1peaker (Peer $2)'

        Parameters list:
              $1: gbgp70-speaker-type
              $2: gbgp70-RemotePeerAddress

        Graceful Restart detected the session establishment for a receiving or
        restarting speaker as specified in speaker-type."
    ::= { gbgpNotificationsPrefix 70 }

gbgpNotification71 NOTIFICATION-TYPE
    OBJECTS { 
              gbgp71-afi, 
              gbgp71-safi,
              gbgp71-RemotePeerAddress 
            }
    STATUS current
    DESCRIPTION
        "Notification of Event GBGP.71

        Message: 'Graceful Restart established restarting speaker not blocking afi/safi $1/$2 (Peer $3)'

        Parameters list:
              $1: gbgp71-afi
              $2: gbgp71-safi
              $3: gbgp71-RemotePeerAddress

        Graceful Restart detected the session establishment for a restarting
        speaker, but no graceful restart capability was received or it was
        received with the 'Restart State' bit set. This peer will not be waited
        for to stop deferring."
    ::= { gbgpNotificationsPrefix 71 }

gbgpNotification72 NOTIFICATION-TYPE
    OBJECTS { 
              gbgp72-dest-addr, 
              gbgp72-dest-len,
              gbgp72-RemotePeerAddress 
            }
    STATUS current
    DESCRIPTION
        "Notification of Event GBGP.72

        Message: 'Graceful Restart route defer $1/$2 (Peer $3)'

        Parameters list:
              $1: gbgp72-dest-addr
              $2: gbgp72-dest-len
              $3: gbgp72-RemotePeerAddress

        Graceful Restart has deferred a restarting speaker route received in an
        update message. The route destination network is specified."
    ::= { gbgpNotificationsPrefix 72 }

gbgpNotification73 NOTIFICATION-TYPE
    OBJECTS { 
              gbgp73-dest-addr, 
              gbgp73-dest-len,
              gbgp73-cause,
              gbgp73-RemotePeerAddress 
            }
    STATUS current
    DESCRIPTION
        "Notification of Event GBGP.73

        Message: 'Graceful Restart stale route delete $1/$2 cause $3 (Peer $4)'

        Parameters list:
              $1: gbgp73-dest-addr
              $2: gbgp73-dest-len
              $3: gbgp73-cause
              $4: gbgp73-RemotePeerAddress

        Graceful Restart has deleted a stale route. The route destination
        network is specified. Possible causes are: 'rx nlri' when
        the receiving speaker stale route is superseded by a nlri received on an
        update message; 'term' when the BGP process is terminating; 'rx eor'
        when the End-of-RIB marker has been received by a receiving speaker;
        'estab' when the receiving speaker BGP session has been established and
        no 'Forwarding State' bit has been received for an address family;
        'stop defer' when the restarting speaker stops deferring an address
        family."
    ::= { gbgpNotificationsPrefix 73 }

gbgpNotification74 NOTIFICATION-TYPE
    OBJECTS { 
              gbgp74-RemotePeerAddress 
            }
    STATUS current
    DESCRIPTION
        "Notification of Event GBGP.74

        Message: 'Graceful Restart stale information timeout (Peer $1)'

        Parameters list:
              $1: gbgp74-RemotePeerAddress

        Graceful Restart stale information has timed out for the specified peer."
    ::= { gbgpNotificationsPrefix 74 }

gbgpNotification75 NOTIFICATION-TYPE
    OBJECTS { 
              gbgp75-cause, 
              gbgp75-RemotePeerAddress 
            }
    STATUS current
    DESCRIPTION
        "Notification of Event GBGP.75

        Message: 'Graceful Restart stale information delete with cause $1 (Peer $2)'

        Parameters list:
              $1: gbgp75-cause
              $2: gbgp75-RemotePeerAddress

        Graceful Restart stale information is deleted. The cause is specified."
    ::= { gbgpNotificationsPrefix 75 }

gbgpNotification76 NOTIFICATION-TYPE
    OBJECTS { 
              gbgp76-cause, 
              gbgp76-RemotePeerAddress 
            }
    STATUS current
    DESCRIPTION
        "Notification of Event GBGP.76

        Message: 'Graceful Restart stale peer delete with cause $1 (Peer $2)'

        Parameters list:
              $1: gbgp76-cause
              $2: gbgp76-RemotePeerAddress

        Graceful Restart stale peer is deleted. This is an idle unconfigured
        peer which lost the stale iformation. The cause is specified."
    ::= { gbgpNotificationsPrefix 76 }

gbgpNotification77 NOTIFICATION-TYPE
    OBJECTS { 
              gbgp77-afi, 
              gbgp77-safi,
              gbgp77-RemotePeerAddress 
            }
    STATUS current
    DESCRIPTION
        "Notification of Event GBGP.77

        Message: 'Graceful Restart initial update deferred for afi/safi $1/$2 (Peer $3)'

        Parameters list:
              $1: gbgp77-afi
              $2: gbgp77-safi
              $3: gbgp77-RemotePeerAddress

        Graceful Restart initial update has been deferred for the specified
        address family."
    ::= { gbgpNotificationsPrefix 77 }

gbgpNotification78 NOTIFICATION-TYPE
    OBJECTS { 
              gbgp78-afi, 
              gbgp78-safi,
              gbgp78-RemotePeerAddress 
            }
    STATUS current
    DESCRIPTION
        "Notification of Event GBGP.78

        Message: 'Graceful Restart initial update with eor for afi/safi $1/$2 (Peer $3)'

        Parameters list:
              $1: gbgp78-afi
              $2: gbgp78-safi
              $3: gbgp78-RemotePeerAddress

        Graceful Restart initial update with End-of-RIB marker has been started
        for the specified address family."
    ::= { gbgpNotificationsPrefix 78 }

gbgpNotification79 NOTIFICATION-TYPE
    OBJECTS { 
              gbgp79-timeout-seconds 
            }
    STATUS current
    DESCRIPTION
        "Notification of Event GBGP.79

        Message: 'Graceful Restart selection deferral started with timeout $1'

        Parameters list:
              $1: gbgp79-timeout-seconds

        Graceful Restart selection deferral started for all address families.
        The selection deferral timer has been started with the specified
        timeout."
    ::= { gbgpNotificationsPrefix 79 }

gbgpNotification80 NOTIFICATION-TYPE
    STATUS current
    DESCRIPTION
        "Notification of Event GBGP.80

        Message: 'Graceful Restart selection deferral terminated'

        Graceful Restart selection deferral has terminated because the BGP
        process is shut down."
    ::= { gbgpNotificationsPrefix 80 }

gbgpNotification81 NOTIFICATION-TYPE
    STATUS current
    DESCRIPTION
        "Notification of Event GBGP.81

        Message: 'Graceful Restart selection deferral timeout'

        Graceful Restart selection deferral timer has expired."
    ::= { gbgpNotificationsPrefix 81 }

gbgpNotification82 NOTIFICATION-TYPE
    STATUS current
    DESCRIPTION
        "Notification of Event GBGP.82

        Message: 'Graceful Restart selection deferral ended'

        Graceful Restart selection deferral ended for all families."
    ::= { gbgpNotificationsPrefix 82 }

gbgpNotification83 NOTIFICATION-TYPE
    OBJECTS { 
              gbgp83-afi, 
              gbgp83-safi 
            }
    STATUS current
    DESCRIPTION
        "Notification of Event GBGP.83

        Message: 'Graceful Restart selection deferral ended for afi/safi $1/$2'

        Parameters list:
              $1: gbgp83-afi
              $2: gbgp83-safi

        Graceful Restart selection deferral ended for the specified address
        family."
    ::= { gbgpNotificationsPrefix 83 }

gbgpNotification84 NOTIFICATION-TYPE
    OBJECTS { 
              gbgp84-dest-addr, 
              gbgp84-dest-len,
              gbgp84-RemotePeerAddress 
            }
    STATUS current
    DESCRIPTION
        "Notification of Event GBGP.84

        Message: 'Graceful Restart route undefer $1/$2 (Peer $3)'

        Parameters list:
              $1: gbgp84-dest-addr
              $2: gbgp84-dest-len
              $3: gbgp84-RemotePeerAddress

        Graceful Restart has stopped deferring a restarting speaker route. The
        route destination network is specified."
    ::= { gbgpNotificationsPrefix 84 }

gbgpNotification85 NOTIFICATION-TYPE
    OBJECTS { 
              gbgp85-RemotePeerAddress 
            }
    STATUS current
    DESCRIPTION
        "Notification of Event GBGP.85

        Message: 'Graceful Restart peer deferral started (Peer $1)'

        Parameters list:
              $1: gbgp85-RemotePeerAddress

        Graceful Restart peer has started address family deferral."
    ::= { gbgpNotificationsPrefix 85 }

gbgpNotification86 NOTIFICATION-TYPE
    OBJECTS { 
              gbgp86-RemotePeerAddress 
            }
    STATUS current
    DESCRIPTION
        "Notification of Event GBGP.86

        Message: 'Graceful Restart peer deferral stopped (Peer $1)'

        Parameters list:
              $1: gbgp86-RemotePeerAddress

        Graceful Restart peer has stopped address family deferral."
    ::= { gbgpNotificationsPrefix 86 }

gbgpNotification87 NOTIFICATION-TYPE
    OBJECTS { 
              gbgp87-RouteDest, 
              gbgp87-MaskLenght,
              gbgp87-NewOrigin 
            }
    STATUS current
    DESCRIPTION
        "Notification of Event GBGP.87

        Message: 'Changed origin of route $1/$2 to $3'

        Parameters list:
              $1: gbgp87-RouteDest
              $2: gbgp87-MaskLenght
              $3: gbgp87-NewOrigin

        The local origin value of a route received in an update packet
        has been changed due to a preconfigured route-map in/out policy
        for this neighbor."
    ::= { gbgpNotificationsPrefix 87 }

gbgpNotification88 NOTIFICATION-TYPE
    OBJECTS { 
              gbgp88-maximum-prefixes, 
              gbgp88-current-prefixes,
              gbgp88-RemotePeerAddress,
              gbgp88-AutonomousSystem 
            }
    STATUS current
    DESCRIPTION
        "Notification of Event GBGP.88

        Message: 'Peer prefix database overflow maximum $1 current $2 (Peer $3/AS $4)'

        Parameters list:
              $1: gbgp88-maximum-prefixes
              $2: gbgp88-current-prefixes
              $3: gbgp88-RemotePeerAddress
              $4: gbgp88-AutonomousSystem

        The peer prefix database is above the maximum-prefix configured limit.
        Both this limit and the current prefix count are shown."
    ::= { gbgpNotificationsPrefix 88 }


END
