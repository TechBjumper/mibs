CTRON-ISDN-CONFIGURATION-MIB DEFINITIONS ::= BEGIN

    --  CTRON-ISDN-CONFIGURATION-MIB  The Cabletron ISDN Configuration MIB.
    --  Revision: 1.00.00
    --  Date:  September 10, 1997

    --  Cabletron Systems, Inc.
    --  35 Industrial Way, P.O. Box 5005
    --  Rochester, NH 03866-0505
    --  (603) 332-9400
    --  support@ctron.com

    --  This module provides authoritative definitions for part
    --  of the naming tree below:
    --
    --  cabletron { enterprises 52 }
    --
    --  This module will be extended, as additional sub-sections
    --  of this naming tree are defined.
    --

    --  Cabletron Systems reserves the right to make changes in 
    --  specification and other information contained in this document 
    --  without prior notice.  The reader should consult Cabletron Systems
    --  to determine whether any such changes have been made.
    --
    --  In no event shall Cabletron Systems be liable for any incidental, 
    --  indirect, special, or consequential damages whatsoever (including 
    --  but not limited to lost profits) arising out of or related to this
    --  document or the information contained in it, even if Cabletron
    --  Systems has been advised of, known, or should have known, the 
    --  possibility of such damages.
    --
    --  Cabletron grants vendors, end-users, and other interested parties
    --  a non-exclusive license to use this Specification in connection
    --  with the management of Cabletron products.

    --  Copyright August 1997 Cabletron Systems


    IMPORTS
        enterprises, Counter    FROM RFC1155-SMI
        OBJECT-TYPE             FROM RFC-1212;

            DisplayString ::= OCTET STRING

    cabletron       OBJECT IDENTIFIER   ::= { enterprises 52 }
--                      1.3.6.1.4.1.52

    mibs            OBJECT IDENTIFIER   ::= { cabletron 4 }
--                      1.3.6.1.4.1.52.4

    ctron           OBJECT IDENTIFIER   ::= { mibs 1 }
--                      1.3.6.1.4.1.52.4.1

    ctDataLink      OBJECT IDENTIFIER   ::= { ctron 2 }
--                      1.3.6.1.4.1.52.4.1.2

    ctronWan        OBJECT IDENTIFIER   ::= { ctDataLink 7 }
--                      1.3.6.1.4.1.52.4.1.2.7

    ctISDNconfigMib OBJECT IDENTIFIER   ::= { ctronWan 4 }
--                      1.3.6.1.4.1.52.4.1.2.7.4

--------------------------------------------------------------------

--  ISDN control object 

    ctISDNcontrol OBJECT IDENTIFIER ::= { ctISDNconfigMib 1 }

--------------------------------------------------------------------

-- Signaling ("D") Channel configuration

--------------------------------------------------------------------

isdnDchTable OBJECT-TYPE
    SYNTAX  SEQUENCE OF IsdnDchEntry
    ACCESS  not-accessible
    STATUS  mandatory
    DESCRIPTION
    "A list of D channnel interfaces entries. The list consists
    of a single entry at this time."
    ::= { ctISDNcontrol 1 }

isdnDchEntry OBJECT-TYPE
    SYNTAX  IsdnDchEntry
    ACCESS  not-accessible
    STATUS  mandatory
    DESCRIPTION
    "A D channnel interface entry containing objects relating to
    the particular D channel."
    INDEX { isdnDchIndex }
    ::= { isdnDchTable 1 }

IsdnDchEntry ::=  
    SEQUENCE {  
        isdnDchIndex   
            INTEGER,
        isdnDchRateAccess
            INTEGER,
        isdnDchAllowedCh
            INTEGER,
        isdnDchChInUse
            INTEGER,
        isdnDchSupportedSwitches
            INTEGER,
        isdnDchSwitchType
            INTEGER,
        isdnDchSPID1
            OCTET STRING,
        isdnDchSPID2
            OCTET STRING,
        isdnDchDirNum1
            OCTET STRING,
        isdnDchDirNum2
            OCTET STRING,
        isdnDchOperStatus
            INTEGER
}  
  
isdnDchIndex  OBJECT-TYPE  
    SYNTAX  INTEGER   
    ACCESS read-only  
    STATUS mandatory  
    DESCRIPTION                                      
    "A unique index for this D Channel of this ISDN-Controller."
   ::= { isdnDchEntry  1 }  
  
isdnDchRateAccess   OBJECT-TYPE
    SYNTAX  INTEGER {  
            other (1), 
            bri1  (2),   -- Basic Rate Access 2x64 Kbps B + 16 Kbps D  
            pri1  (3),   -- Primary Rate Access at 1.544 Mbps  
            pri2  (4)    -- Primary Rate Access at 2.048 Mbps  
        }    
    ACCESS read-only  
    STATUS mandatory  
    DESCRIPTION  
    "The Rate Access of this ISDN interface."
    ::= { isdnDchEntry 2 }  
  
isdnDchAllowedCh   OBJECT-TYPE
    SYNTAX INTEGER -- BIT STRING {1..32}
    ACCESS read-only
    STATUS mandatory  
    DESCRIPTION  
    "A bit string with bit 1 signifiying time slot 1.  A set
    bit means that a B channel may be allocated on that time slot.
    A reset bit means the channel is reserved or otherwise out of service." 
    ::= { isdnDchEntry 3 }  
  
isdnDchChInUse   OBJECT-TYPE
    SYNTAX INTEGER -- BIT STRING {1..32}
    ACCESS read-only  
    STATUS mandatory  
    DESCRIPTION  
    "A bit string with bit 1 signifying time slot 1.  A set
    bit means that a B channel has been allocated on that time slot.
    A reset bit means the channel is available, reserved, or otherwise
    out of service." 
    ::= { isdnDchEntry 4 }  

isdnDchSupportedSwitches   OBJECT-TYPE
    SYNTAX  INTEGER {  -- BIT STRING {1..32}
            bri5ESS(2),
            bridms100(5),
            brini1(10),
            pri4ESS(16),
            pri5ESS(17)
        }    
    ACCESS read-only  
    STATUS mandatory  
    DESCRIPTION  
    "A bit string with each bit position signifying support of
    a specific switch type as indicated by the list. A set bit means
    that that switch type is supported."
    ::= { isdnDchEntry 5 }  
  
isdnDchSwitchType   OBJECT-TYPE
    SYNTAX  INTEGER {
            bri5ESS(2),
            bridms100(5),
            brini1(10),
            pri4ESS(16),
            pri5ESS(17)
          }    
    ACCESS read-write  
    STATUS mandatory  
    DESCRIPTION  
    "Switch type selector as indicated by the list."
    DEFVAL { brini1 }
    ::= { isdnDchEntry 6 }  

isdnDchSPID1 OBJECT-TYPE
    SYNTAX   OCTET STRING  
    ACCESS read-write  
    STATUS mandatory  
    DESCRIPTION  
    "The Service profile identifier for BRI channel 1."
    DEFVAL { "" }
   ::= { isdnDchEntry  7 }  

isdnDchSPID2 OBJECT-TYPE
    SYNTAX   OCTET STRING  
    ACCESS read-write  
    STATUS mandatory  
    DESCRIPTION  
    "The Service profile identifier for BRI channel 2."
    DEFVAL { "" }
   ::= { isdnDchEntry  8 }  
  
isdnDchDirNum1 OBJECT-TYPE
    SYNTAX   OCTET STRING  
    ACCESS read-write  
    STATUS mandatory  
    DESCRIPTION  
    "The local directory number for BRI channel 1."
    DEFVAL { "" }
   ::= { isdnDchEntry  9 }  

isdnDchDirNum2 OBJECT-TYPE
    SYNTAX   OCTET STRING  
    ACCESS read-write  
    STATUS mandatory  
    DESCRIPTION  
    "The local directory number for BRI channel 2."
    DEFVAL { "" }
   ::= { isdnDchEntry  10 }  

isdnDchOperStatus   OBJECT-TYPE
    SYNTAX INTEGER {
            inactive(1),
            active(2)
        }
    ACCESS read-only  
    STATUS mandatory  
    DESCRIPTION  
    "The operational status of the signalling channel."
    ::= { isdnDchEntry 11 }  

--------------------------------------------------------------------

-- Neighbor call control configuration table

--------------------------------------------------------------------

dialCtlNbrCfgTable OBJECT-TYPE
        SYNTAX      SEQUENCE OF DialCtlNbrCfgEntry
        ACCESS      not-accessible
        STATUS      mandatory
        DESCRIPTION
        "The list of neighbors from which the managed device
        will accept calls or to which it will place them."
       ::= { ctISDNcontrol 2}

dialCtlNbrCfgEntry OBJECT-TYPE
        SYNTAX      DialCtlNbrCfgEntry
        ACCESS      not-accessible
        STATUS      mandatory
        DESCRIPTION
        "A single Neighbor. This entry is effectively permanent,
        and contains address information describing the neighbor.
        The value of dialCtlNbrCfgOriginateAddress must be
        specified before a new row in this table can become
        active(1). Any writeable parameters in an existing entry
        can be modified while the entry is active. The modification
        will take effect when the neighbor in question will be
        called the next time."
        INDEX       { dialCtlNbrCfgId, dialCtlNbrCfgIndex }
      ::= { dialCtlNbrCfgTable 1 }

DialCtlNbrCfgEntry ::= SEQUENCE {
            dialCtlNbrCfgId                 INTEGER,
                                            -- neighbor ID
            dialCtlNbrCfgIndex              INTEGER,
                                            -- index value
            dialCtlNbrCfgIfIndex            INTEGER,
            dialCtlNbrCfgOriginateAddress   DisplayString,
                                            -- Call Address (outgoing)
            dialCtlNbrCfgAnswerAddress      DisplayString
                                            -- Call Address (incoming)
        }

dialCtlNbrCfgId OBJECT-TYPE
        SYNTAX      INTEGER (1..20)
        ACCESS      read-only
        STATUS      mandatory
        DESCRIPTION
        "This object defines a single neighbor. There may
        be several entries in this table for one neighbor,
        defining different ways of reaching this neighbor.
        Thus, there may be several entries in this table
        with the same value of dialCtlNbrCfgId.
        Multiple entries for one neighbor may be used to support
        multilink as well as backup lines. A single neighbor
        will be identified by a unique value of this object.
        Several entries for one neighbor MUST have the same
        value of dialCtlNbrCfgId and dialCtlNbrCfgIfIndex
        but still different ifEntries and thus different
        values of dialCtlNbrCfgIndex."
        ::= { dialCtlNbrCfgEntry 1 }

dialCtlNbrCfgIndex OBJECT-TYPE
        SYNTAX      INTEGER (1..20)
        ACCESS      read-only
        STATUS      mandatory
        DESCRIPTION
        "The index value which uniquely identifies an entry
        in this table."
        ::= { dialCtlNbrCfgEntry 2 }

dialCtlNbrCfgIfIndex OBJECT-TYPE
        SYNTAX      INTEGER (1..255)
        ACCESS      read-only
        STATUS      mandatory
        DESCRIPTION
        "The ifIndex value of the interface associated with this
        neighbor."
        ::= { dialCtlNbrCfgEntry 3 }

dialCtlNbrCfgOriginateAddress OBJECT-TYPE
        SYNTAX      DisplayString
        ACCESS      read-write
        STATUS      mandatory
        DESCRIPTION
        "Call Address at which the neighbor will be called.
        Think of this as the set of characters following 'ATDT '
        or the 'phone number' included in a D channel call request.
        The structure of this information will be switch type
        specific."
        DEFVAL      { "" }
        ::= { dialCtlNbrCfgEntry 4 }

dialCtlNbrCfgAnswerAddress OBJECT-TYPE
        SYNTAX      DisplayString
        ACCESS      read-write
        STATUS      mandatory
        DESCRIPTION
        "Calling Party Number information element, as for example
        passed in an ISDN SETUP message by a PBX or switch,
        for incoming calls. This address can be used to identify
        the neighbor. If this address is either unknown or identical
        to dialCtlNbrCfgOriginateAddress, this object will be a zero
        length string."
        DEFVAL      { "" }
        ::= { dialCtlNbrCfgEntry 5 }

--------------------------------------------------------------------

-- General profile configuration table

--------------------------------------------------------------------

rmtProfileTable OBJECT-TYPE
    SYNTAX  SEQUENCE OF RmtProfileEntry
    ACCESS  not-accessible
    STATUS  mandatory
    DESCRIPTION
    "The list of neighbors from which this device will accept calls or
    to which it will place them."
    ::= { ctISDNcontrol 3 }

rmtProfileEntry OBJECT-TYPE
    SYNTAX  RmtProfileEntry
    ACCESS  not-accessible
    STATUS  mandatory
    DESCRIPTION
    "A single Neighbor. This entry is effectively permanent, and contains
    information describing the neighbor."
    INDEX   { rmtProfileEntryIndex }
    ::= { rmtProfileTable 1 }

RmtProfileEntry ::=
 SEQUENCE {
    rmtProfileEntryIndex
        INTEGER,
    rmtProfileEntryName
        OCTET STRING,
    rmtProfileEntryMakerName
        OCTET STRING,
    rmtProfileEntryAction
        INTEGER,
    rmtProfileEntryState
        INTEGER,
    rmtProfileEntryMaxNeighbor
        INTEGER,
    rmtProfileEntryBchInUse
        INTEGER,
    rmtProfileEntryLinkHead
        INTEGER,
    rmtProfileEntryNextLink
        INTEGER,
    rmtProfileEntryMpCapable
        INTEGER,
    rmtProfileEntryMpLineUtilization
        INTEGER (1..100),
    rmtProfileEntryMpHistoryTime
        INTEGER (1..65535),
    rmtProfileEntryMpMoreBWSamples
        INTEGER (1..255),
    rmtProfileEntryMpLessBWSamples
        INTEGER (1..255),
    rmtProfileEntryMpMaxCallsAllowed
        INTEGER (1..255),
    rmtProfileEntryMpCallsToAdd
        INTEGER (1..255),
    rmtProfileEntryMpCallsToRemove
        INTEGER (1..255),
    rmtProfileEntryMpAvgPktSize
        INTEGER (1..1500),
    rmtProfileEntryMpRmtBwCtrl
        INTEGER
}

rmtProfileEntryIndex OBJECT-TYPE
        SYNTAX      INTEGER (1..20)
        ACCESS      read-only
        STATUS      mandatory
        DESCRIPTION
        "The index value which uniquely identifies an entry
        in this table."
        ::= { rmtProfileEntry 1 }

rmtProfileEntryName OBJECT-TYPE
    SYNTAX  OCTET STRING
    ACCESS  read-write
    STATUS  mandatory
    DESCRIPTION
    "ASCII name of the neighbor."
    DEFVAL { "" }
        ::= { rmtProfileEntry 2 }

rmtProfileEntryMakerName OBJECT-TYPE
    SYNTAX  OCTET STRING
    ACCESS  read-write
    STATUS  mandatory
    DESCRIPTION
    "ASCII name of the manufacturer of the neighbor. In other
    words, it is a name by which to uniquely identify the remote 
    access device to which the profile belongs."
    DEFVAL { "" }
    ::= { rmtProfileEntry 3 }

rmtProfileEntryAction OBJECT-TYPE
    SYNTAX  INTEGER {
              idle(1),
              connect(2),
              hangup(3)
          }
    ACCESS  read-write
    STATUS  mandatory
    DESCRIPTION
    "Desired action for the neighbor interface"
    ::= { rmtProfileEntry 4 }

rmtProfileEntryState OBJECT-TYPE
    SYNTAX  INTEGER {
            idle(1),
            calling(2),
            ringing(3),
            connected(4),
            answering(5),
            answered(6)
        }
    ACCESS  read-only
    STATUS  mandatory
    DESCRIPTION
    "Current state of the neighbor interface"
    ::= { rmtProfileEntry 5 }

rmtProfileEntryMaxNeighbor OBJECT-TYPE
    SYNTAX INTEGER 
    ACCESS read-only  
    STATUS mandatory  
    DESCRIPTION  
    "The maximum allowable dialCtlNbrCfgIndex. It is the number
    of instances of the profile."
    DEFVAL { 1 }
    ::= { rmtProfileEntry 6 }

rmtProfileEntryBchInUse    OBJECT-TYPE
    SYNTAX INTEGER -- BIT STRING { 1...32 }
    ACCESS read-only  
    STATUS mandatory  
    DESCRIPTION  
    "A bit string with bit 1 signifiying B channel 1.  A set
    bit means that this channel was assigned for current or
    last call."
    ::= { rmtProfileEntry 7 }

rmtProfileEntryLinkHead OBJECT-TYPE
    SYNTAX  INTEGER (0..20)
    ACCESS read-only  
    STATUS mandatory  
    DESCRIPTION  
    "A zero value signifies it is a primary profile. Otherwise, it is an
    instance profile and the value identifies the primary profile from
    which it was spawned."
    ::= { rmtProfileEntry 8 }  

rmtProfileEntryNextLink OBJECT-TYPE
    SYNTAX  INTEGER (0..20)
    ACCESS read-only  
    STATUS mandatory  
    DESCRIPTION  
    "A non-zero value identifies an instance profile. Whereas, a zero
    value either means it is a primary profile or the last instance
    of a primary profile."
    ::= { rmtProfileEntry 9 }  

rmtProfileEntryMpCapable OBJECT-TYPE
    SYNTAX  INTEGER {
            enabled(1),
            disabled(2)
        }
    ACCESS  read-write
    STATUS  mandatory
    DESCRIPTION
    "MP option selector. Set to a value of one when MP support is
    desired otherwise set to a value of two. The default setting is 
    disabled. When enabled the attempt is made to negotiate MP support.
    Both parties must support MP to be able to successfully negotiate
    MP."
    DEFVAL { disabled } 
    ::= { rmtProfileEntry 10 }
 
rmtProfileEntryMpLineUtilization OBJECT-TYPE
    SYNTAX  INTEGER (1..100)
    ACCESS  read-write
    STATUS  mandatory
    DESCRIPTION
    "Used to set the Line Utilization Threshold (LUT) % to compare
    against the linear weighted percentage to determine when
    more/less bandwidth is to be added/removed. Linear weighting
    is computed (averaged) over the period of time specified by
    the rmtProfileEntryMpHistoryTime object. Additional bandwidth
    is added whenever the linear weighted percentage exceeds the
    LUT % for a consecutive number of average line utilization
    reading(s) (computation(s)) as specified by the
    rmtProfileEntryMpMoreBWSamples object. Conversely,
    additional possible previously added Bandwidth is removed
    whenever the linear weighted percentage falls below the LUT %
    value for a consecutive number of average line utilization
    reading(s) (computation(s)) as specified by the
    rmtProfileEntryMpLessBWSamples object."
    DEFVAL { 50 }
    ::= { rmtProfileEntry 11 }
 
rmtProfileEntryMpHistoryTime OBJECT-TYPE
    SYNTAX  INTEGER (1..65535)
    ACCESS  read-write
    STATUS  mandatory
    DESCRIPTION
    "Used to set the history time value in seconds for the number of line
    utilization reading(s)/sample(s) desired to compute the average
    line utilization. It specifies the window size over which to
    to compute the average line utilization."
    DEFVAL { 60 }
    ::= { rmtProfileEntry 12 }
 
rmtProfileEntryMpMoreBWSamples OBJECT-TYPE
    SYNTAX  INTEGER (1..255)
    ACCESS  read-write
    STATUS  mandatory
    DESCRIPTION
    "Used to set the number of consecutive line utilization average
    computations that must exceed the LUT % value as specified by the
    rmtProfileEntryMpLineUtilization object before allowing possible
    more bandwidth to be added."
    DEFVAL { 5 }
    ::= { rmtProfileEntry 13 }
 
rmtProfileEntryMpLessBWSamples OBJECT-TYPE
    SYNTAX  INTEGER (1..255)
    ACCESS  read-write
    STATUS  mandatory
    DESCRIPTION
    "Used to set the number of consecutive line utilization average
    computations that must fall below the LUT % value as specified by the
    rmtProfileEntryMpLineUtilization object before removing possible
    previously added bandwidth."
    DEFVAL { 5 }
    ::= { rmtProfileEntry 14 }
 
rmtProfileEntryMpMaxCallsAllowed OBJECT-TYPE
    SYNTAX  INTEGER (1..255)
    ACCESS  read-write
    STATUS  mandatory
    DESCRIPTION
    "Used to set the maxium number of channels an ISDN MP capable
    call is allowed."
    DEFVAL { 1 }
    ::= { rmtProfileEntry 15 }
 
rmtProfileEntryMpCallsToAdd OBJECT-TYPE
    SYNTAX  INTEGER (1..255)
    ACCESS  read-write
    STATUS  mandatory
    DESCRIPTION
    "Used to set the number of additional channel(s) (call(s)) to
    increment by whenever the need for more bandwidth is determined."
    DEFVAL { 1 }
    ::= { rmtProfileEntry 16 }
 
rmtProfileEntryMpCallsToRemove OBJECT-TYPE
    SYNTAX  INTEGER (1..255)
    ACCESS  read-write
    STATUS  mandatory
    DESCRIPTION
    "Used to set the number of channel(s) (call(s)) to decrement
    by whenever the need for possible previously added additional
    bandwidth is determined to no longer be needed/desired."
    DEFVAL { 1 }
::= { rmtProfileEntry 17 }

rmtProfileEntryMpAvgPktSize OBJECT-TYPE
    SYNTAX  INTEGER (1..1500)
    ACCESS  read-write
    STATUS  mandatory
    DESCRIPTION
    "Used to set the average packet size by which to determine when
    its best to split a packet. This is an attempt to minimize the
    amount of buffering necessary at the remote device to maintain
    packet sequentiality."
    DEFVAL { 260 }
::= { rmtProfileEntry 18 }
 
rmtProfileEntryMpRmtBwCtrl OBJECT-TYPE
    SYNTAX  INTEGER {
            enabled(1),
            disabled(2)
        }
    ACCESS  read-write
    STATUS  mandatory
    DESCRIPTION
    "MP remote bandwidth control selector. Set to a one when
    bandwidth changes are permitted by either side ie by both
    parties otherwise set to a value of two. The default setting
    is disabled. That is to say, only the caller is permitted
    to change (control) the bandwidth."
    DEFVAL { disabled }
    ::= { rmtProfileEntry 19 }

--------------------------------------------------------------------

   callHistory OBJECT IDENTIFIER ::= { ctISDNconfigMib 2 }
 
--------------------------------------------------------------------

-- Call history table

--------------------------------------------------------------------

callHistoryTableMaxLength OBJECT-TYPE
        SYNTAX      INTEGER 
        ACCESS      read-only
        STATUS      mandatory
        DESCRIPTION
        "The upper limit on the number of entries that the
        callHistoryTable may contain. When this table is full,
        the oldest entry will be deleted and the new one will
        be created."
        DEFVAL { 50 }
        ::= { callHistory 1 }

-- callHistoryTable
-- Table to store the past call information. The Destination number
-- and the call connect and disconnect time, the disconnection cause
-- are stored. These calls could be circuit switched or they could
-- be virtual circuits. History of each and every call is stored,
-- of successful calls as well as of unsuccessful and rejected calls.
-- An entry will be created when a call is cleared.

callHistoryTable OBJECT-TYPE
        SYNTAX      SEQUENCE OF CallHistoryEntry
        ACCESS      not-accessible
        STATUS      mandatory
        DESCRIPTION
        "A table containing information about specific
        calls to a specific destination."
        ::= { callHistory 2 }

callHistoryEntry OBJECT-TYPE
        SYNTAX      CallHistoryEntry
        ACCESS      not-accessible
        STATUS      mandatory
        DESCRIPTION
        "The information regarding a single Connection."
        INDEX       { callHistoryIndex }
        ::= { callHistoryTable 1 }

CallHistoryEntry ::=
        SEQUENCE {
            callHistorySetupTime                 INTEGER,
            callHistoryIndex                     INTEGER,
            callHistoryPeerAddress               DisplayString,
            callHistoryNeighborId                INTEGER,
            callHistoryLogicalIfIndex            INTEGER,
            callHistoryDisconnectCause           INTEGER,
            callHistoryConnectTime               INTEGER,
            callHistoryDisconnectTime            INTEGER,
            callHistoryCallOrigin                INTEGER,
            callHistoryInfoType                  INTEGER,
            callHistoryTransmitPackets           Counter,
            callHistoryTransmitBytes             Counter,
            callHistoryReceivePackets            Counter,
            callHistoryReceiveBytes              Counter
        }

callHistorySetupTime OBJECT-TYPE
        SYNTAX      INTEGER
        ACCESS      read-only
        STATUS      mandatory
        DESCRIPTION
        "The value of system up time when the call associated to this
        entry was started. This will be useful for an NMS to
        retrieve all calls after a specific time. Also, this object
        can be useful in finding large delays between the time the
        call was started and the time the call was connected.
        For ISDN media, this will be the time when the setup
        message was received from or sent to the network."
        ::= { callHistoryEntry 1 }

callHistoryIndex OBJECT-TYPE
        SYNTAX      INTEGER (1..50)
        ACCESS      read-only
        STATUS      mandatory
        DESCRIPTION
        "Index variable to access the CallHistoryEntry objects
        of the callHistoryTable."
        ::= { callHistoryEntry 2 }

callHistoryPeerAddress OBJECT-TYPE
        SYNTAX      DisplayString
        ACCESS      read-only
        STATUS      mandatory
        DESCRIPTION
        "The number this call is connected to. If the number is
        not available, then it will have a length of zero."
        ::= { callHistoryEntry 3 }

callHistoryNeighborId OBJECT-TYPE
        SYNTAX      INTEGER (1..20)
        ACCESS      read-only
        STATUS      mandatory
        DESCRIPTION
        "This is the Id value of the neighbor table entry
        to which this call was made. If a neighbor table entry
        for this call does not exist, the value of this object
        will be zero."
        ::= { callHistoryEntry 4 }

callHistoryLogicalIfIndex OBJECT-TYPE
        SYNTAX      INTEGER (1..255)
        ACCESS      read-only
        STATUS      mandatory
        DESCRIPTION
        "This is the ifIndex value of the logical interface through
        which this call was made."
        ::= { callHistoryEntry 5 }

callHistoryDisconnectCause OBJECT-TYPE
        SYNTAX      INTEGER {
            unassignedNumber(1),
            noRouteToDestination(2),
            channelUnacceptable(6),
            normalCallClearing(16),
            userBusy(17),
            noUserResponding(18),
            callRejected(21),
            numberChangedAddress(22),
            invalidNumberFormat(28),
            normalUnspecified(31),
            noChannelAvailable(34),
            networkOutOfOrder(38),
            temporaryFailure(41),
            switchingEquipmentCongestion(42),
            userInfoDiscarded(43),
            requestedChannelNotAvailable(44),
            outgoingCallsBarred(52),
            incomingCallsBarred(54),
            bearerCapabilityNotPresentlyAvail(58),
            serviceNotAvailable(63),
            bearerServiceNotImplemented(65),
            channelTypeNotImplemented(66),
            onlyRestrictedChannelAvailable(70),
            serviceOrOptionNotImplemeted(79),
            invalidCallReferenceValue(81),
            identifiedChannelDoesNotExist(82),
            invalidDigitValueForAddress(85),
            incompatibleDestination(88),
            destinationAddressMissing(90),
            transitNetworkDoesNotExist(91),
            invalidMessageSpecified(95),
            mandatoryIEmissing(96),
            messageTypeNonexistentOrNotImplemented(97),
            messageNotCompatibleWithCallState(98),
            iEnotImplemented(99),
            invalidIEcontents(100),
            protocolError(111),
            callAlreadyActive(133),
            lineDisabled(134),
            badParameter(135),
            timeoutOccured(136),
            noCallActive(138)
        }
        ACCESS      read-only
        STATUS      mandatory
        DESCRIPTION
        "The encoded network cause value associated with this call.
        The value of this object will depend on the interface type
        as well as on the protocol and protocol version being
        used on this interface. The more common cause values are
        indicated in the list."
        ::= { callHistoryEntry 6 }

callHistoryConnectTime OBJECT-TYPE
        SYNTAX      INTEGER
        ACCESS      read-only
        STATUS      mandatory
        DESCRIPTION
        "The value of system up time when the call was connected."
        ::= { callHistoryEntry 7 }

callHistoryDisconnectTime OBJECT-TYPE
        SYNTAX      INTEGER
        ACCESS      read-only
        STATUS      mandatory
        DESCRIPTION
        "The value of system up time when the call was disconnected."
        ::= { callHistoryEntry 8 }

callHistoryCallOrigin OBJECT-TYPE
        SYNTAX      INTEGER {
            originate(1),
            answer(2),
            callback(3)
        }
        ACCESS      read-only
        STATUS      mandatory
        DESCRIPTION
        "The call origin."
        ::= { callHistoryEntry 9 }

callHistoryInfoType OBJECT-TYPE
        SYNTAX      INTEGER {
            other(1),                   -- e.g. for non-isdn media
            speech(2),
            unrestrictedDigital(3),     -- 64k/s data
            unrestrictedDigital56(4),   -- with 56k rate adaption
            restrictedDigital(5),
            audio31(6),                 -- 3.1 kHz audio
            audio7(7),                  -- 7 kHz audio
            video(8),
            packetSwitched(9)
        }
        ACCESS      read-only
        STATUS      mandatory
        DESCRIPTION
            "The information type for this call."
        ::= { callHistoryEntry 10 }

callHistoryTransmitPackets OBJECT-TYPE
        SYNTAX      Counter
        ACCESS      read-only
        STATUS      mandatory
        DESCRIPTION
        "The number of packets which were transmitted while this
        call was active."
        ::= { callHistoryEntry 11 }

callHistoryTransmitBytes OBJECT-TYPE
        SYNTAX      Counter
        ACCESS      read-only
        STATUS      mandatory
        DESCRIPTION
        "The number of bytes which were transmitted while this
        call was active."
        ::= { callHistoryEntry 12 }

callHistoryReceivePackets OBJECT-TYPE
        SYNTAX      Counter
        ACCESS      read-only
        STATUS      mandatory
        DESCRIPTION
        "The number of packets which were received while this
        call was active."
        ::= { callHistoryEntry 13 }

callHistoryReceiveBytes OBJECT-TYPE
        SYNTAX      Counter
        ACCESS      read-only
        STATUS      mandatory
        DESCRIPTION
        "The number of bytes which were received while this
        call was active."
        ::= { callHistoryEntry 14 }

END
