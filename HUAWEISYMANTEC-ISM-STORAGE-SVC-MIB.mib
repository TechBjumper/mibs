--
-- HUAWEISYMANTEC-ISM-STORAGE-SVC-MIB.my
-- MIB generated by MG-SOFT Visual MIB Builder Version 4.0 Build 347
-- Thursday, February 09, 2012 at 13:52:46
--

	HUAWEISYMANTEC-ISM-STORAGE-SVC-MIB DEFINITIONS ::= BEGIN
 
		IMPORTS
			enterprises, IpAddress, Integer32, Unsigned32, Gauge32, 
			Counter64, OBJECT-TYPE, MODULE-IDENTITY			
				FROM SNMPv2-SMI			
			DisplayString			
				FROM SNMPv2-TC;
	
	
		-- 1.3.6.1.4.1.34774
		huaweisymantec MODULE-IDENTITY 
			LAST-UPDATED "200809171628Z"		-- September 17, 2008 at 16:28 GMT
			ORGANIZATION 
				"HUAWEI-Symantec"
			CONTACT-INFO 
				"Contact-info."
			DESCRIPTION 
				"Description."
			REVISION "200809171629Z"		-- September 17, 2008 at 16:29 GMT
			DESCRIPTION 
				""
			::= { enterprises 34774 }

		
	
--
-- Type definitions
--
	
--  Type definitions
-- 
-- 
-- 
		NodeCodeString ::= OCTET STRING (SIZE (15..17))

		RowStatus ::= INTEGER
			{
			active(1),
			notInService(2),
			notReady(3),
			createAndGo(4),
			createAndWait(5),
			destroy(6)
			}

	
	
--
-- Node definitions
--
	
		-- 1.3.6.1.4.1.34774.4
		hsStorage OBJECT IDENTIFIER ::= { huaweisymantec 4 }
-- 
		
		-- 1.3.6.1.4.1.34774.4.1
		hsISM OBJECT IDENTIFIER ::= { hsStorage 1 }
-- ISM MIB
		
		-- 1.3.6.1.4.1.34774.4.1.1
		common OBJECT IDENTIFIER ::= { hsISM 1 }

		
		-- 1.3.6.1.4.1.34774.4.1.1.6
		version OBJECT-TYPE
			SYNTAX DisplayString
			MAX-ACCESS read-only
			STATUS current
			DESCRIPTION
				"Description."
			::= { common 6 }

		
		-- 1.3.6.1.4.1.34774.4.1.1.5
		totalCapacity OBJECT-TYPE
			SYNTAX Counter64
			MAX-ACCESS read-only
			STATUS current
			DESCRIPTION
				"Description."
			::= { common 5 }

		
		-- 1.3.6.1.4.1.34774.4.1.1.4
		usedCapacity OBJECT-TYPE
			SYNTAX Counter64
			MAX-ACCESS read-only
			STATUS current
			DESCRIPTION
				"Description."
			::= { common 4 }

		
		-- 1.3.6.1.4.1.34774.4.1.1.3
		staus OBJECT-TYPE
			SYNTAX Integer32
			MAX-ACCESS read-only
			STATUS current
			DESCRIPTION
				"Description."
			::= { common 3 }

		
		-- 1.3.6.1.4.1.34774.4.1.1.2
		deviceType OBJECT-TYPE
			SYNTAX Integer32
			MAX-ACCESS read-only
			STATUS current
			DESCRIPTION
				"Description."
			::= { common 2 }

		
		-- 1.3.6.1.4.1.34774.4.1.1.1
		deviceId OBJECT-TYPE
			SYNTAX DisplayString
			MAX-ACCESS read-only
			STATUS current
			DESCRIPTION
				"Description."
			::= { common 1 }

		
		-- 1.3.6.1.4.1.34774.4.1.5
		managerPort OBJECT IDENTIFIER ::= { hsISM 5 }

		
		-- 1.3.6.1.4.1.34774.4.1.5.1
		portNumber OBJECT-TYPE
			SYNTAX Integer32
			MAX-ACCESS read-write
			STATUS current
			DESCRIPTION
				"Description."
			::= { managerPort 1 }

		
		-- 1.3.6.1.4.1.34774.4.1.5.2
		addrTable OBJECT-TYPE
			SYNTAX SEQUENCE OF AddrEntry
			MAX-ACCESS not-accessible
			STATUS current
			DESCRIPTION
				"Description."
			::= { managerPort 2 }

		
		-- 1.3.6.1.4.1.34774.4.1.5.2.1
		addrEntry OBJECT-TYPE
			SYNTAX AddrEntry
			MAX-ACCESS not-accessible
			STATUS current
			DESCRIPTION
				"Description."
			INDEX { addrName }
			::= { addrTable 1 }

		
		AddrEntry ::=
			SEQUENCE { 
				addrName
					OCTET STRING,
				addrIP
					IpAddress
			 }

		-- 1.3.6.1.4.1.34774.4.1.5.2.1.1
		addrName OBJECT-TYPE
			SYNTAX OCTET STRING (SIZE (0..64))
			MAX-ACCESS read-create
			STATUS current
			DESCRIPTION
				"Description."
			::= { addrEntry 1 }

		
		-- 1.3.6.1.4.1.34774.4.1.5.2.1.2
		addrIP OBJECT-TYPE
			SYNTAX IpAddress
			MAX-ACCESS read-create
			STATUS current
			DESCRIPTION
				"Description."
			::= { addrEntry 2 }

		
		-- 1.3.6.1.4.1.34774.4.1.19
		hsStorageService OBJECT IDENTIFIER ::= { hsISM 19 }

		
		-- 1.3.6.1.4.1.34774.4.1.19.1
		hsVirtualArray OBJECT IDENTIFIER ::= { hsStorageService 1 }

		
		-- 1.3.6.1.4.1.34774.4.1.19.1.1
		vis OBJECT IDENTIFIER ::= { hsVirtualArray 1 }

		
		-- 1.3.6.1.4.1.34774.4.1.19.2
		hsNASGateway OBJECT IDENTIFIER ::= { hsStorageService 2 }

		
		-- 1.3.6.1.4.1.34774.4.1.19.3
		hsArray OBJECT IDENTIFIER ::= { hsStorageService 3 }

		
		-- 1.3.6.1.4.1.34774.4.1.19.3.1
		s2600 OBJECT IDENTIFIER ::= { hsArray 1 }

		
		-- 1.3.6.1.4.1.34774.4.1.19.3.2
		s5000 OBJECT IDENTIFIER ::= { hsArray 2 }

		
-- 
		-- 1.3.6.1.4.1.34774.4.1.19.4
		link OBJECT IDENTIFIER ::= { hsStorageService 4 }

		
		-- 1.3.6.1.4.1.34774.4.1.19.4.2
		linkMode OBJECT-TYPE
			SYNTAX Gauge32
			MAX-ACCESS read-only
			STATUS current
			DESCRIPTION
				"
				1 - 
				2 - 
				"
			::= { link 2 }

		
-- 
		-- 1.3.6.1.4.1.34774.4.1.19.4.3
		linkTable OBJECT-TYPE
			SYNTAX SEQUENCE OF LinkEntry
			MAX-ACCESS not-accessible
			STATUS current
			DESCRIPTION
				"Description."
			::= { link 3 }

		
		-- 1.3.6.1.4.1.34774.4.1.19.4.3.1
		linkEntry OBJECT-TYPE
			SYNTAX LinkEntry
			MAX-ACCESS not-accessible
			STATUS current
			DESCRIPTION
				"Description."
			INDEX { linkWWN, linkIP }
			::= { linkTable 1 }

		
		LinkEntry ::=
			SEQUENCE { 
				linkWWN
					OCTET STRING,
				linkIP
					IpAddress,
				linkManagedRelation
					Gauge32
			 }

		-- 1.3.6.1.4.1.34774.4.1.19.4.3.1.1
		linkWWN OBJECT-TYPE
			SYNTAX OCTET STRING
			MAX-ACCESS read-only
			STATUS current
			DESCRIPTION
				"
				"
			::= { linkEntry 1 }

		
		-- 1.3.6.1.4.1.34774.4.1.19.4.3.1.2
		linkIP OBJECT-TYPE
			SYNTAX IpAddress
			MAX-ACCESS read-only
			STATUS current
			DESCRIPTION
				"
				"
			::= { linkEntry 2 }

		
		-- 1.3.6.1.4.1.34774.4.1.19.4.3.1.3
		linkManagedRelation OBJECT-TYPE
			SYNTAX Gauge32
			MAX-ACCESS read-only
			STATUS current
			DESCRIPTION
				"
				0 - 
				1 - 
				"
			::= { linkEntry 3 }

		
		-- 1.3.6.1.4.1.34774.4.1.19.5
		deployMap OBJECT IDENTIFIER ::= { hsStorageService 5 }

		
		-- 1.3.6.1.4.1.34774.4.1.19.5.1
		deployMapTable OBJECT-TYPE
			SYNTAX SEQUENCE OF DeployMapEntry
			MAX-ACCESS not-accessible
			STATUS current
			DESCRIPTION
				"Description"
			::= { deployMap 1 }

		
		-- 1.3.6.1.4.1.34774.4.1.19.5.1.1
		deployMapEntry OBJECT-TYPE
			SYNTAX DeployMapEntry
			MAX-ACCESS not-accessible
			STATUS current
			DESCRIPTION
				"Description."
			INDEX { deviceWwn }
			::= { deployMapTable 1 }

		
		DeployMapEntry ::=
			SEQUENCE { 
				deviceWwn
					OCTET STRING,
				deviceRoom
					Gauge32,
				deviceShelf
					Gauge32,
				deviceSlot
					Gauge32
			 }

		-- 1.3.6.1.4.1.34774.4.1.19.5.1.1.1
		deviceWwn OBJECT-TYPE
			SYNTAX OCTET STRING
			MAX-ACCESS read-only
			STATUS current
			DESCRIPTION
				""
			::= { deployMapEntry 1 }

		
		-- 1.3.6.1.4.1.34774.4.1.19.5.1.1.2
		deviceRoom OBJECT-TYPE
			SYNTAX Gauge32
			MAX-ACCESS read-only
			STATUS current
			DESCRIPTION
				""
			::= { deployMapEntry 2 }

		
		-- 1.3.6.1.4.1.34774.4.1.19.5.1.1.3
		deviceShelf OBJECT-TYPE
			SYNTAX Gauge32
			MAX-ACCESS read-only
			STATUS current
			DESCRIPTION
				""
			::= { deployMapEntry 3 }

		
		-- 1.3.6.1.4.1.34774.4.1.19.5.1.1.4
		deviceSlot OBJECT-TYPE
			SYNTAX Gauge32
			MAX-ACCESS read-only
			STATUS current
			DESCRIPTION
				""
			::= { deployMapEntry 4 }

		
		-- 1.3.6.1.4.1.34774.4.1.19.6
		dha OBJECT IDENTIFIER ::= { hsStorageService 6 }

		
		-- 1.3.6.1.4.1.34774.4.1.19.6.1
		dhaControl OBJECT IDENTIFIER ::= { dha 1 }

		
		-- 1.3.6.1.4.1.34774.4.1.19.6.1.1
		dhaServiceControl OBJECT-TYPE
			SYNTAX Gauge32 (0..1)
			MAX-ACCESS read-write
			STATUS current
			DESCRIPTION
				"can get DHA service's status, and control service
				0 -- stop DHA service
				1 -- start DHA service"
			::= { dhaControl 1 }

		
		-- 1.3.6.1.4.1.34774.4.1.19.6.1.2
		dhaDataControl OBJECT-TYPE
			SYNTAX Gauge32 (0..1)
			MAX-ACCESS read-write
			STATUS current
			DESCRIPTION
				"0 -- stop to download DHA data
				1 -- start to download DHA data"
			::= { dhaControl 2 }

		
		-- 1.3.6.1.4.1.34774.4.1.19.6.2
		dhaPolicy OBJECT IDENTIFIER ::= { dha 2 }

		
		-- 1.3.6.1.4.1.34774.4.1.19.6.2.1
		dhaCpuLimit OBJECT-TYPE
			SYNTAX Gauge32 (1..100)
			MAX-ACCESS read-write
			STATUS current
			DESCRIPTION
				"DHA service stop to collect data when CPU usage is higher than this limit.
				it is a percent."
			::= { dhaPolicy 1 }

		
		-- 1.3.6.1.4.1.34774.4.1.19.6.2.2
		dhaMemoryLimit OBJECT-TYPE
			SYNTAX Gauge32 (1..100)
			MAX-ACCESS read-write
			STATUS current
			DESCRIPTION
				"DHA service stop to collect data when memory usage is higher than this limit.
				it is a percent."
			::= { dhaPolicy 2 }

		
		-- 1.3.6.1.4.1.34774.4.1.19.6.2.3
		dhaCollectionCycle OBJECT-TYPE
			SYNTAX Gauge32
			MAX-ACCESS read-write
			STATUS current
			DESCRIPTION
				"this cycle is DHA start to collect data interval.
				unit is day."
			::= { dhaPolicy 3 }

		
		-- 1.3.6.1.4.1.34774.4.1.19.6.2.4
		dhaCollectionTaskCycle OBJECT-TYPE
			SYNTAX Gauge32 (1..60)
			MAX-ACCESS read-write
			STATUS current
			DESCRIPTION
				"how much minutes is a cycle the task of dha collection collect data."
			::= { dhaPolicy 4 }

		
		-- 1.3.6.1.4.1.34774.4.1.19.6.2.5
		dhaStartCollectTime OBJECT-TYPE
			SYNTAX Unsigned32
			MAX-ACCESS read-write
			STATUS current
			DESCRIPTION
				"the time is DHA service start to collect data.
				the unit is the second calculated from 00:00:00 to start-time in a day.
				because the device is UTC time, so local time need to convert UTC time."
			::= { dhaPolicy 5 }

		
		-- 1.3.6.1.4.1.34774.4.1.19.6.2.6
		dhaFileSpace OBJECT-TYPE
			SYNTAX Gauge32
			MAX-ACCESS read-write
			STATUS current
			DESCRIPTION
				"it is the upper limit saved DHA data.
				the unit is M bytes.
				 "
			::= { dhaPolicy 6 }

		
		-- 1.3.6.1.4.1.34774.4.1.19.6.2.7
		dhaTimingCollectionDelay OBJECT-TYPE
			SYNTAX Gauge32 (1..60)
			MAX-ACCESS read-write
			STATUS current
			DESCRIPTION
				"when DHA service start to collect the data, it will check all limits.
				if it which don't allow by limits exist,
				DHA service will delay some minutes, and continue to retry it.
				this leaf can get or set delay-time, the unit is minute."
			::= { dhaPolicy 7 }

		
		-- 1.3.6.1.4.1.34774.4.1.19.6.2.8
		dhaTimingCollectionRetryTimes OBJECT-TYPE
			SYNTAX Gauge32
			MAX-ACCESS read-write
			STATUS current
			DESCRIPTION
				"when DHA service start to collect the data, it will check all limits.
				if it which don't allow by limits exist,
				DHA service will delay some minutes, and continue to retry it.
				this leaf can get or set delay-times."
			::= { dhaPolicy 8 }

		
		-- 1.3.6.1.4.1.34774.4.1.19.6.2.9
		dhaExceptionCollectionDelay OBJECT-TYPE
			SYNTAX Gauge32
			MAX-ACCESS read-write
			STATUS current
			DESCRIPTION
				"when DHA service had received the exceptional event,
				it will start to collect the data, and check all limits.
				if it which don't allow by limits exist,
				DHA service will delay some minutes, and continue to try it.
				this leaf can get or set delay-time, the unit is minute."
			::= { dhaPolicy 9 }

		
		-- 1.3.6.1.4.1.34774.4.1.19.6.2.10
		dhaExcetpionCollectionRetryTimes OBJECT-TYPE
			SYNTAX Gauge32
			MAX-ACCESS read-write
			STATUS current
			DESCRIPTION
				"when DHA service had received the exceptional event,
				it will start to collect the data, and check all limits.
				if it which don't allow by limits exist,
				DHA service will delay some minutes, and continue to try it.
				this leaf can get or set delay-times."
			::= { dhaPolicy 10 }

		
		-- 1.3.6.1.4.1.34774.4.1.19.7
		managerUser OBJECT IDENTIFIER ::= { hsStorageService 7 }

		
		-- 1.3.6.1.4.1.34774.4.1.19.7.1
		userTable OBJECT-TYPE
			SYNTAX SEQUENCE OF UserEntry
			MAX-ACCESS not-accessible
			STATUS current
			DESCRIPTION
				"Description."
			::= { managerUser 1 }

		
		-- 1.3.6.1.4.1.34774.4.1.19.7.1.1
		userEntry OBJECT-TYPE
			SYNTAX UserEntry
			MAX-ACCESS not-accessible
			STATUS current
			DESCRIPTION
				"Description."
			INDEX { userLevel }
			::= { userTable 1 }

		
		UserEntry ::=
			SEQUENCE { 
				userLevel
					Integer32,
				userName
					OCTET STRING,
				userPassword
					OCTET STRING
			 }

		-- 1.3.6.1.4.1.34774.4.1.19.7.1.1.1
		userLevel OBJECT-TYPE
			SYNTAX Integer32 (1..3)
			MAX-ACCESS read-write
			STATUS current
			DESCRIPTION
				"Description."
			::= { userEntry 1 }

		
		-- 1.3.6.1.4.1.34774.4.1.19.7.1.1.2
		userName OBJECT-TYPE
			SYNTAX OCTET STRING
			MAX-ACCESS read-write
			STATUS current
			DESCRIPTION
				"Description."
			::= { userEntry 2 }

		
		-- 1.3.6.1.4.1.34774.4.1.19.7.1.1.3
		userPassword OBJECT-TYPE
			SYNTAX OCTET STRING
			MAX-ACCESS read-write
			STATUS current
			DESCRIPTION
				"Description."
			::= { userEntry 3 }

		
		-- 1.3.6.1.4.1.34774.4.1.19.8
		hsStoragePhysicalModule OBJECT IDENTIFIER ::= { hsStorageService 8 }

		
		-- 1.3.6.1.4.1.34774.4.1.19.8.2
		hsStorageEnclosureTable OBJECT-TYPE
			SYNTAX SEQUENCE OF HsStorageEnclosureEntry
			MAX-ACCESS not-accessible
			STATUS current
			DESCRIPTION
				"Description."
			::= { hsStoragePhysicalModule 2 }

		
		-- 1.3.6.1.4.1.34774.4.1.19.8.2.1
		hsStorageEnclosureEntry OBJECT-TYPE
			SYNTAX HsStorageEnclosureEntry
			MAX-ACCESS not-accessible
			STATUS current
			DESCRIPTION
				"Description."
			INDEX { hsStorageEnclosureSN }
			::= { hsStorageEnclosureTable 1 }

		
		HsStorageEnclosureEntry ::=
			SEQUENCE { 
				hsStorageEnclosureIfIndex
					Unsigned32,
				hsStorageEnclosureSN
					OCTET STRING,
				hsStorageEnclosureID
					Unsigned32,
				hsStorageEnclosureType
					INTEGER,
				hsStorageEnclosureStatus
					INTEGER
			 }

		-- 1.3.6.1.4.1.34774.4.1.19.8.2.1.1
		hsStorageEnclosureIfIndex OBJECT-TYPE
			SYNTAX Unsigned32
			MAX-ACCESS read-only
			STATUS current
			DESCRIPTION
				"Description."
			::= { hsStorageEnclosureEntry 1 }

		
		-- 1.3.6.1.4.1.34774.4.1.19.8.2.1.2
		hsStorageEnclosureSN OBJECT-TYPE
			SYNTAX OCTET STRING
			MAX-ACCESS read-only
			STATUS current
			DESCRIPTION
				"Description."
			::= { hsStorageEnclosureEntry 2 }

		
		-- 1.3.6.1.4.1.34774.4.1.19.8.2.1.3
		hsStorageEnclosureID OBJECT-TYPE
			SYNTAX Unsigned32
			MAX-ACCESS read-write
			STATUS current
			DESCRIPTION
				"Description."
			::= { hsStorageEnclosureEntry 3 }

		
		-- 1.3.6.1.4.1.34774.4.1.19.8.2.1.4
		hsStorageEnclosureType OBJECT-TYPE
			SYNTAX INTEGER
				{
				expansion(0),
				controller(1)
				}
			MAX-ACCESS read-only
			STATUS current
			DESCRIPTION
				"Description."
			::= { hsStorageEnclosureEntry 4 }

		
		-- 1.3.6.1.4.1.34774.4.1.19.8.2.1.5
		hsStorageEnclosureStatus OBJECT-TYPE
			SYNTAX INTEGER
				{
				nline(0),
				offline(2)
				}
			MAX-ACCESS read-only
			STATUS current
			DESCRIPTION
				"Description."
			::= { hsStorageEnclosureEntry 5 }

		
		-- 1.3.6.1.4.1.34774.4.1.19.8.3
		hsStorageControllerBoardTable OBJECT-TYPE
			SYNTAX SEQUENCE OF HsStorageControllerBoardEntry
			MAX-ACCESS not-accessible
			STATUS current
			DESCRIPTION
				"Description."
			::= { hsStoragePhysicalModule 3 }

		
		-- 1.3.6.1.4.1.34774.4.1.19.8.3.1
		hsStorageControllerBoardEntry OBJECT-TYPE
			SYNTAX HsStorageControllerBoardEntry
			MAX-ACCESS not-accessible
			STATUS current
			DESCRIPTION
				"Description."
			INDEX { hsStorageControllerBoardIfIndex }
			::= { hsStorageControllerBoardTable 1 }

		
		HsStorageControllerBoardEntry ::=
			SEQUENCE { 
				hsStorageControllerBoardIfIndex
					Unsigned32,
				hsStorageControllerBoardEnclosureIfIndex
					Unsigned32,
				hsStorageControllerBoardID
					Unsigned32,
				hsStorageControllerBoardIsPrimary
					INTEGER,
				hsStorageControllerBoardCacheCapacity
					Unsigned32,
				hsStorageControllerBoardCacheHighWater
					INTEGER,
				hsStorageControllerBoardCacheLowWater
					INTEGER,
				hsStorageControllerBoardStatus
					INTEGER,
				hsStorageControllerBoardSoftwareVersion
					OCTET STRING,
				hsStorageControllerBoardLogicalVersion
					OCTET STRING,
				hsStorageControllerBoardSESVersion
					OCTET STRING,
				hsStorageControllerBoardPCBVersion
					OCTET STRING
			 }

		-- 1.3.6.1.4.1.34774.4.1.19.8.3.1.1
		hsStorageControllerBoardIfIndex OBJECT-TYPE
			SYNTAX Unsigned32
			MAX-ACCESS read-only
			STATUS current
			DESCRIPTION
				"Description."
			::= { hsStorageControllerBoardEntry 1 }

		
		-- 1.3.6.1.4.1.34774.4.1.19.8.3.1.2
		hsStorageControllerBoardEnclosureIfIndex OBJECT-TYPE
			SYNTAX Unsigned32
			MAX-ACCESS read-only
			STATUS current
			DESCRIPTION
				"Description."
			::= { hsStorageControllerBoardEntry 2 }

		
		-- 1.3.6.1.4.1.34774.4.1.19.8.3.1.3
		hsStorageControllerBoardID OBJECT-TYPE
			SYNTAX Unsigned32
			MAX-ACCESS read-only
			STATUS current
			DESCRIPTION
				"controller id"
			::= { hsStorageControllerBoardEntry 3 }

		
		-- 1.3.6.1.4.1.34774.4.1.19.8.3.1.4
		hsStorageControllerBoardIsPrimary OBJECT-TYPE
			SYNTAX INTEGER
				{
				secondary(0),
				primary(1)
				}
			MAX-ACCESS read-only
			STATUS current
			DESCRIPTION
				"Description."
			::= { hsStorageControllerBoardEntry 4 }

		
		-- 1.3.6.1.4.1.34774.4.1.19.8.3.1.5
		hsStorageControllerBoardCacheCapacity OBJECT-TYPE
			SYNTAX Unsigned32
			MAX-ACCESS read-only
			STATUS current
			DESCRIPTION
				"units: MB"
			::= { hsStorageControllerBoardEntry 5 }

		
		-- 1.3.6.1.4.1.34774.4.1.19.8.3.1.6
		hsStorageControllerBoardCacheHighWater OBJECT-TYPE
			SYNTAX INTEGER (0..100)
			MAX-ACCESS read-write
			STATUS current
			DESCRIPTION
				"Description."
			::= { hsStorageControllerBoardEntry 6 }

		
		-- 1.3.6.1.4.1.34774.4.1.19.8.3.1.7
		hsStorageControllerBoardCacheLowWater OBJECT-TYPE
			SYNTAX INTEGER (0..100)
			MAX-ACCESS read-write
			STATUS current
			DESCRIPTION
				"Description."
			::= { hsStorageControllerBoardEntry 7 }

		
		-- 1.3.6.1.4.1.34774.4.1.19.8.3.1.8
		hsStorageControllerBoardStatus OBJECT-TYPE
			SYNTAX INTEGER
				{
				offline(0),
				normal(1),
				abnormal(2)
				}
			MAX-ACCESS read-only
			STATUS current
			DESCRIPTION
				"Description."
			::= { hsStorageControllerBoardEntry 8 }

		
		-- 1.3.6.1.4.1.34774.4.1.19.8.3.1.9
		hsStorageControllerBoardSoftwareVersion OBJECT-TYPE
			SYNTAX OCTET STRING
			MAX-ACCESS read-only
			STATUS current
			DESCRIPTION
				"Description."
			::= { hsStorageControllerBoardEntry 9 }

		
		-- 1.3.6.1.4.1.34774.4.1.19.8.3.1.10
		hsStorageControllerBoardLogicalVersion OBJECT-TYPE
			SYNTAX OCTET STRING
			MAX-ACCESS read-only
			STATUS current
			DESCRIPTION
				"Description."
			::= { hsStorageControllerBoardEntry 10 }

		
		-- 1.3.6.1.4.1.34774.4.1.19.8.3.1.11
		hsStorageControllerBoardSESVersion OBJECT-TYPE
			SYNTAX OCTET STRING
			MAX-ACCESS read-only
			STATUS current
			DESCRIPTION
				"Description."
			::= { hsStorageControllerBoardEntry 11 }

		
		-- 1.3.6.1.4.1.34774.4.1.19.8.3.1.12
		hsStorageControllerBoardPCBVersion OBJECT-TYPE
			SYNTAX OCTET STRING
			MAX-ACCESS read-only
			STATUS current
			DESCRIPTION
				"Description."
			::= { hsStorageControllerBoardEntry 12 }

		
		-- 1.3.6.1.4.1.34774.4.1.19.8.4
		hsStorageInterfaceBoardTable OBJECT-TYPE
			SYNTAX SEQUENCE OF HsStorageInterfaceBoardEntry
			MAX-ACCESS not-accessible
			STATUS current
			DESCRIPTION
				"Description."
			::= { hsStoragePhysicalModule 4 }

		
		-- 1.3.6.1.4.1.34774.4.1.19.8.4.1
		hsStorageInterfaceBoardEntry OBJECT-TYPE
			SYNTAX HsStorageInterfaceBoardEntry
			MAX-ACCESS not-accessible
			STATUS current
			DESCRIPTION
				"Description."
			INDEX { hsStorageInterfaceBoardIfIndex }
			::= { hsStorageInterfaceBoardTable 1 }

		
		HsStorageInterfaceBoardEntry ::=
			SEQUENCE { 
				hsStorageInterfaceBoardIfIndex
					Unsigned32,
				hsStorageInterfaceBoardEnclosureIfIndex
					Unsigned32,
				hsStorageInterfaceBoardID
					Unsigned32,
				hsStorageInterfaceBoardController
					Unsigned32,
				hsStorageInterfaceBoardType
					Unsigned32,
				hsStorageInterfaceBoardStatus
					INTEGER,
				hsStorageInterfaceBoardPCBVersion
					OCTET STRING
			 }

		-- 1.3.6.1.4.1.34774.4.1.19.8.4.1.1
		hsStorageInterfaceBoardIfIndex OBJECT-TYPE
			SYNTAX Unsigned32
			MAX-ACCESS read-only
			STATUS current
			DESCRIPTION
				"Description."
			::= { hsStorageInterfaceBoardEntry 1 }

		
		-- 1.3.6.1.4.1.34774.4.1.19.8.4.1.2
		hsStorageInterfaceBoardEnclosureIfIndex OBJECT-TYPE
			SYNTAX Unsigned32
			MAX-ACCESS read-only
			STATUS current
			DESCRIPTION
				"Description."
			::= { hsStorageInterfaceBoardEntry 2 }

		
		-- 1.3.6.1.4.1.34774.4.1.19.8.4.1.3
		hsStorageInterfaceBoardID OBJECT-TYPE
			SYNTAX Unsigned32
			MAX-ACCESS read-only
			STATUS current
			DESCRIPTION
				"Description."
			::= { hsStorageInterfaceBoardEntry 3 }

		
		-- 1.3.6.1.4.1.34774.4.1.19.8.4.1.4
		hsStorageInterfaceBoardController OBJECT-TYPE
			SYNTAX Unsigned32
			MAX-ACCESS read-only
			STATUS current
			DESCRIPTION
				"Description."
			::= { hsStorageInterfaceBoardEntry 4 }

		
		-- 1.3.6.1.4.1.34774.4.1.19.8.4.1.5
		hsStorageInterfaceBoardType OBJECT-TYPE
			SYNTAX Unsigned32
			MAX-ACCESS read-only
			STATUS current
			DESCRIPTION
				"Description."
			::= { hsStorageInterfaceBoardEntry 5 }

		
		-- 1.3.6.1.4.1.34774.4.1.19.8.4.1.6
		hsStorageInterfaceBoardStatus OBJECT-TYPE
			SYNTAX INTEGER
				{
				abnormal(0),
				normal(1),
				fault(2),
				unactivated(3),
				powering-on(4),
				powering-off(5),
				power-off(6)
				}
			MAX-ACCESS read-only
			STATUS current
			DESCRIPTION
				"Description."
			::= { hsStorageInterfaceBoardEntry 6 }

		
		-- 1.3.6.1.4.1.34774.4.1.19.8.4.1.7
		hsStorageInterfaceBoardPCBVersion OBJECT-TYPE
			SYNTAX OCTET STRING
			MAX-ACCESS read-only
			STATUS current
			DESCRIPTION
				"Description."
			::= { hsStorageInterfaceBoardEntry 7 }

		
		-- 1.3.6.1.4.1.34774.4.1.19.8.5
		hsStorageExpansionBoardTable OBJECT-TYPE
			SYNTAX SEQUENCE OF HsStorageExpansionBoardEntry
			MAX-ACCESS not-accessible
			STATUS current
			DESCRIPTION
				"Description."
			::= { hsStoragePhysicalModule 5 }

		
		-- 1.3.6.1.4.1.34774.4.1.19.8.5.1
		hsStorageExpansionBoardEntry OBJECT-TYPE
			SYNTAX HsStorageExpansionBoardEntry
			MAX-ACCESS not-accessible
			STATUS current
			DESCRIPTION
				"Description."
			INDEX { hsStorageExpansionBoardIfIndex }
			::= { hsStorageExpansionBoardTable 1 }

		
		HsStorageExpansionBoardEntry ::=
			SEQUENCE { 
				hsStorageExpansionBoardIfIndex
					Unsigned32,
				hsStorageExpansionBoardEnclosureIfIndex
					Unsigned32,
				hsStorageExpansionBoardType
					INTEGER,
				hsStorageExpansionBoardStatus
					INTEGER,
				hsStorageExpansionBoardLogicVersion
					OCTET STRING,
				hsStorageExpansionBoardSESVersion
					OCTET STRING,
				hsStorageExpansionBoardPCBVersion
					OCTET STRING
			 }

		-- 1.3.6.1.4.1.34774.4.1.19.8.5.1.1
		hsStorageExpansionBoardIfIndex OBJECT-TYPE
			SYNTAX Unsigned32
			MAX-ACCESS read-only
			STATUS current
			DESCRIPTION
				"Description."
			::= { hsStorageExpansionBoardEntry 1 }

		
		-- 1.3.6.1.4.1.34774.4.1.19.8.5.1.2
		hsStorageExpansionBoardEnclosureIfIndex OBJECT-TYPE
			SYNTAX Unsigned32
			MAX-ACCESS read-only
			STATUS current
			DESCRIPTION
				"Description."
			::= { hsStorageExpansionBoardEntry 2 }

		
		-- 1.3.6.1.4.1.34774.4.1.19.8.5.1.3
		hsStorageExpansionBoardType OBJECT-TYPE
			SYNTAX INTEGER
				{
				sas-expansion(0),
				fc-expansion(1)
				}
			MAX-ACCESS read-only
			STATUS current
			DESCRIPTION
				"Description."
			::= { hsStorageExpansionBoardEntry 3 }

		
		-- 1.3.6.1.4.1.34774.4.1.19.8.5.1.4
		hsStorageExpansionBoardStatus OBJECT-TYPE
			SYNTAX INTEGER
				{
				abnormal(0),
				normal(1)
				}
			MAX-ACCESS read-only
			STATUS current
			DESCRIPTION
				"Description."
			::= { hsStorageExpansionBoardEntry 4 }

		
		-- 1.3.6.1.4.1.34774.4.1.19.8.5.1.5
		hsStorageExpansionBoardLogicVersion OBJECT-TYPE
			SYNTAX OCTET STRING
			MAX-ACCESS read-only
			STATUS current
			DESCRIPTION
				"Description."
			::= { hsStorageExpansionBoardEntry 5 }

		
		-- 1.3.6.1.4.1.34774.4.1.19.8.5.1.6
		hsStorageExpansionBoardSESVersion OBJECT-TYPE
			SYNTAX OCTET STRING
			MAX-ACCESS read-only
			STATUS current
			DESCRIPTION
				"Description."
			::= { hsStorageExpansionBoardEntry 6 }

		
		-- 1.3.6.1.4.1.34774.4.1.19.8.5.1.7
		hsStorageExpansionBoardPCBVersion OBJECT-TYPE
			SYNTAX OCTET STRING
			MAX-ACCESS read-only
			STATUS current
			DESCRIPTION
				"Description."
			::= { hsStorageExpansionBoardEntry 7 }

		
		-- 1.3.6.1.4.1.34774.4.1.19.8.6
		hsStorageMGMTPortTable OBJECT-TYPE
			SYNTAX SEQUENCE OF HsStorageMGMTPortEntry
			MAX-ACCESS not-accessible
			STATUS current
			DESCRIPTION
				"Description."
			::= { hsStoragePhysicalModule 6 }

		
		-- 1.3.6.1.4.1.34774.4.1.19.8.6.1
		hsStorageMGMTPortEntry OBJECT-TYPE
			SYNTAX HsStorageMGMTPortEntry
			MAX-ACCESS not-accessible
			STATUS current
			DESCRIPTION
				"Description."
			INDEX { hsStorageMGMTPortIfIndex }
			::= { hsStorageMGMTPortTable 1 }

		
		HsStorageMGMTPortEntry ::=
			SEQUENCE { 
				hsStorageMGMTPortIfIndex
					Unsigned32,
				hsStorageMGMTPortBoardIfIndex
					Unsigned32,
				hsStorageMGMTPortIPAddress
					IpAddress,
				hsStorageMGMTPortNetMask
					IpAddress,
				hsStorageMGMTPortGateWay
					IpAddress,
				hsStorageMGMTPortPhysAddress
					OCTET STRING
			 }

		-- 1.3.6.1.4.1.34774.4.1.19.8.6.1.1
		hsStorageMGMTPortIfIndex OBJECT-TYPE
			SYNTAX Unsigned32
			MAX-ACCESS read-only
			STATUS current
			DESCRIPTION
				"Description."
			::= { hsStorageMGMTPortEntry 1 }

		
		-- 1.3.6.1.4.1.34774.4.1.19.8.6.1.2
		hsStorageMGMTPortBoardIfIndex OBJECT-TYPE
			SYNTAX Unsigned32
			MAX-ACCESS read-only
			STATUS current
			DESCRIPTION
				"Description."
			::= { hsStorageMGMTPortEntry 2 }

		
		-- 1.3.6.1.4.1.34774.4.1.19.8.6.1.3
		hsStorageMGMTPortIPAddress OBJECT-TYPE
			SYNTAX IpAddress
			MAX-ACCESS read-write
			STATUS current
			DESCRIPTION
				"Description."
			::= { hsStorageMGMTPortEntry 3 }

		
		-- 1.3.6.1.4.1.34774.4.1.19.8.6.1.4
		hsStorageMGMTPortNetMask OBJECT-TYPE
			SYNTAX IpAddress
			MAX-ACCESS read-write
			STATUS current
			DESCRIPTION
				"Description."
			::= { hsStorageMGMTPortEntry 4 }

		
		-- 1.3.6.1.4.1.34774.4.1.19.8.6.1.5
		hsStorageMGMTPortGateWay OBJECT-TYPE
			SYNTAX IpAddress
			MAX-ACCESS read-write
			STATUS current
			DESCRIPTION
				"Description."
			::= { hsStorageMGMTPortEntry 5 }

		
		-- 1.3.6.1.4.1.34774.4.1.19.8.6.1.6
		hsStorageMGMTPortPhysAddress OBJECT-TYPE
			SYNTAX OCTET STRING
			MAX-ACCESS read-only
			STATUS current
			DESCRIPTION
				"mac address"
			::= { hsStorageMGMTPortEntry 6 }

		
		-- 1.3.6.1.4.1.34774.4.1.19.8.7
		hsStorageFCPortTable OBJECT-TYPE
			SYNTAX SEQUENCE OF HsStorageFCPortEntry
			MAX-ACCESS not-accessible
			STATUS current
			DESCRIPTION
				"Description."
			::= { hsStoragePhysicalModule 7 }

		
		-- 1.3.6.1.4.1.34774.4.1.19.8.7.1
		hsStorageFCPortEntry OBJECT-TYPE
			SYNTAX HsStorageFCPortEntry
			MAX-ACCESS not-accessible
			STATUS current
			DESCRIPTION
				"Description."
			INDEX { hsStorageFCPortIfIndex }
			::= { hsStorageFCPortTable 1 }

		
		HsStorageFCPortEntry ::=
			SEQUENCE { 
				hsStorageFCPortIfIndex
					Unsigned32,
				hsStorageFCPortBoardIfIndex
					Unsigned32,
				hsStorageFCPortID
					Unsigned32,
				hsStorageFCPortStatus
					INTEGER,
				hsStorageFCPortConfigRate
					INTEGER,
				hsStorageFCPortMode
					INTEGER,
				hsStorageFCPortWWN
					OCTET STRING,
				hsStorageFCPortLogicType
					INTEGER,
				hsStorageFCPortSpeedRate
					INTEGER
			 }

		-- 1.3.6.1.4.1.34774.4.1.19.8.7.1.1
		hsStorageFCPortIfIndex OBJECT-TYPE
			SYNTAX Unsigned32
			MAX-ACCESS read-only
			STATUS current
			DESCRIPTION
				"Description."
			::= { hsStorageFCPortEntry 1 }

		
		-- 1.3.6.1.4.1.34774.4.1.19.8.7.1.2
		hsStorageFCPortBoardIfIndex OBJECT-TYPE
			SYNTAX Unsigned32
			MAX-ACCESS read-only
			STATUS current
			DESCRIPTION
				"owning board ifindex"
			::= { hsStorageFCPortEntry 2 }

		
		-- 1.3.6.1.4.1.34774.4.1.19.8.7.1.3
		hsStorageFCPortID OBJECT-TYPE
			SYNTAX Unsigned32
			MAX-ACCESS read-only
			STATUS current
			DESCRIPTION
				"Description."
			::= { hsStorageFCPortEntry 3 }

		
		-- 1.3.6.1.4.1.34774.4.1.19.8.7.1.4
		hsStorageFCPortStatus OBJECT-TYPE
			SYNTAX INTEGER
				{
				link-down(0),
				link-up(1),
				fault(2)
				}
			MAX-ACCESS read-only
			STATUS current
			DESCRIPTION
				"Description."
			::= { hsStorageFCPortEntry 4 }

		
		-- 1.3.6.1.4.1.34774.4.1.19.8.7.1.5
		hsStorageFCPortConfigRate OBJECT-TYPE
			SYNTAX INTEGER
				{
				auto(0),
				gbps-1(1),
				gbps-2(2),
				gbps-4(4),
				gbps-8(8)
				}
			MAX-ACCESS read-write
			STATUS current
			DESCRIPTION
				"Description."
			::= { hsStorageFCPortEntry 5 }

		
		-- 1.3.6.1.4.1.34774.4.1.19.8.7.1.6
		hsStorageFCPortMode OBJECT-TYPE
			SYNTAX INTEGER
				{
				fabric(1),
				public-loop(2),
				point-to-point(3)
				}
			MAX-ACCESS read-write
			STATUS current
			DESCRIPTION
				"Description."
			::= { hsStorageFCPortEntry 6 }

		
		-- 1.3.6.1.4.1.34774.4.1.19.8.7.1.7
		hsStorageFCPortWWN OBJECT-TYPE
			SYNTAX OCTET STRING
			MAX-ACCESS read-only
			STATUS current
			DESCRIPTION
				"Description."
			::= { hsStorageFCPortEntry 7 }

		
		-- 1.3.6.1.4.1.34774.4.1.19.8.7.1.8
		hsStorageFCPortLogicType OBJECT-TYPE
			SYNTAX INTEGER
				{
				service(1),
				ibc(2),
				ibs(3),
				expansion(4),
				management(5),
				ups-management(6),
				maintenance(8)
				}
			MAX-ACCESS read-only
			STATUS current
			DESCRIPTION
				"Description."
			::= { hsStorageFCPortEntry 8 }

		
		-- 1.3.6.1.4.1.34774.4.1.19.8.7.1.9
		hsStorageFCPortSpeedRate OBJECT-TYPE
			SYNTAX INTEGER
				{
				auto(0),
				gbps-1(1),
				gbps-2(2),
				gbps-4(4),
				gbps-8(8)
				}
			MAX-ACCESS read-only
			STATUS current
			DESCRIPTION
				"Description."
			::= { hsStorageFCPortEntry 9 }

		
		-- 1.3.6.1.4.1.34774.4.1.19.8.8
		hsStorageSASPortTable OBJECT-TYPE
			SYNTAX SEQUENCE OF HsStorageSASPortEntry
			MAX-ACCESS not-accessible
			STATUS current
			DESCRIPTION
				"Description."
			::= { hsStoragePhysicalModule 8 }

		
		-- 1.3.6.1.4.1.34774.4.1.19.8.8.1
		hsStorageSASPortEntry OBJECT-TYPE
			SYNTAX HsStorageSASPortEntry
			MAX-ACCESS not-accessible
			STATUS current
			DESCRIPTION
				"Description."
			INDEX { hsStorageSASPortIfIndex }
			::= { hsStorageSASPortTable 1 }

		
		HsStorageSASPortEntry ::=
			SEQUENCE { 
				hsStorageSASPortIfIndex
					Unsigned32,
				hsStorageSASPortBoardIfIndex
					Unsigned32,
				hsStorageSASPortID
					Unsigned32,
				hsStorageSASPortStatus
					INTEGER,
				hsStorageSASPortConfigRate
					INTEGER,
				hsStorageSASPortWWN
					OCTET STRING,
				hsStorageSASPortLogicType
					INTEGER,
				hsStorageSASPortSpeedRate
					INTEGER
			 }

		-- 1.3.6.1.4.1.34774.4.1.19.8.8.1.1
		hsStorageSASPortIfIndex OBJECT-TYPE
			SYNTAX Unsigned32
			MAX-ACCESS read-only
			STATUS current
			DESCRIPTION
				"Description."
			::= { hsStorageSASPortEntry 1 }

		
		-- 1.3.6.1.4.1.34774.4.1.19.8.8.1.2
		hsStorageSASPortBoardIfIndex OBJECT-TYPE
			SYNTAX Unsigned32
			MAX-ACCESS read-only
			STATUS current
			DESCRIPTION
				"owning board ifindex"
			::= { hsStorageSASPortEntry 2 }

		
		-- 1.3.6.1.4.1.34774.4.1.19.8.8.1.3
		hsStorageSASPortID OBJECT-TYPE
			SYNTAX Unsigned32
			MAX-ACCESS read-only
			STATUS current
			DESCRIPTION
				"Description."
			::= { hsStorageSASPortEntry 3 }

		
		-- 1.3.6.1.4.1.34774.4.1.19.8.8.1.4
		hsStorageSASPortStatus OBJECT-TYPE
			SYNTAX INTEGER
				{
				link-down(0),
				link-up(1),
				fault(2)
				}
			MAX-ACCESS read-only
			STATUS current
			DESCRIPTION
				"Description."
			::= { hsStorageSASPortEntry 4 }

		
		-- 1.3.6.1.4.1.34774.4.1.19.8.8.1.5
		hsStorageSASPortConfigRate OBJECT-TYPE
			SYNTAX INTEGER
				{
				gbps-15(1500),
				gbps-30(3000),
				gbps-60(6000)
				}
			MAX-ACCESS read-only
			STATUS current
			DESCRIPTION
				"Description."
			::= { hsStorageSASPortEntry 5 }

		
		-- 1.3.6.1.4.1.34774.4.1.19.8.8.1.6
		hsStorageSASPortWWN OBJECT-TYPE
			SYNTAX OCTET STRING
			MAX-ACCESS read-only
			STATUS current
			DESCRIPTION
				"Description."
			::= { hsStorageSASPortEntry 6 }

		
		-- 1.3.6.1.4.1.34774.4.1.19.8.8.1.7
		hsStorageSASPortLogicType OBJECT-TYPE
			SYNTAX INTEGER
				{
				service(1),
				ibc(2),
				ibs(3),
				expansion(4),
				management(5),
				ups-management(6),
				maintenance(8)
				}
			MAX-ACCESS read-only
			STATUS current
			DESCRIPTION
				"Description."
			::= { hsStorageSASPortEntry 7 }

		
		-- 1.3.6.1.4.1.34774.4.1.19.8.8.1.8
		hsStorageSASPortSpeedRate OBJECT-TYPE
			SYNTAX INTEGER
				{
				gbps-15(1500),
				gbps-30(3000),
				gbps-60(6000)
				}
			MAX-ACCESS read-only
			STATUS current
			DESCRIPTION
				"Description."
			::= { hsStorageSASPortEntry 8 }

		
		-- 1.3.6.1.4.1.34774.4.1.19.8.9
		hsStorageISCSIPortTable OBJECT-TYPE
			SYNTAX SEQUENCE OF HsStorageISCSIPortEntry
			MAX-ACCESS not-accessible
			STATUS current
			DESCRIPTION
				"Description."
			::= { hsStoragePhysicalModule 9 }

		
		-- 1.3.6.1.4.1.34774.4.1.19.8.9.1
		hsStorageISCSIPortEntry OBJECT-TYPE
			SYNTAX HsStorageISCSIPortEntry
			MAX-ACCESS not-accessible
			STATUS current
			DESCRIPTION
				"Description."
			INDEX { hsStorageISCSIPortIfIndex }
			::= { hsStorageISCSIPortTable 1 }

		
		HsStorageISCSIPortEntry ::=
			SEQUENCE { 
				hsStorageISCSIPortIfIndex
					Unsigned32,
				hsStorageISCSIPortBoardIfIndex
					Unsigned32,
				hsStorageISCSIPortID
					Unsigned32,
				hsStorageISCSIPortStatus
					INTEGER,
				hsStorageISCSIPortIP
					IpAddress,
				hsStorageISCSIPortNetMask
					IpAddress,
				hsStorageISCSIPortBindMode
					INTEGER,
				hsStorageISCSIPortLogicType
					INTEGER
			 }

		-- 1.3.6.1.4.1.34774.4.1.19.8.9.1.1
		hsStorageISCSIPortIfIndex OBJECT-TYPE
			SYNTAX Unsigned32
			MAX-ACCESS read-only
			STATUS current
			DESCRIPTION
				"Description."
			::= { hsStorageISCSIPortEntry 1 }

		
		-- 1.3.6.1.4.1.34774.4.1.19.8.9.1.2
		hsStorageISCSIPortBoardIfIndex OBJECT-TYPE
			SYNTAX Unsigned32
			MAX-ACCESS read-only
			STATUS current
			DESCRIPTION
				"owning board ifindex"
			::= { hsStorageISCSIPortEntry 2 }

		
		-- 1.3.6.1.4.1.34774.4.1.19.8.9.1.3
		hsStorageISCSIPortID OBJECT-TYPE
			SYNTAX Unsigned32
			MAX-ACCESS read-only
			STATUS current
			DESCRIPTION
				"Description."
			::= { hsStorageISCSIPortEntry 3 }

		
		-- 1.3.6.1.4.1.34774.4.1.19.8.9.1.4
		hsStorageISCSIPortStatus OBJECT-TYPE
			SYNTAX INTEGER
				{
				link-down(0),
				link-up(1),
				fault(2)
				}
			MAX-ACCESS read-only
			STATUS current
			DESCRIPTION
				"Description."
			::= { hsStorageISCSIPortEntry 4 }

		
		-- 1.3.6.1.4.1.34774.4.1.19.8.9.1.5
		hsStorageISCSIPortIP OBJECT-TYPE
			SYNTAX IpAddress
			MAX-ACCESS read-write
			STATUS current
			DESCRIPTION
				"Description."
			::= { hsStorageISCSIPortEntry 5 }

		
		-- 1.3.6.1.4.1.34774.4.1.19.8.9.1.6
		hsStorageISCSIPortNetMask OBJECT-TYPE
			SYNTAX IpAddress
			MAX-ACCESS read-write
			STATUS current
			DESCRIPTION
				"Description."
			::= { hsStorageISCSIPortEntry 6 }

		
		-- 1.3.6.1.4.1.34774.4.1.19.8.9.1.7
		hsStorageISCSIPortBindMode OBJECT-TYPE
			SYNTAX INTEGER
			MAX-ACCESS read-only
			STATUS current
			DESCRIPTION
				"Description."
			::= { hsStorageISCSIPortEntry 7 }

		
		-- 1.3.6.1.4.1.34774.4.1.19.8.9.1.8
		hsStorageISCSIPortLogicType OBJECT-TYPE
			SYNTAX INTEGER
				{
				service(1),
				ibc(2),
				ibs(3),
				expansion(4),
				management(5),
				ups-management(6),
				maintenance(8)
				}
			MAX-ACCESS read-only
			STATUS current
			DESCRIPTION
				"Description."
			::= { hsStorageISCSIPortEntry 8 }

		
		-- 1.3.6.1.4.1.34774.4.1.19.8.10
		hsStorageReplicationLinkTable OBJECT-TYPE
			SYNTAX SEQUENCE OF HsStorageReplicationLinkEntry
			MAX-ACCESS not-accessible
			STATUS current
			DESCRIPTION
				"Description."
			::= { hsStoragePhysicalModule 10 }

		
		-- 1.3.6.1.4.1.34774.4.1.19.8.10.1
		hsStorageReplicationLinkEntry OBJECT-TYPE
			SYNTAX HsStorageReplicationLinkEntry
			MAX-ACCESS not-accessible
			STATUS current
			DESCRIPTION
				"Description."
			INDEX { hsStorageReplicationLinkID }
			::= { hsStorageReplicationLinkTable 1 }

		
		HsStorageReplicationLinkEntry ::=
			SEQUENCE { 
				hsStorageReplicationLinkID
					Unsigned32,
				hsStorageReplicationLinkArrayID
					Unsigned32,
				hsStorageReplicationLinkType
					INTEGER,
				hsStorageReplicationLinkStatus
					INTEGER,
				hsStorageReplicationLinkUsed
					INTEGER,
				hsStorageReplicationLinkRowStatus
					RowStatus
			 }

		-- 1.3.6.1.4.1.34774.4.1.19.8.10.1.1
		hsStorageReplicationLinkID OBJECT-TYPE
			SYNTAX Unsigned32
			MAX-ACCESS read-only
			STATUS current
			DESCRIPTION
				"Description."
			::= { hsStorageReplicationLinkEntry 1 }

		
		-- 1.3.6.1.4.1.34774.4.1.19.8.10.1.2
		hsStorageReplicationLinkArrayID OBJECT-TYPE
			SYNTAX Unsigned32
			MAX-ACCESS read-only
			STATUS current
			DESCRIPTION
				"Description."
			::= { hsStorageReplicationLinkEntry 2 }

		
		-- 1.3.6.1.4.1.34774.4.1.19.8.10.1.3
		hsStorageReplicationLinkType OBJECT-TYPE
			SYNTAX INTEGER
				{
				fc(1),
				iscsi(2)
				}
			MAX-ACCESS read-only
			STATUS current
			DESCRIPTION
				"Description."
			::= { hsStorageReplicationLinkEntry 3 }

		
		-- 1.3.6.1.4.1.34774.4.1.19.8.10.1.4
		hsStorageReplicationLinkStatus OBJECT-TYPE
			SYNTAX INTEGER
				{
				connected(1),
				unconnected(2)
				}
			MAX-ACCESS read-only
			STATUS current
			DESCRIPTION
				"Description."
			::= { hsStorageReplicationLinkEntry 4 }

		
		-- 1.3.6.1.4.1.34774.4.1.19.8.10.1.5
		hsStorageReplicationLinkUsed OBJECT-TYPE
			SYNTAX INTEGER
				{
				no(0),
				yes(1)
				}
			MAX-ACCESS read-only
			STATUS current
			DESCRIPTION
				"Description."
			::= { hsStorageReplicationLinkEntry 5 }

		
		-- 1.3.6.1.4.1.34774.4.1.19.8.10.1.50
		hsStorageReplicationLinkRowStatus OBJECT-TYPE
			SYNTAX RowStatus
			MAX-ACCESS read-write
			STATUS current
			DESCRIPTION
				"Description."
			::= { hsStorageReplicationLinkEntry 50 }

		
		-- 1.3.6.1.4.1.34774.4.1.19.9
		hsStorageLogicModule OBJECT IDENTIFIER ::= { hsStorageService 9 }

		
		-- 1.3.6.1.4.1.34774.4.1.19.9.4
		hsStorageLunTable OBJECT-TYPE
			SYNTAX SEQUENCE OF HsStorageLunEntry
			MAX-ACCESS not-accessible
			STATUS current
			DESCRIPTION
				"Description."
			::= { hsStorageLogicModule 4 }

		
		-- 1.3.6.1.4.1.34774.4.1.19.9.4.1
		hsStorageLunEntry OBJECT-TYPE
			SYNTAX HsStorageLunEntry
			MAX-ACCESS not-accessible
			STATUS current
			DESCRIPTION
				"Description."
			INDEX { hsStorageLunID }
			::= { hsStorageLunTable 1 }

		
		HsStorageLunEntry ::=
			SEQUENCE { 
				hsStorageLunID
					Unsigned32,
				hsStorageLunName
					OCTET STRING,
				hsStorageLunWWN
					OCTET STRING,
				hsStorageLunOwningRaid
					Unsigned32,
				hsStorageLunCapacity
					Counter64,
				hsStorageLunOwningController
					Unsigned32,
				hsStorageLunStripDepth
					Unsigned32,
				hsStorageLunWriteStrategy
					INTEGER,
				hsStorageLunPrefetchStrategy
					INTEGER,
				hsStorageLunPrefetchValue
					Unsigned32,
				hsStorageLunStatus
					INTEGER,
				hsStorageLunRowStatus
					RowStatus
			 }

		-- 1.3.6.1.4.1.34774.4.1.19.9.4.1.1
		hsStorageLunID OBJECT-TYPE
			SYNTAX Unsigned32
			MAX-ACCESS read-write
			STATUS current
			DESCRIPTION
				"Description."
			::= { hsStorageLunEntry 1 }

		
		-- 1.3.6.1.4.1.34774.4.1.19.9.4.1.2
		hsStorageLunName OBJECT-TYPE
			SYNTAX OCTET STRING
			MAX-ACCESS read-write
			STATUS current
			DESCRIPTION
				"Description."
			::= { hsStorageLunEntry 2 }

		
		-- 1.3.6.1.4.1.34774.4.1.19.9.4.1.3
		hsStorageLunWWN OBJECT-TYPE
			SYNTAX OCTET STRING
			MAX-ACCESS read-write
			STATUS current
			DESCRIPTION
				"Description."
			::= { hsStorageLunEntry 3 }

		
		-- 1.3.6.1.4.1.34774.4.1.19.9.4.1.4
		hsStorageLunOwningRaid OBJECT-TYPE
			SYNTAX Unsigned32
			MAX-ACCESS read-write
			STATUS current
			DESCRIPTION
				"owning raid id"
			::= { hsStorageLunEntry 4 }

		
		-- 1.3.6.1.4.1.34774.4.1.19.9.4.1.5
		hsStorageLunCapacity OBJECT-TYPE
			SYNTAX Counter64
			MAX-ACCESS read-write
			STATUS current
			DESCRIPTION
				"units: byte"
			::= { hsStorageLunEntry 5 }

		
		-- 1.3.6.1.4.1.34774.4.1.19.9.4.1.6
		hsStorageLunOwningController OBJECT-TYPE
			SYNTAX Unsigned32
			MAX-ACCESS read-write
			STATUS current
			DESCRIPTION
				"owning controller id"
			::= { hsStorageLunEntry 6 }

		
		-- 1.3.6.1.4.1.34774.4.1.19.9.4.1.7
		hsStorageLunStripDepth OBJECT-TYPE
			SYNTAX Unsigned32
			MAX-ACCESS read-write
			STATUS current
			DESCRIPTION
				"units: kb"
			::= { hsStorageLunEntry 7 }

		
		-- 1.3.6.1.4.1.34774.4.1.19.9.4.1.8
		hsStorageLunWriteStrategy OBJECT-TYPE
			SYNTAX INTEGER
				{
				write-through(1),
				write-back-no-mirroring(2),
				write-back-mirroring(3),
				write-back-mandatory-no-mirroring(4),
				write-back-mandatory-mirroring(5)
				}
			MAX-ACCESS read-write
			STATUS current
			DESCRIPTION
				"Description."
			::= { hsStorageLunEntry 8 }

		
		-- 1.3.6.1.4.1.34774.4.1.19.9.4.1.9
		hsStorageLunPrefetchStrategy OBJECT-TYPE
			SYNTAX INTEGER
				{
				none(0),
				constant(1),
				variable(2),
				intelligent(3)
				}
			MAX-ACCESS read-write
			STATUS current
			DESCRIPTION
				"Description."
			::= { hsStorageLunEntry 9 }

		
		-- 1.3.6.1.4.1.34774.4.1.19.9.4.1.10
		hsStorageLunPrefetchValue OBJECT-TYPE
			SYNTAX Unsigned32
			MAX-ACCESS read-write
			STATUS current
			DESCRIPTION
				"need set value when hsStorageLunPrefetchStrategy's value is Constant or Variable.
				Constant, range: 0~1024KB
				Variable, range: 0~65535"
			::= { hsStorageLunEntry 10 }

		
		-- 1.3.6.1.4.1.34774.4.1.19.9.4.1.11
		hsStorageLunStatus OBJECT-TYPE
			SYNTAX INTEGER
				{
				normal(1),
				fault(2),
				not-format(3),
				formatting(4)
				}
			MAX-ACCESS read-write
			STATUS current
			DESCRIPTION
				"Description."
			::= { hsStorageLunEntry 11 }

		
		-- 1.3.6.1.4.1.34774.4.1.19.9.4.1.50
		hsStorageLunRowStatus OBJECT-TYPE
			SYNTAX RowStatus
			MAX-ACCESS read-write
			STATUS current
			DESCRIPTION
				"Description."
			::= { hsStorageLunEntry 50 }

		
		-- 1.3.6.1.4.1.34774.4.1.19.9.5
		hsStorageReplicationPipeTable OBJECT-TYPE
			SYNTAX SEQUENCE OF HsStorageReplicationPipeEntry
			MAX-ACCESS not-accessible
			STATUS current
			DESCRIPTION
				"Description."
			::= { hsStorageLogicModule 5 }

		
		-- 1.3.6.1.4.1.34774.4.1.19.9.5.1
		hsStorageReplicationPipeEntry OBJECT-TYPE
			SYNTAX HsStorageReplicationPipeEntry
			MAX-ACCESS not-accessible
			STATUS current
			DESCRIPTION
				"Description."
			INDEX { hsStorageReplicationPipenID }
			::= { hsStorageReplicationPipeTable 1 }

		
		HsStorageReplicationPipeEntry ::=
			SEQUENCE { 
				hsStorageReplicationPipenID
					Unsigned32,
				hsStorageReplicationPipeType
					INTEGER,
				hsStorageReplicationPipeStatus
					INTEGER,
				hsStorageReplicationPipeUsed
					INTEGER,
				hsStorageReplicationPipeMirrorLink
					INTEGER,
				hsStorageReplicationPipeMirrorLinkTimeout
					Unsigned32,
				hsStorageReplicationPipeRemoteArrayID
					Unsigned32,
				hsStorageReplicationPipeRemoteArrayWWN
					OCTET STRING,
				hsStorageReplicationPipeLocalController
					Unsigned32,
				hsStorageReplicationPipeRemoteController
					Unsigned32,
				hsStorageReplicationPipeLocalPort
					Unsigned32,
				hsStorageReplicationPipeRemotePort
					Unsigned32,
				hsStorageReplicationPipeLocalWWPN
					OCTET STRING,
				hsStorageReplicationPipeRemoteWWPN
					OCTET STRING,
				hsStorageReplicationPipeTargetName
					OCTET STRING,
				hsStorageReplicationPipeInitiatorName
					Integer32,
				hsStorageReplicationPipeRowStatus
					RowStatus
			 }

		-- 1.3.6.1.4.1.34774.4.1.19.9.5.1.1
		hsStorageReplicationPipenID OBJECT-TYPE
			SYNTAX Unsigned32
			MAX-ACCESS read-write
			STATUS current
			DESCRIPTION
				"Description."
			::= { hsStorageReplicationPipeEntry 1 }

		
		-- 1.3.6.1.4.1.34774.4.1.19.9.5.1.2
		hsStorageReplicationPipeType OBJECT-TYPE
			SYNTAX INTEGER
				{
				fc-link(1),
				iSCSI-link(2)
				}
			MAX-ACCESS read-write
			STATUS current
			DESCRIPTION
				"Description."
			::= { hsStorageReplicationPipeEntry 2 }

		
		-- 1.3.6.1.4.1.34774.4.1.19.9.5.1.3
		hsStorageReplicationPipeStatus OBJECT-TYPE
			SYNTAX INTEGER
				{
				connected(1),
				disconnected(2)
				}
			MAX-ACCESS read-write
			STATUS current
			DESCRIPTION
				"Description."
			::= { hsStorageReplicationPipeEntry 3 }

		
		-- 1.3.6.1.4.1.34774.4.1.19.9.5.1.4
		hsStorageReplicationPipeUsed OBJECT-TYPE
			SYNTAX INTEGER
				{
				false(0),
				true(1)
				}
			MAX-ACCESS read-write
			STATUS current
			DESCRIPTION
				"Description."
			::= { hsStorageReplicationPipeEntry 4 }

		
		-- 1.3.6.1.4.1.34774.4.1.19.9.5.1.5
		hsStorageReplicationPipeMirrorLink OBJECT-TYPE
			SYNTAX INTEGER
				{
				false(0),
				true(1)
				}
			MAX-ACCESS read-write
			STATUS current
			DESCRIPTION
				"Description."
			::= { hsStorageReplicationPipeEntry 5 }

		
		-- 1.3.6.1.4.1.34774.4.1.19.9.5.1.6
		hsStorageReplicationPipeMirrorLinkTimeout OBJECT-TYPE
			SYNTAX Unsigned32
			MAX-ACCESS read-write
			STATUS current
			DESCRIPTION
				"Description."
			::= { hsStorageReplicationPipeEntry 6 }

		
		-- 1.3.6.1.4.1.34774.4.1.19.9.5.1.7
		hsStorageReplicationPipeRemoteArrayID OBJECT-TYPE
			SYNTAX Unsigned32
			MAX-ACCESS read-write
			STATUS current
			DESCRIPTION
				"Description."
			::= { hsStorageReplicationPipeEntry 7 }

		
		-- 1.3.6.1.4.1.34774.4.1.19.9.5.1.8
		hsStorageReplicationPipeRemoteArrayWWN OBJECT-TYPE
			SYNTAX OCTET STRING
			MAX-ACCESS read-write
			STATUS current
			DESCRIPTION
				"Description."
			::= { hsStorageReplicationPipeEntry 8 }

		
		-- 1.3.6.1.4.1.34774.4.1.19.9.5.1.9
		hsStorageReplicationPipeLocalController OBJECT-TYPE
			SYNTAX Unsigned32
			MAX-ACCESS read-write
			STATUS current
			DESCRIPTION
				"local controller id"
			::= { hsStorageReplicationPipeEntry 9 }

		
		-- 1.3.6.1.4.1.34774.4.1.19.9.5.1.10
		hsStorageReplicationPipeRemoteController OBJECT-TYPE
			SYNTAX Unsigned32
			MAX-ACCESS read-write
			STATUS current
			DESCRIPTION
				"remote controller id"
			::= { hsStorageReplicationPipeEntry 10 }

		
		-- 1.3.6.1.4.1.34774.4.1.19.9.5.1.11
		hsStorageReplicationPipeLocalPort OBJECT-TYPE
			SYNTAX Unsigned32
			MAX-ACCESS read-write
			STATUS current
			DESCRIPTION
				"local port id"
			::= { hsStorageReplicationPipeEntry 11 }

		
		-- 1.3.6.1.4.1.34774.4.1.19.9.5.1.12
		hsStorageReplicationPipeRemotePort OBJECT-TYPE
			SYNTAX Unsigned32
			MAX-ACCESS read-write
			STATUS current
			DESCRIPTION
				"remote port id"
			::= { hsStorageReplicationPipeEntry 12 }

		
		-- 1.3.6.1.4.1.34774.4.1.19.9.5.1.13
		hsStorageReplicationPipeLocalWWPN OBJECT-TYPE
			SYNTAX OCTET STRING
			MAX-ACCESS read-write
			STATUS current
			DESCRIPTION
				"Description."
			::= { hsStorageReplicationPipeEntry 13 }

		
		-- 1.3.6.1.4.1.34774.4.1.19.9.5.1.14
		hsStorageReplicationPipeRemoteWWPN OBJECT-TYPE
			SYNTAX OCTET STRING
			MAX-ACCESS read-write
			STATUS current
			DESCRIPTION
				"Description."
			::= { hsStorageReplicationPipeEntry 14 }

		
		-- 1.3.6.1.4.1.34774.4.1.19.9.5.1.15
		hsStorageReplicationPipeTargetName OBJECT-TYPE
			SYNTAX OCTET STRING
			MAX-ACCESS read-write
			STATUS current
			DESCRIPTION
				"Description."
			::= { hsStorageReplicationPipeEntry 15 }

		
		-- 1.3.6.1.4.1.34774.4.1.19.9.5.1.16
		hsStorageReplicationPipeInitiatorName OBJECT-TYPE
			SYNTAX Integer32
			MAX-ACCESS read-write
			STATUS current
			DESCRIPTION
				"Description."
			::= { hsStorageReplicationPipeEntry 16 }

		
		-- 1.3.6.1.4.1.34774.4.1.19.9.5.1.50
		hsStorageReplicationPipeRowStatus OBJECT-TYPE
			SYNTAX RowStatus
			MAX-ACCESS read-write
			STATUS current
			DESCRIPTION
				"Description."
			::= { hsStorageReplicationPipeEntry 50 }

		
		-- 1.3.6.1.4.1.34774.4.2
		hsProduct OBJECT IDENTIFIER ::= { hsStorage 2 }

		
		-- 1.3.6.1.4.1.34774.4.2.1
		product-V1500 OBJECT IDENTIFIER ::= { hsProduct 1 }

		
		-- 1.3.6.1.4.1.34774.4.2.2
		product-V1800 OBJECT IDENTIFIER ::= { hsProduct 2 }

		
		-- 1.3.6.1.4.1.34774.4.2.3
		product-S2100 OBJECT IDENTIFIER ::= { hsProduct 3 }

		
		-- 1.3.6.1.4.1.34774.4.2.4
		product-S2300 OBJECT IDENTIFIER ::= { hsProduct 4 }

		
		-- 1.3.6.1.4.1.34774.4.2.5
		product-S5100 OBJECT IDENTIFIER ::= { hsProduct 5 }

		
		-- 1.3.6.1.4.1.34774.4.2.6
		product-S5300 OBJECT IDENTIFIER ::= { hsProduct 6 }

		
		-- 1.3.6.1.4.1.34774.4.2.7
		product-S5500 OBJECT IDENTIFIER ::= { hsProduct 7 }

		
		-- 1.3.6.1.4.1.34774.4.2.8
		product-S5600 OBJECT IDENTIFIER ::= { hsProduct 8 }

		
		-- 1.3.6.1.4.1.34774.4.2.9
		product-VIS OBJECT IDENTIFIER ::= { hsProduct 9 }

		
		-- 1.3.6.1.4.1.34774.4.2.10
		product-S2600 OBJECT IDENTIFIER ::= { hsProduct 10 }

		
		-- 1.3.6.1.4.1.34774.4.2.11
		product-S6800E OBJECT IDENTIFIER ::= { hsProduct 11 }

		
		-- 1.3.6.1.4.1.34774.4.2.12
		prodcut-V1500N OBJECT IDENTIFIER ::= { hsProduct 12 }

		
		-- 1.3.6.1.4.1.34774.4.2.13
		product-S2300E OBJECT IDENTIFIER ::= { hsProduct 13 }

		
	
	END

--
-- HUAWEISYMANTEC-ISM-STORAGE-SVC-MIB.my
--
