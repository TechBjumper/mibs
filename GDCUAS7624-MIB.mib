-- Copyright 1997 General DataComm Inc., Inc. All Rights Reserved.
--
-- Reproduction of this document is authorized on condition that the
-- foregoing copyright notice is included. This General DataComm, GDC,
-- SNMP Management Information Base Specification embodies GDCs'
-- confidential and proprietary intellectual property. GDC retains all
-- title and ownership in the Specification, including any revisions.
--
-- It is GDCs intent to encourage the widespread use of this Specification
-- in connection with the management of GDC's products. GDC grants vendors,
-- end-users, and other interested parties a non-exclusive license to use
-- this Specification in connection with the management of GDC's products.
--
-- This Specification is supplied "AS IS," and GDC makes no warranty,
-- either expressed or implied, as to the use operation, condition, or
-- performance of the Specification.
--
-- GDC UAS7624 MIB
-- **************************************************************************
--                        Revision History
-- **************************************************************************
-- Version	Date		Name		Description
-- 1.00A	15-Oct-97	M. Cyr    	Initial Revision. 
-- 1.00B        25-Nov-97       D. Baylis       Second Revision.
-- 1.00C	08-Dec-97	D. Baylis	1) Fixed main comment (T1 is line 5)
--						2) Updated LED Status
-- 1.00D        12-Jan-98       C. Amorossi     1) Removed uas7624T1CircuitName and
--                                                 uas7624SetRealTime from
--                                                 uas7624MaintenanceTable
--						2) Removed
--						   uas7624UnavailableTimeRegTable
--						3) Added uas7624LineBuildoutMode
--                                                 and uas7624FramingMode to
--						   uas7624ConfigTable
-- 1.00E        19-Jan-98       C. Amorossi     1) Changed enums for 
--                                                 uas7624DiagConfig
--                                              2) Changed description of
--						   uas7624StatLastInitialized
--                                              3) Changed description of
--						   uas7624TestResults
--                                              4) Changed description of
--          					   uas7624ESLocal
--						5) Added enums to
--						   uas7624AlarmCountThreshold
-- 1.00F        23-Jan-98       C. Amorosssi	1) Changed description of
--						   uas7624StatLastInitialized
-- 1.00G	08-Feb-98	C. Amorossi	1) Added uas7624LoopState
-- 1.00H        12-Feb-98       C. Amorossi	1) Added uas7624ConfigMode
-- ***************************************************************************

-- ***************************************************************************
--  MIB definitions begin
-- ***************************************************************************
GDCUAS7624-MIB DEFINITIONS ::= BEGIN

IMPORTS
    enterprises,TimeTicks   FROM RFC1155-SMI
    OBJECT-TYPE		    FROM RFC-1212
    DisplayString	    FROM RFC1213-MIB
    SCinstance		    FROM GDCMACRO-MIB;

gdc			    OBJECT IDENTIFIER ::= { enterprises 498 }
niudiu			    OBJECT IDENTIFIER ::= { gdc 18}
uas7624System		    OBJECT IDENTIFIER ::= { niudiu 1 }

uas7624			    OBJECT IDENTIFIER ::= { niudiu 2 }
uas7624Version		    OBJECT IDENTIFIER ::= { uas7624System 1 }
uas7624Maintenance	    OBJECT IDENTIFIER ::= { uas7624System 2 }
uas7624Configuration	    OBJECT IDENTIFIER ::= { uas7624System 3 }
uas7624Diagnostics	    OBJECT IDENTIFIER ::= { uas7624System 4 }
uas7624Performance	    OBJECT IDENTIFIER ::= { uas7624System 5 }
uas7624AlarmConfig	    OBJECT IDENTIFIER ::= { uas7624System 6 }

-- This MIB module uses the extended OBJECT-TYPE macro as
-- defined in RFC 1212.

-- Note:  All rows in all tables defined within this MIB module are
-- virtual.  They can neither be created or deleted by management
-- operations.
--
--****************************************************************************
-- 	SCinstance is defined as the addressing/indexing method of accessing
--	table objects in this MIB. The SCinstance represents the SpectraComm
--	shelf Slot, Line, Drop and interface address.
--	Represented as SLDi, (Slot, Line, Drop, interface).
--
--
-- 	For the uas7624: 
--
--		Byte		Range (dec.)		Identifies	
--		----		------------		----------
--		[S]lot		1 - 32			Physical Slot
--							1-16:  1st Shelf
--							17-32: 2nd Shelf
--
--		[L]ine		1 - 5			1: DIU(1)
--							2: DIU(2)
--							3: DIU(3)
--							4: DIU(4)
--							5: T1
--		
--		[D]rop		0			for Remotes Only
--
--		[i]nterface     0 - 3			0: Unit
--							1: Loop(1)	
--							2: Loop(2)
--							3: Loop(3)
--
--
--	The format: 	
--			[L]ine:(range) [i]nterface:(range)
--			 
--	is used in the DESCRIPTION fields below to define valid values.
--		 
--	([S]lot is the same for all objects and [D]rop is always 0)
--			
--
-- ****************************************************************************
--
uas7624MIBversion OBJECT-TYPE
    SYNTAX  DisplayString (SIZE (5))
    ACCESS  read-only
    STATUS  mandatory
    DESCRIPTION
	    "Identifies the version of the MIB. The format of the version
	    is x.yzT, where 'x' identifies the major revision number, 'y'
	    identifies the minor revision number, 'z' identifies the
	    typographical revision, and T identifies the test revision.
	    Acceptable values for the individual revision components are
	    as follows:
		 x: 1 - 9
		 y: 0 - 9
		 z: 0 - 9
		 T: A - Z
	    Upon formal release, no designation for the test revision will
	    be present."
    ::= { uas7624Version 1 }



-- ****************************************************************************
--                                Version Table
-- ****************************************************************************
	
uas7624VersionTable OBJECT-TYPE
    SYNTAX  SEQUENCE OF Uas7624VersionEntry
    ACCESS  not-accessible
    STATUS  mandatory
    DESCRIPTION 
	    "The 7624 version table "
    ::= { uas7624Version 2  }

uas7624VersionEntry OBJECT-TYPE
    SYNTAX  Uas7624VersionEntry
    ACCESS  not-accessible
    STATUS  mandatory
    DESCRIPTION
	    "An entry in the GDC uas7624System Version Table."
    INDEX  { uas7624VersionIndex }
    ::= { uas7624VersionTable 1 }
									
Uas7624VersionEntry ::=
    SEQUENCE {
	uas7624VersionIndex SCinstance,
	uas7624FirmwareRev  DisplayString,
	uas7624CardType	    DisplayString,
	uas7624BootRev	    DisplayString
	}

uas7624VersionIndex OBJECT-TYPE
    SYNTAX  SCinstance
    ACCESS  read-only
    STATUS  mandatory
    DESCRIPTION
	    "Integer value which uniquely identifies the uas7624 
	    to which this entry is applicable.
 
		For entire table:	
		SCinstance:	[L]ine=5   	[i]nterface=0"				
    ::= { uas7624VersionEntry 1 }

uas7624FirmwareRev OBJECT-TYPE
    SYNTAX  DisplayString (SIZE(2))
    ACCESS  read-only
    STATUS  mandatory
    DESCRIPTION
	    "The version number of the firmware, to allow products
	    to know which revision is installed.  The released
	    version number is sequenced from --, A-, ... AA, ... ZZ."
    ::= { uas7624VersionEntry 2 }

uas7624CardType	OBJECT-TYPE
    SYNTAX  DisplayString (SIZE(0..16))
    ACCESS  read-only
    STATUS  mandatory
    DESCRIPTION
	    "This variable is used to determine the type
	    of card family installed ex. uas7624."
	::= { uas7624VersionEntry 3 }

uas7624BootRev 	OBJECT-TYPE
    SYNTAX  DisplayString (SIZE(2))
    ACCESS  read-only
    STATUS  mandatory
    DESCRIPTION
	    "The version number of the boot firmware, to allow products
	    to know which revision is installed.  The released version
	    number is sequenced from --, A-, ... AA, ... ZZ.  "
    ::= { uas7624VersionEntry 4 }

--
-- *********************************************************
--  GDC uas7624 Maintenance Table
-- **********************************************************

uas7624MaintenanceTable OBJECT-TYPE
    SYNTAX  SEQUENCE OF Uas7624MaintenanceEntry
    ACCESS  not-accessible
    STATUS  mandatory
    DESCRIPTION
	    "The table describes the maintenance objects for uas7624." 
    ::= { uas7624Maintenance 1  }

uas7624MaintenanceEntry OBJECT-TYPE
    SYNTAX  Uas7624MaintenanceEntry
    ACCESS  not-accessible
    STATUS  mandatory
    DESCRIPTION
	    "An entry in the GDC 7624 Maintenance Table."
    INDEX  { uas7624MaintenanceLineIndex }
    ::= { uas7624MaintenanceTable 1 }

Uas7624MaintenanceEntry ::=
    SEQUENCE {
	uas7624MaintenanceLineIndex SCinstance,
	uas7624SoftReset	    INTEGER,
	uas7624DefaultInit	    INTEGER,
	uas7624ResetMajorAlarm	    INTEGER,
	uas7624ResetMinorAlarm	    INTEGER,
	uas7624ResetStatistics	    INTEGER,
	uas7624StatLastInitialized  TimeTicks,
	uas7624ValidIntervals	    INTEGER,
	uas7624SysUpTime	    INTEGER,
	uas7624LedStatus	    OCTET STRING,
	uas7624AlarmStatus	    OCTET STRING,
	uas7624LoopState	    INTEGER,
	uas7624ConfigMode	    INTEGER
    }

uas7624MaintenanceLineIndex OBJECT-TYPE
    SYNTAX  SCinstance
    ACCESS  read-only
    STATUS  mandatory
    DESCRIPTION
	    "Integer value which uniquely identifies 
	    the uas7624 to which this entry is applicable.

		See DESCRIPTION's below for ranges."
    ::= { uas7624MaintenanceEntry 1 }

uas7624SoftReset OBJECT-TYPE
    SYNTAX  INTEGER {
		norm(1),
		reset(2)
	    }
    ACCESS  read-write
    STATUS  mandatory
    DESCRIPTION
	    "Supports the action of soft resetting the unit.  
	    When this object is set to reset(2), then the unit 
	    performs a soft reset, whose meaning is specific to
	    the type of unit being managed. The value of norm(1) 
	    will be returned when the reset is complete.
	    The value of norm(1) can not be set by management.

		SCinstance:	[L]ine=1-5   	[i]nterface=0"
	::= { uas7624MaintenanceEntry 2 }

uas7624DefaultInit OBJECT-TYPE
    SYNTAX  INTEGER {
		normal(1),
		factoryDefault(2)
	    }
    ACCESS  read-write
    STATUS  mandatory
    DESCRIPTION
	    "This is used to allow the NonVolatile Configuration to 
	    be set to a factory default state.  When this value is set
	    to factoryDefault(2) the unit will perform  a reset to make 
	    the default configuration take affect. 
	    The value of normal(1) will be returned when the 
	    initialization is complete.
	    The value of normal(1) can not be set by management.

		SCinstance:	[L]ine=1-5   	[i]nterface=0"
	::= { uas7624MaintenanceEntry 3 }

uas7624ResetMajorAlarm	OBJECT-TYPE
    SYNTAX  INTEGER {
		norm(1),
		reset(2)
	    }
    ACCESS  read-write 
    STATUS  mandatory
    DESCRIPTION 
	    " This variable is used.

		SCinstance:	[L]ine=1-4   	[i]nterface=1-3"
    ::= { uas7624MaintenanceEntry 4 }
 
uas7624ResetMinorAlarm OBJECT-TYPE
    SYNTAX  INTEGER {
		norm(1),
		reset(2)
	    }
    ACCESS  read-write 
    STATUS  mandatory
    DESCRIPTION 
	" This variable is used.

	    SCinstance:	[L]ine=1-4   	[i]nterface=1-3"
    ::= { uas7624MaintenanceEntry 5 }

uas7624ResetStatistics OBJECT-TYPE
    SYNTAX  INTEGER {
		norm(1),
		reset(2)
	    }
    ACCESS  read-write
    STATUS  mandatory
    DESCRIPTION
	    "This variable is used to reset the performance intervals.
	    When it is set to reset, the performance tables and uas7624Valid
	    intervals are reset to zero. The value of norm(1) can not be set 
	    by management.

		SCinstance:	[L]ine=1-4   	[i]nterface=1-3
				[L]ine=5   	[i]nterface=0"
    ::= { uas7624MaintenanceEntry 6 }

uas7624StatLastInitialized OBJECT-TYPE
    SYNTAX  TimeTicks
    ACCESS  read-only
    STATUS  mandatory
    DESCRIPTION
	    "The elapsed time since the statistics were last initialized. 
	    This will be zero'd when uas7624ResetStatistics is reset(2).

		SCinstance:	[L]ine=1-4   	[i]nterface=1-3
				[L]ine=5   	[i]nterface=0"
    ::= {uas7624MaintenanceEntry 7 }

uas7624ValidIntervals OBJECT-TYPE
    SYNTAX  INTEGER (1..96)
    ACCESS  read-only
    STATUS  mandatory
    DESCRIPTION
	    "The number of  previous  intervals  for  which
	    valid data was collected.  The value will be 96 for the T1 
	    interface and 16 for the loop interface
	    unless the interface was brought on-line within
	    the last 24 hours, in which case the value will
	    be the number of complete 15  minute  intervals
	    the since interface has been online.	
	    Note: The loop interface values are 1-16, T1 values are 1-96.

		SCinstance:	[L]ine=1-4   	[i]nterface=1-3
				[L]ine=5   	[i]nterface=0"
    ::= {uas7624MaintenanceEntry 8 }

uas7624SysUpTime OBJECT-TYPE
    SYNTAX  INTEGER (1..2147483647)
    ACCESS  read-only
    STATUS  mandatory
    DESCRIPTION
	    "This variable is used to report the elapsed system tick
	    time for conversion to real time at the controller and is
	    not related to the sysUpTime referenced in MIB-II.
	    Upon power-up of the unit, the elapsed time is cleared.
	    The elapsed time counter rolls over upon reaching the
	    maximum count.

		SCinstance:	[L]ine=5   	[i]nterface=0"
    ::= { uas7624MaintenanceEntry 9 }

uas7624LedStatus OBJECT-TYPE
    SYNTAX  OCTET STRING (SIZE(2))
    ACCESS  read-only
    STATUS  mandatory
    DESCRIPTION
	"Returns a bitwise snapshot of the front panel LED state.
	based on the Line:


	For SCinstance:	[L]ine=1-4   	[i]nterface=0

		key 
		---
		01 = SOLID GREEN 	Good Condition and in Sync 
		10 = SOLID RED		Alarm State (no Current or no Sync)
		11 = FLASHING GREEN	Loop in Test

		1.7 - n/a
		1.6 - f/u
		1.5 - 2^1     
		1.4 - 2^0 	Loop 1	(01, 10, 11)
		1.3 - f/u		
		1.2 - f/u				
		1.1 - 2^1 
		1.0 - 2^0 	Loop 2	(01, 10, 11)

		2.7 - f/u
		2.6 - f/u
		2.5 - f/u
		2.4 - f/u	
		2.3 - 2^1 
		2.2 - 2^0 	Loop 3	(01, 10, 11)
		2.1 - f/u
		2.0 - f/u		



	For SCinstance:	[L]ine=5     	[i]nterface=0


		1.7 - n/a
		1.6 - f/u
		1.5 - f/u  
		1.4 - f/u
		1.3 - f/u		
		1.2 - f/u				
		1.1 - f/u
		1.0 - f/u

		2.7 - n/a
		2.6 - f/u
		2.5 - Network AIS	1:RED (Alarm Indication Signal)
		2.4 - Network LVC	1:RED (Line Code Violation)
		2.3 - Network LOS 	1:RED (Loss Of Signal)
		2.2 - Network OOF	1:RED (Out Of Frame)
		2.1 - ALARM	        1: FLASHING RED (AIS, LVC, LOS, or OOF)
		2.0 - Test Mode		1: RED (in test mode)
	"
    ::= { uas7624MaintenanceEntry 10 }
	
uas7624AlarmStatus OBJECT-TYPE
    SYNTAX  OCTET STRING (SIZE(4))
    ACCESS  read-only
    STATUS  mandatory
    DESCRIPTION
	    "Returns a bit-wise Status of alarms with
	    both masked and unmasked.

	For SCinstance:	[L]ine=1-4   	[i]nterface=0

		1.7 - f/u
		1.6 - Power-up
		1.5 - f/u
		1.4 - Loop 1 OOS
		1.3 - Loop 1 Sealing Current Non-Continuity
		1.2 - Loop 1 ES
		1.1 - Loop 1 SES
		1.0 - Loop 1 UAS

		2.7 - f/u
		2.6 - f/u
		2.5 - f/u
		2.4 - Loop 2 OOS
		2.3 - Loop 2 Sealing Current Non-Continuity
		2.2 - Loop 2 ES
		2.1 - Loop 2 SES
		2.0 - Loop 2 UAS

		3.7 - f/u
		3.6 - f/u
		3.5 - f/u
		3.4 - Loop 3 OOS
		3.3 - Loop 3 Sealing Current Non-Continuity
		3.2 - Loop 3 ES
		3.1 - Loop 3 SES
		3.0 - Loop 3 UAS

		4.7 - f/u
		4.6 - f/u
		4.5 - Loop 1 Major
		4.4 - Loop 1 Minor
		4.3 - Loop 2 Major
		4.2 - Loop 2 Minor
		4.1 - Loop 3 Major
		4.0 - Loop 3 Minor

	For SCinstance:	[L]ine=5     	[i]nterface=0

		1.7 - f/u
		1.6 - LOS
		1.5 - LOF
		1.4 - AIS
		1.3 - f/u		
		1.2 - Received Yellow			
		1.1 - f/u 
		1.0 - f/u

		2.7 - f/u
		2.6 - LCV
		2.5 - CRC
		2.4 - f/u	
		2.3 - f/u 
		2.2 - f/u
		2.1 - f/u
		2.0 - f/u		

		3.7 - f/u
		3.6 - f/u
		3.5 - f/u
		3.4 - f/u	
		3.3 - f/u 
		3.2 - f/u
		3.1 - f/u
		3.0 - f/u		

		4.7 - f/u
		4.6 - ES
		4.5 - BES
		4.4 - SES	
		4.3 - UAS 
		4.2 - f/u
		4.1 - f/u
		4.0 - Power-up"

    ::= {uas7624MaintenanceEntry 11 }

uas7624LoopState OBJECT-TYPE
    SYNTAX  INTEGER {
		inhibit(1),
		enable(2)
	    }
    ACCESS  read-write 
    STATUS  mandatory
    DESCRIPTION 
	"A setting of inhibit(1) stops operation on the loop
         and a setting of enable(2) starts operation on the
	 loop.
	 SCinstance:	[L]ine=1-4   	[i]nterface=1-3"
    ::= { uas7624MaintenanceEntry 12 }

uas7624ConfigMode OBJECT-TYPE
    SYNTAX  INTEGER {
		hardMode(1),
		softMode(2)
	    }
    ACCESS  read-only
    STATUS  mandatory
    DESCRIPTION
	    "This variable is used to report the mode, either soft or
	     hard, of the the uas7624.  If the unit is in hard mode
	     then the options in the uas7624ConfigTable are read-only.
	     If the unit is in soft mode then the options in the
	     uas7624ConfigTable are read-write.
		SCinstance:	[L]ine=5   	[i]nterface=0"
    ::= { uas7624MaintenanceEntry 13 }

--
-- ********************************************************************
-- The GDC 7624 Configuration Table
-- ********************************************************************
--

uas7624ConfigTable OBJECT-TYPE
    SYNTAX  SEQUENCE OF Uas7624ConfigEntry
    ACCESS  not-accessible
    STATUS  mandatory
    DESCRIPTION
	    "The GDC Configuration table."
    ::= { uas7624Configuration 1 }

uas7624ConfigEntry OBJECT-TYPE
    SYNTAX  Uas7624ConfigEntry
    ACCESS  not-accessible
    STATUS  mandatory
    DESCRIPTION
	    "The GDC Configuration table entry."
    INDEX { uas7624ConfigIndex }
    ::= { uas7624ConfigTable 1 }

Uas7624ConfigEntry ::= 
    SEQUENCE {
	uas7624ConfigIndex		 SCinstance,
	uas7624NetworkInterfaceType	 INTEGER,
	uas7624TransmitClockSource	 INTEGER,
	uas7624PreEqualization		 INTEGER,
	uas7624Framing			 INTEGER,
	uas7624LineCoding		 INTEGER,
	uas7624LineBuildout		 INTEGER,
	uas7624FDLMode			 INTEGER,
	uas7624Loopback			 INTEGER,
	uas7624AISLoopdown		 INTEGER,
	uas7624LineBuildoutMode          INTEGER,
	uas7624FramingMode               INTEGER
    }
	
uas7624ConfigIndex OBJECT-TYPE
    SYNTAX  SCinstance
    ACCESS  read-only
    STATUS  mandatory
    DESCRIPTION
	    "Integer value which uniquely identifies the uas7624 
	    to which this entry is applicable.

		For entire table:	
		SCinstance:	[L]ine=5   	[i]nterface=0"
    ::= { uas7624ConfigEntry 1 }

uas7624NetworkInterfaceType OBJECT-TYPE
    SYNTAX  INTEGER {
		ds1(1),
		dsx1(2)
	    }
    ACCESS  read-write
    STATUS  mandatory
    DESCRIPTION
	    "Sets the transmit range to DSX-1 short or DS-1 long "
    ::= { uas7624ConfigEntry 2 }

uas7624TransmitClockSource OBJECT-TYPE
    SYNTAX  INTEGER {
		recovered(1),
		internal(2)
	    }
    ACCESS  read-write
    STATUS  mandatory
    DESCRIPTION
	"Sets the transmit clock source."
    ::= { uas7624ConfigEntry 3 }

uas7624PreEqualization OBJECT-TYPE
    SYNTAX  INTEGER {
		none(1),
		feet130(2),
		feet260(3),
		feet390(4),
		feet530(5),
		feet655(6)
	    }
    ACCESS  read-write
    STATUS  mandatory
    DESCRIPTION
	    "Pre-Equalization distance"
    ::= { uas7624ConfigEntry 4 }

uas7624Framing OBJECT-TYPE
    SYNTAX  INTEGER {
		eSF(1),
		d4(2)
	    }
    ACCESS  read-write
    STATUS  mandatory
    DESCRIPTION
	    "Set the framing for the interface.
		Abbreviations are as follows:
	 	eSF - Extended Super Frame
	 	d4  -  Super Frame"
    ::= {uas7624ConfigEntry 5 }

uas7624LineCoding OBJECT-TYPE
    SYNTAX  INTEGER {
		b8zs(1),
		ami(2)
	    }
    ACCESS  read-write
    STATUS  mandatory
    DESCRIPTION
	"Sets the line coding for the interface."
    ::= {uas7624ConfigEntry 6 }
 
uas7624LineBuildout OBJECT-TYPE
    SYNTAX  INTEGER  {
		dB0(1),
		dB75(2),
		dB15(3),
		dB22(4)
	    }
    ACCESS  read-write
    STATUS  mandatory
    DESCRIPTION
	"Sets the line build out for the T1 interface."
    ::= {uas7624ConfigEntry 7 }
 
uas7624FDLMode OBJECT-TYPE
    SYNTAX  INTEGER {
		none(1),
		aNSIT1403(2),
		tR54016(3)
	    }
    ACCESS  read-write
    STATUS  mandatory
    DESCRIPTION
	    "Sets the Facility Data Link Mode."
    ::= {uas7624ConfigEntry 8 }
 
uas7624Loopback OBJECT-TYPE
    SYNTAX  INTEGER {
		inhibitloop(1),
		payloadloop(2),
		lineloop(3)
	    }
    ACCESS  read-write
    STATUS  mandatory
    DESCRIPTION
	    "Sets the loopback type"
    ::= {uas7624ConfigEntry 9 }

uas7624AISLoopdown OBJECT-TYPE
    SYNTAX  INTEGER (4..60)
    ACCESS  read-write
    STATUS  mandatory
    DESCRIPTION
	    "Sets AIS unloop time where 4 = inhibit,
	    5 thru 60 = number of seconds"
    ::= {uas7624ConfigEntry 10 }

uas7624LineBuildoutMode OBJECT-TYPE
    SYNTAX  INTEGER {
		auto(1),
		manual(2)
 	   }
    ACCESS read-write
    STATUS mandatory
    DESCRIPTION
	     "Sets the line build out mode for the T1 interface."
    ::= {uas7624ConfigEntry 11 }

uas7624FramingMode OBJECT-TYPE
    SYNTAX INTEGER {
	       auto(1),
	       manual(2)
	   }
    ACCESS read-write
    STATUS mandatory
    DESCRIPTION
	     "Set the framing mode."
    ::= {uas7624ConfigEntry 12 }



--
-- ********************************************************************
-- GDC 7624 Diagnostics
-- ********************************************************************
-- This table contains the diagnostic test information.
	
uas7624DiagTable OBJECT-TYPE
    SYNTAX  SEQUENCE OF Uas7624DiagEntry
    ACCESS  not-accessible
    STATUS  mandatory
    DESCRIPTION
	    "The GDC 7624 Diagnostics table.  Information in the entries of
	    this table support diagnostics testing, both active testing
	    via patterns, and passive testing via loopbacks."
    ::= { uas7624Diagnostics 1 }

uas7624DiagEntry OBJECT-TYPE
    SYNTAX  Uas7624DiagEntry
    ACCESS  not-accessible
    STATUS  mandatory
    DESCRIPTION
	    "The GDC 7624 Diagnostics table entry."
    INDEX { uas7624DiagIndex }
    ::= { uas7624DiagTable 1 }

Uas7624DiagEntry ::= 
    SEQUENCE {
	uas7624DiagIndex 		 SCinstance,
	uas7624DiagConfig		 INTEGER,
	uas7624T1TestLimit		 INTEGER,
	uas7624T1TestExecutionStatus	 INTEGER,
	uas7624T1TestExceptions 	 INTEGER,
	uas7624TestResults		 INTEGER,
	uas7624ResetTestResults 	 INTEGER
    }

uas7624DiagIndex OBJECT-TYPE
    SYNTAX  SCinstance
    ACCESS  read-only
    STATUS  mandatory
    DESCRIPTION
	    "Integer value which uniquely identifies the uas7624 to which this
	    entry is applicable.

		See DESCRIPTION's below for ranges."
    ::= { uas7624DiagEntry 1 }


uas7624DiagConfig OBJECT-TYPE
    SYNTAX  INTEGER {
		stopTest(1),
		lineLoopback(2),
		payloadLoopback(3),
		digitalLoopback(4),
		selfTest(5),			 
		rdl(6),
		rdlSelfTest(7)
	    }
    ACCESS  read-write
    STATUS  mandatory
    DESCRIPTION
	    "	Selects test to run. (1) stops test.

				    SCinstance:
		stopTest(1)	    [L]ine=1-5 	[i]nterface=0-3
		lineLoopback(2)	    [L]ine=5   	[i]nterface=0
		payloadLoopback(3)  [L]ine=5   	[i]nterface=0
		digitalLoopback(4)  [L]ine=1-4 	[i]nterface=1-3
		selfTest(5)	    [L]ine=1-4 	[i]nterface=1-3
		rdl(6)		    [L]ine=1-4 	[i]nterface=1-3
		rdlSelfTest(7)	    [L]ine=1-4 	[i]nterface=1-3"
    ::= { uas7624DiagEntry 2 }

uas7624T1TestLimit OBJECT-TYPE
    SYNTAX  INTEGER{
		noLimit(1),
		testTime1Min(2),
		testTime2Mins(3),
		testTime3Mins(4),
		testTime4Mins(5),
		testTime5Mins(6),
		testTime6Mins(7),
		testTime7Mins(8),
		testTime8Mins(9),
		testTime9Mins(10),
		testTime10Mins(11),
		testTime15Mins(12),
		testTime20Mins(13),
		testTime25Mins(14),
		testTime30Mins(15),
		testTime30Secs(16)
	    }                  
    ACCESS  read-write
    STATUS  mandatory
    DESCRIPTION
	    "Selects the duration to run a T1 diagnostic test.  The value(1)
	    noLimit signifies that the test should run indefinitely until
	    explicitly terminated.

		SCinstance:	[L]ine=5  	[i]nterface=0"
    ::= { uas7624DiagEntry 3 }

uas7624T1TestExecutionStatus OBJECT-TYPE
    SYNTAX  INTEGER {
		notInTest(1),		    -- a test is not running
		testInProgress(2),	    -- the test is running
		testCompleted(4),	    -- the test is complete
		testCompletedNotInTest(5)   -- test has completed,
					    --	    no longer in test
	    }
    ACCESS  read-only
    STATUS  mandatory
    DESCRIPTION
	    "This variable reports the status of a T1 test.  
	    notInTest(1) indicates a test is not running.  
	    testInProgress(2) indicates that a test is
	    currently running.  testCompleted(4) indicates that a test has run
	    and is completed. 
	    testCompletedNotInTest(5) indicates that a test has
	    completed and it is no longer in test.

	    SCinstance:	[L]ine=5   	[i]nterface=0"
    ::= { uas7624DiagEntry 4 }

uas7624T1TestExceptions OBJECT-TYPE
    SYNTAX  INTEGER (0..7)
    ACCESS  read-only
    STATUS  mandatory
    DESCRIPTION
	    "Indicates T1 test exceptions that have occurred that may affect
	    interpretation of the test results.
	    The value of this object is a sum.  This sum initially take
	    the value zero.  Then, for each exception, the value
	    associated with the exception is added to the sum.

	    The exception values are:
    
		 value  exception
		     1   a timed test was preempted so the result
			   cannot be viewed in relation to the test
			   duration
		     2   the results overflowed so the result cannot be
			   viewed as an absolute value
		     4   the test was performed while synchronization
			   could not be performed so the result may not
			   be accurate.

	    SCinstance:	[L]ine=5   	[i]nterface=0"
    ::= { uas7624DiagEntry 5 }

uas7624TestResults OBJECT-TYPE
    SYNTAX  INTEGER(0..1048576)
    ACCESS  read-only
    STATUS  mandatory
    DESCRIPTION
	    "The results of the last T1 diagnostic test.  This can be the
	    current test running or the last completed test.

	    Note that the interpretation of these results may be affected
	    by the value of the uas7624TestExceptions object.

	    This function reads the DIU self test results in
	    bit errors. 2^20

		SCinstance:	[L]ine=1-4 	[i]nterface=1-3
				[L]ine=5   	[i]nterface=0"
    ::= { uas7624DiagEntry 6 }


uas7624ResetTestResults	OBJECT-TYPE
    SYNTAX  INTEGER {
		norm(1),   -- read-only
		reset(2)   -- write-only
	    }
    ACCESS  read-write
    STATUS  mandatory
    DESCRIPTION
	    "Resets the diagnostic T1 or Loop error count.

		SCinstance:	[L]ine=1-4 	[i]nterface=1-3
				[L]ine=5   	[i]nterface=0"
    ::= { uas7624DiagEntry 7 }

--
-- ********************************************************************
-- GDC uas7624 Alarm Object Identifier Definitions
-- ********************************************************************

uas7624Alarms				OBJECT IDENTIFIER ::= {uas7624 1 }

uas7624NoResponseAlm		    OBJECT IDENTIFIER ::= {uas7624Alarms 1}
uas7624DiagRxErrAlm		    OBJECT IDENTIFIER ::= {uas7624Alarms 2}
uas7624PowerUpAlm		    OBJECT IDENTIFIER ::= {uas7624Alarms 3}
uas7624LossOfSignalAlm		    OBJECT IDENTIFIER ::= {uas7624Alarms 4}
uas7624LossOfFrameAlm		    OBJECT IDENTIFIER ::= {uas7624Alarms 5}
uas7624AisAlm			    OBJECT IDENTIFIER ::= {uas7624Alarms 6}
uas7624YellowAlm		    OBJECT IDENTIFIER ::= {uas7624Alarms 7}
uas7624OutofSyncAlm		    OBJECT IDENTIFIER ::= {uas7624Alarms 8}
uas7624SealingCurrentNoContAlm	    OBJECT IDENTIFIER ::= {uas7624Alarms 9}
uas7624UASAlm			    OBJECT IDENTIFIER ::= {uas7624Alarms 10}
uas7624ESAlm			    OBJECT IDENTIFIER ::= {uas7624Alarms 11}
uas7624LineCodeViolationAlm	    OBJECT IDENTIFIER ::= {uas7624Alarms 12}
uas7624CRCAlm			    OBJECT IDENTIFIER ::= {uas7624Alarms 13}
uas7624BESAlm			    OBJECT IDENTIFIER ::= {uas7624Alarms 14}
uas7624SESAlm			    OBJECT IDENTIFIER ::= {uas7624Alarms 15}
uas7624MajorBERAlm		    OBJECT IDENTIFIER ::= {uas7624Alarms 16}
uas7624MinorBERAlm		    OBJECT IDENTIFIER ::= {uas7624Alarms 17}
	


-- ALARM				Mask- Valid  Valid    Window   Thres
--					able   Line   int    Line int Line int
-- ============================================================================
-- uas7624NoResponseAlm			no    1-5     0 	no	no
-- uas7624DiagRxErrAlm			no    1-5     0         no	no
-- uas7624PowerUpAlm			no    1-5     0	        no	no
-- uas7624LossofSignalAlm		yes   5	      0	        no	no  
-- uas7624LossOfFrameAlm		yes   5       0 	no	no  
-- uas7624AisAlm			yes   5       0	        no	no  
-- uas7624YellowAlm			yes   5       0	        no	no  
-- uas7624OutofSyncAlm			yes   1-4     1-3	no	no
-- uas7624SealingCurrentNoContinuityAlm	yes   1-4     1-3	no	no
-- uas7624UASAlm			yes   1-4,5   1-3,0    5  0    5  0
-- uas7624ESAlm				yes   1-4,5   1-3,0    5  0    5  0
-- uas7624LineCodeViolationAlm		yes   5       0	       5  0    5  0
-- uas7624CRCAlm			yes   5       0	       5  0    5  0
-- uas7624BESAlm			yes   5       0	       5  0    5  0
-- uas7624SESAlm			yes   5       0	       5  0    5  0
-- uas7624MajorBERAlm			yes   1-4     1-3       no    1-4 1-3
-- uas7624MinorBERAlm			yes   1-4     1-3	no    1-4 1-3

--
-- ********************************************************************
-- GDC uas7624 Alarm Configuration
-- ********************************************************************

uas7624AlarmConfigTable OBJECT-TYPE
    SYNTAX  SEQUENCE OF Uas7624AlarmConfigEntry
    ACCESS  not-accessible
    STATUS  mandatory
    DESCRIPTION
	    "This table contains entries that configure Alarm reporting."
    ::= { uas7624AlarmConfig 1 }

uas7624AlarmConfigEntry OBJECT-TYPE
    SYNTAX  Uas7624AlarmConfigEntry
    ACCESS  not-accessible
    STATUS  mandatory
    DESCRIPTION
	    "An entry in the uas7624 Alarm Configuration table."
    INDEX { uas7624AlarmConfigIndex, uas7624AlarmConfigIdentifier }
    ::= { uas7624AlarmConfigTable 1 }

Uas7624AlarmConfigEntry ::=
    SEQUENCE {
	uas7624AlarmConfigIndex		SCinstance,
	uas7624AlarmConfigIdentifier	OBJECT IDENTIFIER,
	uas7624AlarmCountWindow		INTEGER,
	uas7624AlarmCountThreshold	INTEGER
    }

uas7624AlarmConfigIndex OBJECT-TYPE
    SYNTAX  SCinstance
    ACCESS  read-only
    STATUS  mandatory
    DESCRIPTION
	    "Integer value which uniquely identifies the uas7624 to which this
	    entry is applicable.
		
		For this table:
		SCinstance:	[L]ine=1-4 	[i]nterface=1-3
				[L]ine=5   	[i]nterface=0"
    ::= { uas7624AlarmConfigEntry 1 }

uas7624AlarmConfigIdentifier OBJECT-TYPE
    SYNTAX  OBJECT IDENTIFIER
    ACCESS  read-only
    STATUS  mandatory
    DESCRIPTION
	    "The unique alarm identifier assigned to this alarm type.
	    The format of this identifier is an OBJECT IDENTIFIER that has
	    the following format: {iso(1) org(3) dod(6) internet(1)
	    private(4) enterprises(1) gdc(498) xxx(x) alarm(z) yyy(y) 
	    where xxx(x) is the administratively assigned family object 
	    identifier (z) is the object identifier for alarms in the family
	    defined MIB and yyy(y) is the administratively assigned alarm 
	    type identifier for this alarm."
    ::= { uas7624AlarmConfigEntry 2 }

uas7624AlarmCountWindow OBJECT-TYPE
    SYNTAX INTEGER{
		disabled(1),
		last1sec(2),
		last10sec(3),
		last30sec(4),
		last1min(5),
		last15min(6),
		last1hr(7),
		last24hr(8),
		infinite(9)
	    }
    ACCESS  read-write
    STATUS  mandatory
    DESCRIPTION
	    "This variable sets/reads the alarm window.

	    This window is used with the alarm threshold to determine
	    how long the alarm should be active before reporting.

	    Default: disabled(1)"
    ::= { uas7624AlarmConfigEntry 3 }

uas7624AlarmCountThreshold OBJECT-TYPE
    SYNTAX  INTEGER {
		thresGT1(1),     -- [L]ine=5
		thresGT3(2),     -- [L]ine=5
		thresGT10(3),    -- [L]ine=5
		thresGT100(4),   -- [L]ine=5
		thresGT1000(5),  -- [L]ine=5
		thresGT10000(6), -- [L]ine=5
		thres10E03(7),   -- [L]ine=1-4
		thres10E04(8),   -- [L]ine=1-4
		thres10E05(9),   -- [L]ine=1-4
		thres10E06(10)   -- [L]ine=1-4
	    }
    ACCESS  read-write
    STATUS  mandatory
    DESCRIPTION
	    "This function sets/reads the alarm threshold criteria.

	    This threshold is used along with the the alarm window to 
	    determine the number of instances in a given time frame for
	    an alarm to occur before the alarm is considered active.

	    Default: thresGT1(1)"
    ::= { uas7624AlarmConfigEntry 4 }

--
-- ********************************************************************
-- GDC LOCAL uas7624 Alarm Configuration
-- ********************************************************************
-- Local Alarms are alarms that optionally activate the backplane
-- Major or Minor buses. These alarms changes are never reported in an
-- unsolicited message to the proxy agent hence, the reason for the alarm
-- card. These alarms are different from the previously defined alarms
-- in that the mask state has three possible values.

uas7624LocalAlarmConfigTable OBJECT-TYPE
    SYNTAX SEQUENCE OF Uas7624LocalAlarmConfigEntry
    ACCESS not-accessible
    STATUS mandatory
    DESCRIPTION
	    "The uas7624LocalAlarmConfigTable contains entries 
	    that configure alarm reporting to the alarm card."
    ::= { uas7624AlarmConfig 2 }

uas7624LocalAlarmConfigEntry OBJECT-TYPE
    SYNTAX Uas7624LocalAlarmConfigEntry
    ACCESS not-accessible
    STATUS mandatory
    DESCRIPTION
	    "An entry in the GDC Local Alarm Configuration table."
    INDEX { uas7624LocalAlarmConfigIndex }
    ::= { uas7624LocalAlarmConfigTable 1 }

Uas7624LocalAlarmConfigEntry ::=
    SEQUENCE {
	uas7624LocalAlarmConfigIndex	SCinstance,
	uas7624LOSLocal			INTEGER,
	uas7624LOFLocal			INTEGER,
	uas7624AISLocal			INTEGER,
	uas7624YELLOWLocal		INTEGER,
	uas7624LineCodeViolationLocal	INTEGER,
	uas7624CRCLocal			INTEGER,
	uas7624ESLocal			INTEGER,
	uas7624BESLocal			INTEGER,
	uas7624SESLocal			INTEGER,
	uas7624UASLocal			INTEGER,
	uas7624OutofSyncLocal		INTEGER,
	uas7624NoSealingCurrentLocal	INTEGER
    }

uas7624LocalAlarmConfigIndex OBJECT-TYPE
    SYNTAX  SCinstance
    ACCESS  read-only
    STATUS  mandatory
    DESCRIPTION
	    "Integer value which uniquely identifies the uas7624 to which this
	    entry is applicable.

		For this table:
		See DESCRIPTION's below for ranges."
      ::= { uas7624LocalAlarmConfigEntry 1 }

uas7624LOSLocal OBJECT-TYPE
    SYNTAX  INTEGER {
		disabled(1),
		enabledMajor(2),
		enabledMinor(3)
	    }
    ACCESS  read-write
    STATUS  mandatory
    DESCRIPTION
	    "Disables or enables the alarm on the Major buss or Minor Buss.
		SCinstance:	[L]ine=5   	[i]nterface=0"
      ::= { uas7624LocalAlarmConfigEntry 2 }

uas7624LOFLocal OBJECT-TYPE
    SYNTAX  INTEGER {
		disabled(1),
		enabledMajor(2),
		enabledMinor(3)
	    }
    ACCESS  read-write
    STATUS  mandatory
    DESCRIPTION
	    "Disables or enables the alarm on the Major buss or Minor Buss.
		SCinstance:	[L]ine=5   	[i]nterface=0"
      ::= { uas7624LocalAlarmConfigEntry 3 }

uas7624AISLocal OBJECT-TYPE
    SYNTAX  INTEGER {
		disabled(1),
		enabledMajor(2),
		enabledMinor(3)
	    }
    ACCESS  read-write
    STATUS  mandatory
    DESCRIPTION
	    "Disables or enables the alarm on the Major buss or Minor Buss.
		SCinstance:	[L]ine=5   	[i]nterface=0"
      ::= { uas7624LocalAlarmConfigEntry 4 }

uas7624YELLOWLocal OBJECT-TYPE
    SYNTAX  INTEGER {
		disabled(1),
		enabledMajor(2),
		enabledMinor(3)
	    }
    ACCESS  read-write
    STATUS  mandatory
    DESCRIPTION
	    "Disables or enables the alarm on the Major buss or Minor Buss.
		SCinstance:	[L]ine=5   	[i]nterface=0"
      ::= { uas7624LocalAlarmConfigEntry 5 }

uas7624LineCodeViolationLocal OBJECT-TYPE
    SYNTAX  INTEGER {
		disabled(1),
		enabledMajor(2),
		enabledMinor(3)
	    }
    ACCESS  read-write
    STATUS  mandatory
    DESCRIPTION
	    "Disables or enables the alarm on the Major buss or Minor Buss.
		SCinstance:	[L]ine=5   	[i]nterface=0"
      ::= { uas7624LocalAlarmConfigEntry 6 }

uas7624CRCLocal OBJECT-TYPE
    SYNTAX  INTEGER {
		disabled(1),
		enabledMajor(2),
		enabledMinor(3)
	    }
    ACCESS  read-write
    STATUS  mandatory
    DESCRIPTION
	    "Disables or enables the alarm on the Major buss or Minor Buss.
		SCinstance:	[L]ine=5   	[i]nterface=0"
      ::= { uas7624LocalAlarmConfigEntry 7 }


uas7624ESLocal OBJECT-TYPE
    SYNTAX  INTEGER {
		disabled(1),
		enabledMajor(2),
		enabledMinor(3)
	    }
    ACCESS  read-write
    STATUS  mandatory
    DESCRIPTION
	    "Disables or enables the alarm on the Major buss or Minor Buss.
		SCinstance:	[L]ine=1-4 	[i]nterface=1-3
				[L]ine=5   	[i]nterface=0"
      ::= { uas7624LocalAlarmConfigEntry 10 }

uas7624BESLocal OBJECT-TYPE
    SYNTAX  INTEGER {
		disabled(1),
		enabledMajor(2),
		enabledMinor(3)
	    }
    ACCESS  read-write
    STATUS  mandatory
    DESCRIPTION
	    "Disables or enables the alarm on the Major buss or Minor Buss.
		SCinstance:	[L]ine=5   	[i]nterface=0"
      ::= { uas7624LocalAlarmConfigEntry 11 }

uas7624SESLocal OBJECT-TYPE
    SYNTAX  INTEGER {
		disabled(1),
		enabledMajor(2),
		enabledMinor(3)
	    }
    ACCESS  read-write
    STATUS  mandatory
    DESCRIPTION
	    "Disables or enables the alarm on the Major buss or Minor Buss.
		SCinstance:	[L]ine=5   	[i]nterface=0"
     ::= { uas7624LocalAlarmConfigEntry 12 }

uas7624UASLocal OBJECT-TYPE
    SYNTAX  INTEGER {
		disabled(1),
		enabledMajor(2),
		enabledMinor(3)
	    }
    ACCESS  read-write
    STATUS  mandatory
    DESCRIPTION
	    "Disables or enables the alarm on the Major buss or Minor Buss.
		SCinstance:	[L]ine=1-4 	[i]nterface=1-3
				[L]ine=5   	[i]nterface=0"
    ::= { uas7624LocalAlarmConfigEntry 13 }

uas7624OutofSyncLocal OBJECT-TYPE
    SYNTAX  INTEGER {
		disabled(1),
		enabledMajor(2),
		enabledMinor(3)
	    }
    ACCESS  read-write
    STATUS  mandatory
    DESCRIPTION
	    "Disables or enables the alarm on the Major buss or Minor Buss.
		SCinstance:	[L]ine=1-4 	[i]nterface=1-3"
    ::= { uas7624LocalAlarmConfigEntry 14 }

uas7624NoSealingCurrentLocal       OBJECT-TYPE
    SYNTAX  INTEGER {
		disabled(1),
		enabledMajor(2),
		enabledMinor(3)
	    }
    ACCESS  read-write
    STATUS  mandatory
    DESCRIPTION
	    "Disables or enables the alarm on the Major buss or Minor Buss.
		SCinstance:	[L]ine=1-4 	[i]nterface=1-3"
    ::= { uas7624LocalAlarmConfigEntry 15 }

--
-- ********************************************************************
-- ATT Current Performance Table
-- ********************************************************************

uas7624CurrentTable OBJECT-TYPE
    SYNTAX  SEQUENCE OF Uas7624CurrentEntry
    ACCESS  not-accessible
    STATUS  mandatory
    DESCRIPTION
	    "The uas7624 Current table contains various statistics being
	    collected for the current 15 minute interval."
    ::= { uas7624Performance 3 }


uas7624CurrentEntry OBJECT-TYPE
    SYNTAX  Uas7624CurrentEntry
    ACCESS  not-accessible
    STATUS  mandatory
    DESCRIPTION
	    "An entry in the uas7624 Current table."
    INDEX   { uas7624CurrentIndex }
    ::= { uas7624CurrentTable 1 }

Uas7624CurrentEntry ::=
    SEQUENCE {
	uas7624CurrentIndex SCinstance,
	uas7624CurrentStat  OCTET STRING
    }

uas7624CurrentIndex OBJECT-TYPE
    SYNTAX  SCinstance
    ACCESS  read-only
    STATUS  mandatory
    DESCRIPTION
	    "Integer value which uniquely identifies the uas7624 to which this
	    entry is applicable.

		For this table:
		SCinstance:	[L]ine=1-4 	[i]nterface=1-3
				[L]ine=5   	[i]nterface=0"
    ::= { uas7624CurrentEntry 1 }

uas7624CurrentStat  OBJECT-TYPE
    SYNTAX  OCTET STRING (SIZE(10..17))
    ACCESS  read-only
    STATUS  mandatory
    DESCRIPTION
	    "

	    Returns a bitwise snapshot of the interval statistics.
	    for [L]ine=1-4 	[i]nterface=1-3  (SIZE (10))
		 Octet 1 bit 7 - not used
			 bit 6 - future use
			 bit 5 - future use
			 bit 4 - future use
			 bit 3 - future use
			 bit 2 - future use
			 bit 1 - 2^1
			 bit 0 - 2^0  Loop ID  

		 Octet 2 bit 7 - not used
			 bit 6 - future use
			 bit 5 - future use
			 bit 4 - future use
			 bit 3 - future use
			 bit 2 - 2^9   
			 bit 1 - 2^8
			 bit 0 - 2^7
		 Octet 3 bit 7 - not used
			 bit 6 - 2^6
			 bit 5 - 2^5 
			 bit 4 - 2^4 
			 bit 3 - 2^3 
			 bit 2 - 2^2 
			 bit 1 - 2^1
			 bit 0 - 2^0  Errored Seconds



		 Octet 4 bit 7 - not used
			 bit 6 - future use
			 bit 5 - future use
			 bit 4 - future use
			 bit 3 - future use
			 bit 2 - 2^9   
			 bit 1 - 2^8
			 bit 0 - 2^7
		 Octet 5 bit 7 - not used
			 bit 6 - 2^6
			 bit 5 - 2^5 
			 bit 4 - 2^4 
			 bit 3 - 2^3 
			 bit 2 - 2^2 
			 bit 1 - 2^1
			 bit 0 - 2^0  Severely Errored Seconds




		 Octet 6 bit 7 - not used
			 bit 6 - future use
			 bit 5 - future use
			 bit 4 - future use
			 bit 3 - future use
			 bit 2 - 2^9   
			 bit 1 - 2^8
			 bit 0 - 2^7
		 Octet 7 bit 7 - not used
			 bit 6 - 2^6
			 bit 5 - 2^5 
			 bit 4 - 2^4 
			 bit 3 - 2^3 
			 bit 2 - 2^2 
			 bit 1 - 2^1
			 bit 0 - 2^0   Unavailable Seconds


		 Octet 8 bit 7 - not used
			 bit 6 - future use
			 bit 5 - future use 
			 bit 4 - future use 
			 bit 3 - future use 
			 bit 2 - 2^16
			 bit 1 - 2^15
			 bit 0 - 2^14  
		 Octet 9 bit 7 - not used
			 bit 6 - 2^13
			 bit 5 - 2^12
			 bit 4 - 2^11
			 bit 3 - 2^10
			 bit 2 - 2^9 
			 bit 1 - 2^8
			 bit 0 - 2^7   
		Octet 10 bit 7 - not used
			 bit 6 - 2^6
			 bit 5 - 2^5 
			 bit 4 - 2^4 
			 bit 3 - 2^3 
			 bit 2 - 2^2 
			 bit 1 - 2^1
			 bit 0 - 2^0   FEBE (Far End Block Error Count)

	    OR,

	    Returns a bitwise snapshot of the interval statistics.
	    for [L]ine=5   	[i]nterface=0    (SIZE (17))

		 Octet 1 bit 7 - not used
			 bit 6 - future use
			 bit 5 - future use
			 bit 4 - future use
			 bit 3 - future use
			 bit 2 - future use
			 bit 1 - future use
			 bit 0 - 1: New Interval
		 Octet 2 bit 7 - not used
			 bit 6 - future use
			 bit 5 - future use
			 bit 4 - future use
			 bit 3 - future use
			 bit 2 - future use
			 bit 1 - 2^15
			 bit 0 - 2^14
		 Octet 3 bit 7 - not used
			 bit 6 - 2^13
			 bit 5 - 2^12
			 bit 4 - 2^11
			 bit 3 - 2^10
			 bit 2 - 2^9
			 bit 1 - 2^8
			 bit 0 - 2^7
		 Octet 4 bit 7 - not used
			 bit 6 - 2^6 
			 bit 5 - 2^5 
			 bit 4 - 2^4 
			 bit 3 - 2^3 
			 bit 2 - 2^2 
			 bit 1 - 2^1 
			 bit 0 - 2^0    Errored Seconds
		 Octet 5 bit 7 - not used
			 bit 6 - future use
			 bit 5 - future use
			 bit 4 - future use
			 bit 3 - future use
			 bit 2 - future use
			 bit 1 - 2^15
			 bit 0 - 2^14
		 Octet 6 bit 7 - not used
			 bit 6 - 2^13
			 bit 5 - 2^12
			 bit 4 - 2^11
			 bit 3 - 2^10
			 bit 2 - 2^9
			 bit 1 - 2^8
			 bit 0 - 2^7
		 Octet 7 bit 7 - not used
			 bit 6 - 2^6 
			 bit 5 - 2^5 
			 bit 4 - 2^4 
			 bit 3 - 2^3 
			 bit 2 - 2^2 
			 bit 1 - 2^1 
			 bit 0 - 2^0    Severely Errored Seconds
		 Octet 8 bit 7 - not used
			 bit 6 - future use
			 bit 5 - future use
			 bit 4 - future use
			 bit 3 - future use
			 bit 2 - future use
			 bit 1 - 2^15
			 bit 0 - 2^14
		 Octet 9 bit 7 - not used
			 bit 6 - 2^13
			 bit 5 - 2^12
			 bit 4 - 2^11
			 bit 3 - 2^10
			 bit 2 - 2^9
			 bit 1 - 2^8
			 bit 0 - 2^7
		Octet 10 bit 7 - not used
			 bit 6 - 2^6 
			 bit 5 - 2^5 
			 bit 4 - 2^4 
			 bit 3 - 2^3 
			 bit 2 - 2^2 
			 bit 1 - 2^1 
			 bit 0 - 2^0    Bursty Errored Seconds
		Octet 11 bit 7 - not used
			 bit 6 - future use
			 bit 5 - future use
			 bit 4 - future use
			 bit 3 - future use
			 bit 2 - future use
			 bit 1 - 2^15
			 bit 0 - 2^14
		Octet 12 bit 7 - not used
			 bit 6 - 2^13
			 bit 5 - 2^12
			 bit 4 - 2^11
			 bit 3 - 2^10
			 bit 2 - 2^9
			 bit 1 - 2^8
			 bit 0 - 2^7
		Octet 13 bit 7 - not used
			 bit 6 - 2^6 
			 bit 5 - 2^5 
			 bit 4 - 2^4 
			 bit 3 - 2^3 
			 bit 2 - 2^2 
			 bit 1 - 2^1 
			 bit 0 - 2^0    Unavailable Seconds
		Octet 14 bit 7 - not used
			 bit 6 - future use
			 bit 5 - future use
			 bit 4 - future use
			 bit 3 - future use
			 bit 2 - future use
			 bit 1 - future use
			 bit 0 - 2^7 
		Octet 15 bit 7 - not used
			 bit 6 - 2^6 
			 bit 5 - 2^5 
			 bit 4 - 2^4 
			 bit 3 - 2^3 
			 bit 2 - 2^2 
			 bit 1 - 2^1 
			 bit 0 - 2^0    Controlled Slip Seconds
		Octet 16 bit 7 - not used
			 bit 6 - future use
			 bit 5 - future use
			 bit 4 - future use
			 bit 3 - future use
			 bit 2 - future use
			 bit 1 - future use
			 bit 0 - 2^7 
		Octet 17 bit 7 - not used
			 bit 6 - 2^6 
			 bit 5 - 2^5 
			 bit 4 - 2^4 
			 bit 3 - 2^3 
			 bit 2 - 2^2 
			 bit 1 - 2^1 
			 bit 0 - 2^0    Loss of Frame Count"
    ::= {uas7624CurrentEntry 2 }


--
-- ********************************************************************
-- ATT Interval Performance Table
-- ********************************************************************

uas7624IntervalTable OBJECT-TYPE
    SYNTAX  SEQUENCE OF Uas7624IntervalEntry
    ACCESS  not-accessible
    STATUS  mandatory
    DESCRIPTION
	    "The uas7624 Interval table contains various statistics 
	    collected by each Interface over the previous 24 hours of 
	    operation.

		For this table:
		SCinstance: [L]ine=1-4 	[i]nterface=1-3	 [I]nterval=1-15
			    [L]ine=5   	[i]nterface=0	 [I]nterval=1-96"
    ::= { uas7624Performance 4 }


uas7624IntervalEntry OBJECT-TYPE
    SYNTAX  Uas7624IntervalEntry
    ACCESS  not-accessible
    STATUS  mandatory
    DESCRIPTION
	    "An entry in the DS1 Interval table."
    INDEX   { uas7624IntervalIndex, uas7624IntervalNumber }
    ::= { uas7624IntervalTable 1 }

Uas7624IntervalEntry ::=
    SEQUENCE {
	uas7624IntervalIndex	SCinstance,
	uas7624IntervalNumber	INTEGER,
	uas7624IntervalStat	OCTET STRING
    }

uas7624IntervalIndex OBJECT-TYPE
    SYNTAX  SCinstance
    ACCESS  read-only
    STATUS  mandatory
    DESCRIPTION
	    "Integer value which uniquely identifies the uas7624 to which this
	    entry is applicable."
    ::= { uas7624IntervalEntry 1 }

uas7624IntervalNumber OBJECT-TYPE
    SYNTAX  INTEGER (1..96)
    ACCESS  read-only
    STATUS  mandatory
    DESCRIPTION
	    "For the T1 interface: A number between 1 and 96, 
	    where 1 is the most recently completed 15 minute 
	    interval and 96 is the least recently completed 15 
	    minutes interval   (assuming   that  all  96  
	    intervals  are valid).  For the Loop interfaces: 
	    A number between 1 and 16."
    ::= { uas7624IntervalEntry 2 }

uas7624IntervalStat OBJECT-TYPE
    SYNTAX  OCTET STRING (SIZE(11..16))
    ACCESS  read-only
    STATUS  mandatory
    DESCRIPTION
	"
	    Returns a bitwise snapshot of the interval statistics.
	    for [L]ine=1-4 	[i]nterface=1-3  (SIZE (11))




		 Octet 1 bit 7 - not used
			 bit 6 - future use
			 bit 5 - future use
			 bit 4 - future use
			 bit 3 - future use
			 bit 2 - future use
			 bit 1 - 2^1
			 bit 0 - 2^0  Loop ID  

		 Octet 2 bit 7 - not used
			 bit 6 - future use
			 bit 5 - future use
			 bit 4 - future use
			 bit 3 - 2^3        
			 bit 2 - 2^2       
			 bit 1 - 2^1
			 bit 0 - 2^0  Interval 

		 Octet 3 bit 7 - not used
			 bit 6 - future use
			 bit 5 - future use
			 bit 4 - future use
			 bit 3 - future use
			 bit 2 - 2^9   
			 bit 1 - 2^8
			 bit 0 - 2^7
		 Octet 4 bit 7 - not used
			 bit 6 - 2^6
			 bit 5 - 2^5 
			 bit 4 - 2^4 
			 bit 3 - 2^3 
			 bit 2 - 2^2 
			 bit 1 - 2^1
			 bit 0 - 2^0  Errored Seconds



		 Octet 5 bit 7 - not used
			 bit 6 - future use
			 bit 5 - future use
			 bit 4 - future use
			 bit 3 - future use
			 bit 2 - 2^9   
			 bit 1 - 2^8
			 bit 0 - 2^7
		 Octet 6 bit 7 - not used
			 bit 6 - 2^6
			 bit 5 - 2^5 
			 bit 4 - 2^4 
			 bit 3 - 2^3 
			 bit 2 - 2^2 
			 bit 1 - 2^1
			 bit 0 - 2^0  Severely Errored Seconds




		 Octet 7 bit 7 - not used
			 bit 6 - future use
			 bit 5 - future use
			 bit 4 - future use
			 bit 3 - future use
			 bit 2 - 2^9   
			 bit 1 - 2^8
			 bit 0 - 2^7
		 Octet 8 bit 7 - not used
			 bit 6 - 2^6
			 bit 5 - 2^5 
			 bit 4 - 2^4 
			 bit 3 - 2^3 
			 bit 2 - 2^2 
			 bit 1 - 2^1
			 bit 0 - 2^0   Unavailable Seconds

		 Octet 9 bit 7 - not used
			 bit 6 - future use
			 bit 5 - future use 
			 bit 4 - future use 
			 bit 3 - future use 
			 bit 2 - 2^16
			 bit 1 - 2^15
			 bit 0 - 2^14  
		Octet 10 bit 7 - not used
			 bit 6 - 2^13
			 bit 5 - 2^12
			 bit 4 - 2^11
			 bit 3 - 2^10
			 bit 2 - 2^9 
			 bit 1 - 2^8
			 bit 0 - 2^7   
		Octet 11 bit 7 - not used
			 bit 6 - 2^6
			 bit 5 - 2^5 
			 bit 4 - 2^4 
			 bit 3 - 2^3 
			 bit 2 - 2^2 
			 bit 1 - 2^1
			 bit 0 - 2^0   	FEBE (Far End Block Error Count)



	    OR,

	    Returns a bitwise snapshot of the interval statistics.
	    for [L]ine=5   	[i]nterface=0    (SIZE (16))


		 Octet 1 bit 7 - not used
			 bit 6 - future use
			 bit 5 - future use
			 bit 4 - future use
			 bit 3 - future use
			 bit 2 - future use
			 bit 1 - 2^15
			 bit 0 - 2^14
		 Octet 2 bit 7 - not used
			 bit 6 - 2^13
			 bit 5 - 2^12
			 bit 4 - 2^11
			 bit 3 - 2^10
			 bit 2 - 2^9
			 bit 1 - 2^8
			 bit 0 - 2^7
		 Octet 3 bit 7 - not used
			 bit 6 - 2^6 
			 bit 5 - 2^5 
			 bit 4 - 2^4 
			 bit 3 - 2^3 
			 bit 2 - 2^2 
			 bit 1 - 2^1 
			 bit 0 - 2^0    Errored Seconds
		 Octet 4 bit 7 - not used
			 bit 6 - future use
			 bit 5 - future use
			 bit 4 - future use
			 bit 3 - future use
			 bit 2 - future use
			 bit 1 - 2^15
			 bit 0 - 2^14
		 Octet 5 bit 7 - not used
			 bit 6 - 2^13
			 bit 5 - 2^12
			 bit 4 - 2^11
			 bit 3 - 2^10
			 bit 2 - 2^9
			 bit 1 - 2^8
			 bit 0 - 2^7
		 Octet 6 bit 7 - not used
			 bit 6 - 2^6 
			 bit 5 - 2^5 
			 bit 4 - 2^4 
			 bit 3 - 2^3 
			 bit 2 - 2^2 
			 bit 1 - 2^1 
			 bit 0 - 2^0    Severely Errored Seconds
		 Octet 7 bit 7 - not used
			 bit 6 - future use
			 bit 5 - future use
			 bit 4 - future use
			 bit 3 - future use
			 bit 2 - future use
			 bit 1 - 2^15
			 bit 0 - 2^14
		 Octet 8 bit 7 - not used
			 bit 6 - 2^13
			 bit 5 - 2^12
			 bit 4 - 2^11
			 bit 3 - 2^10
			 bit 2 - 2^9
			 bit 1 - 2^8
			 bit 0 - 2^7
		 Octet 9 bit 7 - not used
			 bit 6 - 2^6 
			 bit 5 - 2^5 
			 bit 4 - 2^4 
			 bit 3 - 2^3 
			 bit 2 - 2^2 
			 bit 1 - 2^1 
			 bit 0 - 2^0    Bursty Errored Seconds
		Octet 10 bit 7 - not used
			 bit 6 - future use
			 bit 5 - future use
			 bit 4 - future use
			 bit 3 - future use
			 bit 2 - future use
			 bit 1 - 2^15
			 bit 0 - 2^14
		Octet 11 bit 7 - not used
			 bit 6 - 2^13
			 bit 5 - 2^12
			 bit 4 - 2^11
			 bit 3 - 2^10
			 bit 2 - 2^9
			 bit 1 - 2^8
			 bit 0 - 2^7
		Octet 12 bit 7 - not used
			 bit 6 - 2^6 
			 bit 5 - 2^5 
			 bit 4 - 2^4 
			 bit 3 - 2^3 
			 bit 2 - 2^2 
			 bit 1 - 2^1 
			 bit 0 - 2^0    Unavailable Seconds
		Octet 13 bit 7 - not used
			 bit 6 - future use
			 bit 5 - future use
			 bit 4 - future use
			 bit 3 - future use
			 bit 2 - future use
			 bit 1 - future use
			 bit 0 - 2^7 
		Octet 14 bit 7 - not used
			 bit 6 - 2^6 
			 bit 5 - 2^5 
			 bit 4 - 2^4 
			 bit 3 - 2^3 
			 bit 2 - 2^2 
			 bit 1 - 2^1 
			 bit 0 - 2^0    Controlled Slip Seconds
		Octet 15 bit 7 - not used
			 bit 6 - future use
			 bit 5 - future use
			 bit 4 - future use
			 bit 3 - future use
			 bit 2 - future use
			 bit 1 - future use
			 bit 0 - 2^7 
		Octet 16 bit 7 - not used
			 bit 6 - 2^6 
			 bit 5 - 2^5 
			 bit 4 - 2^4 
			 bit 3 - 2^3 
			 bit 2 - 2^2 
			 bit 1 - 2^1 
			 bit 0 - 2^0    Loss of Frame Count"

    ::= {uas7624IntervalEntry 3 }

--
-- ********************************************************************
-- ATT Total Performance Table
-- ********************************************************************

uas7624TotalTable OBJECT-TYPE
    SYNTAX  SEQUENCE OF Uas7624TotalEntry
    ACCESS  not-accessible
    STATUS  mandatory
    DESCRIPTION
	    "The DS1 Total table.  24 hour interval."
    ::= { uas7624Performance 5 }

uas7624TotalEntry OBJECT-TYPE
    SYNTAX  Uas7624TotalEntry
    ACCESS  not-accessible
    STATUS  mandatory
    DESCRIPTION
	    "An entry in the DS1 Total table."
    INDEX   { uas7624TotalIndex }
    ::= { uas7624TotalTable 1 }

Uas7624TotalEntry ::=
    SEQUENCE {
	uas7624TotalIndex	SCinstance,
	uas7624TotalStat	OCTET STRING
    }

uas7624TotalIndex OBJECT-TYPE
    SYNTAX  SCinstance
    ACCESS  read-only
    STATUS  mandatory
    DESCRIPTION
	    "Integer value which uniquely identifies the uas7624 to which this
	    entry is applicable.

		For this table:
		SCinstance:	[L]ine=1-4 	[i]nterface=1-3 
				[L]ine=5   	[i]nterface=0"
    ::= { uas7624TotalEntry 1 }

uas7624TotalStat OBJECT-TYPE
    SYNTAX  OCTET STRING (SIZE(14..17))
    ACCESS  read-only
    STATUS  mandatory
    DESCRIPTION
	    "

	    Returns a bitwise snapshot of the interval statistics.
	    for [L]ine=1-4 	[i]nterface=1-3  (SIZE (14))

		 Octet 1 bit 7 - not used
			 bit 6 - future use
			 bit 5 - future use
			 bit 4 - future use
			 bit 3 - future use
			 bit 2 - future use
			 bit 1 - 2^1
			 bit 0 - 2^0  Loop ID  

		 Octet 2 bit 7 - not used
			 bit 6 - future use
			 bit 5 - future use
			 bit 4 - future use
			 bit 3 - future use
			 bit 2 - >65535
			 bit 1 - 2^15
			 bit 0 - 2^14
		 Octet 3 bit 7 - not used
			 bit 6 - 2^13
			 bit 5 - 2^12
			 bit 4 - 2^11
			 bit 3 - 2^10
			 bit 2 - 2^9
			 bit 1 - 2^8
			 bit 0 - 2^7
		 Octet 4 bit 7 - not used
			 bit 6 - 2^6 
			 bit 5 - 2^5 
			 bit 4 - 2^4 
			 bit 3 - 2^3 
			 bit 2 - 2^2 
			 bit 1 - 2^1 
			 bit 0 - 2^0    Errored  Seconds


		 Octet 5 bit 7 - not used
			 bit 6 - future use
			 bit 5 - future use
			 bit 4 - future use
			 bit 3 - future use
			 bit 2 - >65535
			 bit 1 - 2^15
			 bit 0 - 2^14
		 Octet 6 bit 7 - not used
			 bit 6 - 2^13
			 bit 5 - 2^12
			 bit 4 - 2^11
			 bit 3 - 2^10
			 bit 2 - 2^9
			 bit 1 - 2^8
			 bit 0 - 2^7
		 Octet 7 bit 7 - not used
			 bit 6 - 2^6 
			 bit 5 - 2^5 
			 bit 4 - 2^4 
			 bit 3 - 2^3 
			 bit 2 - 2^2 
			 bit 1 - 2^1 
			 bit 0 - 2^0    Severely Errored Seconds


		 Octet 8 bit 7 - not used
			 bit 6 - future use
			 bit 5 - future use
			 bit 4 - future use
			 bit 3 - future use
			 bit 2 - >65535
			 bit 1 - 2^15
			 bit 0 - 2^14
		 Octet 9 bit 7 - not used
			 bit 6 - 2^13
			 bit 5 - 2^12
			 bit 4 - 2^11
			 bit 3 - 2^10
			 bit 2 - 2^9
			 bit 1 - 2^8
			 bit 0 - 2^7
        	Octet 10 bit 7 - not used
			 bit 6 - 2^6 
			 bit 5 - 2^5 
			 bit 4 - 2^4 
			 bit 3 - 2^3 
			 bit 2 - 2^2 
			 bit 1 - 2^1 
			 bit 0 - 2^0    Unavailable Seconds

		Octet 11 bit 7 - not used
			 bit 6 - future use
			 bit 5 - future use
			 bit 4 - future use
			 bit 3 - future use
			 bit 2 - 2^23
			 bit 1 - 2^22
			 bit 0 - 2^21  
		Octet 12 bit 7 - not used
			 bit 6 - 2^20
			 bit 5 - 2^19
			 bit 4 - 2^18
			 bit 3 - 2^17
			 bit 2 - 2^16
			 bit 1 - 2^15
			 bit 0 - 2^14   
		Octet 13 bit 7 - not used
			 bit 6 - 2^13
			 bit 5 - 2^12
			 bit 4 - 2^11
			 bit 3 - 2^10
			 bit 2 - 2^9 
			 bit 1 - 2^8
			 bit 0 - 2^7   
		Octet 14 bit 7 - not used
			 bit 6 - 2^6
			 bit 5 - 2^5 
			 bit 4 - 2^4 
			 bit 3 - 2^3 
			 bit 2 - 2^2 
			 bit 1 - 2^1
			 bit 0 - 2^0    FEBE (Far End Block Error Count)


	    OR,

	    Returns a bitwise snapshot of the interval statistics.
	    for [L]ine=5   	[i]nterface=0    (SIZE (17))



		 Octet 1 bit 7 - not used
			 bit 6 - future use
			 bit 5 - future use
			 bit 4 - future use
			 bit 3 - future use
			 bit 2 - future use
			 bit 1 - future use
			 bit 0 - 1: New Interval
		 Octet 2 bit 7 - not used
			 bit 6 - future use
			 bit 5 - future use
			 bit 4 - future use
			 bit 3 - future use
			 bit 2 - future use
			 bit 1 - 2^15
			 bit 0 - 2^14
		 Octet 3 bit 7 - not used
			 bit 6 - 2^13
			 bit 5 - 2^12
			 bit 4 - 2^11
			 bit 3 - 2^10
			 bit 2 - 2^9
			 bit 1 - 2^8
			 bit 0 - 2^7
		 Octet 4 bit 7 - not used
			 bit 6 - 2^6 
			 bit 5 - 2^5 
			 bit 4 - 2^4 
			 bit 3 - 2^3 
			 bit 2 - 2^2 
			 bit 1 - 2^1 
			 bit 0 - 2^0    Errored Seconds
		 Octet 5 bit 7 - not used
			 bit 6 - future use
			 bit 5 - future use
			 bit 4 - future use
			 bit 3 - future use
			 bit 2 - future use
			 bit 1 - 2^15
			 bit 0 - 2^14
		 Octet 6 bit 7 - not used
			 bit 6 - 2^13
			 bit 5 - 2^12
			 bit 4 - 2^11
			 bit 3 - 2^10
			 bit 2 - 2^9
			 bit 1 - 2^8
			 bit 0 - 2^7
		 Octet 7 bit 7 - not used
			 bit 6 - 2^6 
			 bit 5 - 2^5 
			 bit 4 - 2^4 
			 bit 3 - 2^3 
			 bit 2 - 2^2 
			 bit 1 - 2^1 
			 bit 0 - 2^0    Severely Errored Seconds
		 Octet 8 bit 7 - not used
			 bit 6 - future use
			 bit 5 - future use
			 bit 4 - future use
			 bit 3 - future use
			 bit 2 - future use
			 bit 1 - 2^15
			 bit 0 - 2^14
		 Octet 9 bit 7 - not used
			 bit 6 - 2^13
			 bit 5 - 2^12
			 bit 4 - 2^11
			 bit 3 - 2^10
			 bit 2 - 2^9
			 bit 1 - 2^8
			 bit 0 - 2^7
		Octet 10 bit 7 - not used
			 bit 6 - 2^6 
			 bit 5 - 2^5 
			 bit 4 - 2^4 
			 bit 3 - 2^3 
			 bit 2 - 2^2 
			 bit 1 - 2^1 
			 bit 0 - 2^0    Bursty Errored Seconds
		Octet 11 bit 7 - not used
			 bit 6 - future use
			 bit 5 - future use
			 bit 4 - future use
			 bit 3 - future use
			 bit 2 - future use
			 bit 1 - 2^15
			 bit 0 - 2^14
		Octet 12 bit 7 - not used
			 bit 6 - 2^13
			 bit 5 - 2^12
			 bit 4 - 2^11
			 bit 3 - 2^10
			 bit 2 - 2^9
			 bit 1 - 2^8
			 bit 0 - 2^7
		Octet 13 bit 7 - not used
			 bit 6 - 2^6 
			 bit 5 - 2^5 
			 bit 4 - 2^4 
			 bit 3 - 2^3 
			 bit 2 - 2^2 
			 bit 1 - 2^1 
			 bit 0 - 2^0    Unavailable Seconds
		Octet 14 bit 7 - not used
			 bit 6 - future use
			 bit 5 - future use
			 bit 4 - future use
			 bit 3 - future use
			 bit 2 - future use
			 bit 1 - future use
			 bit 0 - 2^7 
		Octet 15 bit 7 - not used
			 bit 6 - 2^6 
			 bit 5 - 2^5 
			 bit 4 - 2^4 
			 bit 3 - 2^3 
			 bit 2 - 2^2 
			 bit 1 - 2^1 
			 bit 0 - 2^0    Controlled Slip Seconds
		Octet 16 bit 7 - not used
			 bit 6 - future use
			 bit 5 - future use
			 bit 4 - future use
			 bit 3 - future use
			 bit 2 - future use
			 bit 1 - future use
			 bit 0 - 2^7 
		Octet 17 bit 7 - not used
			 bit 6 - 2^6 
			 bit 5 - 2^5 
			 bit 4 - 2^4 
			 bit 3 - 2^3 
			 bit 2 - 2^2 
			 bit 1 - 2^1 
			 bit 0 - 2^0    Loss of Frame Count"
    ::= {uas7624TotalEntry 2 }

--
-- ********************************************************************
--  GDC 7624 Recent 24 Hour Performance Table
-- ********************************************************************

uas7624Recent24HrTable OBJECT-TYPE
    SYNTAX  SEQUENCE OF Uas7624Recent24HrEntry
    ACCESS  not-accessible
    STATUS  mandatory
    DESCRIPTION
	    "The Recent24Hr table.  4 hour interval"
 ::= { uas7624Performance 6 }

uas7624Recent24HrEntry OBJECT-TYPE
    SYNTAX  Uas7624Recent24HrEntry
    ACCESS  not-accessible
    STATUS  mandatory
    DESCRIPTION
	    "An entry in the Recent24Hr table."
    INDEX   { uas7624Recent24HrIndex }
    ::= { uas7624Recent24HrTable 1 }

Uas7624Recent24HrEntry ::=
    SEQUENCE {
	uas7624Recent24HrIndex	SCinstance,
	uas7624Recent24HrStat	OCTET STRING
    }

uas7624Recent24HrIndex OBJECT-TYPE
    SYNTAX  SCinstance
    ACCESS  read-only
    STATUS  mandatory
    DESCRIPTION
	    "The index value which uniquely identifies the interface to
	    which this entry is applicable.  This has the form of a

		For this table:
		SCinstance:	[L]ine=1-4 	[i]nterface=1-3"

    ::= { uas7624Recent24HrEntry 1 }

uas7624Recent24HrStat OBJECT-TYPE
    SYNTAX  OCTET STRING (SIZE (14))
    ACCESS  read-only
    STATUS  mandatory
    DESCRIPTION
		"Returns a bitwise snapshot of the interval statistics.
		 Octet 1 bit 7 - not used
			 bit 6 - future use
			 bit 5 - future use
			 bit 4 - future use
			 bit 3 - future use
			 bit 2 - future use
			 bit 1 - 2^1
			 bit 0 - 2^0  Loop ID  

		 Octet 2 bit 7 - not used
			 bit 6 - future use
			 bit 5 - future use
			 bit 4 - future use
			 bit 3 - future use
			 bit 2 - >65535
			 bit 1 - 2^15
			 bit 0 - 2^14
		 Octet 3 bit 7 - not used
			 bit 6 - 2^13
			 bit 5 - 2^12
			 bit 4 - 2^11
			 bit 3 - 2^10
			 bit 2 - 2^9
			 bit 1 - 2^8
			 bit 0 - 2^7
		 Octet 4 bit 7 - not used
			 bit 6 - 2^6 
			 bit 5 - 2^5 
			 bit 4 - 2^4 
			 bit 3 - 2^3 
			 bit 2 - 2^2 
			 bit 1 - 2^1 
			 bit 0 - 2^0    Errored  Seconds


		 Octet 5 bit 7 - not used
			 bit 6 - future use
			 bit 5 - future use
			 bit 4 - future use
			 bit 3 - future use
			 bit 2 - >65535
			 bit 1 - 2^15
			 bit 0 - 2^14
		 Octet 6 bit 7 - not used
			 bit 6 - 2^13
			 bit 5 - 2^12
			 bit 4 - 2^11
			 bit 3 - 2^10
			 bit 2 - 2^9
			 bit 1 - 2^8
			 bit 0 - 2^7
		 Octet 7 bit 7 - not used
			 bit 6 - 2^6 
			 bit 5 - 2^5 
			 bit 4 - 2^4 
			 bit 3 - 2^3 
			 bit 2 - 2^2 
			 bit 1 - 2^1 
			 bit 0 - 2^0    Severely Errored Seconds


		 Octet 8 bit 7 - not used
			 bit 6 - future use
			 bit 5 - future use
			 bit 4 - future use
			 bit 3 - future use
			 bit 2 - >65535
			 bit 1 - 2^15
			 bit 0 - 2^14
		 Octet 9 bit 7 - not used
			 bit 6 - 2^13
			 bit 5 - 2^12
			 bit 4 - 2^11
			 bit 3 - 2^10
			 bit 2 - 2^9
			 bit 1 - 2^8
			 bit 0 - 2^7
        	Octet 10 bit 7 - not used
			 bit 6 - 2^6 
			 bit 5 - 2^5 
			 bit 4 - 2^4 
			 bit 3 - 2^3 
			 bit 2 - 2^2 
			 bit 1 - 2^1 
			 bit 0 - 2^0    Unavailable Seconds

		Octet 11 bit 7 - not used
			 bit 6 - future use
			 bit 5 - future use
			 bit 4 - future use
			 bit 3 - future use
			 bit 2 - 2^23
			 bit 1 - 2^22
			 bit 0 - 2^21  
		Octet 12 bit 7 - not used
			 bit 6 - 2^20
			 bit 5 - 2^19
			 bit 4 - 2^18
			 bit 3 - 2^17
			 bit 2 - 2^16
			 bit 1 - 2^15
			 bit 0 - 2^14   
		Octet 13 bit 7 - not used
			 bit 6 - 2^13
			 bit 5 - 2^12
			 bit 4 - 2^11
			 bit 3 - 2^10
			 bit 2 - 2^9 
			 bit 1 - 2^8
			 bit 0 - 2^7   
		Octet 14 bit 7 - not used
			 bit 6 - 2^6
			 bit 5 - 2^5 
			 bit 4 - 2^4 
			 bit 3 - 2^3 
			 bit 2 - 2^2 
			 bit 1 - 2^1
			 bit 0 - 2^0    FEBE (Far End Block Error Count)"    
    ::= {uas7624Recent24HrEntry 2 }

-- ****************************************************************************
--                       mib definitions end
-- ****************************************************************************
END
