OMNI-gx2PSDC-MIB DEFINITIONS ::= BEGIN

    IMPORTS
	IpAddress, TimeTicks, Counter            
					      FROM RFC1155-SMI
	OBJECT-TYPE
					      FROM RFC-1212
	sysUpTime, DisplayString
					      FROM RFC1213-MIB
	TRAP-TYPE
					      FROM RFC-1215
	gi, motproxies
					      FROM NLS-BBNIDENT-MIB
	gx2Psdc
					      FROM GX2HFC-MIB

	trapIdentifier,trapNetworkElemModelNumber,
	trapNetworkElemSerialNum, trapPerceivedSeverity,
	trapNetworkElemOperState, trapNetworkElemAlarmStatus,
	trapNetworkElemAdminState, trapNetworkElemAvailStatus,
	trapText, trapNETrapLastTrapTimeStamp, trapChangedObjectId,
	trapChangedValueInteger, trapChangedValueDisplayString
					      FROM NLSBBN-TRAPS-MIB;



	       -- This MIB module uses the extended OBJECT-TYPE macro as
	       -- defined in RFC1212 and the TRAP-TYPE macro as defined
	       -- in RFC 1215.

		   --REVISION	"5" Aug 11, 2008
		   --DESCRIPTION
		   --			Added revision and description comment section


		--    OMNISTAR PSE (Power Supply)  MIB MODULE

	-- This MIB module defines information for management of HFC networks
		--
		-- The MIB module assumes that all generic (static) network element
		-- information is defined in a different module such as the HFC module
		-- The MIB consists of two groups:
		-- the device type descriptor subgroup and
		-- gx2Psdc Network Elements subgroup.
		-- The device type descriptor subgroup is used to define
		-- parameters specific to gx2Psdc device type.
		-- These parameters are common across all network elements
		-- from gx2Psdc device type.
		--
		-- The gx2Psdc Network Elements subgroup is
		-- a list of gx2Psdc type elements in the
		-- current network topology with nominal
		-- and current parameter values for the
		-- individual network elements; the individual
		-- network elements are identified by
		-- index from hfcCommonTable.
		-- That implies what hfcCommonTableIndex and
		-- gx2PsdcTableIndex are equal for each individual
		-- network element.
		-- This table is an extension of the hfcCommonTable
		-- for all elements of gx2Psdc type.
		--
		-- Both groups are mandatory for management of gx2Psdc devices.

-- ****************************************************************************
		--
		-- All floating point numbers will be represented by an IEEE 32 Bit
		-- number. Conversion of this number must be done on the user
        -- interface to view the actual floating point number.
		--

		Float ::= Counter  -- UNSIGNED (32 BITS)

-- ****************************************************************************

		-- gx2Psdc Device Descriptor subgroup.

		-- The device type descriptor subgroup is used to define
		-- parameters specific to gx2Psdc device type.
		-- These parameters are common across all network elements
		-- from gx2Psdc device type.


		gx2PsdcDescriptor OBJECT IDENTIFIER ::= {gx2Psdc 1}



--*****************************************************************************
-- // Section: Table definitions

		--              gx2Psdc Table

		-- Contains a list of all gx2Psdc type devices in
		-- the network. Each device is characterized with
		-- current network topology information, with nominal
		-- and current parameter values for the
		-- individual network elements;
		--
		-- The individual network elements indentified by
		-- index from hfcCommonTable.
		-- That implies what hfcCommonTableIndex and
		-- gx2PsdcTableIndex are equal for each individual
		-- nettwork element.
		-- This table should be used as an extension of the hfcCommonTable
		-- for all elements of gx2Psdc type.

-- // Section: Table definitions - Analog

	       gx2PsdcAnalogTable                    OBJECT-TYPE
			 SYNTAX             SEQUENCE OF Gx2PsdcAnalogEntry
			 ACCESS             not-accessible
			 STATUS             mandatory
			 DESCRIPTION
			 "This table contains gx2Psdc specific parameters with
			  nominal and current values."
			 ::= { gx2Psdc 2 }


	       gx2PsdcAnalogEntry               OBJECT-TYPE
			 SYNTAX             Gx2PsdcAnalogEntry
			 ACCESS             not-accessible
			 STATUS             mandatory
			 DESCRIPTION
			 "This list contains digital product class and the
			  associated RF channel parameters and descriptions."
			 INDEX { gx2PsdcAnalogTableIndex }
			 ::= { gx2PsdcAnalogTable  1}

--*****************************************************************************
-- // Section: Table definitions - Status

	       gx2PsdcStatusTable                    OBJECT-TYPE
			 SYNTAX             SEQUENCE OF Gx2PsdcStatusEntry
			 ACCESS             not-accessible
			 STATUS             mandatory
			 DESCRIPTION
			 "This table contains gx2Psdc specific parameters with
			  nominal and current values."
			 ::= { gx2Psdc 3 }

	       gx2PsdcStatusEntry               OBJECT-TYPE
			 SYNTAX             Gx2PsdcStatusEntry
			 ACCESS             not-accessible
			 STATUS             mandatory
			 DESCRIPTION
			 "This list contains digital product class and the
			  associated RF channel parameters and descriptions."
			 INDEX { gx2PsdcStatusTableIndex }
			 ::= { gx2PsdcStatusTable  2}

--*****************************************************************************
-- // Section: Table definitions - Factory

	       gx2PsdcFactoryTable                    OBJECT-TYPE
			 SYNTAX             SEQUENCE OF Gx2PsdcFactoryEntry
			 ACCESS             not-accessible
			 STATUS             mandatory
			 DESCRIPTION
			 "This table contains gx2Psdc specific parameters with
			  nominal and current values."
			 ::= { gx2Psdc 4 }

	       gx2PsdcFactoryEntry               OBJECT-TYPE
			 SYNTAX             Gx2PsdcFactoryEntry
			 ACCESS             not-accessible
			 STATUS             mandatory
			 DESCRIPTION
			 "This list contains Factory parameters and descriptions."
			 INDEX { gx2PsdcFactoryTableIndex }
			 ::= { gx2PsdcFactoryTable  3}

--*****************************************************************************

	       gx2PsdcHoldTimeTable                    OBJECT-TYPE
			 SYNTAX             SEQUENCE OF Gx2PsdcHoldTimeEntry
			 ACCESS             not-accessible
			 STATUS             mandatory
			 DESCRIPTION
			 "This table contains gx2Psdc specific parameters with
			  nominal and current values."
			 ::= { gx2Psdc 5 }

	       gx2PsdcHoldTimeEntry               OBJECT-TYPE
			 SYNTAX             Gx2PsdcHoldTimeEntry
			 ACCESS             not-accessible
			 STATUS             mandatory
			 DESCRIPTION
			 "This list contains digital product class and the
			  associated RF channel parameters and descriptions."
			 INDEX { rxgx2PsdcHoldTimeTableIndex, rxgx2PsdcHoldTimeSpecIndex }
			 ::= { gx2PsdcHoldTimeTable  4}

--***********************************************************************
-- // Section: Table definitions - Digital
	       gx2PsdcDigitalTable                    OBJECT-TYPE
			 SYNTAX             SEQUENCE OF Gx2PsdcDigitalEntry
			 ACCESS             not-accessible
			 STATUS             mandatory
			 DESCRIPTION
			 "This table contains gx2Psdc specific parameters with
			  nominal and current values."
			 ::= { gx2Psdc 6 }

	       gx2PsdcDigitalEntry               OBJECT-TYPE
			 SYNTAX             Gx2PsdcDigitalEntry
			 ACCESS             not-accessible
			 STATUS             mandatory
			 DESCRIPTION
			 "This list contains digital parameters and descriptions."
			 INDEX { gx2PsdcDigitalTableIndex }
			 ::= { gx2PsdcDigitalTable  5}

--***********************************************************************
-- // Section: Analog parameters

	      Gx2PsdcAnalogEntry    ::= SEQUENCE
	       {
		gx2PsdcAnalogTableIndex         INTEGER,

		--           Analog Parameters
-- // Analog parameter : Fan Current
		pslabelFanCurrent 	DisplayString (SIZE (0..80)),
		psuomFanCurrent		DisplayString (SIZE (0..80)),
		psmajorHighFanCurrent	Float,
		psmajorLowFanCurrent	Float,
		psminorHighFanCurrent	Float,
		psminorLowFanCurrent	Float,
		pscurrentValueFanCurrent	Float,
		psstateFlagFanCurrent	INTEGER,
		psminValueFanCurrent	Float,
		psmaxValueFanCurrent 	Float,
		psalarmStateFanCurrent	INTEGER,

-- // Analog parameter : +12 Volts
		pslabel12Volt 		DisplayString (SIZE (0..80)),
		psuom12Volt			DisplayString (SIZE (0..80)),
		psmajorHigh12Volt		Float,
		psmajorLow12Volt		Float,
		psminorHigh12Volt		Float,
		psminorLow12Volt		Float,
		pscurrentValue12Volt	Float,
		psstateFlag12Volt		INTEGER,
		psminValue12Volt		Float,
		psmaxValue12Volt 		Float,
		psalarmState12Volt	INTEGER,

-- // Analog parameter : +5 Volts
		pslabel5Volt 		DisplayString (SIZE (0..80)),
		psuom5Volt			DisplayString (SIZE (0..80)),
		psmajorHigh5Volt		Float,
		psmajorLow5Volt		Float,
		psminorHigh5Volt		Float,
		psminorLow5Volt		Float,
		pscurrentValue5Volt	Float,
		psstateFlag5Volt		INTEGER,
		psminValue5Volt		Float,
		psmaxValue5Volt 		Float,
		psalarmState5Volt		INTEGER,

-- // Analog parameter : +3.7 Volts
		pslabel3Volt		DisplayString (SIZE (0..80)),
		psuom3Volt			DisplayString (SIZE (0..80)),
		psmajorHigh3Volt		Float,
		psmajorLow3Volt		Float,
		psminorHigh3Volt		Float,
		psminorLow3Volt		Float,
		pscurrentValue3Volt	Float,
		psstateFlag3Volt		INTEGER,
		psminValue3Volt		Float,
		psmaxValue3Volt 		Float,
		psalarmState3Volt		INTEGER,

-- // Analog parameter : Ambient Temperature
		pslabelAmbientTemp		DisplayString (SIZE (0..80)),
		psuomAmbientTemp			DisplayString (SIZE (0..80)),
		psmajorHighAmbientTemp		Float,
		psmajorLowAmbientTemp		Float,
		psminorHighAmbientTemp		Float,
		psminorLowAmbientTemp		Float,
		pscurrentValueAmbientTemp	Float,
		psstateFlagAmbientTemp		INTEGER,
		psminValueAmbientTemp		Float,
		psmaxValueAmbientTemp 		Float,
		psalarmStateAmbientTemp		INTEGER,

-- // Analog parameter : Main Temp (heat sink)
		pslabelMainTemp			DisplayString (SIZE (0..80)),
		psuomMainTemp			DisplayString (SIZE (0..80)),
		psmajorHighMainTemp		Float,
		psmajorLowMainTemp		Float,
		psminorHighMainTemp		Float,
		psminorLowMainTemp		Float,
		pscurrentValueMainTemp		Float,
		psstateFlagMainTemp		INTEGER,
		psminValueMainTemp		Float,
		psmaxValueMainTemp 		Float,
		psalarmStateMainTemp		INTEGER,

-- // Analog parameter : +12 Volt anode
		pslabel12AnodeVolt		DisplayString (SIZE (0..80)),
		psuom12AnodeVolt			DisplayString (SIZE (0..80)),
		psmajorHigh12AnodeVolt		Float,
		psmajorLow12AnodeVolt		Float,
		psminorHigh12AnodeVolt		Float,
		psminorLow12AnodeVolt		Float,
		pscurrentValue12AnodeVolt	Float,
		psstateFlag12AnodeVolt		INTEGER,
		psminValue12AnodeVolt		Float,
		psmaxValue12AnodeVolt		Float,
		psalarmState12AnodeVolt		INTEGER,

-- // Analog parameter : +5 Volt anode
		pslabel5AnodeVolt			DisplayString (SIZE (0..80)),
		psuom5AnodeVolt			DisplayString (SIZE (0..80)),
		psmajorHigh5AnodeVolt		Float,
		psmajorLow5AnodeVolt		Float,
		psminorHigh5AnodeVolt		Float,
		psminorLow5AnodeVolt		Float,
		pscurrentValue5AnodeVolt	Float,
		psstateFlag5AnodeVolt		INTEGER,
		psminValue5AnodeVolt		Float,
		psmaxValue5AnodeVolt		Float,
		psalarmState5AnodeVolt		INTEGER,

-- // Analog parameter : +3.7 Volt anode
		pslabel3AnodeVolt			DisplayString (SIZE (0..80)),
		psuom3AnodeVolt			DisplayString (SIZE (0..80)),
		psmajorHigh3AnodeVolt		Float,
		psmajorLow3AnodeVolt		Float,
		psminorHigh3AnodeVolt		Float,
		psminorLow3AnodeVolt		Float,
		pscurrentValue3AnodeVolt	Float,
		psstateFlag3AnodeVolt		INTEGER,
		psminValue3AnodeVolt		Float,
		psmaxValue3AnodeVolt		Float,
		psalarmState3AnodeVolt		INTEGER
		}

-- ****************  Digital Parameters ***********************
      Gx2PsdcDigitalEntry    ::= SEQUENCE  
      {
		gx2PsdcDigitalTableIndex    INTEGER,
		psdclabelNVfanAlrm			DisplayString (SIZE (0..80)),
		psdcenumNVfanAlrm			DisplayString (SIZE (0..80)),
		psdcvalueNVfanAlrm			INTEGER,
		psdcstateflagNVfanAlrm  	INTEGER
	  }

		-- ****************  Status Parameters ************************************
-- // Section: Status parameters

	    Gx2PsdcStatusEntry    ::= SEQUENCE
	    {

		gx2PsdcStatusTableIndex         INTEGER,

-- // Status parameter : Boot
		pslabelBoot				DisplayString (SIZE (0..80)),
		psvalueBoot				INTEGER,
		psstateflagBoot			INTEGER,

-- // Status parameter : Flash
		pslabelFlash			DisplayString (SIZE (0..80)),
		psvalueFlash			INTEGER,
		psstateflagFlash			INTEGER,

-- // Status parameter : Factory Data CRC
		pslabelFactoryDataCRC 		DisplayString (SIZE (0..80)),
		psvalueFactoryDataCRC		INTEGER,
		psstateflagFactoryDataCRC	INTEGER,

-- // Status parameter : Alarm Data CRC
		pslabelPsdcDataCRC 		DisplayString (SIZE (0..80)),
		psvaluePsdcDataCRC 		INTEGER,
		psstateflagPsdcDataCRC		INTEGER,

-- // Status parameter : Hardware status
		pslabelPsdcHwStatus 		DisplayString (SIZE (0..80)),
		psvaluePsdcHwStatus 		INTEGER,
		psstateflagPsdcHwStatus		INTEGER

		}


		-- ****************  Factory Parameters *************************************
-- // Section: Factory parameters
	    Gx2PsdcFactoryEntry    ::= SEQUENCE
	    {
		gx2PsdcFactoryTableIndex         INTEGER,
		psbootControlByteValue  	INTEGER,
		psbootStatusByteValue   	INTEGER,
		psbank1CRCValue    			INTEGER,
		psbank2CRCValue    			INTEGER,
		psprgEEPROMByteValue    	INTEGER,
		psfactoryCRCValue    		INTEGER,
		pscalculateCRCValue    		INTEGER,
		pshourMeterValue    		INTEGER,
		psflashPrgCntAValue    		INTEGER,
		psflashPrgCntBValue    		INTEGER,
		psflashBankARevValue    	DisplayString (SIZE (0..80)),
		psflashBankBRevValue    	DisplayString (SIZE (0..80))

		}

		-- ****************  Hold Time Parameters *************************************
	    Gx2PsdcHoldTimeEntry    ::= SEQUENCE  
	    {
		rxgx2PsdcHoldTimeTableIndex        INTEGER,
		rxgx2PsdcHoldTimeSpecIndex         INTEGER,   
		rxgx2PsdcHoldTimeData  			 INTEGER
		}


-- // Section: Analog parameter detail
        -- ************** Analog Parameters ****************************
		gx2PsdcAnalogTableIndex              OBJECT-TYPE
			   SYNTAX           INTEGER (1..4294967295)
			   ACCESS           read-only
			   STATUS           mandatory
			   DESCRIPTION
			   "The value of this object identifies the network
			    element. This index is equal to the
			    hfcCommonTableIndex for the same element."
			   ::= { gx2PsdcAnalogEntry 1}

-- // New Parameter - Fan Current
		pslabelFanCurrent     OBJECT-TYPE
			   SYNTAX           DisplayString (SIZE (0..80))
			   ACCESS           read-only
			   STATUS           optional
			   DESCRIPTION
			   "The value of this object provides the label of the Fan Current Analog parameter."
			   ::= { gx2PsdcAnalogEntry 2}

		psuomFanCurrent       OBJECT-TYPE
			   SYNTAX           DisplayString (SIZE (0..80))
			   ACCESS           read-only
			   STATUS           optional
			   DESCRIPTION
			   "The value of this object provides the Unit of Measure of the Fan Current Analog
			    parameter."
			   ::= { gx2PsdcAnalogEntry 3}

		psmajorHighFanCurrent OBJECT-TYPE
			   SYNTAX           Float
			   ACCESS           read-only
			   STATUS           mandatory
			   DESCRIPTION
			   "The value of this object provides the Major High alarm value of the Fan Current
			    Analog parameter. This value is a floating point number that is represented as
		  	    an IEEE 32 Bit number"
			   ::= { gx2PsdcAnalogEntry 4}


		psmajorLowFanCurrent  OBJECT-TYPE
			   SYNTAX           Float
			   ACCESS           read-only
			   STATUS           mandatory
			   DESCRIPTION
			   "The value of this object provides the Major Low alarm value of the Fan Current
			    Analog parameter. This value is a floating point number that is represented as
			    an IEEE 32 Bit number"
			   ::= { gx2PsdcAnalogEntry 5}

		psminorHighFanCurrent OBJECT-TYPE
			   SYNTAX           Float
			   ACCESS           read-only
			   STATUS           mandatory
			   DESCRIPTION
			   "The value of this object provides the Minor High alarm value of the Fan Current
			    Analog parameter. This value is a floating point number that is represented as
			    an IEEE 32 Bit number."
			   ::= { gx2PsdcAnalogEntry 6}

		psminorLowFanCurrent  OBJECT-TYPE
			   SYNTAX           Float
			   ACCESS           read-only
			   STATUS           mandatory
			   DESCRIPTION
			   "The value of this object provides the Minor Low alarm value of the Fan Current
			    Analog parameter. This value is a floating point number that is represented
			    as an IEEE 32 Bit number."
			   ::= { gx2PsdcAnalogEntry 7}

		pscurrentValueFanCurrent  OBJECT-TYPE
			   SYNTAX           Float
			   ACCESS           read-only
			   STATUS           mandatory
			   DESCRIPTION
			   "The value of this object provides the Current value of the Fan Current Analog
			    parameter. This value is a floating point number that is represented as an
			    IEEE 32 Bit number."
			   ::= { gx2PsdcAnalogEntry 8}

		psstateFlagFanCurrent  OBJECT-TYPE
			   SYNTAX           INTEGER
								{
								hidden(1),
								read-only(2),
								updateable(3)
								}
			   ACCESS           read-only
			   STATUS           mandatory
			   DESCRIPTION
			   "The value of this object provides the state of the Fan Current Analog
			    parameter. (0-Hidden 1-Read-Only, 2-Updateable)"
			   ::= { gx2PsdcAnalogEntry 9}

		psminValueFanCurrent  OBJECT-TYPE
			   SYNTAX           Float
			   ACCESS           read-only
			   STATUS           mandatory
			   DESCRIPTION
			   "The value of this object provides the minimum value the Fan Current Analog
			    parameter can achieve. This value is a floating point number that is
			    represented as an IEEE 32 Bit number."
			   ::= { gx2PsdcAnalogEntry 10}

		psmaxValueFanCurrent  OBJECT-TYPE
			   SYNTAX           Float
			   ACCESS           read-only
			   STATUS           mandatory
			   DESCRIPTION
			   "The value of this object provides the maximum value the Fan Current Analog
			    parameter can achive. This value is a floating point number that is represented
			    as an IEEE 32 Bit number."
			   ::= { gx2PsdcAnalogEntry 11}

		psalarmStateFanCurrent  OBJECT-TYPE
			   SYNTAX           INTEGER
									{
									noAlarm(1),
									majorLowAlarm(2),
									minorLowAlarm(3),
									minorHighAlarm(4),
									majorHighAlarm(5),
									informational(6)
									}
			   ACCESS           read-only
			   STATUS           mandatory
			   DESCRIPTION
			   "The value of this object provides the curent alarm state of the Fan Current
			    Analog parameter."
			   ::= { gx2PsdcAnalogEntry 12}

-- // New Parameter : 12 Volt

		pslabel12Volt         OBJECT-TYPE
			   SYNTAX           DisplayString (SIZE (0..80))
			   ACCESS           read-only
			   STATUS           optional
			   DESCRIPTION
			   "The value of this object provides the label of the 12 Volt Analog parameter."
			   ::= { gx2PsdcAnalogEntry 13}

		psuom12Volt           OBJECT-TYPE
			   SYNTAX           DisplayString (SIZE (0..80))
			   ACCESS           read-only
			   STATUS           optional
			   DESCRIPTION
			   "The value of this object provides the unit of measure of the 12 Volt
		            Analog parameter."
			   ::= { gx2PsdcAnalogEntry 14}

		psmajorHigh12Volt     OBJECT-TYPE
			   SYNTAX           Float
			   ACCESS           read-only
			   STATUS           mandatory
			   DESCRIPTION
			   "The value of this object provides the Major High alarm value of the 12 Volt
			    Analog parameter. This value is a floating point number that is represented
		  	    as an IEEE 32 Bit number."
			   ::= { gx2PsdcAnalogEntry 15}


		psmajorLow12Volt      OBJECT-TYPE
			   SYNTAX           Float
			   ACCESS           read-only
			   STATUS           mandatory
			   DESCRIPTION
			   "The value of this object provides the Major Low alarm value of the 12 Volt
			    Analog parameter. This value is a floating point number that is represented
			    as an IEEE 32 Bit number."
			   ::= { gx2PsdcAnalogEntry 16}

		psminorHigh12Volt     OBJECT-TYPE
			   SYNTAX           Float
			   ACCESS           read-only
			   STATUS           mandatory
			   DESCRIPTION
			   "The value of this object provides the Minor High alarm value of the 12 Volt
			    Analog parameter. This value is a floating point number that is represented
			    as an IEEE 32 Bit number."
			   ::= { gx2PsdcAnalogEntry 17}

		psminorLow12Volt      OBJECT-TYPE
			   SYNTAX           Float
			   ACCESS           read-only
			   STATUS           mandatory
			   DESCRIPTION
			   "The value of this object provides the Minor Low alarm value of the 12 Volt
			    Analog parameter. This value is a floating point number that is represented
			    as an IEEE 32 Bit number."
			   ::= { gx2PsdcAnalogEntry 18}

		pscurrentValue12Volt  OBJECT-TYPE
			   SYNTAX           Float
			   ACCESS           read-only
			   STATUS           mandatory
			   DESCRIPTION
			   "The value of this object provides the Current value of the 12 Volt Analog
			    parameter. This value is a floating point number that is represented as an
			    IEEE 32 Bit number."
			   ::= { gx2PsdcAnalogEntry 19}

		psstateFlag12Volt     OBJECT-TYPE
			   SYNTAX           INTEGER
								{
								hidden(1),
								read-only(2),
								updateable(3)
								}
			   ACCESS           read-only
			   STATUS           mandatory
			   DESCRIPTION
			   "The value of this object provides the state of the 12 Volt Analog parameter.
			   (0-Hidden 1-Read-Only, 2-Updateable)"
			   ::= { gx2PsdcAnalogEntry 20}

		psminValue12Volt      OBJECT-TYPE
			   SYNTAX           Float
			   ACCESS           read-only
			   STATUS           mandatory
			   DESCRIPTION
			   "The value of this object provides the minimum value the 12 Volt Analog
			    parameter can achieve. This value is a floating point number that is
			    represented as an IEEE 32 Bit number."
			   ::= { gx2PsdcAnalogEntry 21}

		psmaxValue12Volt      OBJECT-TYPE
			   SYNTAX           Float
			   ACCESS           read-only
			   STATUS           mandatory
			   DESCRIPTION
			   "The value of this object provides the maximum value the 12 Volt Analog
  			    parameter can achieve. This value is a floating point number that is
			    represented as an IEEE 32 Bit number."
			   ::= { gx2PsdcAnalogEntry 22}

		psalarmState12Volt    OBJECT-TYPE
			   SYNTAX           INTEGER
									{
									noAlarm(1),
									majorLowAlarm(2),
									minorLowAlarm(3),
									minorHighAlarm(4),
									majorHighAlarm(5),
									informational(6)
									}
			   ACCESS           read-only
			   STATUS           mandatory
			   DESCRIPTION
			   "The value of this object provides the curent alarm state of the 12 Volt Analog
			    parameter."
			   ::= { gx2PsdcAnalogEntry 23}
-- // New Parameter : 5 Volt

		pslabel5Volt      OBJECT-TYPE
			   SYNTAX           DisplayString (SIZE (0..80))
			   ACCESS           read-only
			   STATUS           optional
			   DESCRIPTION
			   "The value of this object provides the label of the Attenuator Setting Analog
			    parameter."
			   ::= { gx2PsdcAnalogEntry 24}

		psuom5Volt        OBJECT-TYPE
			   SYNTAX           DisplayString (SIZE (0..80))
			   ACCESS           read-only
			   STATUS           optional
			   DESCRIPTION
			   "The value of this object provides the Unit of Measure of the 5 Volt Analog
			    parameter."
			   ::= { gx2PsdcAnalogEntry 25}

		psmajorHigh5Volt  OBJECT-TYPE
			   SYNTAX           Float
			   ACCESS           read-only
			   STATUS           mandatory
			   DESCRIPTION
			   "The value of this object provides the Major High alarm value of the 5 Volt
			    Analog parameter. This value is a floating point number that is represented
			    as an IEEE 32 Bit number."
			   ::= { gx2PsdcAnalogEntry 26}


		psmajorLow5Volt   OBJECT-TYPE
			   SYNTAX           Float
			   ACCESS           read-only
			   STATUS           mandatory
			   DESCRIPTION
			   "The value of this object provides the Major Low alarm value of the 5 Volt
			    Analog parameter. This value is a floating point number that is represented
			    as an IEEE 32 Bit number."
			   ::= { gx2PsdcAnalogEntry 27}

		psminorHigh5Volt  OBJECT-TYPE
			   SYNTAX           Float
			   ACCESS           read-only
			   STATUS           mandatory
			   DESCRIPTION
            "The value of this object provides the Minor High alarm value of the 5 Volt
			    Analog parameter. This value is a floating point number that is represented
			    as an IEEE 32 Bit number."
			   ::= { gx2PsdcAnalogEntry 28}

		psminorLow5Volt   OBJECT-TYPE
			   SYNTAX           Float
			   ACCESS           read-only
			   STATUS           mandatory
			   DESCRIPTION
			   "The value of this object provides the Minor Low alarm value of the 5 Volt
			    Analog parameter. This value is a floating point number that is represented
			    as an IEEE 32 Bit number."
			   ::= { gx2PsdcAnalogEntry 29}

		pscurrentValue5Volt   OBJECT-TYPE
			   SYNTAX           Float
			   ACCESS           read-only
			   STATUS           mandatory
			   DESCRIPTION
			   "The value of this object provides the Current value of the 5 Volt Analog
			    parameter. This value is a floating point number that is represented as
			    an IEEE 32 Bit number."
			   ::= { gx2PsdcAnalogEntry 30}

		psstateFlag5Volt  OBJECT-TYPE
			   SYNTAX           INTEGER
								{
								hidden(1),
								read-only(2),
								updateable(3)
								}
			   ACCESS           read-only
			   STATUS           mandatory
			   DESCRIPTION
			   "The value of this object provides the state of the 5 Volt Analog parameter.
			   (0-Hidden 1-Read-Only, 2-Updateable)."
			   ::= { gx2PsdcAnalogEntry 31}

		psminValue5Volt   OBJECT-TYPE
			   SYNTAX           Float
			   ACCESS           read-only
			   STATUS           mandatory
			   DESCRIPTION
			   "The value of this object provides the minimum value the 5 Volt Analog
			    parameter can achieve. This value is a floating point number that is
			    represented as an IEEE 32 Bit number."
			   ::= { gx2PsdcAnalogEntry 32}

		psmaxValue5Volt   OBJECT-TYPE
			   SYNTAX           Float
			   ACCESS           read-only
			   STATUS           mandatory
			   DESCRIPTION
			   "The value of this object provides the maximum value the 5 Volt Analog parameter
			    can achieve. This value is a floating point number that is represented as an
			    IEEE 32 Bit number."
			   ::= { gx2PsdcAnalogEntry 33}

		psalarmState5Volt OBJECT-TYPE
			   SYNTAX           INTEGER
									{
									noAlarm(1),
									majorLowAlarm(2),
									minorLowAlarm(3),
									minorHighAlarm(4),
									majorHighAlarm(5),
									informational(6)
									}
			   ACCESS           read-only
			   STATUS           mandatory
			   DESCRIPTION
			   "The value of this object provides the curent alarm state of the 5 Volt
			    Analog parameter. "
			   ::= { gx2PsdcAnalogEntry 34}
-- // New Parameter : 3.7 Volt

		pslabel3Volt             OBJECT-TYPE
			   SYNTAX           DisplayString (SIZE (0..80))
			   ACCESS           read-only
			   STATUS           optional
			   DESCRIPTION
			   "The value of this object provides the label of the
			    3 Anode Volt Analog parameter."
			   ::= { gx2PsdcAnalogEntry 35}

		psuom3Volt               OBJECT-TYPE
			   SYNTAX           DisplayString (SIZE (0..80))
			   ACCESS           read-only
			   STATUS           optional
			   DESCRIPTION
            "The value of this object provides the Unit of Measure of the 3.7V anode voltage
             analog parameter."
			   ::= { gx2PsdcAnalogEntry 36}

		psmajorHigh3Volt         OBJECT-TYPE
			   SYNTAX           Float
			   ACCESS           read-only
			   STATUS           mandatory
			   DESCRIPTION
            "The value of this object provides the Major High alarm value of the 3.7V anode
             voltage analog parameter. This value is a floating point number that is
			    represented as an IEEE 32 Bit number."
			   ::= { gx2PsdcAnalogEntry 37}


		psmajorLow3Volt          OBJECT-TYPE
			   SYNTAX           Float
			   ACCESS           read-only
			   STATUS           mandatory
			   DESCRIPTION
            "The value of this object provides the Major Low alarm value of the 3.7V anode
             voltage analog parameter. This value is a floating point number that is
             represented as an IEEE 32 Bit number."
			   ::= { gx2PsdcAnalogEntry 38}

		psminorHigh3Volt         OBJECT-TYPE
			   SYNTAX           Float
			   ACCESS           read-only
			   STATUS           mandatory
			   DESCRIPTION
            "The value of this object provides the Minor High alarm value of the 3.7V anode
             voltage analog parameter. This value is a floating point number that is
             represented as an IEEE 32 Bit number."
			   ::= { gx2PsdcAnalogEntry 39}

		psminorLow3Volt          OBJECT-TYPE
			   SYNTAX           Float
			   ACCESS           read-only
			   STATUS           mandatory
			   DESCRIPTION
            "The value of this object provides the Minor Low alarm value of the 3.7V anode
             voltage analog parameter. This value is a floating point number that is
             represented as an IEEE 32 Bit number."
			   ::= { gx2PsdcAnalogEntry 40}

		pscurrentValue3Volt      OBJECT-TYPE
			   SYNTAX           Float
			   ACCESS           read-only
			   STATUS           mandatory
			   DESCRIPTION
            "The value of this object provides the Current value of the 3.7V anode voltage
             analog parameter. This value is a floating point number that is represented
             as an IEEE 32 Bit number."
			   ::= { gx2PsdcAnalogEntry 41}

		psstateFlag3Volt         OBJECT-TYPE
			   SYNTAX           INTEGER
								{
								hidden(1),
								read-only(2),
								updateable(3)
								}
			   ACCESS           read-only
			   STATUS           mandatory
			   DESCRIPTION
            "The value of this object provides the state of the 3 Volt Analog parameter.
             (0-Hidden 1-Read-Only, 2-Updateable). "
			   ::= { gx2PsdcAnalogEntry 42}

		psminValue3Volt          OBJECT-TYPE
			   SYNTAX           Float
			   ACCESS           read-only
			   STATUS           mandatory
			   DESCRIPTION
            "The value of this object provides the minimum value that the 3.7V anode voltage
             analog parameter can achieve. This value is a floating point number that is
             represented as an IEEE 32 Bit number."
			   ::= { gx2PsdcAnalogEntry 43}

		psmaxValue3Volt          OBJECT-TYPE
			   SYNTAX           Float
			   ACCESS           read-only
			   STATUS           mandatory
			   DESCRIPTION
            "The value of this object provides the maximum value that the 3.7V anode voltage
             analog parameter can achieve. This value is a floating point number that is
             represented as an IEEE 32 Bit number."
			   ::= { gx2PsdcAnalogEntry 44}

		psalarmState3Volt        OBJECT-TYPE
			   SYNTAX           INTEGER
									{
									noAlarm(1),
									majorLowAlarm(2),
									minorLowAlarm(3),
									minorHighAlarm(4),
									majorHighAlarm(5),
									informational(6)
									}
			   ACCESS           read-only
			   STATUS           mandatory
			   DESCRIPTION
            "The value of this object provides the curent alarm state of the 3.7V anode
             voltage analog parameter. "
			   ::= { gx2PsdcAnalogEntry 45}
-- // New Parameter : Ambient Temp

		pslabelAmbientTemp            OBJECT-TYPE
			   SYNTAX           DisplayString (SIZE (0..80))
			   ACCESS           read-only
			   STATUS           optional
			   DESCRIPTION
			   "The value of this object provides the label of the
			    Ambient Temperature Current Analog parameter."
			   ::= { gx2PsdcAnalogEntry 46}

		psuomAmbientTemp              OBJECT-TYPE
			   SYNTAX           DisplayString (SIZE (0..80))
			   ACCESS           read-only
			   STATUS           optional
			   DESCRIPTION
			   "The value of this object provides the Unit of Measure of the
			    Ambient Temperature Analog parameter."
			   ::= { gx2PsdcAnalogEntry 47}

		psmajorHighAmbientTemp        OBJECT-TYPE
			   SYNTAX           Float
			   ACCESS           read-only
			   STATUS           mandatory
			   DESCRIPTION
			   "The value of this object provides the Major High alarm value
of the Ambient Temperature Analog parameter. This value is a floating point number that is represented as an IEEE 32 Bit number."
			   ::= { gx2PsdcAnalogEntry 48}


		psmajorLowAmbientTemp         OBJECT-TYPE
			   SYNTAX           Float
			   ACCESS           read-only
			   STATUS           mandatory
			   DESCRIPTION
			   "The value of this object provides the Major Low alarm value
of the Ambient Temperature Analog parameter. This value is a floating point number that is represented as an IEEE 32 Bit number."
			   ::= { gx2PsdcAnalogEntry 49}

		psminorHighAmbientTemp        OBJECT-TYPE
			   SYNTAX           Float
			   ACCESS           read-only
			   STATUS           mandatory
			   DESCRIPTION
			   "The value of this object provides the Minor High alarm value
of the Ambient Temperature Analog parameter. This value is a floating point number that is represented as an IEEE 32 Bit number."
			   ::= { gx2PsdcAnalogEntry 50}

		psminorLowAmbientTemp         OBJECT-TYPE
			   SYNTAX           Float
			   ACCESS           read-only
			   STATUS           mandatory
			   DESCRIPTION
			   "The value of this object provides the Minor Low alarm value
of the Ambient Temperature Analog parameter. This value is a floating point number that is represented as an IEEE 32 Bit number."
			   ::= { gx2PsdcAnalogEntry 51}

		pscurrentValueAmbientTemp     OBJECT-TYPE
			   SYNTAX           Float
			   ACCESS           read-only
			   STATUS           mandatory
			   DESCRIPTION
			   "The value of this object provides the Current value
of the Ambient Temperature Analog parameter. This value is a floating point number that is represented as an IEEE 32 Bit number."
			   ::= { gx2PsdcAnalogEntry 52}

		psstateFlagAmbientTemp        OBJECT-TYPE
			   SYNTAX           INTEGER
								{
								hidden(1),
								read-only(2),
								updateable(3)
								}
			   ACCESS           read-only
			   STATUS           mandatory
			   DESCRIPTION
			   "The value of this object provides the state
			    of the Ambient Temperature Analog parameter. (0-Hidden
			          1-Read-Only, 2-Updateable)."
			   ::= { gx2PsdcAnalogEntry 53}

		psminValueAmbientTemp         OBJECT-TYPE
			   SYNTAX           Float
			   ACCESS           read-only
			   STATUS           mandatory
			   DESCRIPTION
			   "The value of this object provides the minimum value
			    the Ambient Temperature Analog parameter can achive."
			   ::= { gx2PsdcAnalogEntry 54}

		psmaxValueAmbientTemp         OBJECT-TYPE
			   SYNTAX           Float
			   ACCESS           read-only
			   STATUS           mandatory
			   DESCRIPTION
			   "The value of this object provides the maximum value
the Ambient Temperature Analog parameter can achive. This value is a floating point number that is represented as an IEEE 32 Bit number."
			   ::= { gx2PsdcAnalogEntry 55}

		psalarmStateAmbientTemp       OBJECT-TYPE
			   SYNTAX           INTEGER
									{
									noAlarm(1),
									majorLowAlarm(2),
									minorLowAlarm(3),
									minorHighAlarm(4),
									majorHighAlarm(5),
									informational(6)
									}
			   ACCESS           read-only
			   STATUS           mandatory
			   DESCRIPTION
			   "The value of this object provides the curent alarm state of
the Ambient Temperature Analog parameter. "
			   ::= { gx2PsdcAnalogEntry 56}
-- // New Parameter : Main Temp (heat sink temp)

		pslabelMainTemp           OBJECT-TYPE
			   SYNTAX           DisplayString (SIZE (0..80))
			   ACCESS           read-only
			   STATUS           optional
			   DESCRIPTION
			   "The value of this object provides the label of the
			    Main Board Temperature Analog parameter."
			   ::= { gx2PsdcAnalogEntry 57}

		psuomMainTemp             OBJECT-TYPE
			   SYNTAX           DisplayString (SIZE (0..80))
			   ACCESS           read-only
			   STATUS           optional
			   DESCRIPTION
			   "The value of this object provides the Unit of Measure of the
			    Main Board Temperature Analog parameter.."
			   ::= { gx2PsdcAnalogEntry 58}

		psmajorHighMainTemp       OBJECT-TYPE
			   SYNTAX           Float
			   ACCESS           read-only
			   STATUS           mandatory
			   DESCRIPTION
            "The value of this object provides the Major High alarm value of the Main Board
             Temperature Analog parameter. This value is a floating point number that is
             represented as an IEEE 32 Bit number."
			   ::= { gx2PsdcAnalogEntry 59}


		psmajorLowMainTemp        OBJECT-TYPE
			   SYNTAX           Float
			   ACCESS           read-only
			   STATUS           mandatory
			   DESCRIPTION
            "The value of this object provides the Major Low alarm value of the Main Board
             Temperature Analog parameter. This value is a floating point number that is
             represented as an IEEE 32 Bit number."
			   ::= { gx2PsdcAnalogEntry 60}

		psminorHighMainTemp       OBJECT-TYPE
			   SYNTAX           Float
			   ACCESS           read-only
			   STATUS           mandatory
			   DESCRIPTION
            "The value of this object provides the Minor High alarm value of the Main Board
             Temperature Analog parameter. This value is a floating point number that is
             represented as an IEEE 32 Bit number."
			   ::= { gx2PsdcAnalogEntry 61}

		psminorLowMainTemp        OBJECT-TYPE
			   SYNTAX           Float
			   ACCESS           read-only
			   STATUS           mandatory
			   DESCRIPTION
            "The value of this object provides the Minor Low alarm value of the Main Board
             Temperature Analog parameter. This value is a floating point number that is
             represented as an IEEE 32 Bit number."
			   ::= { gx2PsdcAnalogEntry 62}

		pscurrentValueMainTemp    OBJECT-TYPE
			   SYNTAX           Float
			   ACCESS           read-only
			   STATUS           mandatory
			   DESCRIPTION
            "The value of this object provides the Current value of the Main Board
             Temperature Analog parameter. This value is a floating point number that
             is represented as an IEEE 32 Bit number."
			   ::= { gx2PsdcAnalogEntry 63}

		psstateFlagMainTemp       OBJECT-TYPE
			   SYNTAX           INTEGER
								{
								hidden(1),
								read-only(2),
								updateable(3)
								}
			   ACCESS           read-only
			   STATUS           mandatory
			   DESCRIPTION
            "The value of this object provides the state of the Main Board Temperature
             Analog parameter.
             (0-Hidden 1-Read-Only, 2-Updateable)."
			   ::= { gx2PsdcAnalogEntry 64}

		psminValueMainTemp        OBJECT-TYPE
			   SYNTAX           Float
			   ACCESS           read-only
			   STATUS           mandatory
			   DESCRIPTION
            "The value of this object provides the minimum value the Main Board Temperature
             Analog parameter can achieve. This value is a floating point number that is
             represented as an IEEE 32 Bit number."
			   ::= { gx2PsdcAnalogEntry 65}

		psmaxValueMainTemp        OBJECT-TYPE
			   SYNTAX           Float
			   ACCESS           read-only
			   STATUS           mandatory
			   DESCRIPTION
            "The value of this object provides the maximum value the Main Board Temperature
             Analog parameter can achieve. This value is a floating point number that is
             represented as an IEEE 32 Bit number."
			   ::= { gx2PsdcAnalogEntry 66}

		psalarmStateMainTemp      OBJECT-TYPE
			   SYNTAX           INTEGER
									{
									noAlarm(1),
									majorLowAlarm(2),
									minorLowAlarm(3),
									minorHighAlarm(4),
									majorHighAlarm(5),
									informational(6)
									}
			   ACCESS           read-only
			   STATUS           mandatory
			   DESCRIPTION
			   "The value of this object provides the curent alarm state of
			    the Main Board Temperature Analog parameter."
			   ::= { gx2PsdcAnalogEntry 67}
-- // New Parameter : 12 Volt anode

		pslabel12AnodeVolt            OBJECT-TYPE
			   SYNTAX           DisplayString (SIZE (0..80))
			   ACCESS           read-only
			   STATUS           optional
			   DESCRIPTION
			   "The value of this object provides the label of the
			    +12 Anode Voltage Analog parameter."
			   ::= { gx2PsdcAnalogEntry 68}

		psuom12AnodeVolt              OBJECT-TYPE
			   SYNTAX           DisplayString (SIZE (0..80))
			   ACCESS           read-only
			   STATUS           optional
			   DESCRIPTION
			   "The value of this object provides the Unit of Measure of the
			    +12 Anode Voltage Analog parameter."
			   ::= { gx2PsdcAnalogEntry 69}

		psmajorHigh12AnodeVolt        OBJECT-TYPE
			   SYNTAX           Float
			   ACCESS           read-only
			   STATUS           mandatory
			   DESCRIPTION
            "The value of this object provides the Major High alarm value of the +12V anode
            voltage analog parameter. This value is a floating point number that is
            represented as an IEEE 32 Bit number."
			   ::= { gx2PsdcAnalogEntry 70}


		psmajorLow12AnodeVolt         OBJECT-TYPE
			   SYNTAX           Float
			   ACCESS           read-only
			   STATUS           mandatory
			   DESCRIPTION
            "The value of this object provides the Major Low alarm value of the +12V anode
            voltage analog parameter. This value is a floating point number that is
             represented as an IEEE 32 Bit number."
			   ::= { gx2PsdcAnalogEntry 71}

		psminorHigh12AnodeVolt        OBJECT-TYPE
			   SYNTAX           Float
			   ACCESS           read-only
			   STATUS           mandatory
			   DESCRIPTION
            "The value of this object provides the Minor High alarm value of the +12V anode
             voltage analog parameter. This value is a floating point number that is
             represented as an IEEE 32 Bit number."
			   ::= { gx2PsdcAnalogEntry 72}

		psminorLow12AnodeVolt         OBJECT-TYPE
			   SYNTAX           Float
			   ACCESS           read-only
			   STATUS           mandatory
			   DESCRIPTION
            "The value of this object provides the Minor Low alarm value of the +12V anode
             voltage analog parameter. This value is a floating point number that is
             represented as an IEEE 32 Bit number."
			   ::= { gx2PsdcAnalogEntry 73}

		pscurrentValue12AnodeVolt     OBJECT-TYPE
			   SYNTAX           Float
			   ACCESS           read-only
			   STATUS           mandatory
			   DESCRIPTION
            "The value of this object provides the Current value of the +12V anode voltage
             analog parameter. This value is a floating point number that is represented
             as an IEEE 32 Bit number."
			   ::= { gx2PsdcAnalogEntry 74}

		psstateFlag12AnodeVolt        OBJECT-TYPE
			   SYNTAX           INTEGER
								{
								hidden(1),
								read-only(2),
								updateable(3)
								}
			   ACCESS           read-only
			   STATUS           mandatory
			   DESCRIPTION
            "The value of this object provides the state of the +12V anode voltage
             analog parameter.
             (0-Hidden 1-Read-Only, 2-Updateable)."
			   ::= { gx2PsdcAnalogEntry 75}

		psminValue12AnodeVolt         OBJECT-TYPE
			   SYNTAX           Float
			   ACCESS           read-only
			   STATUS           mandatory
			   DESCRIPTION
            "The value of this object provides the minimum value the +12V anode voltage
             analog parameter can achieve. This value is a floating point number that is
             represented as an IEEE 32 Bit number."
			   ::= { gx2PsdcAnalogEntry 76}

		psmaxValue12AnodeVolt         OBJECT-TYPE
			   SYNTAX           Float
			   ACCESS           read-only
			   STATUS           mandatory
			   DESCRIPTION
            "The value of this object provides the maximum value the +12V anode voltage
             analog parameter can achieve. This value is a floating point number that is
             represented as an IEEE 32 Bit number."
			   ::= { gx2PsdcAnalogEntry 77}

		psalarmState12AnodeVolt       OBJECT-TYPE
			   SYNTAX           INTEGER
									{
									noAlarm(1),
									majorLowAlarm(2),
									minorLowAlarm(3),
									minorHighAlarm(4),
									majorHighAlarm(5),
									informational(6)
									}
			   ACCESS           read-only
			   STATUS           mandatory
			   DESCRIPTION
			   "The value of this object provides the curent alarm state of
             the +12V anode voltage analog parameter."
			   ::= { gx2PsdcAnalogEntry 78}

-- // New Parameter : 5 Volt anode

		pslabel5AnodeVolt              OBJECT-TYPE
			   SYNTAX           DisplayString (SIZE (0..80))
			   ACCESS           read-only
			   STATUS           optional
			   DESCRIPTION
			   "The value of this object provides the label of the
			    Module Temperature Analog parameter."
			   ::= { gx2PsdcAnalogEntry 79}

		psuom5AnodeVolt                OBJECT-TYPE
			   SYNTAX           DisplayString (SIZE (0..80))
			   ACCESS           read-only
			   STATUS           optional
			   DESCRIPTION
			   "The value of this object provides the Unit of Measure of the
			    5 Anode Volt Analog parameter."
			   ::= { gx2PsdcAnalogEntry 80}

		psmajorHigh5AnodeVolt          OBJECT-TYPE
			   SYNTAX           Float
			   ACCESS           read-only
			   STATUS           mandatory
			   DESCRIPTION
            "The value of this object provides the Major High alarm value of the 5V anode
             voltage analog parameter. This value is a floating point number that is
             represented as an IEEE 32 Bit number."
			   ::= { gx2PsdcAnalogEntry 81}


		psmajorLow5AnodeVolt           OBJECT-TYPE
			   SYNTAX           Float
			   ACCESS           read-only
			   STATUS           mandatory
			   DESCRIPTION
            "The value of this object provides the Major Low alarm value of the 5V anode
             volt analog parameter. This value is a floating point number that is
             represented as an IEEE 32 Bit number."
			   ::= { gx2PsdcAnalogEntry 82}

		psminorHigh5AnodeVolt          OBJECT-TYPE
			   SYNTAX           Float
			   ACCESS           read-only
			   STATUS           mandatory
			   DESCRIPTION
            "The value of this object provides the Minor High alarm value of the 5V anode
             volt analog parameter. This value is a floating point number that is
             represented as an IEEE 32 Bit number."
			   ::= { gx2PsdcAnalogEntry 83}

		psminorLow5AnodeVolt           OBJECT-TYPE
			   SYNTAX           Float
			   ACCESS           read-only
			   STATUS           mandatory
			   DESCRIPTION
            "The value of this object provides the Minor Low alarm value of the 5V anode
             volt analog parameter. This value is a floating point number that is
             represented as an IEEE 32 Bit number."
			   ::= { gx2PsdcAnalogEntry 84}

		pscurrentValue5AnodeVolt       OBJECT-TYPE
			   SYNTAX           Float
			   ACCESS           read-only
			   STATUS           mandatory
			   DESCRIPTION
            "The value of this object provides the Current value of the 5V anode volt
             analog parameter. This value is a floating point number that is represented
             as an IEEE 32 Bit number."
			   ::= { gx2PsdcAnalogEntry 85}

		psstateFlag5AnodeVolt          OBJECT-TYPE
			   SYNTAX           INTEGER
								{
								hidden(1),
								read-only(2),
								updateable(3)
								}
			   ACCESS           read-only
			   STATUS           mandatory
			   DESCRIPTION
			   "The value of this object provides the state
			    of the 5 Anode Volt Analog parameter. (0-Hidden
			          1-Read-Only, 2-Updateable)."
			   ::= { gx2PsdcAnalogEntry 86}

		psminValue5AnodeVolt           OBJECT-TYPE
			   SYNTAX           Float
			   ACCESS           read-only
			   STATUS           mandatory
			   DESCRIPTION
            "The value of this object provides the minimum value the 5V anode volt analog
             parameter can achieve. This value is a floating point number that is
             represented as an IEEE 32 Bit number."
			   ::= { gx2PsdcAnalogEntry 87}

		psmaxValue5AnodeVolt           OBJECT-TYPE
			   SYNTAX           Float
			   ACCESS           read-only
			   STATUS           mandatory
			   DESCRIPTION
            "The value of this object provides the maximum value the 5V anode volt analog
             parameter can achieve. This value is a floating point number that is
             represented as an IEEE 32 Bit number."
			   ::= { gx2PsdcAnalogEntry 88}

		psalarmState5AnodeVolt         OBJECT-TYPE
			   SYNTAX           INTEGER
									{
									noAlarm(1),
									majorLowAlarm(2),
									minorLowAlarm(3),
									minorHighAlarm(4),
									majorHighAlarm(5),
									informational(6)
									}
			   ACCESS           read-only
			   STATUS           mandatory
			   DESCRIPTION
            "The value of this object provides the curent alarm state of the 5V anode
             voltage analog parameter."
			   ::= { gx2PsdcAnalogEntry 89}

-- // New Parameter : 3.7 Volt anode

		pslabel3AnodeVolt               OBJECT-TYPE
			   SYNTAX           DisplayString (SIZE (0..80))
			   ACCESS           read-only
			   STATUS           optional
			   DESCRIPTION
            "The value of this object provides the label of the 3.7V anode voltage
             parameter."
			   ::= { gx2PsdcAnalogEntry 90}

		psuom3AnodeVolt                 OBJECT-TYPE
			   SYNTAX           DisplayString (SIZE (0..80))
			   ACCESS           read-only
			   STATUS           optional
			   DESCRIPTION
            "The value of this object provides the Unit of Measure of the 3.7V anode voltage
             parameter."
			   ::= { gx2PsdcAnalogEntry 91}

		psmajorHigh3AnodeVolt           OBJECT-TYPE
			   SYNTAX           Float
			   ACCESS           read-only
			   STATUS           mandatory
			   DESCRIPTION
            "The value of this object provides the Major High alarm value for the 3.7V anode
             voltage parameter. This value is a floating point number that is represented as
             an IEEE 32 Bit number."
			   ::= { gx2PsdcAnalogEntry 92}

		psmajorLow3AnodeVolt            OBJECT-TYPE
			   SYNTAX           Float
			   ACCESS           read-only
			   STATUS           mandatory
			   DESCRIPTION
            "The value of this object provides the Major Low alarm value for the 3.7V anode
             voltage parameter. This value is a floating point number that is represented as
             an IEEE 32 Bit number."
			   ::= { gx2PsdcAnalogEntry 93}

		psminorHigh3AnodeVolt           OBJECT-TYPE
			   SYNTAX           Float
			   ACCESS           read-only
			   STATUS           mandatory
			   DESCRIPTION
            "The value of this object provides the Minor High alarm value for the 3.7V anode
             voltage parameter. This value is a floating point number that is represented as
             an IEEE 32 Bit number."
			   ::= { gx2PsdcAnalogEntry 94}

		psminorLow3AnodeVolt            OBJECT-TYPE
			   SYNTAX           Float
			   ACCESS           read-only
			   STATUS           mandatory
			   DESCRIPTION
            "The value of this object provides the Minor Low alarm value for the 3.7V anode
             voltage parameter. This value is a floating point number that is represented as
             an IEEE 32 Bit number."
			   ::= { gx2PsdcAnalogEntry 95}

		pscurrentValue3AnodeVolt        OBJECT-TYPE
			   SYNTAX           Float
			   ACCESS           read-only
			   STATUS           mandatory
			   DESCRIPTION
            "The value of this object provides the Current value of the 3.7V anode voltage
             parameter. This value is a floating point number that is represented as an
             IEEE 32 Bit number."
			   ::= { gx2PsdcAnalogEntry 96}

		psstateFlag3AnodeVolt           OBJECT-TYPE
			   SYNTAX           INTEGER
								{
								hidden(1),
								read-only(2),
								updateable(3)
								}
			   ACCESS           read-only
			   STATUS           mandatory
			   DESCRIPTION
            "The value of this object provides the state of the 3.7V anode voltage
             parameter.
             (0-Hidden 1-Read-Only, 2-Updateable)."
			   ::= { gx2PsdcAnalogEntry 97}

		psminValue3AnodeVolt            OBJECT-TYPE
			   SYNTAX           Float
			   ACCESS           read-only
			   STATUS           mandatory
			   DESCRIPTION
            "The value of this object provides the minimum value that 3.7V anode voltage
            parameter can achieve. This value is a floating point number that is represented
            as an IEEE 32 Bit number."
            ::= { gx2PsdcAnalogEntry 98}

		psmaxValue3AnodeVolt            OBJECT-TYPE
			   SYNTAX           Float
			   ACCESS           read-only
			   STATUS           mandatory
			   DESCRIPTION
            "The value of this object provides the maximum value that 3.7V anode voltage
             parameter can achieve. This value is a floating point number that is
             represented as an IEEE 32 Bit number."
			   ::= { gx2PsdcAnalogEntry 99}

		psalarmState3AnodeVolt          OBJECT-TYPE
			   SYNTAX           INTEGER
									{
									noAlarm(1),
									majorLowAlarm(2),
									minorLowAlarm(3),
									minorHighAlarm(4),
									majorHighAlarm(5),
									informational(6)
									}
			   ACCESS           read-only
			   STATUS           mandatory
			   DESCRIPTION
            "The value of this object provides the curent alarm state of the 3.7V anode
             voltage parameter."
			   ::= { gx2PsdcAnalogEntry 100}

-- ************************ Digital parameters **********************************
		gx2PsdcDigitalTableIndex              OBJECT-TYPE
			   SYNTAX           INTEGER (1..4294967295)
			   ACCESS           read-only
			   STATUS           mandatory
			   DESCRIPTION
			   "The value of this object identifies the network
			    element. This index is equal to the
			    hfcCommonTableIndex for the same element."
			   ::= { gx2PsdcDigitalEntry 1}

-- New parameter
		psdclabelNVfanAlrm                	OBJECT-TYPE
			   SYNTAX       		DisplayString (SIZE (0..80))         
			   ACCESS           	read-only
			   STATUS           	optional
			   DESCRIPTION
			   "The value of this object provides the label of the
			    RF Input Control  Digital parameter."
			   ::= { gx2PsdcDigitalEntry 2}

		psdcenumNVfanAlrm               		OBJECT-TYPE
			   SYNTAX       		DisplayString (SIZE (0..80))         
			   ACCESS           	read-only
			   STATUS           	optional
			   DESCRIPTION
			   "The value of this object represents the Enumeration values
			    possible for the Digital parameter. Each Enumerated values is
			    separated by a common. The first value has a enumerated value of 1."
			   ::= { gx2PsdcDigitalEntry 3}

		psdcvalueNVfanAlrm                	OBJECT-TYPE
			   SYNTAX       		INTEGER
					    	{  
					    	none(1),
							unacknowledged(2),
							acknowledged(3)
					    	}
			   ACCESS           	read-write
			   STATUS           	mandatory
			   DESCRIPTION
			   "The value of this object is the current value of the parameter."
			   ::= { gx2PsdcDigitalEntry 4}

		psdcstateflagNVfanAlrm              OBJECT-TYPE
			   SYNTAX       		INTEGER
								{
								hidden(1),
								read-only(2),
								updateable(3)
								}
			   ACCESS           	read-only
			   STATUS           	mandatory
			   DESCRIPTION
			   "The value of this object provides the state
			    of the RF Input Control  Digital parameter. (0-Hidden	
			          1-Read-Only, 2-Updateable)."
			   ::= { gx2PsdcDigitalEntry 5}

-- // Section: Status parameter detail
		--*********** STATUS *****************
		gx2PsdcStatusTableIndex              OBJECT-TYPE
			   SYNTAX           INTEGER (1..4294967295)
			   ACCESS           read-only
			   STATUS           mandatory
			   DESCRIPTION
			   "The value of this object identifies the network
			    element. This index is equal to the
			    hfcCommonTableIndex for the same element."
			   ::= { gx2PsdcStatusEntry 1}

-- // New Parameter : Boot status
      pslabelBoot                OBJECT-TYPE
			   SYNTAX       		DisplayString (SIZE (0..80))
			   ACCESS           	read-only
			   STATUS           	optional
			   DESCRIPTION
			   "The value of this object provides the label of the
			    Boot Status  Status parameter."
			   ::= { gx2PsdcStatusEntry 2}

		psvalueBoot              		OBJECT-TYPE
			   SYNTAX       		INTEGER
									{
									ok(1),
									undetermined(2),
									warning(3),
									minor(4),
									major(5),
									critical(6)
									}
			   ACCESS           	read-only
			   STATUS           	mandatory
			   DESCRIPTION
			   "The value of this object provides the current state of
			    the parameter (0-Ok, 1-Undetermined
			    2-Warning, 3-Minor, 4-Major, 5-Critical)."
			   ::= { gx2PsdcStatusEntry 3}

		psstateflagBoot     	OBJECT-TYPE
			   SYNTAX       		INTEGER
								{
								hidden(1),
								read-only(2),
								updateable(3)
								}
			   ACCESS           	read-only
			   STATUS           	mandatory
			   DESCRIPTION
			   "The value of this object provides the state
			    of the the parameter. (0-Hidden 1-Read-Only, 2-Updateable)."
			   ::= { gx2PsdcStatusEntry  4}

--New Parameter
		pslabelFlash               	OBJECT-TYPE
			   SYNTAX       		DisplayString (SIZE (0..80))
			   ACCESS           	read-only
			   STATUS           	optional
			   DESCRIPTION
			   "The value of this object provides the label of the
			    Flash Status  Status parameter."
			   ::= { gx2PsdcStatusEntry 5}

		psvalueFlash              	OBJECT-TYPE
			   SYNTAX       		INTEGER
									{
									ok(1),
									undetermined(2),
									warning(3),
									minor(4),
									major(5),
									critical(6)
									}
			   ACCESS           	read-only
			   STATUS           	mandatory
			   DESCRIPTION
			   "The value of this object provides the current state of
			    the parameter (0-Ok, 1-Undetermined
			    2-Warning, 3-Minor, 4-Major, 5-Critical)."
			   ::= { gx2PsdcStatusEntry 6}

		psstateflagFlash     	OBJECT-TYPE
			   SYNTAX       		INTEGER
								{
								hidden(1),
								read-only(2),
								updateable(3)
								}
			   ACCESS           	read-only
			   STATUS           	mandatory
			   DESCRIPTION
			   "The value of this object provides the state
			    of the the parameter. (0-Hidden 1-Read-Only, 2-Updateable)."
			   ::= { gx2PsdcStatusEntry  7}
-- // New Parameter : Factory Data CRC

		pslabelFactoryDataCRC           OBJECT-TYPE
			   SYNTAX       		DisplayString (SIZE (0..80))
			   ACCESS           	read-only
			   STATUS           	optional
			   DESCRIPTION
			   "The value of this object provides the label of the
			    Factory Data CRC Status parameter."
			   ::= { gx2PsdcStatusEntry 8}

		psvalueFactoryDataCRC          	OBJECT-TYPE
			   SYNTAX       		INTEGER
									{
									ok(1),
									undetermined(2),
									warning(3),
									minor(4),
									major(5),
									critical(6)
									}
			   ACCESS           	read-only
			   STATUS           	mandatory
			   DESCRIPTION
			   "The value of this object provides the current state of
			    the parameter (0-Ok, 1-Undetermined
			    2-Warning, 3-Minor, 4-Major, 5-Critical)."
			   ::= { gx2PsdcStatusEntry 9}

		psstateflagFactoryDataCRC     	OBJECT-TYPE
			   SYNTAX       		INTEGER
								{
								hidden(1),
								read-only(2),
								updateable(3)
								}
			   ACCESS           	read-only
			   STATUS           	mandatory
			   DESCRIPTION
			   "The value of this object provides the state
			    of the the parameter. (0-Hidden 1-Read-Only, 2-Updateable)."
			   ::= { gx2PsdcStatusEntry  10}

-- // New Parameter : Alarm Data CRC
		pslabelPsdcDataCRC             OBJECT-TYPE
			   SYNTAX       		DisplayString (SIZE (0..80))
			   ACCESS           	read-only
			   STATUS           	optional
			   DESCRIPTION
			   "The value of this object provides the label of the
			    Laser Data CRC Status parameter."
			   ::= { gx2PsdcStatusEntry 11}

		psvaluePsdcDataCRC           	OBJECT-TYPE
			   SYNTAX       		INTEGER
									{
									ok(1),
									undetermined(2),
									warning(3),
									minor(4),
									major(5),
									critical(6)
									}
			   ACCESS           	read-only
			   STATUS           	mandatory
			   DESCRIPTION
			   "The value of this object provides the current state of
			    the parameter (0-Ok, 1-Undetermined
			    2-Warning, 3-Minor, 4-Major, 5-Critical)."
			   ::= { gx2PsdcStatusEntry 12}

		psstateflagPsdcDataCRC     	OBJECT-TYPE
			   SYNTAX       		INTEGER
								{
								hidden(1),
								read-only(2),
								updateable(3)
								}
			   ACCESS           	read-only
			   STATUS           	mandatory
			   DESCRIPTION
			   "The value of this object provides the state
			    of the the parameter. (0-Hidden 1-Read-Only, 2-Updateable)."
			   ::= { gx2PsdcStatusEntry  13}

-- // New Parameter : Hardware Status
		pslabelPsdcHwStatus             OBJECT-TYPE
			   SYNTAX       		DisplayString (SIZE (0..80))
			   ACCESS           	read-only
			   STATUS           	optional
			   DESCRIPTION
			   "The value of this object provides the label of the
			    Hw Status parameter."
			   ::= { gx2PsdcStatusEntry 14}

		psvaluePsdcHwStatus           	OBJECT-TYPE
			   SYNTAX       		INTEGER
									{
									ok(1),
									undetermined(2),
									warning(3),
									minor(4),
									major(5),
									critical(6)
									}
			   ACCESS           	read-only
			   STATUS           	mandatory
			   DESCRIPTION
			   "The value of this object provides the current state of
			    the parameter (0-Ok, 1-Undetermined
			    2-Warning, 3-Minor, 4-Major, 5-Critical)."
			   ::= { gx2PsdcStatusEntry 15}

		psstateflagPsdcHwStatus     	OBJECT-TYPE
			   SYNTAX       		INTEGER
								{
								hidden(1),
								read-only(2),
								updateable(3)
								}
			   ACCESS           	read-only
			   STATUS           	mandatory
			   DESCRIPTION
			   "The value of this object provides the state
			    of the the parameter. (0-Hidden 1-Read-Only, 2-Updateable)."
			   ::= { gx2PsdcStatusEntry  16}


-- // Section: Factory parameter detail
      gx2PsdcFactoryTableIndex              OBJECT-TYPE
			   SYNTAX           INTEGER (1..4294967295)
			   ACCESS           read-only
			   STATUS           mandatory
			   DESCRIPTION
			   "The value of this object identifies the network
			    element. This index is equal to the
			    hfcCommonTableIndex for the same element."
			   ::= { gx2PsdcFactoryEntry 1}

-- // New Parameter : boot control byte
		psbootControlByteValue          	OBJECT-TYPE
			   SYNTAX       		INTEGER
			   ACCESS           	read-only
			   STATUS           	mandatory
			   DESCRIPTION
            "The value of this object indicates which bank the firmware
             is currently being boot from.

             Boot Control Byte bit definition as follows :
             bit 0 : boot bit (0=boot from bank 0, 1=boot from bank 1)
             bit 1 : bank 0 status (0=bank is blank/bad, 1=bank is OK)
             bit 2 : bank 1 status (0=bank is blank/bad, 1=bank is OK)
             bits 3-7 : not used"

			   ::= { gx2PsdcFactoryEntry 2}

-- // New Parameter : boot status byte
		psbootStatusByteValue          	OBJECT-TYPE
			   SYNTAX       		INTEGER
			   ACCESS           	read-only
			   STATUS           	mandatory
			   DESCRIPTION
             "This object indicates the status of the last boot

            Boot Status Byte bit definitions as follows:
            bit 0 : bank 0 status (0=bank is OK or not used, 1=bank failed boot)
            bit 1 : bank 1 status (0=bank is OK or not used, 1=bank failed boot)
            bit 2 : active bank (0=bank 0 active, 1=bank 1 active)
            bits 3-7: not used"
			   ::= { gx2PsdcFactoryEntry 3}

-- // New Parameter : bank 0 CRC
		psbank1CRCValue          		OBJECT-TYPE
			   SYNTAX       		INTEGER
			   ACCESS           	read-only
			   STATUS           	mandatory
			   DESCRIPTION
			   "This object provides the CRC code of bank 0."
			   ::= { gx2PsdcFactoryEntry 4}

-- // New Parameter : bank 1 CRC
		psbank2CRCValue          		OBJECT-TYPE
			   SYNTAX       		INTEGER
			   ACCESS           	read-only
			   STATUS           	mandatory
			   DESCRIPTION
			   "This object provides the CRC code of bank 1."
			   ::= { gx2PsdcFactoryEntry 5}

-- // New Parameter : programmed EEPROM byte
		psprgEEPROMByteValue          		OBJECT-TYPE
			   SYNTAX       		INTEGER
			   ACCESS           	read-only
			   STATUS           	mandatory
			   DESCRIPTION
			   "This object indicates if the EEPROM has been programmed"
			   ::= { gx2PsdcFactoryEntry 6}

-- // New Parameter : factory CRC
		psfactoryCRCValue          		OBJECT-TYPE
			   SYNTAX       		INTEGER
			   ACCESS           	read-only
			   STATUS           	mandatory
			   DESCRIPTION
			   "This object provides the CRC code for the Factory data."
			   ::= { gx2PsdcFactoryEntry 7}

-- // New Parameter : calculate CRC command
		pscalculateCRCValue          		OBJECT-TYPE
			   SYNTAX       		INTEGER
					    		{
							factory(1),
							na(2),
							alarm(3)
					    		}
			   ACCESS           	read-only
			   STATUS           	mandatory
			   DESCRIPTION
            "This object indicates which of the Emnums will have the CRC calculated.

            Calculate CRC command defintions as follows :
            0x00 : recalculate factory data CRC
            0x02 : recalculate alarm data CRC
            other values not defined"

			   ::= { gx2PsdcFactoryEntry 8}

-- // New Parameter : hour meter
		pshourMeterValue          		OBJECT-TYPE
			   SYNTAX       		INTEGER
			   ACCESS           	read-only
			   STATUS           	mandatory
			   DESCRIPTION
			   "This object provides the hour meter reading of the module."
			   ::= { gx2PsdcFactoryEntry 9}

-- // New Parameter : Flash program counter A
		psflashPrgCntAValue          		OBJECT-TYPE
			   SYNTAX       		INTEGER
			   ACCESS           	read-only
			   STATUS           	mandatory
			   DESCRIPTION
			   "This object provides the number of times Bank 1 flash has been
                      programmed."
			   ::= { gx2PsdcFactoryEntry 10}

-- // New Parameter : Flash program counter B
		psflashPrgCntBValue          		OBJECT-TYPE
			   SYNTAX       		INTEGER
			   ACCESS           	read-only
			   STATUS           	mandatory
			   DESCRIPTION
			   "This object provides the number of times Bank 1 flash has been
                      programmed."
			   ::= { gx2PsdcFactoryEntry 11}

-- // New Parameter : Firmware Rev Bank 0
		psflashBankARevValue          		OBJECT-TYPE
			   SYNTAX       		DisplayString (SIZE (0..80))
			   ACCESS           	read-only
			   STATUS           	mandatory
			   DESCRIPTION
             "This object provides the CRC code of bank 0.
            The value is best displayed in Hex format"
            ::= { gx2PsdcFactoryEntry 12}

-- // New Parameter : Firmware Rev Bank 1
		psflashBankBRevValue          		OBJECT-TYPE
			   SYNTAX       		DisplayString (SIZE (0..80))
			   ACCESS           	read-only
			   STATUS           	mandatory
			   DESCRIPTION
             "This object provides the CRC code of bank 1.
            The value is best displayed in Hex format"

			   ::= { gx2PsdcFactoryEntry 13}

            -- ************ Hold Time DATA ****************
		rxgx2PsdcHoldTimeTableIndex              OBJECT-TYPE
			   SYNTAX           INTEGER (1..4294967295)
			   ACCESS           read-only
			   STATUS           mandatory
			   DESCRIPTION
			   "The value of this object is the index of the data object."
			   ::= { gx2PsdcHoldTimeEntry 1}

		rxgx2PsdcHoldTimeSpecIndex              OBJECT-TYPE
			   SYNTAX           INTEGER (1..4294967295)
			   ACCESS           read-only
			   STATUS           mandatory
			   DESCRIPTION
			   "The value of this object identifies the index of the alarm object to be modified."
			   ::= { gx2PsdcHoldTimeEntry 2}

		rxgx2PsdcHoldTimeData          	OBJECT-TYPE
			   SYNTAX       		INTEGER
			   ACCESS           	read-write
			   STATUS           	mandatory
			   DESCRIPTION
			   "The value of this object provides access to the hold timers used 
			   to suppress nose on analog objects. This object is a 32 bit object. 
			   Validation data is entered into bytes zero and one of the object. 
			   Bytes three and four are used to entering the hold time for the 
			   specified alarm object. The Hold timer data ranges from 0 to 1300 seconds.
			   The index of this object corresponds to the alarm object to be modified. 
			   Alarm Hold timers correspond to the index of this object as follows:  
			   Index 1 = xxx, index 2 = xxxx, Index 3 = xxxx, 
			   The hold time is represented in seconds."
			   ::= { gx2PsdcHoldTimeEntry 3}




-- // Section: Traps
-- ****************************************************************
--
-- TRAP DEFINITIONS
--
--
-- Every trap generated by an HFC agents will include first 9 identical
-- fields. If particular variable is not supported in
-- particular TRAP-TYPE then default value will be returned.
--
-- DESCRIPTION will include explanation of use of generic
-- variables (trapAdditionalInfo******.)  If no
-- DESCRIPTION is given then generic variables will contain
-- default values.
--
-- *****************************************************************
-- **************************************************************************
--                          Power Supply Module traps
-- **************************************************************************
-- // Trap 1  : integer congif change
   trapPSDCConfigChangeInteger TRAP-TYPE
       ENTERPRISE gx2Psdc
       VARIABLES
	       {
		trapIdentifier,
		trapNetworkElemModelNumber,
		trapNetworkElemSerialNum,
		trapPerceivedSeverity,
		trapNetworkElemOperState,
		trapNetworkElemAlarmStatus,
		trapNetworkElemAdminState,
		trapNetworkElemAvailStatus,
		trapText,
		trapChangedObjectId,
		trapChangedValueInteger,
		trapNETrapLastTrapTimeStamp
	       }
       DESCRIPTION
	"This trap is issued if configuration of a single variable
	 with integer type was changed (via ANY interface).
	 TrapChangedValueInteger variable may contain current reading
	 of that variable.
	 trapPerceivedSeverity - 'indeterminate'"
  ::= 1

-- // Trap 2  : string config change
   trapPSDCConfigChangeDisplayString TRAP-TYPE
       ENTERPRISE gx2Psdc
       VARIABLES
	       {
		trapIdentifier,
		trapNetworkElemModelNumber,
		trapNetworkElemSerialNum,
		trapPerceivedSeverity,
		trapNetworkElemOperState,
		trapNetworkElemAlarmStatus,
		trapNetworkElemAdminState,
		trapNetworkElemAvailStatus,
		trapText,
		trapChangedObjectId,
		trapChangedValueDisplayString,
		trapNETrapLastTrapTimeStamp
	       }
       DESCRIPTION
	"This trap is issued if configuration of a single variable
	 with DispalayString type was changed (via ANY interface).
	 TrapChangedValueDisplayString variable may contain current reading
	 of that variable.
	 trapPerceivedSeverity - 'indeterminate'"
  ::= 2

-- // Trap 3  : Fan current
  trapPSDCFanCurrent TRAP-TYPE
	ENTERPRISE gx2Psdc
	VARIABLES
		{
		 trapIdentifier,
		 trapNetworkElemModelNumber,
		 trapNetworkElemSerialNum,
		 trapPerceivedSeverity,
		 trapNetworkElemOperState,
		 trapNetworkElemAlarmStatus,
		 trapNetworkElemAdminState,
		 trapNetworkElemAvailStatus,
		 trapText,
		 trapChangedObjectId,
		 trapChangedValueInteger,
		 trapNETrapLastTrapTimeStamp
		}
	DESCRIPTION
   "This trap is issued when a Fan Current event has occurred."
  ::= 3

-- // Trap 4  : 12 Volt
  trapPSDC12Volt TRAP-TYPE
	ENTERPRISE gx2Psdc
	VARIABLES
		{
		 trapIdentifier,
		 trapNetworkElemModelNumber,
		 trapNetworkElemSerialNum,
		 trapPerceivedSeverity,
		 trapNetworkElemOperState,
		 trapNetworkElemAlarmStatus,
		 trapNetworkElemAdminState,
		 trapNetworkElemAvailStatus,
		 trapText,
		 trapChangedObjectId,
		 trapChangedValueInteger,
		 trapNETrapLastTrapTimeStamp
		}
	DESCRIPTION
   "This trap is issued when the 12 Volts is in an alarm condition."
  ::= 4

-- // Trap 5  : 5 Volt
  trapPSDC5Volt TRAP-TYPE
	ENTERPRISE gx2Psdc
	VARIABLES
		{
		 trapIdentifier,
		 trapNetworkElemModelNumber,
		 trapNetworkElemSerialNum,
		 trapPerceivedSeverity,
		 trapNetworkElemOperState,
		 trapNetworkElemAlarmStatus,
		 trapNetworkElemAdminState,
		 trapNetworkElemAvailStatus,
		 trapText,
		 trapChangedObjectId,
		 trapChangedValueInteger,
		 trapNETrapLastTrapTimeStamp
		}
	DESCRIPTION
   "This trap is issued when the 5 Voltage is in an alarm condition."
  ::= 5

-- // Trap 6  : 3.7 Volt
  trapPSDC3Volt TRAP-TYPE
	ENTERPRISE gx2Psdc
	VARIABLES
		{
		 trapIdentifier,
		 trapNetworkElemModelNumber,
		 trapNetworkElemSerialNum,
		 trapPerceivedSeverity,
		 trapNetworkElemOperState,
		 trapNetworkElemAlarmStatus,
		 trapNetworkElemAdminState,
		 trapNetworkElemAvailStatus,
		 trapText,
		 trapChangedObjectId,
		 trapChangedValueInteger,
		 trapNETrapLastTrapTimeStamp
		}
	DESCRIPTION
   "This trap is issued when the 3.7 Voltage is in an alarm condition."
  ::= 6

-- // Trap 7  : Ambient Temperature
  trapPSDCAmbientTemp TRAP-TYPE
	ENTERPRISE gx2Psdc
	VARIABLES
		{
		 trapIdentifier,
		 trapNetworkElemModelNumber,
		 trapNetworkElemSerialNum,
		 trapPerceivedSeverity,
		 trapNetworkElemOperState,
		 trapNetworkElemAlarmStatus,
		 trapNetworkElemAdminState,
		 trapNetworkElemAvailStatus,
		 trapText,
		 trapChangedObjectId,
		 trapChangedValueInteger,
		 trapNETrapLastTrapTimeStamp
		}
	DESCRIPTION
   "This trap is issued when the Ambient Temperature is in an alarm condition."
  ::= 7

-- // Trap 8  : Heat Sink Temperature
  trapPSDCMainTemp
 TRAP-TYPE
	ENTERPRISE gx2Psdc
	VARIABLES
		{
		 trapIdentifier,
		 trapNetworkElemModelNumber,
		 trapNetworkElemSerialNum,
		 trapPerceivedSeverity,
		 trapNetworkElemOperState,
		 trapNetworkElemAlarmStatus,
		 trapNetworkElemAdminState,
		 trapNetworkElemAvailStatus,
		 trapText,
		 trapChangedObjectId,
		 trapChangedValueInteger,
		 trapNETrapLastTrapTimeStamp
		}
	DESCRIPTION
   "This trap is issued when the Main Temperature is in an alarm condition."
  ::= 8

-- // Trap 9  : 12 Anode Voltage
  trapPSDC12AnodeVolt TRAP-TYPE

	ENTERPRISE gx2Psdc
	VARIABLES
		{       
		 trapIdentifier,
		 trapNetworkElemModelNumber,
		 trapNetworkElemSerialNum,
		 trapPerceivedSeverity,
		 trapNetworkElemOperState,
		 trapNetworkElemAlarmStatus,  
		 trapNetworkElemAdminState,
		 trapNetworkElemAvailStatus,
		 trapText,
		 trapChangedObjectId,
		 trapChangedValueInteger,
		 trapNETrapLastTrapTimeStamp
		}
	DESCRIPTION
	"This trap is issued when the 12 Anode Voltage is in an alarm condition."

  ::= 9

-- // Trap 10  : 5 Anode Voltage
  trapPSDC5AnodeVolt TRAP-TYPE

	ENTERPRISE gx2Psdc
	VARIABLES
		{       
		 trapIdentifier,
		 trapNetworkElemModelNumber,
		 trapNetworkElemSerialNum,
		 trapPerceivedSeverity,
		 trapNetworkElemOperState,
		 trapNetworkElemAlarmStatus,  
		 trapNetworkElemAdminState,
		 trapNetworkElemAvailStatus,
		 trapText,
		 trapChangedObjectId,
		 trapChangedValueInteger,
		 trapNETrapLastTrapTimeStamp
		}
	DESCRIPTION
	"This trap is issued when the 5 Anode Voltage is in an alarm condition."
  ::= 10

-- // Trap 11  : 3.7 Anode Voltage
  trapPSDC3AnodeVolt TRAP-TYPE

	ENTERPRISE gx2Psdc
	VARIABLES
		{       
		 trapIdentifier,
		 trapNetworkElemModelNumber,
		 trapNetworkElemSerialNum,
		 trapPerceivedSeverity,
		 trapNetworkElemOperState,
		 trapNetworkElemAlarmStatus,  
		 trapNetworkElemAdminState,
		 trapNetworkElemAvailStatus,
		 trapText,
		 trapChangedObjectId,
		 trapChangedValueInteger,
		 trapNETrapLastTrapTimeStamp
		}
	DESCRIPTION
	"This trap is issued when the 3 Anode Voltage is in an alarm condition."
  ::= 11

-- // Trap 12 : EEPROM Checksum
  trapPSDCEEChksmAlarm TRAP-TYPE
	ENTERPRISE gx2Psdc
	VARIABLES
		{
		 trapIdentifier,
		 trapNetworkElemModelNumber,
		 trapNetworkElemSerialNum,
		 trapPerceivedSeverity,
		 trapNetworkElemOperState,
		 trapNetworkElemAlarmStatus,
		 trapNetworkElemAdminState,
		 trapNetworkElemAvailStatus,
		 trapText,
		 trapChangedObjectId,
		 trapChangedValueInteger,
		 trapNETrapLastTrapTimeStamp
		}
	DESCRIPTION
   "This trap is issued when the Power Supply EEPROM Factory data CRC fails."
  ::= 12

-- // Trap 13 : Flash Alarm
  trapPSDCFlashAlarm TRAP-TYPE
	ENTERPRISE gx2Psdc
	VARIABLES
		{
		 trapIdentifier,
		 trapNetworkElemModelNumber,
		 trapNetworkElemSerialNum,
		 trapPerceivedSeverity,
		 trapNetworkElemOperState,
		 trapNetworkElemAlarmStatus,
		 trapNetworkElemAdminState,
		 trapNetworkElemAvailStatus,
		 trapText,
		 trapChangedObjectId,
		 trapChangedValueInteger,
		 trapNETrapLastTrapTimeStamp
		}
	DESCRIPTION
   "This trap is issued when the embedded board flash has a problem."
  ::= 13

-- // Trap 14 : Boot Error
   trapPSDCBootAlarm TRAP-TYPE
   ENTERPRISE gx2Psdc
   VARIABLES
      {
       trapIdentifier,
       trapNetworkElemModelNumber,
       trapNetworkElemSerialNum,
       trapPerceivedSeverity,
       trapNetworkElemOperState,
       trapNetworkElemAlarmStatus,
       trapNetworkElemAdminState,
       trapNetworkElemAvailStatus,
       trapText,
       trapChangedObjectId,
       trapChangedValueInteger,
       trapNETrapLastTrapTimeStamp
      }
   DESCRIPTION
   "This trap is issued when the Module Boot from either bank fails."
  ::= 14

-- // Trap 15 : Alarm Reporting
	trapPSDCAlarmReportingStatus TRAP-TYPE
	ENTERPRISE gx2Psdc
	VARIABLES
		{       
		 trapIdentifier,
		 trapNetworkElemModelNumber,
		 trapNetworkElemSerialNum,
		 trapPerceivedSeverity,
		 trapNetworkElemOperState,
		 trapNetworkElemAlarmStatus,  
		 trapNetworkElemAdminState,
		 trapNetworkElemAvailStatus,
		 trapText,
		 trapChangedObjectId,
		 trapChangedValueInteger,
		 trapNETrapLastTrapTimeStamp
		}
	DESCRIPTION
	"This trap is issued when the Alarm reporting is turned off."
  ::= 15


-- // Trap 16 : Brick Type
   trapPSbrickType TRAP-TYPE
	ENTERPRISE gx2Psdc
	VARIABLES
		{
		 trapIdentifier,
		 trapNetworkElemModelNumber,
		 trapNetworkElemSerialNum,
		 trapPerceivedSeverity,
		 trapNetworkElemOperState,
		 trapNetworkElemAlarmStatus,
		 trapNetworkElemAdminState,
		 trapNetworkElemAvailStatus,
		 trapText,
		 trapChangedObjectId,
		 trapChangedValueInteger,
		 trapNETrapLastTrapTimeStamp
		}
	DESCRIPTION
   "This trap is issued when power supply brick type is not a valid type."
  ::= 16

-- // Trap 17 : Power supply failure
   trapPSsupplyFailure TRAP-TYPE
   ENTERPRISE gx2Psdc
   VARIABLES
      {
       trapIdentifier,
       trapNetworkElemModelNumber,
       trapNetworkElemSerialNum,
       trapPerceivedSeverity,
       trapNetworkElemOperState,
       trapNetworkElemAlarmStatus,
       trapNetworkElemAdminState,
       trapNetworkElemAvailStatus,
       trapText,
       trapChangedObjectId,
       trapChangedValueInteger,
       trapNETrapLastTrapTimeStamp
      }
   DESCRIPTION
   "This trap is issued when power supply fail condition occurs.
    (+12V , +5.1V, or _3.7V anode voltage out of spec.)"
  ::= 17

-- // Trap 18 : Alarm Checksum
  trapPSDCALARMChksmAlarm TRAP-TYPE
	ENTERPRISE gx2Psdc
	VARIABLES
		{
		 trapIdentifier,
		 trapNetworkElemModelNumber,
		 trapNetworkElemSerialNum,
		 trapPerceivedSeverity,
		 trapNetworkElemOperState,
		 trapNetworkElemAlarmStatus,
		 trapNetworkElemAdminState,
		 trapNetworkElemAvailStatus,
		 trapText,
		 trapChangedObjectId,
		 trapChangedValueInteger,
		 trapNETrapLastTrapTimeStamp
		}
	DESCRIPTION
   "This trap is issued when the Power Supply Alarm Data CRC check fails."
  ::= 18




  END
