ZTE-AN-VMAC-MIB DEFINITIONS ::= BEGIN

IMPORTS
    MODULE-IDENTITY, OBJECT-TYPE, Integer32         FROM SNMPv2-SMI
    MODULE-COMPLIANCE, OBJECT-GROUP                 FROM SNMPv2-CONF              
    RowStatus, MacAddress, DisplayString            FROM SNMPv2-TC
    zxAnServiceSecurity                             FROM ZTE-AN-SMI
    VlanId                                          FROM ZTE-AN-TC-MIB
    zxAnSubIfIndex                                  FROM ZTE-AN-IF-MIB
    ifIndex                                         FROM IF-MIB;
    
    zxAnVmacMib MODULE-IDENTITY
        LAST-UPDATED    "1205240000Z"  -- May 24, 2012
        ORGANIZATION    "ZTE Corporation"
        CONTACT-INFO    "Yang Xi   ZTE Corporation
                        Mail: yang.xi8@zte.com.cn
                        Tel : +86-21-68897487"
        DESCRIPTION     "The MIB module for the management of VMAC."
        REVISION        "1205240000Z"  -- May 24, 2012
        DESCRIPTION     "Initial version of this MIB module."
        ::= { zxAnServiceSecurity 58 }

--------------------------------------------------------------------------------
-- Following objects are defined.
-- 1. VMAC Global Objects
-- 2. VMAC VLAN Objects
-- 3. VMAC Interface Objects
-- 3.1 VMAC Interface Configuration Table
-- 3.2 VMAC Interface VLAN Translation Table
-- 3.3 VMAC Interface Reserved MAC Table
-- 3.4 VMAC Interface Translation Table
-- 4. VMAC Profile Objects
-- 4.1 VMAC Profile Table
-- 4.2 VMAC Profile Item Table
--------------------------------------------------------------------------------

    zxAnVmacGlobalObjects    OBJECT IDENTIFIER ::= { zxAnVmacMib 1 }
    zxAnVmacObjects          OBJECT IDENTIFIER ::= { zxAnVmacMib 2 }
    zxAnVmacVlanObjects      OBJECT IDENTIFIER ::= { zxAnVmacObjects 1 }    
    zxAnVmacIfObjects        OBJECT IDENTIFIER ::= { zxAnVmacObjects 2 }
    zxAnVmacProfileObjects   OBJECT IDENTIFIER ::= { zxAnVmacObjects 3 }

--------------------------------------------------------------------------------
-- 1. VMAC Global Objects
--------------------------------------------------------------------------------

    zxAnVmacAccessNodeId  OBJECT-TYPE
        SYNTAX      Integer32(0..65535)
        MAX-ACCESS  read-write
        STATUS      current
        DESCRIPTION
            "Access node ID."
        ::= { zxAnVmacGlobalObjects 1 }

    zxAnVmacConfProfileName  OBJECT-TYPE
        SYNTAX      DisplayString(SIZE(0..32))
        MAX-ACCESS  read-write
        STATUS      current
        DESCRIPTION
            "Configured profile name.
             Empty string means no profile is configured."
        ::= { zxAnVmacGlobalObjects 3 }

--------------------------------------------------------------------------------
-- 2. VMAC VLAN Objects
--------------------------------------------------------------------------------

    zxAnVmacVlanTable OBJECT-TYPE
        SYNTAX      SEQUENCE OF ZxAnVmacVlanEntry
        MAX-ACCESS  not-accessible
        STATUS      current
        DESCRIPTION
            "Virtual MAC address VLAN table."
        ::= { zxAnVmacVlanObjects 2 }
    
    zxAnVmacVlanEntry OBJECT-TYPE
        SYNTAX      ZxAnVmacVlanEntry
        MAX-ACCESS  not-accessible
        STATUS      current
        DESCRIPTION
            "Virtual MAC address VLAN entry."
        INDEX  { zxAnVmacVid }
        ::= { zxAnVmacVlanTable 1 }
    
    ZxAnVmacVlanEntry ::= SEQUENCE {
        zxAnVmacVid                VlanId, 
        zxAnVmacVlanTranslateMode  INTEGER,
        zxAnVmacVlanRowStatus      RowStatus
        }
    
    zxAnVmacVid OBJECT-TYPE
        SYNTAX      VlanId
        MAX-ACCESS  not-accessible
        STATUS      current
        DESCRIPTION
            "VLAN ID."
        ::= { zxAnVmacVlanEntry 1 }
    
    zxAnVmacVlanTranslateMode OBJECT-TYPE
        SYNTAX      INTEGER {
            oneToOne(1),
            nToOne(2) -- not support
        }
        MAX-ACCESS  read-only
        STATUS      current
        DESCRIPTION
            "The virtual MAC address translation mode."
        ::= { zxAnVmacVlanEntry 2 }

    zxAnVmacVlanRowStatus OBJECT-TYPE
        SYNTAX      RowStatus
        MAX-ACCESS  read-create
        STATUS      current
        DESCRIPTION
            "The status of this conceptual row.
            
            The supported actions of this conceptual row only include:
            'createAndGo' and 'destroy'.

            To create a row in this table, a manager must set this object to 
            createAndGo(4), and must comply with the multi-variables binding 
            rule described in zxAnVmacVlanEntry.
    
            To delete a row in this table, a manager must set this object to 
            destroy(6). 
             
            To get this object, the agent always returns active(1)."
        ::= { zxAnVmacVlanEntry 50 }

------------------------------------------------------------------------------
-- 3. VMAC Interface Objects
------------------------------------------------------------------------------   
        
------------------------------------------------------------------------------
-- 3.4 VMAC Interface Translation Table
------------------------------------------------------------------------------  
    zxAnVmacIfTranslateTable OBJECT-TYPE
        SYNTAX      SEQUENCE OF ZxAnVmacIfTranslateEntry
        MAX-ACCESS  not-accessible
        STATUS      current
        DESCRIPTION
            "Interface virtual MAC address translation table."
        ::= { zxAnVmacIfObjects 5 }
        
    zxAnVmacIfTranslateEntry OBJECT-TYPE
        SYNTAX      ZxAnVmacIfTranslateEntry
        MAX-ACCESS  not-accessible
        STATUS      current
        DESCRIPTION
            "Interface virtual MAC address translation entry."
        INDEX   
        { 
            ifIndex,
            zxAnSubIfIndex,
            zxAnVmacIfTranslateSrcMac
        }
        ::= { zxAnVmacIfTranslateTable 1}
    
    ZxAnVmacIfTranslateEntry ::= SEQUENCE {
        zxAnVmacIfTranslateSrcMac    MacAddress,
        zxAnVmacIfTranslateVmac      MacAddress
     }
         
    zxAnVmacIfTranslateSrcMac OBJECT-TYPE
        SYNTAX      MacAddress
        MAX-ACCESS  not-accessible
        STATUS      current
        DESCRIPTION
            "Source MAC address."
        ::= { zxAnVmacIfTranslateEntry 1 } 
           
    zxAnVmacIfTranslateVmac OBJECT-TYPE
        SYNTAX      MacAddress
        MAX-ACCESS  read-only
        STATUS      current
        DESCRIPTION
            "Virtual MAC address."
        ::= { zxAnVmacIfTranslateEntry 2 }    
        
--------------------------------------------------------------------------------
-- 4. VMAC Profile Objects
--------------------------------------------------------------------------------

--------------------------------------------------------------------------------
-- 4.1 VMAC Profile Table
--------------------------------------------------------------------------------

    zxAnVmacProfileTable OBJECT-TYPE
        SYNTAX      SEQUENCE OF ZxAnVmacProfileEntry
        MAX-ACCESS  not-accessible
        STATUS      current
        DESCRIPTION
            "Virtual MAC address profile table."
        ::= { zxAnVmacProfileObjects 2 }
        
    zxAnVmacProfileEntry OBJECT-TYPE
        SYNTAX      ZxAnVmacProfileEntry
        MAX-ACCESS  not-accessible
        STATUS      current
        DESCRIPTION
            "Virtual MAC address profile entry."
        INDEX  { zxAnVmacProfileName }
        ::= { zxAnVmacProfileTable 1}
    
    ZxAnVmacProfileEntry ::= SEQUENCE {
        zxAnVmacProfileName        DisplayString, 
        zxAnVmacProfileRowStatus   RowStatus      
    }
    
    zxAnVmacProfileName OBJECT-TYPE
        SYNTAX      DisplayString(SIZE(1..32))
        MAX-ACCESS  not-accessible
        STATUS      current
        DESCRIPTION  
            "Virtual MAC address profile name."
        ::= {zxAnVmacProfileEntry 1}  
        
    zxAnVmacProfileRowStatus OBJECT-TYPE
        SYNTAX      RowStatus
        MAX-ACCESS  read-create
        STATUS      current
        DESCRIPTION
            "The status of this conceptual row.
            
            The supported actions of this conceptual row only include:
            'createAndGo' and 'destroy'.

            To create a row in this table, a manager must set this object to 
            createAndGo(4), and must comply with the multi-variables binding 
            rule described in zxAnVmacProfileEntry.
    
            To delete a row in this table, a manager must set this object to 
            destroy(6). 
             
            To get this object, the agent always returns active(1)."
        ::= { zxAnVmacProfileEntry 50 }  
        
--------------------------------------------------------------------------------
-- 4.2 VMAC Profile Item Table
--------------------------------------------------------------------------------   

    zxAnVmacProfileItemTable OBJECT-TYPE
        SYNTAX      SEQUENCE OF ZxAnVmacProfileItemEntry
        MAX-ACCESS  not-accessible
        STATUS      current
        DESCRIPTION
            "Virtual MAC address profile item table."
        ::= { zxAnVmacProfileObjects 3 }
        
    zxAnVmacProfileItemEntry OBJECT-TYPE
        SYNTAX      ZxAnVmacProfileItemEntry
        MAX-ACCESS  not-accessible
        STATUS      current
        DESCRIPTION
            "Virtual MAC address profile item entry."
        INDEX  { zxAnVmacProfileName, zxAnVmacProfileItemIndex }
        ::= { zxAnVmacProfileItemTable 1}
    
    ZxAnVmacProfileItemEntry ::= SEQUENCE {
        zxAnVmacProfileItemIndex         Integer32,
        zxAnVmacProfileItemAlgorithm     INTEGER,
        zxAnVmacProfileItemCtrlByteValue Integer32,
        zxAnVmacProfileItemCircuitIdType INTEGER,
        zxAnVmacProfileItemBitWidth      Integer32,
        zxAnVmacProfileItemRowStatus     RowStatus
    }
    
    zxAnVmacProfileItemIndex OBJECT-TYPE
        SYNTAX      Integer32(1..32)
        MAX-ACCESS  not-accessible
        STATUS      current
        DESCRIPTION
            "Virtual MAC address profile item index."
        ::= { zxAnVmacProfileItemEntry 1 }    
        
    zxAnVmacProfileItemAlgorithm  OBJECT-TYPE
        SYNTAX      INTEGER {
            ctrlByte(1),
            circuitId(2),
            addressSpace(3)
        }
        MAX-ACCESS  read-create
        STATUS      current
        DESCRIPTION
            "VMAC generation algorithms.
             
             ctrlByte(1) - Generate control byte segment of the VMAC packet with
                           zxAnVmacProfileItemCtrlByteValue and 
                           zxAnVmacProfileItemBitWidth.
             circuitId(2) - Generate circuit ID segments of the VMAC packet with
                            zxAnVmacProfileItemVariableType and 
                            zxAnVmacProfileItemBitWidth.
             addressSpace(3) - Generate address space of the VMAC packet with 
                               zxAnVmacProfileItemBitWidth."
        ::= { zxAnVmacProfileItemEntry 2 }      

    zxAnVmacProfileItemCtrlByteValue OBJECT-TYPE
        SYNTAX      Integer32(0..65535)
        MAX-ACCESS  read-create
        STATUS      current
        DESCRIPTION
            "Virtual MAC profile constant value.
             
             If zxAnVmacProfileItemType is not ctrlByte(1), this object should 
             be set '0'."
        ::= { zxAnVmacProfileItemEntry 3 }
    
    zxAnVmacProfileItemCircuitIdType OBJECT-TYPE
        SYNTAX      INTEGER {
            unused(1),
            accessNodeId(2),
            chassis(3),
            rack(4),
            frame(5),
            slot(6),
            subSlot(7),
            port(8),
            onu(9)
        }
        MAX-ACCESS  read-create
        STATUS      current
        DESCRIPTION
            "Virtual MAC profile circuit ID type.
             
             If zxAnVmacProfileItemType is not circuitId(2), this object should 
             be set unused(1)."
        ::= { zxAnVmacProfileItemEntry 4 }  
        
    zxAnVmacProfileItemBitWidth OBJECT-TYPE
        SYNTAX      Integer32(1..48)
        MAX-ACCESS  read-create
        STATUS      current
        DESCRIPTION
            "Bit width. If zxAnVmacProfileItemAlgorithm is addressSpace(3), the max value of this object is 3."
        ::= { zxAnVmacProfileItemEntry 5 }
        
    zxAnVmacProfileItemRowStatus OBJECT-TYPE
        SYNTAX      RowStatus
        MAX-ACCESS  read-create
        STATUS      current
        DESCRIPTION
            "The status of this conceptual row.
            
            The supported actions of this conceptual row only include:
            'createAndGo' and 'destroy'.

            To create a row in this table, a manager must set this object to 
            createAndGo(4), and must comply with the multi-variables binding 
            rule described in zxAnVmacProfileItemEntry.
    
            To delete a row in this table, a manager must set this object to 
            destroy(6). 
             
            To get this object, the agent always returns active(1)."
        ::= { zxAnVmacProfileItemEntry 50 }
END
