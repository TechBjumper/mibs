-- file automatically created


TELDAT-TRAP-SDLC-MIB DEFINITIONS ::= BEGIN


IMPORTS
	MODULE-IDENTITY,OBJECT-TYPE,OBJECT-IDENTITY,NOTIFICATION-TYPE,Integer32,IpAddress
		FROM SNMPv2-SMI
	DisplayString
		FROM SNMPv2-TC
	telEventTraps
		FROM TELDAT-MIB;


sdlcTrapsMIB MODULE-IDENTITY
    LAST-UPDATED "201401200930Z"
    ORGANIZATION "Teldat, S.A."
    CONTACT-INFO 
        "Teldat, S.A.
        Customer Service

        Postal: Parque Tecnologico de Madrid
                Tres Cantos 28760
                Madrid, SPAIN

        Tel.: +34 918 076 565

        http://www.teldat.com"
    DESCRIPTION
        "This Module Information Base file is defined for managing received
        SNMP notifications generated by the SDLC event subsystem."
    REVISION "201401200930Z"
    DESCRIPTION "Initial implementation"
        ::= { telEventTraps 90 }


sdlcEventsGroup	OBJECT IDENTIFIER	::= { sdlcTrapsMIB 1 }

sdlcNotifications	OBJECT IDENTIFIER	::= { sdlcTrapsMIB 2 }
sdlcNotificationsPrefix	OBJECT IDENTIFIER	::= { sdlcNotifications 0 }

sdlcEventObjects1 OBJECT-IDENTITY
    STATUS current
    DESCRIPTION
        "Event SDLC.1
        DLSw SDLC has been initialized for operation over the serial
        device and is now available for use in the router."
    ::= { sdlcEventsGroup 1 }

sdlc1-interface OBJECT-TYPE
    SYNTAX DisplayString
    MAX-ACCESS accessible-for-notify
    STATUS current
    DESCRIPTION
        "Parameter 'interface' in event SDLC.1"
    ::= { sdlcEventObjects1 1 }

sdlcEventObjects2 OBJECT-IDENTITY
    STATUS current
    DESCRIPTION
        "Event SDLC.2
        An open was attempted on an SDLC station, but a configuration
        record was not defined via the ADD STATION command. The station will be
        opened using default configuration value. This station will be
        listed in the monitor process LIST STATION ALL command. An
        asterisk * next to the station address signifies that a
        default configuration is in use."
    ::= { sdlcEventsGroup 2 }

sdlc2-address OBJECT-TYPE
    SYNTAX Integer32
    MAX-ACCESS accessible-for-notify
    STATUS current
    DESCRIPTION
        "Parameter 'address' in event SDLC.2"
    ::= { sdlcEventObjects2 1 }

sdlc2-interface OBJECT-TYPE
    SYNTAX DisplayString
    MAX-ACCESS accessible-for-notify
    STATUS current
    DESCRIPTION
        "Parameter 'interface' in event SDLC.2"
    ::= { sdlcEventObjects2 2 }

sdlcEventObjects3 OBJECT-IDENTITY
    STATUS current
    DESCRIPTION
        "Event SDLC.3
        There is currently no memory available to copy user data to
        SDLC. Another attempt will be made at a later time."
    ::= { sdlcEventsGroup 3 }

sdlc3-interface OBJECT-TYPE
    SYNTAX DisplayString
    MAX-ACCESS accessible-for-notify
    STATUS current
    DESCRIPTION
        "Parameter 'interface' in event SDLC.3"
    ::= { sdlcEventObjects3 1 }

sdlcEventObjects4 OBJECT-IDENTITY
    STATUS current
    DESCRIPTION
        "Event SDLC.4
        A frame was received on an interface that is not yet owned by
        an SDLC client. All packets received are dropped until an
        SDLC client opens the port for use."
    ::= { sdlcEventsGroup 4 }

sdlc4-interface OBJECT-TYPE
    SYNTAX DisplayString
    MAX-ACCESS accessible-for-notify
    STATUS current
    DESCRIPTION
        "Parameter 'interface' in event SDLC.4"
    ::= { sdlcEventObjects4 1 }

sdlcEventObjects5 OBJECT-IDENTITY
    STATUS current
    DESCRIPTION
        "Event SDLC.5
        An incoming packet was dropped due to no SDLC receive credit
        or a temporary memory shortage."
    ::= { sdlcEventsGroup 5 }

sdlc5-interface OBJECT-TYPE
    SYNTAX DisplayString
    MAX-ACCESS accessible-for-notify
    STATUS current
    DESCRIPTION
        "Parameter 'interface' in event SDLC.5"
    ::= { sdlcEventObjects5 1 }

sdlcEventObjects6 OBJECT-IDENTITY
    STATUS current
    DESCRIPTION
        "Event SDLC.6
        real-sdlc-in received a packet with I-ERR set."
    ::= { sdlcEventsGroup 6 }

sdlc6-interface OBJECT-TYPE
    SYNTAX DisplayString
    MAX-ACCESS accessible-for-notify
    STATUS current
    DESCRIPTION
        "Parameter 'interface' in event SDLC.6"
    ::= { sdlcEventObjects6 1 }

sdlcEventObjects7 OBJECT-IDENTITY
    STATUS current
    DESCRIPTION
        "Event SDLC.7
        The call to netsend() failed while trying to send a frame from SDLC."
    ::= { sdlcEventsGroup 7 }

sdlc7-interface OBJECT-TYPE
    SYNTAX DisplayString
    MAX-ACCESS accessible-for-notify
    STATUS current
    DESCRIPTION
        "Parameter 'interface' in event SDLC.7"
    ::= { sdlcEventObjects7 1 }

sdlc7-status OBJECT-TYPE
    SYNTAX Integer32
    MAX-ACCESS accessible-for-notify
    STATUS current
    DESCRIPTION
        "Parameter 'status' in event SDLC.7"
    ::= { sdlcEventObjects7 2 }

sdlcEventObjects8 OBJECT-IDENTITY
    STATUS current
    DESCRIPTION
        "Event SDLC.8
        The router transmitted an SDLC frame. This is the entire frame,
        including the SDLC header. The router logs all transmitted SDLC
        frames with this message. To log only transmitted SDLC I-frames,
        use SDLC-53."
    ::= { sdlcEventsGroup 8 }

sdlc8-count OBJECT-TYPE
    SYNTAX Integer32
    MAX-ACCESS accessible-for-notify
    STATUS current
    DESCRIPTION
        "Parameter 'count' in event SDLC.8"
    ::= { sdlcEventObjects8 1 }

sdlc8-address OBJECT-TYPE
    SYNTAX Integer32
    MAX-ACCESS accessible-for-notify
    STATUS current
    DESCRIPTION
        "Parameter 'address' in event SDLC.8"
    ::= { sdlcEventObjects8 2 }

sdlc8-interface OBJECT-TYPE
    SYNTAX DisplayString
    MAX-ACCESS accessible-for-notify
    STATUS current
    DESCRIPTION
        "Parameter 'interface' in event SDLC.8"
    ::= { sdlcEventObjects8 3 }

sdlc8-octets OBJECT-TYPE
    SYNTAX DisplayString
    MAX-ACCESS accessible-for-notify
    STATUS current
    DESCRIPTION
        "Parameter 'octets' in event SDLC.8"
    ::= { sdlcEventObjects8 4 }

sdlcEventObjects9 OBJECT-IDENTITY
    STATUS current
    DESCRIPTION
        "Event SDLC.9
        The router received an SDLC frame. This is the entire frame, including
        the SDLC header. The router logs all received SDLC frames with this
        message. To log only received SDLC I-frames, use SDLC-52."
    ::= { sdlcEventsGroup 9 }

sdlc9-count OBJECT-TYPE
    SYNTAX Integer32
    MAX-ACCESS accessible-for-notify
    STATUS current
    DESCRIPTION
        "Parameter 'count' in event SDLC.9"
    ::= { sdlcEventObjects9 1 }

sdlc9-address OBJECT-TYPE
    SYNTAX Integer32
    MAX-ACCESS accessible-for-notify
    STATUS current
    DESCRIPTION
        "Parameter 'address' in event SDLC.9"
    ::= { sdlcEventObjects9 2 }

sdlc9-interface OBJECT-TYPE
    SYNTAX DisplayString
    MAX-ACCESS accessible-for-notify
    STATUS current
    DESCRIPTION
        "Parameter 'interface' in event SDLC.9"
    ::= { sdlcEventObjects9 3 }

sdlc9-octets OBJECT-TYPE
    SYNTAX DisplayString
    MAX-ACCESS accessible-for-notify
    STATUS current
    DESCRIPTION
        "Parameter 'octets' in event SDLC.9"
    ::= { sdlcEventObjects9 4 }

sdlcEventObjects10 OBJECT-IDENTITY
    STATUS current
    DESCRIPTION
        "Event SDLC.10
        An entity in the router has attached to the interface and can
        now use SDLC services."
    ::= { sdlcEventsGroup 10 }

sdlc10-interface OBJECT-TYPE
    SYNTAX DisplayString
    MAX-ACCESS accessible-for-notify
    STATUS current
    DESCRIPTION
        "Parameter 'interface' in event SDLC.10"
    ::= { sdlcEventObjects10 1 }

sdlcEventObjects11 OBJECT-IDENTITY
    STATUS current
    DESCRIPTION
        "Event SDLC.11
        An entity in the router is no longer using SDLC services
        on this interface."
    ::= { sdlcEventsGroup 11 }

sdlc11-interface OBJECT-TYPE
    SYNTAX DisplayString
    MAX-ACCESS accessible-for-notify
    STATUS current
    DESCRIPTION
        "Parameter 'interface' in event SDLC.11"
    ::= { sdlcEventObjects11 1 }

sdlcEventObjects12 OBJECT-IDENTITY
    STATUS current
    DESCRIPTION
        "Event SDLC.12
        An interface signal has changed state. Note: an unwieldy number
        of these messages will be generated when the interface is
        operating in half duplex mode."
    ::= { sdlcEventsGroup 12 }

sdlc12-exception OBJECT-TYPE
    SYNTAX DisplayString
    MAX-ACCESS accessible-for-notify
    STATUS current
    DESCRIPTION
        "Parameter 'exception' in event SDLC.12"
    ::= { sdlcEventObjects12 1 }

sdlc12-interface OBJECT-TYPE
    SYNTAX DisplayString
    MAX-ACCESS accessible-for-notify
    STATUS current
    DESCRIPTION
        "Parameter 'interface' in event SDLC.12"
    ::= { sdlcEventObjects12 2 }

sdlcEventObjects13 OBJECT-IDENTITY
    STATUS current
    DESCRIPTION
        "Event SDLC.13
        The SDLC link is now operating in Normal Response Mode,
        meaning that a SDLC connection is now in progress."
    ::= { sdlcEventsGroup 13 }

sdlc13-address OBJECT-TYPE
    SYNTAX Integer32
    MAX-ACCESS accessible-for-notify
    STATUS current
    DESCRIPTION
        "Parameter 'address' in event SDLC.13"
    ::= { sdlcEventObjects13 1 }

sdlc13-interface OBJECT-TYPE
    SYNTAX DisplayString
    MAX-ACCESS accessible-for-notify
    STATUS current
    DESCRIPTION
        "Parameter 'interface' in event SDLC.13"
    ::= { sdlcEventObjects13 2 }

sdlcEventObjects14 OBJECT-IDENTITY
    STATUS current
    DESCRIPTION
        "Event SDLC.14
        An attempt by the router to connect to a remote link station
        has been refused."
    ::= { sdlcEventsGroup 14 }

sdlc14-address OBJECT-TYPE
    SYNTAX Integer32
    MAX-ACCESS accessible-for-notify
    STATUS current
    DESCRIPTION
        "Parameter 'address' in event SDLC.14"
    ::= { sdlcEventObjects14 1 }

sdlc14-interface OBJECT-TYPE
    SYNTAX DisplayString
    MAX-ACCESS accessible-for-notify
    STATUS current
    DESCRIPTION
        "Parameter 'interface' in event SDLC.14"
    ::= { sdlcEventObjects14 2 }

sdlcEventObjects15 OBJECT-IDENTITY
    STATUS current
    DESCRIPTION
        "Event SDLC.15
        The SDLC link is now operating in Normal Disconnect Mode,
        meaning that a SDLC connection has been terminated in an
        orderly fashion."
    ::= { sdlcEventsGroup 15 }

sdlc15-address OBJECT-TYPE
    SYNTAX Integer32
    MAX-ACCESS accessible-for-notify
    STATUS current
    DESCRIPTION
        "Parameter 'address' in event SDLC.15"
    ::= { sdlcEventObjects15 1 }

sdlc15-interface OBJECT-TYPE
    SYNTAX DisplayString
    MAX-ACCESS accessible-for-notify
    STATUS current
    DESCRIPTION
        "Parameter 'interface' in event SDLC.15"
    ::= { sdlcEventObjects15 2 }

sdlcEventObjects16 OBJECT-IDENTITY
    STATUS current
    DESCRIPTION
        "Event SDLC.16
        The SDLC protocol has been initialized."
    ::= { sdlcEventsGroup 16 }

sdlc16-address OBJECT-TYPE
    SYNTAX Integer32
    MAX-ACCESS accessible-for-notify
    STATUS current
    DESCRIPTION
        "Parameter 'address' in event SDLC.16"
    ::= { sdlcEventObjects16 1 }

sdlc16-exception OBJECT-TYPE
    SYNTAX Integer32
    MAX-ACCESS accessible-for-notify
    STATUS current
    DESCRIPTION
        "Parameter 'exception' in event SDLC.16"
    ::= { sdlcEventObjects16 2 }

sdlc16-interface OBJECT-TYPE
    SYNTAX DisplayString
    MAX-ACCESS accessible-for-notify
    STATUS current
    DESCRIPTION
        "Parameter 'interface' in event SDLC.16"
    ::= { sdlcEventObjects16 3 }

sdlcEventObjects17 OBJECT-IDENTITY
    STATUS current
    DESCRIPTION
        "Event SDLC.17
        SDLC received a frame to the broadcast address on a multipoint line.
        The frame was dropped."
    ::= { sdlcEventsGroup 17 }

sdlc17-interface OBJECT-TYPE
    SYNTAX DisplayString
    MAX-ACCESS accessible-for-notify
    STATUS current
    DESCRIPTION
        "Parameter 'interface' in event SDLC.17"
    ::= { sdlcEventObjects17 1 }

sdlcEventObjects18 OBJECT-IDENTITY
    STATUS current
    DESCRIPTION
        "Event SDLC.18
        SDLC could not be initialized because there is no SDLC link
        configuration for this interface."
    ::= { sdlcEventsGroup 18 }

sdlc18-interface OBJECT-TYPE
    SYNTAX DisplayString
    MAX-ACCESS accessible-for-notify
    STATUS current
    DESCRIPTION
        "Parameter 'interface' in event SDLC.18"
    ::= { sdlcEventObjects18 1 }

sdlcEventObjects19 OBJECT-IDENTITY
    STATUS current
    DESCRIPTION
        "Event SDLC.19
        SDLC could not control one or more signals on the interface. This
        could occur if you attempt to run SDLC over an unsupported interface."
    ::= { sdlcEventsGroup 19 }

sdlc19-interface OBJECT-TYPE
    SYNTAX DisplayString
    MAX-ACCESS accessible-for-notify
    STATUS current
    DESCRIPTION
        "Parameter 'interface' in event SDLC.19"
    ::= { sdlcEventObjects19 1 }

sdlc19-reason OBJECT-TYPE
    SYNTAX DisplayString
    MAX-ACCESS accessible-for-notify
    STATUS current
    DESCRIPTION
        "Parameter 'reason' in event SDLC.19"
    ::= { sdlcEventObjects19 2 }

sdlcEventObjects20 OBJECT-IDENTITY
    STATUS current
    DESCRIPTION
        "Event SDLC.20
        SDLC detected a fault on the link, and terminated all active SDLC
        connections on the link. This is usually due to a loss of DSR, CTS, or
        DCD on a full-duplex line, or loss of DSR on a half-duplex line."
    ::= { sdlcEventsGroup 20 }

sdlc20-interface OBJECT-TYPE
    SYNTAX DisplayString
    MAX-ACCESS accessible-for-notify
    STATUS current
    DESCRIPTION
        "Parameter 'interface' in event SDLC.20"
    ::= { sdlcEventObjects20 1 }

sdlc20-address OBJECT-TYPE
    SYNTAX Integer32
    MAX-ACCESS accessible-for-notify
    STATUS current
    DESCRIPTION
        "Parameter 'address' in event SDLC.20"
    ::= { sdlcEventObjects20 2 }

sdlcEventObjects21 OBJECT-IDENTITY
    STATUS current
    DESCRIPTION
        "Event SDLC.21
        SDLC has received more than the number of frames configured as
        the RECEIVE WINDOW before SDLC could respond."
    ::= { sdlcEventsGroup 21 }

sdlc21-interface OBJECT-TYPE
    SYNTAX DisplayString
    MAX-ACCESS accessible-for-notify
    STATUS current
    DESCRIPTION
        "Parameter 'interface' in event SDLC.21"
    ::= { sdlcEventObjects21 1 }

sdlc21-address OBJECT-TYPE
    SYNTAX Integer32
    MAX-ACCESS accessible-for-notify
    STATUS current
    DESCRIPTION
        "Parameter 'address' in event SDLC.21"
    ::= { sdlcEventObjects21 2 }

sdlcEventObjects22 OBJECT-IDENTITY
    STATUS current
    DESCRIPTION
        "Event SDLC.22
        The router detected a SDLC protocol error. As a result, the router
        terminated the SDLC connection."
    ::= { sdlcEventsGroup 22 }

sdlc22-interface OBJECT-TYPE
    SYNTAX DisplayString
    MAX-ACCESS accessible-for-notify
    STATUS current
    DESCRIPTION
        "Parameter 'interface' in event SDLC.22"
    ::= { sdlcEventObjects22 1 }

sdlc22-address OBJECT-TYPE
    SYNTAX Integer32
    MAX-ACCESS accessible-for-notify
    STATUS current
    DESCRIPTION
        "Parameter 'address' in event SDLC.22"
    ::= { sdlcEventObjects22 2 }

sdlcEventObjects23 OBJECT-IDENTITY
    STATUS current
    DESCRIPTION
        "Event SDLC.23
        The remote link station is not responding to XID frames the router sent."
    ::= { sdlcEventsGroup 23 }

sdlc23-interface OBJECT-TYPE
    SYNTAX DisplayString
    MAX-ACCESS accessible-for-notify
    STATUS current
    DESCRIPTION
        "Parameter 'interface' in event SDLC.23"
    ::= { sdlcEventObjects23 1 }

sdlc23-address OBJECT-TYPE
    SYNTAX Integer32
    MAX-ACCESS accessible-for-notify
    STATUS current
    DESCRIPTION
        "Parameter 'address' in event SDLC.23"
    ::= { sdlcEventObjects23 2 }

sdlcEventObjects24 OBJECT-IDENTITY
    STATUS current
    DESCRIPTION
        "Event SDLC.24
        The remote link station is not responding to TEST frames the router
        sent."
    ::= { sdlcEventsGroup 24 }

sdlc24-interface OBJECT-TYPE
    SYNTAX DisplayString
    MAX-ACCESS accessible-for-notify
    STATUS current
    DESCRIPTION
        "Parameter 'interface' in event SDLC.24"
    ::= { sdlcEventObjects24 1 }

sdlc24-address OBJECT-TYPE
    SYNTAX Integer32
    MAX-ACCESS accessible-for-notify
    STATUS current
    DESCRIPTION
        "Parameter 'address' in event SDLC.24"
    ::= { sdlcEventObjects24 2 }

sdlcEventObjects25 OBJECT-IDENTITY
    STATUS current
    DESCRIPTION
        "Event SDLC.25
        The remote link station is not responding to SNRM frames the router
        sent. The connection attempt has failed."
    ::= { sdlcEventsGroup 25 }

sdlc25-interface OBJECT-TYPE
    SYNTAX DisplayString
    MAX-ACCESS accessible-for-notify
    STATUS current
    DESCRIPTION
        "Parameter 'interface' in event SDLC.25"
    ::= { sdlcEventObjects25 1 }

sdlc25-address OBJECT-TYPE
    SYNTAX Integer32
    MAX-ACCESS accessible-for-notify
    STATUS current
    DESCRIPTION
        "Parameter 'address' in event SDLC.25"
    ::= { sdlcEventObjects25 2 }

sdlcEventObjects26 OBJECT-IDENTITY
    STATUS current
    DESCRIPTION
        "Event SDLC.26
        The remote link station is not responding to polls (RR or RNR)
        sent by the router. As a result, the router terminated the connection."
    ::= { sdlcEventsGroup 26 }

sdlc26-interface OBJECT-TYPE
    SYNTAX DisplayString
    MAX-ACCESS accessible-for-notify
    STATUS current
    DESCRIPTION
        "Parameter 'interface' in event SDLC.26"
    ::= { sdlcEventObjects26 1 }

sdlc26-address OBJECT-TYPE
    SYNTAX Integer32
    MAX-ACCESS accessible-for-notify
    STATUS current
    DESCRIPTION
        "Parameter 'address' in event SDLC.26"
    ::= { sdlcEventObjects26 2 }

sdlcEventObjects27 OBJECT-IDENTITY
    STATUS current
    DESCRIPTION
        "Event SDLC.27
        SDLC has received a Frame Reject (FRMR) frame indicating that
        the remote link station received a frame with an invalid
        control field."
    ::= { sdlcEventsGroup 27 }

sdlc27-interface OBJECT-TYPE
    SYNTAX DisplayString
    MAX-ACCESS accessible-for-notify
    STATUS current
    DESCRIPTION
        "Parameter 'interface' in event SDLC.27"
    ::= { sdlcEventObjects27 1 }

sdlc27-address OBJECT-TYPE
    SYNTAX Integer32
    MAX-ACCESS accessible-for-notify
    STATUS current
    DESCRIPTION
        "Parameter 'address' in event SDLC.27"
    ::= { sdlcEventObjects27 2 }

sdlcEventObjects28 OBJECT-IDENTITY
    STATUS current
    DESCRIPTION
        "Event SDLC.28
        SDLC has received a Frame Reject (FRMR) frame indicating that
        the remote link station received a frame that was too short."
    ::= { sdlcEventsGroup 28 }

sdlc28-interface OBJECT-TYPE
    SYNTAX DisplayString
    MAX-ACCESS accessible-for-notify
    STATUS current
    DESCRIPTION
        "Parameter 'interface' in event SDLC.28"
    ::= { sdlcEventObjects28 1 }

sdlc28-address OBJECT-TYPE
    SYNTAX Integer32
    MAX-ACCESS accessible-for-notify
    STATUS current
    DESCRIPTION
        "Parameter 'address' in event SDLC.28"
    ::= { sdlcEventObjects28 2 }

sdlcEventObjects29 OBJECT-IDENTITY
    STATUS current
    DESCRIPTION
        "Event SDLC.29
        SDLC has received a Frame Reject (FRMR) frame indicating that
        the remote link station received a frame that was too long."
    ::= { sdlcEventsGroup 29 }

sdlc29-interface OBJECT-TYPE
    SYNTAX DisplayString
    MAX-ACCESS accessible-for-notify
    STATUS current
    DESCRIPTION
        "Parameter 'interface' in event SDLC.29"
    ::= { sdlcEventObjects29 1 }

sdlc29-address OBJECT-TYPE
    SYNTAX Integer32
    MAX-ACCESS accessible-for-notify
    STATUS current
    DESCRIPTION
        "Parameter 'address' in event SDLC.29"
    ::= { sdlcEventObjects29 2 }

sdlcEventObjects30 OBJECT-IDENTITY
    STATUS current
    DESCRIPTION
        "Event SDLC.30
        SDLC has received a Frame Reject (FRMR) frame indicating that
        the remote link station received a frame with an invalid N(r)
        in the control field."
    ::= { sdlcEventsGroup 30 }

sdlc30-interface OBJECT-TYPE
    SYNTAX DisplayString
    MAX-ACCESS accessible-for-notify
    STATUS current
    DESCRIPTION
        "Parameter 'interface' in event SDLC.30"
    ::= { sdlcEventObjects30 1 }

sdlc30-address OBJECT-TYPE
    SYNTAX Integer32
    MAX-ACCESS accessible-for-notify
    STATUS current
    DESCRIPTION
        "Parameter 'address' in event SDLC.30"
    ::= { sdlcEventObjects30 2 }

sdlcEventObjects31 OBJECT-IDENTITY
    STATUS current
    DESCRIPTION
        "Event SDLC.31
        SDLC has received a Frame Reject (FRMR) frame indicating that
        the remote link station received an I-frame with no data in
        the I field."
    ::= { sdlcEventsGroup 31 }

sdlc31-interface OBJECT-TYPE
    SYNTAX DisplayString
    MAX-ACCESS accessible-for-notify
    STATUS current
    DESCRIPTION
        "Parameter 'interface' in event SDLC.31"
    ::= { sdlcEventObjects31 1 }

sdlc31-address OBJECT-TYPE
    SYNTAX Integer32
    MAX-ACCESS accessible-for-notify
    STATUS current
    DESCRIPTION
        "Parameter 'address' in event SDLC.31"
    ::= { sdlcEventObjects31 2 }

sdlcEventObjects32 OBJECT-IDENTITY
    STATUS current
    DESCRIPTION
        "Event SDLC.32
        SDLC has received a frame with an invalid control field."
    ::= { sdlcEventsGroup 32 }

sdlc32-interface OBJECT-TYPE
    SYNTAX DisplayString
    MAX-ACCESS accessible-for-notify
    STATUS current
    DESCRIPTION
        "Parameter 'interface' in event SDLC.32"
    ::= { sdlcEventObjects32 1 }

sdlc32-address OBJECT-TYPE
    SYNTAX Integer32
    MAX-ACCESS accessible-for-notify
    STATUS current
    DESCRIPTION
        "Parameter 'address' in event SDLC.32"
    ::= { sdlcEventObjects32 2 }

sdlcEventObjects33 OBJECT-IDENTITY
    STATUS current
    DESCRIPTION
        "Event SDLC.33
        SDLC has received a frame that was too short."
    ::= { sdlcEventsGroup 33 }

sdlc33-interface OBJECT-TYPE
    SYNTAX DisplayString
    MAX-ACCESS accessible-for-notify
    STATUS current
    DESCRIPTION
        "Parameter 'interface' in event SDLC.33"
    ::= { sdlcEventObjects33 1 }

sdlc33-address OBJECT-TYPE
    SYNTAX Integer32
    MAX-ACCESS accessible-for-notify
    STATUS current
    DESCRIPTION
        "Parameter 'address' in event SDLC.33"
    ::= { sdlcEventObjects33 2 }

sdlcEventObjects34 OBJECT-IDENTITY
    STATUS current
    DESCRIPTION
        "Event SDLC.34
        SDLC has received a frame that was too long."
    ::= { sdlcEventsGroup 34 }

sdlc34-interface OBJECT-TYPE
    SYNTAX DisplayString
    MAX-ACCESS accessible-for-notify
    STATUS current
    DESCRIPTION
        "Parameter 'interface' in event SDLC.34"
    ::= { sdlcEventObjects34 1 }

sdlc34-address OBJECT-TYPE
    SYNTAX Integer32
    MAX-ACCESS accessible-for-notify
    STATUS current
    DESCRIPTION
        "Parameter 'address' in event SDLC.34"
    ::= { sdlcEventObjects34 2 }

sdlcEventObjects35 OBJECT-IDENTITY
    STATUS current
    DESCRIPTION
        "Event SDLC.35
        SDLC has received a frame with an invalid N(r) in the control field."
    ::= { sdlcEventsGroup 35 }

sdlc35-interface OBJECT-TYPE
    SYNTAX DisplayString
    MAX-ACCESS accessible-for-notify
    STATUS current
    DESCRIPTION
        "Parameter 'interface' in event SDLC.35"
    ::= { sdlcEventObjects35 1 }

sdlc35-address OBJECT-TYPE
    SYNTAX Integer32
    MAX-ACCESS accessible-for-notify
    STATUS current
    DESCRIPTION
        "Parameter 'address' in event SDLC.35"
    ::= { sdlcEventObjects35 2 }

sdlcEventObjects36 OBJECT-IDENTITY
    STATUS current
    DESCRIPTION
        "Event SDLC.36
        SDLC received a Disconnected Mode (DM) frame. A remote secondary link
        station sent the frame to indicate that it accepted a previously
        received DISC frame. The link disconnection is now complete."
    ::= { sdlcEventsGroup 36 }

sdlc36-interface OBJECT-TYPE
    SYNTAX DisplayString
    MAX-ACCESS accessible-for-notify
    STATUS current
    DESCRIPTION
        "Parameter 'interface' in event SDLC.36"
    ::= { sdlcEventObjects36 1 }

sdlc36-address OBJECT-TYPE
    SYNTAX Integer32
    MAX-ACCESS accessible-for-notify
    STATUS current
    DESCRIPTION
        "Parameter 'address' in event SDLC.36"
    ::= { sdlcEventObjects36 2 }

sdlcEventObjects37 OBJECT-IDENTITY
    STATUS current
    DESCRIPTION
        "Event SDLC.37
        SDLC received a Request Disconnect (RD) frame. The SDLC client should
        respond to this by sending a Disconnect (DISC) frame."
    ::= { sdlcEventsGroup 37 }

sdlc37-interface OBJECT-TYPE
    SYNTAX DisplayString
    MAX-ACCESS accessible-for-notify
    STATUS current
    DESCRIPTION
        "Parameter 'interface' in event SDLC.37"
    ::= { sdlcEventObjects37 1 }

sdlc37-address OBJECT-TYPE
    SYNTAX Integer32
    MAX-ACCESS accessible-for-notify
    STATUS current
    DESCRIPTION
        "Parameter 'address' in event SDLC.37"
    ::= { sdlcEventObjects37 2 }

sdlcEventObjects38 OBJECT-IDENTITY
    STATUS current
    DESCRIPTION
        "Event SDLC.38
        SDLC received a Request Initialization Mode (RIM) frame.
        The SDLC client should respond to this by sending a
        Set Initialization Mode (SIM) frame."
    ::= { sdlcEventsGroup 38 }

sdlc38-interface OBJECT-TYPE
    SYNTAX DisplayString
    MAX-ACCESS accessible-for-notify
    STATUS current
    DESCRIPTION
        "Parameter 'interface' in event SDLC.38"
    ::= { sdlcEventObjects38 1 }

sdlc38-address OBJECT-TYPE
    SYNTAX Integer32
    MAX-ACCESS accessible-for-notify
    STATUS current
    DESCRIPTION
        "Parameter 'address' in event SDLC.38"
    ::= { sdlcEventObjects38 2 }

sdlcEventObjects39 OBJECT-IDENTITY
    STATUS current
    DESCRIPTION
        "Event SDLC.39
        Inactivity detection."
    ::= { sdlcEventsGroup 39 }

sdlc39-interface OBJECT-TYPE
    SYNTAX DisplayString
    MAX-ACCESS accessible-for-notify
    STATUS current
    DESCRIPTION
        "Parameter 'interface' in event SDLC.39"
    ::= { sdlcEventObjects39 1 }

sdlc39-address OBJECT-TYPE
    SYNTAX Integer32
    MAX-ACCESS accessible-for-notify
    STATUS current
    DESCRIPTION
        "Parameter 'address' in event SDLC.39"
    ::= { sdlcEventObjects39 2 }

sdlcEventObjects40 OBJECT-IDENTITY
    STATUS current
    DESCRIPTION
        "Event SDLC.40
        SDLC entered a frame reject (FRMR) state because it
        received a frame with an invalid control field."
    ::= { sdlcEventsGroup 40 }

sdlc40-interface OBJECT-TYPE
    SYNTAX DisplayString
    MAX-ACCESS accessible-for-notify
    STATUS current
    DESCRIPTION
        "Parameter 'interface' in event SDLC.40"
    ::= { sdlcEventObjects40 1 }

sdlc40-address OBJECT-TYPE
    SYNTAX Integer32
    MAX-ACCESS accessible-for-notify
    STATUS current
    DESCRIPTION
        "Parameter 'address' in event SDLC.40"
    ::= { sdlcEventObjects40 2 }

sdlcEventObjects41 OBJECT-IDENTITY
    STATUS current
    DESCRIPTION
        "Event SDLC.41
        SDLC entered a frame reject (FRMR) state because it
        received a frame that was too short."
    ::= { sdlcEventsGroup 41 }

sdlc41-interface OBJECT-TYPE
    SYNTAX DisplayString
    MAX-ACCESS accessible-for-notify
    STATUS current
    DESCRIPTION
        "Parameter 'interface' in event SDLC.41"
    ::= { sdlcEventObjects41 1 }

sdlc41-address OBJECT-TYPE
    SYNTAX Integer32
    MAX-ACCESS accessible-for-notify
    STATUS current
    DESCRIPTION
        "Parameter 'address' in event SDLC.41"
    ::= { sdlcEventObjects41 2 }

sdlcEventObjects42 OBJECT-IDENTITY
    STATUS current
    DESCRIPTION
        "Event SDLC.42
        SDLC entered a frame reject (FRMR) state because it
        received a frame that was too long."
    ::= { sdlcEventsGroup 42 }

sdlc42-interface OBJECT-TYPE
    SYNTAX DisplayString
    MAX-ACCESS accessible-for-notify
    STATUS current
    DESCRIPTION
        "Parameter 'interface' in event SDLC.42"
    ::= { sdlcEventObjects42 1 }

sdlc42-address OBJECT-TYPE
    SYNTAX Integer32
    MAX-ACCESS accessible-for-notify
    STATUS current
    DESCRIPTION
        "Parameter 'address' in event SDLC.42"
    ::= { sdlcEventObjects42 2 }

sdlcEventObjects43 OBJECT-IDENTITY
    STATUS current
    DESCRIPTION
        "Event SDLC.43
        SDLC entered a frame reject (FRMR) state because it
        received a frame with an invalid N(r) in the control field."
    ::= { sdlcEventsGroup 43 }

sdlc43-interface OBJECT-TYPE
    SYNTAX DisplayString
    MAX-ACCESS accessible-for-notify
    STATUS current
    DESCRIPTION
        "Parameter 'interface' in event SDLC.43"
    ::= { sdlcEventObjects43 1 }

sdlc43-address OBJECT-TYPE
    SYNTAX Integer32
    MAX-ACCESS accessible-for-notify
    STATUS current
    DESCRIPTION
        "Parameter 'address' in event SDLC.43"
    ::= { sdlcEventObjects43 2 }

sdlcEventObjects44 OBJECT-IDENTITY
    STATUS current
    DESCRIPTION
        "Event SDLC.44
        SDLC received a SNRM while in Normal Response Mode (NRM) state."
    ::= { sdlcEventsGroup 44 }

sdlc44-interface OBJECT-TYPE
    SYNTAX DisplayString
    MAX-ACCESS accessible-for-notify
    STATUS current
    DESCRIPTION
        "Parameter 'interface' in event SDLC.44"
    ::= { sdlcEventObjects44 1 }

sdlc44-address OBJECT-TYPE
    SYNTAX Integer32
    MAX-ACCESS accessible-for-notify
    STATUS current
    DESCRIPTION
        "Parameter 'address' in event SDLC.44"
    ::= { sdlcEventObjects44 2 }

sdlcEventObjects45 OBJECT-IDENTITY
    STATUS current
    DESCRIPTION
        "Event SDLC.45
        The user disabled the interface from the SDLC console. All current
        connections are terminated."
    ::= { sdlcEventsGroup 45 }

sdlc45-interface OBJECT-TYPE
    SYNTAX DisplayString
    MAX-ACCESS accessible-for-notify
    STATUS current
    DESCRIPTION
        "Parameter 'interface' in event SDLC.45"
    ::= { sdlcEventObjects45 1 }

sdlc45-address OBJECT-TYPE
    SYNTAX Integer32
    MAX-ACCESS accessible-for-notify
    STATUS current
    DESCRIPTION
        "Parameter 'address' in event SDLC.45"
    ::= { sdlcEventObjects45 2 }

sdlcEventObjects46 OBJECT-IDENTITY
    STATUS current
    DESCRIPTION
        "Event SDLC.46
        The user enabled the interface from the SDLC console."
    ::= { sdlcEventsGroup 46 }

sdlc46-interface OBJECT-TYPE
    SYNTAX DisplayString
    MAX-ACCESS accessible-for-notify
    STATUS current
    DESCRIPTION
        "Parameter 'interface' in event SDLC.46"
    ::= { sdlcEventObjects46 1 }

sdlc46-address OBJECT-TYPE
    SYNTAX Integer32
    MAX-ACCESS accessible-for-notify
    STATUS current
    DESCRIPTION
        "Parameter 'address' in event SDLC.46"
    ::= { sdlcEventObjects46 2 }

sdlcEventObjects47 OBJECT-IDENTITY
    STATUS current
    DESCRIPTION
        "Event SDLC.47
        The interface has been closed by SDLC. SDLC is no longer running over
        this interface."
    ::= { sdlcEventsGroup 47 }

sdlc47-interface OBJECT-TYPE
    SYNTAX DisplayString
    MAX-ACCESS accessible-for-notify
    STATUS current
    DESCRIPTION
        "Parameter 'interface' in event SDLC.47"
    ::= { sdlcEventObjects47 1 }

sdlcEventObjects48 OBJECT-IDENTITY
    STATUS current
    DESCRIPTION
        "Event SDLC.48
        The user disabled a remote link station on this interface from
        the SDLC console. Any existing connection was terminated."
    ::= { sdlcEventsGroup 48 }

sdlc48-interface OBJECT-TYPE
    SYNTAX DisplayString
    MAX-ACCESS accessible-for-notify
    STATUS current
    DESCRIPTION
        "Parameter 'interface' in event SDLC.48"
    ::= { sdlcEventObjects48 1 }

sdlc48-address OBJECT-TYPE
    SYNTAX Integer32
    MAX-ACCESS accessible-for-notify
    STATUS current
    DESCRIPTION
        "Parameter 'address' in event SDLC.48"
    ::= { sdlcEventObjects48 2 }

sdlcEventObjects49 OBJECT-IDENTITY
    STATUS current
    DESCRIPTION
        "Event SDLC.49
        The user enabled a remote link station has been enabled on this
        interface from the SDLC console."
    ::= { sdlcEventsGroup 49 }

sdlc49-interface OBJECT-TYPE
    SYNTAX DisplayString
    MAX-ACCESS accessible-for-notify
    STATUS current
    DESCRIPTION
        "Parameter 'interface' in event SDLC.49"
    ::= { sdlcEventObjects49 1 }

sdlc49-address OBJECT-TYPE
    SYNTAX Integer32
    MAX-ACCESS accessible-for-notify
    STATUS current
    DESCRIPTION
        "Parameter 'address' in event SDLC.49"
    ::= { sdlcEventObjects49 2 }

sdlcEventObjects50 OBJECT-IDENTITY
    STATUS current
    DESCRIPTION
        "Event SDLC.50
        The router received an Unnumbered Information (UI) frame on this
        interface."
    ::= { sdlcEventsGroup 50 }

sdlc50-interface OBJECT-TYPE
    SYNTAX DisplayString
    MAX-ACCESS accessible-for-notify
    STATUS current
    DESCRIPTION
        "Parameter 'interface' in event SDLC.50"
    ::= { sdlcEventObjects50 1 }

sdlc50-address OBJECT-TYPE
    SYNTAX Integer32
    MAX-ACCESS accessible-for-notify
    STATUS current
    DESCRIPTION
        "Parameter 'address' in event SDLC.50"
    ::= { sdlcEventObjects50 2 }

sdlc50-octets OBJECT-TYPE
    SYNTAX DisplayString
    MAX-ACCESS accessible-for-notify
    STATUS current
    DESCRIPTION
        "Parameter 'octets' in event SDLC.50"
    ::= { sdlcEventObjects50 3 }

sdlcEventObjects51 OBJECT-IDENTITY
    STATUS current
    DESCRIPTION
        "Event SDLC.51
        The router transmitted an Unnumbered Information (UI) frame on this
        interface."
    ::= { sdlcEventsGroup 51 }

sdlc51-interface OBJECT-TYPE
    SYNTAX DisplayString
    MAX-ACCESS accessible-for-notify
    STATUS current
    DESCRIPTION
        "Parameter 'interface' in event SDLC.51"
    ::= { sdlcEventObjects51 1 }

sdlc51-address OBJECT-TYPE
    SYNTAX Integer32
    MAX-ACCESS accessible-for-notify
    STATUS current
    DESCRIPTION
        "Parameter 'address' in event SDLC.51"
    ::= { sdlcEventObjects51 2 }

sdlc51-octets OBJECT-TYPE
    SYNTAX DisplayString
    MAX-ACCESS accessible-for-notify
    STATUS current
    DESCRIPTION
        "Parameter 'octets' in event SDLC.51"
    ::= { sdlcEventObjects51 3 }

sdlcEventObjects52 OBJECT-IDENTITY
    STATUS current
    DESCRIPTION
        "Event SDLC.52
        The router received an Information (I) frame on this interface.
        To log all received SDLC frames, use SDLC-9."
    ::= { sdlcEventsGroup 52 }

sdlc52-interface OBJECT-TYPE
    SYNTAX DisplayString
    MAX-ACCESS accessible-for-notify
    STATUS current
    DESCRIPTION
        "Parameter 'interface' in event SDLC.52"
    ::= { sdlcEventObjects52 1 }

sdlc52-address OBJECT-TYPE
    SYNTAX Integer32
    MAX-ACCESS accessible-for-notify
    STATUS current
    DESCRIPTION
        "Parameter 'address' in event SDLC.52"
    ::= { sdlcEventObjects52 2 }

sdlc52-byte-count OBJECT-TYPE
    SYNTAX Integer32
    MAX-ACCESS accessible-for-notify
    STATUS current
    DESCRIPTION
        "Parameter 'byte-count' in event SDLC.52"
    ::= { sdlcEventObjects52 3 }

sdlc52-octets OBJECT-TYPE
    SYNTAX DisplayString
    MAX-ACCESS accessible-for-notify
    STATUS current
    DESCRIPTION
        "Parameter 'octets' in event SDLC.52"
    ::= { sdlcEventObjects52 4 }

sdlcEventObjects53 OBJECT-IDENTITY
    STATUS current
    DESCRIPTION
        "Event SDLC.53
        The router transmitted an Information (I) frame has been transmitted
        on this interface. To log all received SDLC frames, use SDLC-8."
    ::= { sdlcEventsGroup 53 }

sdlc53-interface OBJECT-TYPE
    SYNTAX DisplayString
    MAX-ACCESS accessible-for-notify
    STATUS current
    DESCRIPTION
        "Parameter 'interface' in event SDLC.53"
    ::= { sdlcEventObjects53 1 }

sdlc53-address OBJECT-TYPE
    SYNTAX Integer32
    MAX-ACCESS accessible-for-notify
    STATUS current
    DESCRIPTION
        "Parameter 'address' in event SDLC.53"
    ::= { sdlcEventObjects53 2 }

sdlc53-byte-count OBJECT-TYPE
    SYNTAX Integer32
    MAX-ACCESS accessible-for-notify
    STATUS current
    DESCRIPTION
        "Parameter 'byte-count' in event SDLC.53"
    ::= { sdlcEventObjects53 3 }

sdlc53-octets OBJECT-TYPE
    SYNTAX DisplayString
    MAX-ACCESS accessible-for-notify
    STATUS current
    DESCRIPTION
        "Parameter 'octets' in event SDLC.53"
    ::= { sdlcEventObjects53 4 }

sdlcEventObjects54 OBJECT-IDENTITY
    STATUS current
    DESCRIPTION
        "Event SDLC.54
        The max BTU size configured for a remote link station exceeds that
        defined for the link. The router adjusted the value for the remote link
        station temporarily. To avoid this message in the future, change
        the max BTU size with the SET REMOTE MAX-PACKET command."
    ::= { sdlcEventsGroup 54 }

sdlc54-interface OBJECT-TYPE
    SYNTAX DisplayString
    MAX-ACCESS accessible-for-notify
    STATUS current
    DESCRIPTION
        "Parameter 'interface' in event SDLC.54"
    ::= { sdlcEventObjects54 1 }

sdlc54-address OBJECT-TYPE
    SYNTAX Integer32
    MAX-ACCESS accessible-for-notify
    STATUS current
    DESCRIPTION
        "Parameter 'address' in event SDLC.54"
    ::= { sdlcEventObjects54 2 }

sdlc54-oldBTUSize OBJECT-TYPE
    SYNTAX Integer32
    MAX-ACCESS accessible-for-notify
    STATUS current
    DESCRIPTION
        "Parameter 'oldBTUSize' in event SDLC.54"
    ::= { sdlcEventObjects54 3 }

sdlc54-newBTUSize OBJECT-TYPE
    SYNTAX Integer32
    MAX-ACCESS accessible-for-notify
    STATUS current
    DESCRIPTION
        "Parameter 'newBTUSize' in event SDLC.54"
    ::= { sdlcEventObjects54 4 }

sdlcEventObjects55 OBJECT-IDENTITY
    STATUS current
    DESCRIPTION
        "Event SDLC.55
        The modulo for this link has been changed by the user, rendering the
        window sizes for all pre-defined remote link stations invalid.
        The window size has been temporarily adjusted. When a link is
        configured for mod-8, the valid window sizes are 0 to 7. When the link
        is configured for mod-128, the valid window sizes are 8 to 128.
        To avoid this message in the future, change the receive window size
        with the 'SET REMOTE RECEIVE-WINDOW' command."
    ::= { sdlcEventsGroup 55 }

sdlc55-interface OBJECT-TYPE
    SYNTAX DisplayString
    MAX-ACCESS accessible-for-notify
    STATUS current
    DESCRIPTION
        "Parameter 'interface' in event SDLC.55"
    ::= { sdlcEventObjects55 1 }

sdlc55-address OBJECT-TYPE
    SYNTAX Integer32
    MAX-ACCESS accessible-for-notify
    STATUS current
    DESCRIPTION
        "Parameter 'address' in event SDLC.55"
    ::= { sdlcEventObjects55 2 }

sdlc55-oldRxWindow OBJECT-TYPE
    SYNTAX Integer32
    MAX-ACCESS accessible-for-notify
    STATUS current
    DESCRIPTION
        "Parameter 'oldRxWindow' in event SDLC.55"
    ::= { sdlcEventObjects55 3 }

sdlc55-newRxWindow OBJECT-TYPE
    SYNTAX Integer32
    MAX-ACCESS accessible-for-notify
    STATUS current
    DESCRIPTION
        "Parameter 'newRxWindow' in event SDLC.55"
    ::= { sdlcEventObjects55 4 }

sdlcEventObjects56 OBJECT-IDENTITY
    STATUS current
    DESCRIPTION
        "Event SDLC.56
        The modulo for this link has been changed by the user, rendering the
        window sizes for all pre-defined remote link stations invalid.
        The window size has been temporarily adjusted. When a link is
        configured for mod-8, the valid window sizes are 0 to 7. When the link
        is configured for mod-128, the valid window sizes are 8 to 128.
        To avoid this message in the future, change the transmit window size
        with the 'SET REMOTE TRANSMIT-WINDOW' command."
    ::= { sdlcEventsGroup 56 }

sdlc56-interface OBJECT-TYPE
    SYNTAX DisplayString
    MAX-ACCESS accessible-for-notify
    STATUS current
    DESCRIPTION
        "Parameter 'interface' in event SDLC.56"
    ::= { sdlcEventObjects56 1 }

sdlc56-address OBJECT-TYPE
    SYNTAX Integer32
    MAX-ACCESS accessible-for-notify
    STATUS current
    DESCRIPTION
        "Parameter 'address' in event SDLC.56"
    ::= { sdlcEventObjects56 2 }

sdlc56-oldTxWindow OBJECT-TYPE
    SYNTAX Integer32
    MAX-ACCESS accessible-for-notify
    STATUS current
    DESCRIPTION
        "Parameter 'oldTxWindow' in event SDLC.56"
    ::= { sdlcEventObjects56 3 }

sdlc56-newTxWindow OBJECT-TYPE
    SYNTAX Integer32
    MAX-ACCESS accessible-for-notify
    STATUS current
    DESCRIPTION
        "Parameter 'newTxWindow' in event SDLC.56"
    ::= { sdlcEventObjects56 4 }

sdlcEventObjects57 OBJECT-IDENTITY
    STATUS current
    DESCRIPTION
        "Event SDLC.57
        The link configuration was somehow corrupted, possibly due to
        a software upgrade. A default link configuration has been created.
        Before operating SDLC, review the newly-created configuration and
        adjust as necessary."
    ::= { sdlcEventsGroup 57 }

sdlc57-interface OBJECT-TYPE
    SYNTAX DisplayString
    MAX-ACCESS accessible-for-notify
    STATUS current
    DESCRIPTION
        "Parameter 'interface' in event SDLC.57"
    ::= { sdlcEventObjects57 1 }

sdlcEventObjects58 OBJECT-IDENTITY
    STATUS current
    DESCRIPTION
        "Event SDLC.58
        An invalid XID/TEST timeout value was detected in the link
        configuration, possibly due to a software upgrade. It has been
        temporarily changed to a valid value. To avoid this message in
        the future, set the XID/TEST timeout from the SDLC config prompt
        for this interface."
    ::= { sdlcEventsGroup 58 }

sdlc58-interface OBJECT-TYPE
    SYNTAX DisplayString
    MAX-ACCESS accessible-for-notify
    STATUS current
    DESCRIPTION
        "Parameter 'interface' in event SDLC.58"
    ::= { sdlcEventObjects58 1 }

sdlcEventObjects59 OBJECT-IDENTITY
    STATUS current
    DESCRIPTION
        "Event SDLC.59
        An invalid XID/TEST retry value was detected in the link configuration,
        possibly due to a software upgrade. It has been temporarily changed to
        a valid value. To avoid this message in the future, set the XID/TEST
        retry count from the SDLC config prompt for this interface."
    ::= { sdlcEventsGroup 59 }

sdlc59-interface OBJECT-TYPE
    SYNTAX DisplayString
    MAX-ACCESS accessible-for-notify
    STATUS current
    DESCRIPTION
        "Parameter 'interface' in event SDLC.59"
    ::= { sdlcEventObjects59 1 }

sdlcEventObjects60 OBJECT-IDENTITY
    STATUS current
    DESCRIPTION
        "Event SDLC.60
        An invalid SNRM timeout value was detected in the link configuration,
        possibly due to a software upgrade. It has been temporarily changed to
        a valid value. To avoid this message in the future, set the
        SNRM timeout from the SDLC config prompt for this interface."
    ::= { sdlcEventsGroup 60 }

sdlc60-interface OBJECT-TYPE
    SYNTAX DisplayString
    MAX-ACCESS accessible-for-notify
    STATUS current
    DESCRIPTION
        "Parameter 'interface' in event SDLC.60"
    ::= { sdlcEventObjects60 1 }

sdlcEventObjects61 OBJECT-IDENTITY
    STATUS current
    DESCRIPTION
        "Event SDLC.61
        An invalid SNRM retry value was detected in the link configuration,
        possibly due to a software upgrade. It has been temporarily changed to
        a valid value. To avoid this message in the future, set the
        SNRM retry count from the SDLC config prompt for this interface."
    ::= { sdlcEventsGroup 61 }

sdlc61-interface OBJECT-TYPE
    SYNTAX DisplayString
    MAX-ACCESS accessible-for-notify
    STATUS current
    DESCRIPTION
        "Parameter 'interface' in event SDLC.61"
    ::= { sdlcEventObjects61 1 }

sdlcEventObjects62 OBJECT-IDENTITY
    STATUS current
    DESCRIPTION
        "Event SDLC.62
        An invalid POLL timeout value was detected in the link configuration,
        possibly due to a software upgrade. It has been temporarily changed to
        a valid value. To avoid this message in the future, set the
        POLL timeout from the SDLC config prompt for this interface."
    ::= { sdlcEventsGroup 62 }

sdlc62-interface OBJECT-TYPE
    SYNTAX DisplayString
    MAX-ACCESS accessible-for-notify
    STATUS current
    DESCRIPTION
        "Parameter 'interface' in event SDLC.62"
    ::= { sdlcEventObjects62 1 }

sdlcEventObjects63 OBJECT-IDENTITY
    STATUS current
    DESCRIPTION
        "Event SDLC.63
        An invalid inter-POLL delay value was detected in the link
        configuration, possibly due to a software upgrade. It has been
        temporarily changed to a valid value. To avoid this message in the
        future, set the inter-POLL delay from the SDLC config prompt for this
        interface."
    ::= { sdlcEventsGroup 63 }

sdlc63-interface OBJECT-TYPE
    SYNTAX DisplayString
    MAX-ACCESS accessible-for-notify
    STATUS current
    DESCRIPTION
        "Parameter 'interface' in event SDLC.63"
    ::= { sdlcEventObjects63 1 }

sdlcEventObjects64 OBJECT-IDENTITY
    STATUS current
    DESCRIPTION
        "Event SDLC.64
        An invalid POLL retry value was detected in the link configuration,
        possibly due to a software upgrade. It has been temporarily changed to
        a valid value. To avoid this message in the future, set
        the POLL retry count from the SDLC config prompt for this interface."
    ::= { sdlcEventsGroup 64 }

sdlc64-interface OBJECT-TYPE
    SYNTAX DisplayString
    MAX-ACCESS accessible-for-notify
    STATUS current
    DESCRIPTION
        "Parameter 'interface' in event SDLC.64"
    ::= { sdlcEventObjects64 1 }

sdlcEventObjects65 OBJECT-IDENTITY
    STATUS current
    DESCRIPTION
        "Event SDLC.65
        An invalid inactivity timeout value was detected in the link
        configuration, possibly due to a software upgrade. It has been
        temporarily changed to a valid value. To avoid this message in the
        future, set the inactivity timeout from the SDLC config prompt for this
        interface."
    ::= { sdlcEventsGroup 65 }

sdlc65-interface OBJECT-TYPE
    SYNTAX DisplayString
    MAX-ACCESS accessible-for-notify
    STATUS current
    DESCRIPTION
        "Parameter 'interface' in event SDLC.65"
    ::= { sdlcEventObjects65 1 }

sdlcEventObjects66 OBJECT-IDENTITY
    STATUS current
    DESCRIPTION
        "Event SDLC.66
        An invalid RTS hold value was detected in the link configuration,
        possibly due to a software upgrade. It has been temporarily changed to
        a valid value. To avoid this message in the future, set the RTS hold
        value from the SDLC config prompt for this interface."
    ::= { sdlcEventsGroup 66 }

sdlc66-interface OBJECT-TYPE
    SYNTAX DisplayString
    MAX-ACCESS accessible-for-notify
    STATUS current
    DESCRIPTION
        "Parameter 'interface' in event SDLC.66"
    ::= { sdlcEventObjects66 1 }

sdlcEventObjects67 OBJECT-IDENTITY
    STATUS current
    DESCRIPTION
        "Event SDLC.67
        An invalid maximum frame size value was detected in the link
        configuration, possibly due to a software upgrade. It has been
        temporarily changed to a valid value. To avoid this message in the
        future, set the maximum frame size from the SDLC config prompt for
        this interface."
    ::= { sdlcEventsGroup 67 }

sdlc67-interface OBJECT-TYPE
    SYNTAX DisplayString
    MAX-ACCESS accessible-for-notify
    STATUS current
    DESCRIPTION
        "Parameter 'interface' in event SDLC.67"
    ::= { sdlcEventObjects67 1 }

sdlcEventObjects68 OBJECT-IDENTITY
    STATUS current
    DESCRIPTION
        "Event SDLC.68
        The link counters have been reset from the SDLC console."
    ::= { sdlcEventsGroup 68 }

sdlc68-interface OBJECT-TYPE
    SYNTAX DisplayString
    MAX-ACCESS accessible-for-notify
    STATUS current
    DESCRIPTION
        "Parameter 'interface' in event SDLC.68"
    ::= { sdlcEventObjects68 1 }

sdlcEventObjects69 OBJECT-IDENTITY
    STATUS current
    DESCRIPTION
        "Event SDLC.69
        The link counters could not be reset from the SDLC console.
        This is usually a temporary condition. Retry the operation."
    ::= { sdlcEventsGroup 69 }

sdlc69-interface OBJECT-TYPE
    SYNTAX DisplayString
    MAX-ACCESS accessible-for-notify
    STATUS current
    DESCRIPTION
        "Parameter 'interface' in event SDLC.69"
    ::= { sdlcEventObjects69 1 }

sdlcEventObjects70 OBJECT-IDENTITY
    STATUS current
    DESCRIPTION
        "Event SDLC.70
        The user reset the counters for a remote secondary station
        from the SDLC console."
    ::= { sdlcEventsGroup 70 }

sdlc70-interface OBJECT-TYPE
    SYNTAX DisplayString
    MAX-ACCESS accessible-for-notify
    STATUS current
    DESCRIPTION
        "Parameter 'interface' in event SDLC.70"
    ::= { sdlcEventObjects70 1 }

sdlc70-address OBJECT-TYPE
    SYNTAX Integer32
    MAX-ACCESS accessible-for-notify
    STATUS current
    DESCRIPTION
        "Parameter 'address' in event SDLC.70"
    ::= { sdlcEventObjects70 2 }

sdlcEventObjects71 OBJECT-IDENTITY
    STATUS current
    DESCRIPTION
        "Event SDLC.71
        The user could not reset the counters for a remote secondary station
        from the SDLC console. This is usually a temporary condition.
        Retry the operation."
    ::= { sdlcEventsGroup 71 }

sdlc71-interface OBJECT-TYPE
    SYNTAX DisplayString
    MAX-ACCESS accessible-for-notify
    STATUS current
    DESCRIPTION
        "Parameter 'interface' in event SDLC.71"
    ::= { sdlcEventObjects71 1 }

sdlc71-address OBJECT-TYPE
    SYNTAX Integer32
    MAX-ACCESS accessible-for-notify
    STATUS current
    DESCRIPTION
        "Parameter 'address' in event SDLC.71"
    ::= { sdlcEventObjects71 2 }

sdlcEventObjects72 OBJECT-IDENTITY
    STATUS current
    DESCRIPTION
        "Event SDLC.72
        The remote link station has been closed by the router and is no
        longer active."
    ::= { sdlcEventsGroup 72 }

sdlc72-interface OBJECT-TYPE
    SYNTAX DisplayString
    MAX-ACCESS accessible-for-notify
    STATUS current
    DESCRIPTION
        "Parameter 'interface' in event SDLC.72"
    ::= { sdlcEventObjects72 1 }

sdlc72-address OBJECT-TYPE
    SYNTAX Integer32
    MAX-ACCESS accessible-for-notify
    STATUS current
    DESCRIPTION
        "Parameter 'address' in event SDLC.72"
    ::= { sdlcEventObjects72 2 }

sdlcEventObjects73 OBJECT-IDENTITY
    STATUS current
    DESCRIPTION
        "Event SDLC.73
        SDLC failed to allocate memory from the router's heap because it has
        already allocated its fair share. SDLC will recover from this usually
        temporary problem."
    ::= { sdlcEventsGroup 73 }

sdlc73-interface OBJECT-TYPE
    SYNTAX DisplayString
    MAX-ACCESS accessible-for-notify
    STATUS current
    DESCRIPTION
        "Parameter 'interface' in event SDLC.73"
    ::= { sdlcEventObjects73 1 }

sdlcEventObjects74 OBJECT-IDENTITY
    STATUS current
    DESCRIPTION
        "Event SDLC.74
        SDLC failed to allocate a high-priority buffer from the router's heap.
        As a result, SDLC will temporarily experience a loss of performance.
        SDLC sessions could possibly be lost if the condition persists."
    ::= { sdlcEventsGroup 74 }

sdlc74-interface OBJECT-TYPE
    SYNTAX DisplayString
    MAX-ACCESS accessible-for-notify
    STATUS current
    DESCRIPTION
        "Parameter 'interface' in event SDLC.74"
    ::= { sdlcEventObjects74 1 }

sdlcEventObjects75 OBJECT-IDENTITY
    STATUS current
    DESCRIPTION
        "Event SDLC.75
        SDLC failed to allocate memory from the router's heap because the heap
        is exhausted. SDLC will recover from this usually temporary problem."
    ::= { sdlcEventsGroup 75 }

sdlc75-interface OBJECT-TYPE
    SYNTAX DisplayString
    MAX-ACCESS accessible-for-notify
    STATUS current
    DESCRIPTION
        "Parameter 'interface' in event SDLC.75"
    ::= { sdlcEventObjects75 1 }

sdlcEventObjects76 OBJECT-IDENTITY
    STATUS current
    DESCRIPTION
        "Event SDLC.76
        SDLC could not send an Information (I) frame to the interface.
        SDLC will attempt to re-transmit it later."
    ::= { sdlcEventsGroup 76 }

sdlc76-interface OBJECT-TYPE
    SYNTAX DisplayString
    MAX-ACCESS accessible-for-notify
    STATUS current
    DESCRIPTION
        "Parameter 'interface' in event SDLC.76"
    ::= { sdlcEventObjects76 1 }

sdlcEventObjects77 OBJECT-IDENTITY
    STATUS current
    DESCRIPTION
        "Event SDLC.77
        SDLC could not send a Supervisory (S) frame to the interface.
        SDLC will attempt to re-transmit it later."
    ::= { sdlcEventsGroup 77 }

sdlc77-interface OBJECT-TYPE
    SYNTAX DisplayString
    MAX-ACCESS accessible-for-notify
    STATUS current
    DESCRIPTION
        "Parameter 'interface' in event SDLC.77"
    ::= { sdlcEventObjects77 1 }

sdlcEventObjects78 OBJECT-IDENTITY
    STATUS current
    DESCRIPTION
        "Event SDLC.78
        SDLC could not send an Unnumbered Information (UI) frame to
        the interface. SDLC will attempt to re-transmit it later."
    ::= { sdlcEventsGroup 78 }

sdlc78-interface OBJECT-TYPE
    SYNTAX DisplayString
    MAX-ACCESS accessible-for-notify
    STATUS current
    DESCRIPTION
        "Parameter 'interface' in event SDLC.78"
    ::= { sdlcEventObjects78 1 }

sdlcEventObjects79 OBJECT-IDENTITY
    STATUS current
    DESCRIPTION
        "Event SDLC.79
        SDLC could not send an XID or TEST frame to the interface.
        SDLC will attempt to re-transmit it later."
    ::= { sdlcEventsGroup 79 }

sdlc79-interface OBJECT-TYPE
    SYNTAX DisplayString
    MAX-ACCESS accessible-for-notify
    STATUS current
    DESCRIPTION
        "Parameter 'interface' in event SDLC.79"
    ::= { sdlcEventObjects79 1 }

sdlcEventObjects80 OBJECT-IDENTITY
    STATUS current
    DESCRIPTION
        "Event SDLC.80
        SDLC received an invalid frame type. This frame was ignored."
    ::= { sdlcEventsGroup 80 }

sdlc80-interface OBJECT-TYPE
    SYNTAX DisplayString
    MAX-ACCESS accessible-for-notify
    STATUS current
    DESCRIPTION
        "Parameter 'interface' in event SDLC.80"
    ::= { sdlcEventObjects80 1 }

sdlcEventObjects81 OBJECT-IDENTITY
    STATUS current
    DESCRIPTION
        "Event SDLC.81
        SDLC received a frame from a remote link station that it had
        not polled. This frame was ignored. This error may also occur if
        the poll response timeout is too short."
    ::= { sdlcEventsGroup 81 }

sdlc81-interface OBJECT-TYPE
    SYNTAX DisplayString
    MAX-ACCESS accessible-for-notify
    STATUS current
    DESCRIPTION
        "Parameter 'interface' in event SDLC.81"
    ::= { sdlcEventObjects81 1 }

sdlcEventObjects82 OBJECT-IDENTITY
    STATUS current
    DESCRIPTION
        "Event SDLC.82
        SDLC received an Unnumbered Information (UI) frame without the
        Final (F) bit set. This frame was dropped."
    ::= { sdlcEventsGroup 82 }

sdlc82-interface OBJECT-TYPE
    SYNTAX DisplayString
    MAX-ACCESS accessible-for-notify
    STATUS current
    DESCRIPTION
        "Parameter 'interface' in event SDLC.82"
    ::= { sdlcEventObjects82 1 }

sdlcEventObjects83 OBJECT-IDENTITY
    STATUS current
    DESCRIPTION
        "Event SDLC.83
        SDLC received a frame to the broadcast address on a multipoint line.
        The frame was dropped."
    ::= { sdlcEventsGroup 83 }

sdlc83-interface OBJECT-TYPE
    SYNTAX DisplayString
    MAX-ACCESS accessible-for-notify
    STATUS current
    DESCRIPTION
        "Parameter 'interface' in event SDLC.83"
    ::= { sdlcEventObjects83 1 }

sdlcEventObjects84 OBJECT-IDENTITY
    STATUS current
    DESCRIPTION
        "Event SDLC.84
        SDLC could not be initialized because there is no SDLC link
        configuration for this interface."
    ::= { sdlcEventsGroup 84 }

sdlc84-interface OBJECT-TYPE
    SYNTAX DisplayString
    MAX-ACCESS accessible-for-notify
    STATUS current
    DESCRIPTION
        "Parameter 'interface' in event SDLC.84"
    ::= { sdlcEventObjects84 1 }

sdlcEventObjects85 OBJECT-IDENTITY
    STATUS current
    DESCRIPTION
        "Event SDLC.85
        SDLC could not control one or more signals on the interface. This could
        occur if you attempt to run SDLC over an unsupported interface."
    ::= { sdlcEventsGroup 85 }

sdlc85-interface OBJECT-TYPE
    SYNTAX DisplayString
    MAX-ACCESS accessible-for-notify
    STATUS current
    DESCRIPTION
        "Parameter 'interface' in event SDLC.85"
    ::= { sdlcEventObjects85 1 }

sdlc85-reason OBJECT-TYPE
    SYNTAX DisplayString
    MAX-ACCESS accessible-for-notify
    STATUS current
    DESCRIPTION
        "Parameter 'reason' in event SDLC.85"
    ::= { sdlcEventObjects85 2 }

sdlcEventObjects86 OBJECT-IDENTITY
    STATUS current
    DESCRIPTION
        "Event SDLC.86
        DCD went high during transmission of a frame in half duplex mode.
        This is a protocol violation, and the interface will go down shortly
        in order to correct the problem."
    ::= { sdlcEventsGroup 86 }

sdlc86-interface OBJECT-TYPE
    SYNTAX DisplayString
    MAX-ACCESS accessible-for-notify
    STATUS current
    DESCRIPTION
        "Parameter 'interface' in event SDLC.86"
    ::= { sdlcEventObjects86 1 }

sdlcEventObjects87 OBJECT-IDENTITY
    STATUS current
    DESCRIPTION
        "Event SDLC.87
        The CTS signal has transitioned to low while the interface was
        recovering from a half-duplex protocol violation. The link is now in
        the correct state and data transfer may resume."
    ::= { sdlcEventsGroup 87 }

sdlc87-interface OBJECT-TYPE
    SYNTAX DisplayString
    MAX-ACCESS accessible-for-notify
    STATUS current
    DESCRIPTION
        "Parameter 'interface' in event SDLC.87"
    ::= { sdlcEventObjects87 1 }

sdlcEventObjects88 OBJECT-IDENTITY
    STATUS current
    DESCRIPTION
        "Event SDLC.88
        A signal was asserted by the connected device while the line was idle.
        When operating in half-duplex mode, only the DTR/DSR signal should be
        asserted on an idle interface."
    ::= { sdlcEventsGroup 88 }

sdlc88-interface OBJECT-TYPE
    SYNTAX DisplayString
    MAX-ACCESS accessible-for-notify
    STATUS current
    DESCRIPTION
        "Parameter 'interface' in event SDLC.88"
    ::= { sdlcEventObjects88 1 }

sdlcEventObjects89 OBJECT-IDENTITY
    STATUS current
    DESCRIPTION
        "Event SDLC.89
        The DSR or CTS signal went low during transmission. This is a protocol
        violation, and the interface will go down shortly in order to correct
        the problem."
    ::= { sdlcEventsGroup 89 }

sdlc89-interface OBJECT-TYPE
    SYNTAX DisplayString
    MAX-ACCESS accessible-for-notify
    STATUS current
    DESCRIPTION
        "Parameter 'interface' in event SDLC.89"
    ::= { sdlcEventObjects89 1 }

sdlcEventObjects90 OBJECT-IDENTITY
    STATUS current
    DESCRIPTION
        "Event SDLC.90
        SDLC received a frame other than a UA while trying to close
        the link station. The router ignored this frame."
    ::= { sdlcEventsGroup 90 }

sdlc90-interface OBJECT-TYPE
    SYNTAX DisplayString
    MAX-ACCESS accessible-for-notify
    STATUS current
    DESCRIPTION
        "Parameter 'interface' in event SDLC.90"
    ::= { sdlcEventObjects90 1 }

sdlc90-address OBJECT-TYPE
    SYNTAX Integer32
    MAX-ACCESS accessible-for-notify
    STATUS current
    DESCRIPTION
        "Parameter 'address' in event SDLC.90"
    ::= { sdlcEventObjects90 2 }

sdlcEventObjects91 OBJECT-IDENTITY
    STATUS current
    DESCRIPTION
        "Event SDLC.91
        An SDLC remote link station was added by the user from the
        SDLC console and is now available for use."
    ::= { sdlcEventsGroup 91 }

sdlc91-address OBJECT-TYPE
    SYNTAX Integer32
    MAX-ACCESS accessible-for-notify
    STATUS current
    DESCRIPTION
        "Parameter 'address' in event SDLC.91"
    ::= { sdlcEventObjects91 1 }

sdlc91-interface OBJECT-TYPE
    SYNTAX DisplayString
    MAX-ACCESS accessible-for-notify
    STATUS current
    DESCRIPTION
        "Parameter 'interface' in event SDLC.91"
    ::= { sdlcEventObjects91 2 }

sdlcEventObjects92 OBJECT-IDENTITY
    STATUS current
    DESCRIPTION
        "Event SDLC.92
        An SDLC remote link station was deleted by the user from the
        SDLC console and is no longer available for use."
    ::= { sdlcEventsGroup 92 }

sdlc92-address OBJECT-TYPE
    SYNTAX Integer32
    MAX-ACCESS accessible-for-notify
    STATUS current
    DESCRIPTION
        "Parameter 'address' in event SDLC.92"
    ::= { sdlcEventObjects92 1 }

sdlc92-interface OBJECT-TYPE
    SYNTAX DisplayString
    MAX-ACCESS accessible-for-notify
    STATUS current
    DESCRIPTION
        "Parameter 'interface' in event SDLC.92"
    ::= { sdlcEventObjects92 2 }

sdlcEventObjects93 OBJECT-IDENTITY
    STATUS current
    DESCRIPTION
        "Event SDLC.93
        SDLC received a frame from a remote link station that contains an
        unrecognized station address. The router ignored this frame."
    ::= { sdlcEventsGroup 93 }

sdlc93-interface OBJECT-TYPE
    SYNTAX DisplayString
    MAX-ACCESS accessible-for-notify
    STATUS current
    DESCRIPTION
        "Parameter 'interface' in event SDLC.93"
    ::= { sdlcEventObjects93 1 }

sdlcEventObjects94 OBJECT-IDENTITY
    STATUS current
    DESCRIPTION
        "Event SDLC.94
        The router ignored the received frame for this station, because
        the target station is in a disabled state."
    ::= { sdlcEventsGroup 94 }

sdlc94-interface OBJECT-TYPE
    SYNTAX DisplayString
    MAX-ACCESS accessible-for-notify
    STATUS current
    DESCRIPTION
        "Parameter 'interface' in event SDLC.94"
    ::= { sdlcEventObjects94 1 }

sdlc94-address OBJECT-TYPE
    SYNTAX Integer32
    MAX-ACCESS accessible-for-notify
    STATUS current
    DESCRIPTION
        "Parameter 'address' in event SDLC.94"
    ::= { sdlcEventObjects94 2 }

sdlcEventObjects95 OBJECT-IDENTITY
    STATUS current
    DESCRIPTION
        "Event SDLC.95
        The local SDLC secondary link station received a null XID frame from a
        remote link station while in NRM. We treat this as an indication that
        the link failed at the sending end and this is an attempt to reestablish
        the connection."
    ::= { sdlcEventsGroup 95 }

sdlc95-interface OBJECT-TYPE
    SYNTAX DisplayString
    MAX-ACCESS accessible-for-notify
    STATUS current
    DESCRIPTION
        "Parameter 'interface' in event SDLC.95"
    ::= { sdlcEventObjects95 1 }

sdlc95-address OBJECT-TYPE
    SYNTAX Integer32
    MAX-ACCESS accessible-for-notify
    STATUS current
    DESCRIPTION
        "Parameter 'address' in event SDLC.95"
    ::= { sdlcEventObjects95 2 }


sdlcNotification1 NOTIFICATION-TYPE
    OBJECTS { 
              sdlc1-interface 
            }
    STATUS current
    DESCRIPTION
        "Notification of Event SDLC.1

        Message: 'SDLC support installed for QSL, on interface $1'

        Parameters list:
              $1: sdlc1-interface

        DLSw SDLC has been initialized for operation over the serial
        device and is now available for use in the router."
    ::= { sdlcNotificationsPrefix 1 }

sdlcNotification2 NOTIFICATION-TYPE
    OBJECTS { 
              sdlc2-address, 
              sdlc2-interface 
            }
    STATUS current
    DESCRIPTION
        "Notification of Event SDLC.2

        Message: 'No remote configuration was defined for SDLC address $1 - default settings used, on interface $2'

        Parameters list:
              $1: sdlc2-address
              $2: sdlc2-interface

        An open was attempted on an SDLC station, but a configuration
        record was not defined via the ADD STATION command. The station will be
        opened using default configuration value. This station will be
        listed in the monitor process LIST STATION ALL command. An
        asterisk * next to the station address signifies that a
        default configuration is in use."
    ::= { sdlcNotificationsPrefix 2 }

sdlcNotification3 NOTIFICATION-TYPE
    OBJECTS { 
              sdlc3-interface 
            }
    STATUS current
    DESCRIPTION
        "Notification of Event SDLC.3

        Message: 'Cannot copy a user buffer to to SDLC - Out of memory, on interface $1'

        Parameters list:
              $1: sdlc3-interface

        There is currently no memory available to copy user data to
        SDLC. Another attempt will be made at a later time."
    ::= { sdlcNotificationsPrefix 3 }

sdlcNotification4 NOTIFICATION-TYPE
    OBJECTS { 
              sdlc4-interface 
            }
    STATUS current
    DESCRIPTION
        "Notification of Event SDLC.4

        Message: 'Inbound frame was dropped - SDLC not yet active on interface $1'

        Parameters list:
              $1: sdlc4-interface

        A frame was received on an interface that is not yet owned by
        an SDLC client. All packets received are dropped until an
        SDLC client opens the port for use."
    ::= { sdlcNotificationsPrefix 4 }

sdlcNotification5 NOTIFICATION-TYPE
    OBJECTS { 
              sdlc5-interface 
            }
    STATUS current
    DESCRIPTION
        "Notification of Event SDLC.5

        Message: 'Packet dropped due to no SDLC credit or memory shortage, on interface $1. Temporary'

        Parameters list:
              $1: sdlc5-interface

        An incoming packet was dropped due to no SDLC receive credit
        or a temporary memory shortage."
    ::= { sdlcNotificationsPrefix 5 }

sdlcNotification6 NOTIFICATION-TYPE
    OBJECTS { 
              sdlc6-interface 
            }
    STATUS current
    DESCRIPTION
        "Notification of Event SDLC.6

        Message: 'Packet received with I-ERR set, on interface $1'

        Parameters list:
              $1: sdlc6-interface

        real-sdlc-in received a packet with I-ERR set."
    ::= { sdlcNotificationsPrefix 6 }

sdlcNotification7 NOTIFICATION-TYPE
    OBJECTS { 
              sdlc7-interface, 
              sdlc7-status 
            }
    STATUS current
    DESCRIPTION
        "Notification of Event SDLC.7

        Message: 'Failure to send packet to device, on interface $1, status = $2'

        Parameters list:
              $1: sdlc7-interface
              $2: sdlc7-status

        The call to netsend() failed while trying to send a frame from SDLC."
    ::= { sdlcNotificationsPrefix 7 }

sdlcNotification8 NOTIFICATION-TYPE
    OBJECTS { 
              sdlc8-count, 
              sdlc8-address,
              sdlc8-interface,
              sdlc8-octets 
            }
    STATUS current
    DESCRIPTION
        "Notification of Event SDLC.8

        Message: 'Transmit $1 bytes to link station $2, on interface $3:$4'

        Parameters list:
              $1: sdlc8-count
              $2: sdlc8-address
              $3: sdlc8-interface
              $4: sdlc8-octets

        The router transmitted an SDLC frame. This is the entire frame,
        including the SDLC header. The router logs all transmitted SDLC
        frames with this message. To log only transmitted SDLC I-frames,
        use SDLC-53."
    ::= { sdlcNotificationsPrefix 8 }

sdlcNotification9 NOTIFICATION-TYPE
    OBJECTS { 
              sdlc9-count, 
              sdlc9-address,
              sdlc9-interface,
              sdlc9-octets 
            }
    STATUS current
    DESCRIPTION
        "Notification of Event SDLC.9

        Message: 'Received $1 bytes from link station $2, on interface $3:$4'

        Parameters list:
              $1: sdlc9-count
              $2: sdlc9-address
              $3: sdlc9-interface
              $4: sdlc9-octets

        The router received an SDLC frame. This is the entire frame, including
        the SDLC header. The router logs all received SDLC frames with this
        message. To log only received SDLC I-frames, use SDLC-52."
    ::= { sdlcNotificationsPrefix 9 }

sdlcNotification10 NOTIFICATION-TYPE
    OBJECTS { 
              sdlc10-interface 
            }
    STATUS current
    DESCRIPTION
        "Notification of Event SDLC.10

        Message: 'Request to bring up SDLC, on interface $1'

        Parameters list:
              $1: sdlc10-interface

        An entity in the router has attached to the interface and can
        now use SDLC services."
    ::= { sdlcNotificationsPrefix 10 }

sdlcNotification11 NOTIFICATION-TYPE
    OBJECTS { 
              sdlc11-interface 
            }
    STATUS current
    DESCRIPTION
        "Notification of Event SDLC.11

        Message: 'Request to bring down SDLC, on interface $1'

        Parameters list:
              $1: sdlc11-interface

        An entity in the router is no longer using SDLC services
        on this interface."
    ::= { sdlcNotificationsPrefix 11 }

sdlcNotification12 NOTIFICATION-TYPE
    OBJECTS { 
              sdlc12-exception, 
              sdlc12-interface 
            }
    STATUS current
    DESCRIPTION
        "Notification of Event SDLC.12

        Message: 'Link status change $1 occurred, on interface $2'

        Parameters list:
              $1: sdlc12-exception
              $2: sdlc12-interface

        An interface signal has changed state. Note: an unwieldy number
        of these messages will be generated when the interface is
        operating in half duplex mode."
    ::= { sdlcNotificationsPrefix 12 }

sdlcNotification13 NOTIFICATION-TYPE
    OBJECTS { 
              sdlc13-address, 
              sdlc13-interface 
            }
    STATUS current
    DESCRIPTION
        "Notification of Event SDLC.13

        Message: 'Station $1 is now UP, on interface $2'

        Parameters list:
              $1: sdlc13-address
              $2: sdlc13-interface

        The SDLC link is now operating in Normal Response Mode,
        meaning that a SDLC connection is now in progress."
    ::= { sdlcNotificationsPrefix 13 }

sdlcNotification14 NOTIFICATION-TYPE
    OBJECTS { 
              sdlc14-address, 
              sdlc14-interface 
            }
    STATUS current
    DESCRIPTION
        "Notification of Event SDLC.14

        Message: 'Remote station refused SNRM, link station $1 remains DOWN on interface $2'

        Parameters list:
              $1: sdlc14-address
              $2: sdlc14-interface

        An attempt by the router to connect to a remote link station
        has been refused."
    ::= { sdlcNotificationsPrefix 14 }

sdlcNotification15 NOTIFICATION-TYPE
    OBJECTS { 
              sdlc15-address, 
              sdlc15-interface 
            }
    STATUS current
    DESCRIPTION
        "Notification of Event SDLC.15

        Message: 'Station $1 is now DOWN, on interface $2'

        Parameters list:
              $1: sdlc15-address
              $2: sdlc15-interface

        The SDLC link is now operating in Normal Disconnect Mode,
        meaning that a SDLC connection has been terminated in an
        orderly fashion."
    ::= { sdlcNotificationsPrefix 15 }

sdlcNotification16 NOTIFICATION-TYPE
    OBJECTS { 
              sdlc16-address, 
              sdlc16-exception,
              sdlc16-interface 
            }
    STATUS current
    DESCRIPTION
        "Notification of Event SDLC.16

        Message: 'An exception occurred on Link Station $1: exception $2, on interface $3'

        Parameters list:
              $1: sdlc16-address
              $2: sdlc16-exception
              $3: sdlc16-interface

        The SDLC protocol has been initialized."
    ::= { sdlcNotificationsPrefix 16 }

sdlcNotification17 NOTIFICATION-TYPE
    OBJECTS { 
              sdlc17-interface 
            }
    STATUS current
    DESCRIPTION
        "Notification of Event SDLC.17

        Message: 'Interface $1: received a broadcast frame from a secondary station on a multipoint line - dropped'

        Parameters list:
              $1: sdlc17-interface

        SDLC received a frame to the broadcast address on a multipoint line.
        The frame was dropped."
    ::= { sdlcNotificationsPrefix 17 }

sdlcNotification18 NOTIFICATION-TYPE
    OBJECTS { 
              sdlc18-interface 
            }
    STATUS current
    DESCRIPTION
        "Notification of Event SDLC.18

        Message: 'Interface $1: SDLC not brought up because no LINK configuration is defined'

        Parameters list:
              $1: sdlc18-interface

        SDLC could not be initialized because there is no SDLC link
        configuration for this interface."
    ::= { sdlcNotificationsPrefix 18 }

sdlcNotification19 NOTIFICATION-TYPE
    OBJECTS { 
              sdlc19-interface, 
              sdlc19-reason 
            }
    STATUS current
    DESCRIPTION
        "Notification of Event SDLC.19

        Message: 'Interface $1: signal control request failed because $2'

        Parameters list:
              $1: sdlc19-interface
              $2: sdlc19-reason

        SDLC could not control one or more signals on the interface. This
        could occur if you attempt to run SDLC over an unsupported interface."
    ::= { sdlcNotificationsPrefix 19 }

sdlcNotification20 NOTIFICATION-TYPE
    OBJECTS { 
              sdlc20-interface, 
              sdlc20-address 
            }
    STATUS current
    DESCRIPTION
        "Notification of Event SDLC.20

        Message: 'Interface $1 SDLC station $2: DLC-LINK-FAULT-CONDITION'

        Parameters list:
              $1: sdlc20-interface
              $2: sdlc20-address

        SDLC detected a fault on the link, and terminated all active SDLC
        connections on the link. This is usually due to a loss of DSR, CTS, or
        DCD on a full-duplex line, or loss of DSR on a half-duplex line."
    ::= { sdlcNotificationsPrefix 20 }

sdlcNotification21 NOTIFICATION-TYPE
    OBJECTS { 
              sdlc21-interface, 
              sdlc21-address 
            }
    STATUS current
    DESCRIPTION
        "Notification of Event SDLC.21

        Message: 'Interface $1 SDLC station $2: DLC-RX-EXCEED-WINDOW-SIZE'

        Parameters list:
              $1: sdlc21-interface
              $2: sdlc21-address

        SDLC has received more than the number of frames configured as
        the RECEIVE WINDOW before SDLC could respond."
    ::= { sdlcNotificationsPrefix 21 }

sdlcNotification22 NOTIFICATION-TYPE
    OBJECTS { 
              sdlc22-interface, 
              sdlc22-address 
            }
    STATUS current
    DESCRIPTION
        "Notification of Event SDLC.22

        Message: 'Interface $1 SDLC station $2: DLC-RX-LOCAL-PROTOCOL-ERROR'

        Parameters list:
              $1: sdlc22-interface
              $2: sdlc22-address

        The router detected a SDLC protocol error. As a result, the router
        terminated the SDLC connection."
    ::= { sdlcNotificationsPrefix 22 }

sdlcNotification23 NOTIFICATION-TYPE
    OBJECTS { 
              sdlc23-interface, 
              sdlc23-address 
            }
    STATUS current
    DESCRIPTION
        "Notification of Event SDLC.23

        Message: 'Interface $1 SDLC station $2: DLC-XID-RETRY-LIMIT-REACHED'

        Parameters list:
              $1: sdlc23-interface
              $2: sdlc23-address

        The remote link station is not responding to XID frames the router sent."
    ::= { sdlcNotificationsPrefix 23 }

sdlcNotification24 NOTIFICATION-TYPE
    OBJECTS { 
              sdlc24-interface, 
              sdlc24-address 
            }
    STATUS current
    DESCRIPTION
        "Notification of Event SDLC.24

        Message: 'Interface $1 SDLC station $2: DLC-TEST-RETRY-LIMIT-REACHED'

        Parameters list:
              $1: sdlc24-interface
              $2: sdlc24-address

        The remote link station is not responding to TEST frames the router
        sent."
    ::= { sdlcNotificationsPrefix 24 }

sdlcNotification25 NOTIFICATION-TYPE
    OBJECTS { 
              sdlc25-interface, 
              sdlc25-address 
            }
    STATUS current
    DESCRIPTION
        "Notification of Event SDLC.25

        Message: 'Interface $1 SDLC station $2: DLC-SNRM-RETRY-LIMIT-REACHED'

        Parameters list:
              $1: sdlc25-interface
              $2: sdlc25-address

        The remote link station is not responding to SNRM frames the router
        sent. The connection attempt has failed."
    ::= { sdlcNotificationsPrefix 25 }

sdlcNotification26 NOTIFICATION-TYPE
    OBJECTS { 
              sdlc26-interface, 
              sdlc26-address 
            }
    STATUS current
    DESCRIPTION
        "Notification of Event SDLC.26

        Message: 'Interface $1 SDLC station $2: DLC-POLL-RETRY-LIMIT-REACHED'

        Parameters list:
              $1: sdlc26-interface
              $2: sdlc26-address

        The remote link station is not responding to polls (RR or RNR)
        sent by the router. As a result, the router terminated the connection."
    ::= { sdlcNotificationsPrefix 26 }

sdlcNotification27 NOTIFICATION-TYPE
    OBJECTS { 
              sdlc27-interface, 
              sdlc27-address 
            }
    STATUS current
    DESCRIPTION
        "Notification of Event SDLC.27

        Message: 'Interface $1 SDLC station $2: DLC-RX-FRMR-INV-CTL-FIELD'

        Parameters list:
              $1: sdlc27-interface
              $2: sdlc27-address

        SDLC has received a Frame Reject (FRMR) frame indicating that
        the remote link station received a frame with an invalid
        control field."
    ::= { sdlcNotificationsPrefix 27 }

sdlcNotification28 NOTIFICATION-TYPE
    OBJECTS { 
              sdlc28-interface, 
              sdlc28-address 
            }
    STATUS current
    DESCRIPTION
        "Notification of Event SDLC.28

        Message: 'Interface $1 SDLC station $2: DLC-RX-FRMR-INV-LENGTH'

        Parameters list:
              $1: sdlc28-interface
              $2: sdlc28-address

        SDLC has received a Frame Reject (FRMR) frame indicating that
        the remote link station received a frame that was too short."
    ::= { sdlcNotificationsPrefix 28 }

sdlcNotification29 NOTIFICATION-TYPE
    OBJECTS { 
              sdlc29-interface, 
              sdlc29-address 
            }
    STATUS current
    DESCRIPTION
        "Notification of Event SDLC.29

        Message: 'Interface $1 SDLC station $2: DLC-RX-FRMR-LONG-I-FIELD'

        Parameters list:
              $1: sdlc29-interface
              $2: sdlc29-address

        SDLC has received a Frame Reject (FRMR) frame indicating that
        the remote link station received a frame that was too long."
    ::= { sdlcNotificationsPrefix 29 }

sdlcNotification30 NOTIFICATION-TYPE
    OBJECTS { 
              sdlc30-interface, 
              sdlc30-address 
            }
    STATUS current
    DESCRIPTION
        "Notification of Event SDLC.30

        Message: 'Interface $1 SDLC station $2: DLC-RX-FRMR-INV-NR'

        Parameters list:
              $1: sdlc30-interface
              $2: sdlc30-address

        SDLC has received a Frame Reject (FRMR) frame indicating that
        the remote link station received a frame with an invalid N(r)
        in the control field."
    ::= { sdlcNotificationsPrefix 30 }

sdlcNotification31 NOTIFICATION-TYPE
    OBJECTS { 
              sdlc31-interface, 
              sdlc31-address 
            }
    STATUS current
    DESCRIPTION
        "Notification of Event SDLC.31

        Message: 'Interface $1 SDLC station $2: DLC-RX-FRMR-NO-I-FIELD'

        Parameters list:
              $1: sdlc31-interface
              $2: sdlc31-address

        SDLC has received a Frame Reject (FRMR) frame indicating that
        the remote link station received an I-frame with no data in
        the I field."
    ::= { sdlcNotificationsPrefix 31 }

sdlcNotification32 NOTIFICATION-TYPE
    OBJECTS { 
              sdlc32-interface, 
              sdlc32-address 
            }
    STATUS current
    DESCRIPTION
        "Notification of Event SDLC.32

        Message: 'Interface $1 SDLC station $2: DLC-RX-FRAME-INV-CTL-FIELD'

        Parameters list:
              $1: sdlc32-interface
              $2: sdlc32-address

        SDLC has received a frame with an invalid control field."
    ::= { sdlcNotificationsPrefix 32 }

sdlcNotification33 NOTIFICATION-TYPE
    OBJECTS { 
              sdlc33-interface, 
              sdlc33-address 
            }
    STATUS current
    DESCRIPTION
        "Notification of Event SDLC.33

        Message: 'Interface $1 SDLC station $2: DLC-RX-FRAME-INV-LENGTH'

        Parameters list:
              $1: sdlc33-interface
              $2: sdlc33-address

        SDLC has received a frame that was too short."
    ::= { sdlcNotificationsPrefix 33 }

sdlcNotification34 NOTIFICATION-TYPE
    OBJECTS { 
              sdlc34-interface, 
              sdlc34-address 
            }
    STATUS current
    DESCRIPTION
        "Notification of Event SDLC.34

        Message: 'Interface $1 SDLC station $2: DLC-RX-FRAME-LONG-I-FIELD'

        Parameters list:
              $1: sdlc34-interface
              $2: sdlc34-address

        SDLC has received a frame that was too long."
    ::= { sdlcNotificationsPrefix 34 }

sdlcNotification35 NOTIFICATION-TYPE
    OBJECTS { 
              sdlc35-interface, 
              sdlc35-address 
            }
    STATUS current
    DESCRIPTION
        "Notification of Event SDLC.35

        Message: 'Interface $1 SDLC station $2: DLC-RX-FRAME-INV-NR'

        Parameters list:
              $1: sdlc35-interface
              $2: sdlc35-address

        SDLC has received a frame with an invalid N(r) in the control field."
    ::= { sdlcNotificationsPrefix 35 }

sdlcNotification36 NOTIFICATION-TYPE
    OBJECTS { 
              sdlc36-interface, 
              sdlc36-address 
            }
    STATUS current
    DESCRIPTION
        "Notification of Event SDLC.36

        Message: 'Interface $1 SDLC station $2: DLC-RX-DM'

        Parameters list:
              $1: sdlc36-interface
              $2: sdlc36-address

        SDLC received a Disconnected Mode (DM) frame. A remote secondary link
        station sent the frame to indicate that it accepted a previously
        received DISC frame. The link disconnection is now complete."
    ::= { sdlcNotificationsPrefix 36 }

sdlcNotification37 NOTIFICATION-TYPE
    OBJECTS { 
              sdlc37-interface, 
              sdlc37-address 
            }
    STATUS current
    DESCRIPTION
        "Notification of Event SDLC.37

        Message: 'Interface $1 SDLC station $2: DLC-RX-RD'

        Parameters list:
              $1: sdlc37-interface
              $2: sdlc37-address

        SDLC received a Request Disconnect (RD) frame. The SDLC client should
        respond to this by sending a Disconnect (DISC) frame."
    ::= { sdlcNotificationsPrefix 37 }

sdlcNotification38 NOTIFICATION-TYPE
    OBJECTS { 
              sdlc38-interface, 
              sdlc38-address 
            }
    STATUS current
    DESCRIPTION
        "Notification of Event SDLC.38

        Message: 'Interface $1 SDLC station $2: DLC-RX-RIM'

        Parameters list:
              $1: sdlc38-interface
              $2: sdlc38-address

        SDLC received a Request Initialization Mode (RIM) frame.
        The SDLC client should respond to this by sending a
        Set Initialization Mode (SIM) frame."
    ::= { sdlcNotificationsPrefix 38 }

sdlcNotification39 NOTIFICATION-TYPE
    OBJECTS { 
              sdlc39-interface, 
              sdlc39-address 
            }
    STATUS current
    DESCRIPTION
        "Notification of Event SDLC.39

        Message: 'Interface $1 SDLC station $2: DLC-LINK-INACTIVITY-DETECTION'

        Parameters list:
              $1: sdlc39-interface
              $2: sdlc39-address

        Inactivity detection."
    ::= { sdlcNotificationsPrefix 39 }

sdlcNotification40 NOTIFICATION-TYPE
    OBJECTS { 
              sdlc40-interface, 
              sdlc40-address 
            }
    STATUS current
    DESCRIPTION
        "Notification of Event SDLC.40

        Message: 'Interface $1 SDLC station $2: DLC-TX-FRMR-INV-CTL-FIELD'

        Parameters list:
              $1: sdlc40-interface
              $2: sdlc40-address

        SDLC entered a frame reject (FRMR) state because it
        received a frame with an invalid control field."
    ::= { sdlcNotificationsPrefix 40 }

sdlcNotification41 NOTIFICATION-TYPE
    OBJECTS { 
              sdlc41-interface, 
              sdlc41-address 
            }
    STATUS current
    DESCRIPTION
        "Notification of Event SDLC.41

        Message: 'Interface $1 SDLC station $2: DLC-TX-FRMR-INV-LENGTH'

        Parameters list:
              $1: sdlc41-interface
              $2: sdlc41-address

        SDLC entered a frame reject (FRMR) state because it
        received a frame that was too short."
    ::= { sdlcNotificationsPrefix 41 }

sdlcNotification42 NOTIFICATION-TYPE
    OBJECTS { 
              sdlc42-interface, 
              sdlc42-address 
            }
    STATUS current
    DESCRIPTION
        "Notification of Event SDLC.42

        Message: 'Interface $1 SDLC station $2: DLC-TX-FRMR-LONG-I-FIELD'

        Parameters list:
              $1: sdlc42-interface
              $2: sdlc42-address

        SDLC entered a frame reject (FRMR) state because it
        received a frame that was too long."
    ::= { sdlcNotificationsPrefix 42 }

sdlcNotification43 NOTIFICATION-TYPE
    OBJECTS { 
              sdlc43-interface, 
              sdlc43-address 
            }
    STATUS current
    DESCRIPTION
        "Notification of Event SDLC.43

        Message: 'Interface $1 SDLC station $2: DLC-TX-FRMR-INV-NR'

        Parameters list:
              $1: sdlc43-interface
              $2: sdlc43-address

        SDLC entered a frame reject (FRMR) state because it
        received a frame with an invalid N(r) in the control field."
    ::= { sdlcNotificationsPrefix 43 }

sdlcNotification44 NOTIFICATION-TYPE
    OBJECTS { 
              sdlc44-interface, 
              sdlc44-address 
            }
    STATUS current
    DESCRIPTION
        "Notification of Event SDLC.44

        Message: 'Interface $1 SDLC station $2: DLC-RX-SNRM-WHILE-IN-NRM'

        Parameters list:
              $1: sdlc44-interface
              $2: sdlc44-address

        SDLC received a SNRM while in Normal Response Mode (NRM) state."
    ::= { sdlcNotificationsPrefix 44 }

sdlcNotification45 NOTIFICATION-TYPE
    OBJECTS { 
              sdlc45-interface, 
              sdlc45-address 
            }
    STATUS current
    DESCRIPTION
        "Notification of Event SDLC.45

        Message: 'Interface $1 SDLC station $2: DLC-PORT-DISABLED'

        Parameters list:
              $1: sdlc45-interface
              $2: sdlc45-address

        The user disabled the interface from the SDLC console. All current
        connections are terminated."
    ::= { sdlcNotificationsPrefix 45 }

sdlcNotification46 NOTIFICATION-TYPE
    OBJECTS { 
              sdlc46-interface, 
              sdlc46-address 
            }
    STATUS current
    DESCRIPTION
        "Notification of Event SDLC.46

        Message: 'Interface $1 SDLC station $2: DLC-PORT-ENABLED'

        Parameters list:
              $1: sdlc46-interface
              $2: sdlc46-address

        The user enabled the interface from the SDLC console."
    ::= { sdlcNotificationsPrefix 46 }

sdlcNotification47 NOTIFICATION-TYPE
    OBJECTS { 
              sdlc47-interface 
            }
    STATUS current
    DESCRIPTION
        "Notification of Event SDLC.47

        Message: 'Interface $1 SDLC link: DLC-STATION-CLOSED'

        Parameters list:
              $1: sdlc47-interface

        The interface has been closed by SDLC. SDLC is no longer running over
        this interface."
    ::= { sdlcNotificationsPrefix 47 }

sdlcNotification48 NOTIFICATION-TYPE
    OBJECTS { 
              sdlc48-interface, 
              sdlc48-address 
            }
    STATUS current
    DESCRIPTION
        "Notification of Event SDLC.48

        Message: 'Interface $1 SDLC station $2: DLC-LS-DISABLED'

        Parameters list:
              $1: sdlc48-interface
              $2: sdlc48-address

        The user disabled a remote link station on this interface from
        the SDLC console. Any existing connection was terminated."
    ::= { sdlcNotificationsPrefix 48 }

sdlcNotification49 NOTIFICATION-TYPE
    OBJECTS { 
              sdlc49-interface, 
              sdlc49-address 
            }
    STATUS current
    DESCRIPTION
        "Notification of Event SDLC.49

        Message: 'Interface $1 SDLC station $2: DLC-LS-ENABLED'

        Parameters list:
              $1: sdlc49-interface
              $2: sdlc49-address

        The user enabled a remote link station has been enabled on this
        interface from the SDLC console."
    ::= { sdlcNotificationsPrefix 49 }

sdlcNotification50 NOTIFICATION-TYPE
    OBJECTS { 
              sdlc50-interface, 
              sdlc50-address,
              sdlc50-octets 
            }
    STATUS current
    DESCRIPTION
        "Notification of Event SDLC.50

        Message: 'Interface $1 received UI from SDLC addr $2:$3'

        Parameters list:
              $1: sdlc50-interface
              $2: sdlc50-address
              $3: sdlc50-octets

        The router received an Unnumbered Information (UI) frame on this
        interface."
    ::= { sdlcNotificationsPrefix 50 }

sdlcNotification51 NOTIFICATION-TYPE
    OBJECTS { 
              sdlc51-interface, 
              sdlc51-address,
              sdlc51-octets 
            }
    STATUS current
    DESCRIPTION
        "Notification of Event SDLC.51

        Message: 'Interface $1 sent UI to SDLC addr $2:$3'

        Parameters list:
              $1: sdlc51-interface
              $2: sdlc51-address
              $3: sdlc51-octets

        The router transmitted an Unnumbered Information (UI) frame on this
        interface."
    ::= { sdlcNotificationsPrefix 51 }

sdlcNotification52 NOTIFICATION-TYPE
    OBJECTS { 
              sdlc52-interface, 
              sdlc52-address,
              sdlc52-byte-count,
              sdlc52-octets 
            }
    STATUS current
    DESCRIPTION
        "Notification of Event SDLC.52

        Message: 'Interface $1 received I from SDLC addr $2 $3 bytes:$4'

        Parameters list:
              $1: sdlc52-interface
              $2: sdlc52-address
              $3: sdlc52-byte-count
              $4: sdlc52-octets

        The router received an Information (I) frame on this interface.
        To log all received SDLC frames, use SDLC-9."
    ::= { sdlcNotificationsPrefix 52 }

sdlcNotification53 NOTIFICATION-TYPE
    OBJECTS { 
              sdlc53-interface, 
              sdlc53-address,
              sdlc53-byte-count,
              sdlc53-octets 
            }
    STATUS current
    DESCRIPTION
        "Notification of Event SDLC.53

        Message: 'Interface $1 sent I to SDLC addr $2 $3 bytes:$4'

        Parameters list:
              $1: sdlc53-interface
              $2: sdlc53-address
              $3: sdlc53-byte-count
              $4: sdlc53-octets

        The router transmitted an Information (I) frame has been transmitted
        on this interface. To log all received SDLC frames, use SDLC-8."
    ::= { sdlcNotificationsPrefix 53 }

sdlcNotification54 NOTIFICATION-TYPE
    OBJECTS { 
              sdlc54-interface, 
              sdlc54-address,
              sdlc54-oldBTUSize,
              sdlc54-newBTUSize 
            }
    STATUS current
    DESCRIPTION
        "Notification of Event SDLC.54

        Message: 'Interface $1 Station $2, Max BTU size too large for link - adjusted ($3 -> $4)'

        Parameters list:
              $1: sdlc54-interface
              $2: sdlc54-address
              $3: sdlc54-oldBTUSize
              $4: sdlc54-newBTUSize

        The max BTU size configured for a remote link station exceeds that
        defined for the link. The router adjusted the value for the remote link
        station temporarily. To avoid this message in the future, change
        the max BTU size with the SET REMOTE MAX-PACKET command."
    ::= { sdlcNotificationsPrefix 54 }

sdlcNotification55 NOTIFICATION-TYPE
    OBJECTS { 
              sdlc55-interface, 
              sdlc55-address,
              sdlc55-oldRxWindow,
              sdlc55-newRxWindow 
            }
    STATUS current
    DESCRIPTION
        "Notification of Event SDLC.55

        Message: 'Interface $1 Station $2, Window size is inconsistent with modulo for link - adjusted ($3 -> $4)'

        Parameters list:
              $1: sdlc55-interface
              $2: sdlc55-address
              $3: sdlc55-oldRxWindow
              $4: sdlc55-newRxWindow

        The modulo for this link has been changed by the user, rendering the
        window sizes for all pre-defined remote link stations invalid.
        The window size has been temporarily adjusted. When a link is
        configured for mod-8, the valid window sizes are 0 to 7. When the link
        is configured for mod-128, the valid window sizes are 8 to 128.
        To avoid this message in the future, change the receive window size
        with the 'SET REMOTE RECEIVE-WINDOW' command."
    ::= { sdlcNotificationsPrefix 55 }

sdlcNotification56 NOTIFICATION-TYPE
    OBJECTS { 
              sdlc56-interface, 
              sdlc56-address,
              sdlc56-oldTxWindow,
              sdlc56-newTxWindow 
            }
    STATUS current
    DESCRIPTION
        "Notification of Event SDLC.56

        Message: 'Interface $1 Station $2, Window size is inconsistent with modulo for link - adjusted ($3 -> $4)'

        Parameters list:
              $1: sdlc56-interface
              $2: sdlc56-address
              $3: sdlc56-oldTxWindow
              $4: sdlc56-newTxWindow

        The modulo for this link has been changed by the user, rendering the
        window sizes for all pre-defined remote link stations invalid.
        The window size has been temporarily adjusted. When a link is
        configured for mod-8, the valid window sizes are 0 to 7. When the link
        is configured for mod-128, the valid window sizes are 8 to 128.
        To avoid this message in the future, change the transmit window size
        with the 'SET REMOTE TRANSMIT-WINDOW' command."
    ::= { sdlcNotificationsPrefix 56 }

sdlcNotification57 NOTIFICATION-TYPE
    OBJECTS { 
              sdlc57-interface 
            }
    STATUS current
    DESCRIPTION
        "Notification of Event SDLC.57

        Message: 'Interface $1 - Link configuration corrupted, using defaults'

        Parameters list:
              $1: sdlc57-interface

        The link configuration was somehow corrupted, possibly due to
        a software upgrade. A default link configuration has been created.
        Before operating SDLC, review the newly-created configuration and
        adjust as necessary."
    ::= { sdlcNotificationsPrefix 57 }

sdlcNotification58 NOTIFICATION-TYPE
    OBJECTS { 
              sdlc58-interface 
            }
    STATUS current
    DESCRIPTION
        "Notification of Event SDLC.58

        Message: 'Interface $1 - Configured XID/TEST timeout corrupted - fixed'

        Parameters list:
              $1: sdlc58-interface

        An invalid XID/TEST timeout value was detected in the link
        configuration, possibly due to a software upgrade. It has been
        temporarily changed to a valid value. To avoid this message in
        the future, set the XID/TEST timeout from the SDLC config prompt
        for this interface."
    ::= { sdlcNotificationsPrefix 58 }

sdlcNotification59 NOTIFICATION-TYPE
    OBJECTS { 
              sdlc59-interface 
            }
    STATUS current
    DESCRIPTION
        "Notification of Event SDLC.59

        Message: 'Interface $1 - Configured XID/TEST retry count corrupted - fixed'

        Parameters list:
              $1: sdlc59-interface

        An invalid XID/TEST retry value was detected in the link configuration,
        possibly due to a software upgrade. It has been temporarily changed to
        a valid value. To avoid this message in the future, set the XID/TEST
        retry count from the SDLC config prompt for this interface."
    ::= { sdlcNotificationsPrefix 59 }

sdlcNotification60 NOTIFICATION-TYPE
    OBJECTS { 
              sdlc60-interface 
            }
    STATUS current
    DESCRIPTION
        "Notification of Event SDLC.60

        Message: 'Interface $1 - Configured XID/TEST timeout value corrupted - fixed'

        Parameters list:
              $1: sdlc60-interface

        An invalid SNRM timeout value was detected in the link configuration,
        possibly due to a software upgrade. It has been temporarily changed to
        a valid value. To avoid this message in the future, set the
        SNRM timeout from the SDLC config prompt for this interface."
    ::= { sdlcNotificationsPrefix 60 }

sdlcNotification61 NOTIFICATION-TYPE
    OBJECTS { 
              sdlc61-interface 
            }
    STATUS current
    DESCRIPTION
        "Notification of Event SDLC.61

        Message: 'Interface $1 - Configured SNRM retry count corrupted - fixed'

        Parameters list:
              $1: sdlc61-interface

        An invalid SNRM retry value was detected in the link configuration,
        possibly due to a software upgrade. It has been temporarily changed to
        a valid value. To avoid this message in the future, set the
        SNRM retry count from the SDLC config prompt for this interface."
    ::= { sdlcNotificationsPrefix 61 }

sdlcNotification62 NOTIFICATION-TYPE
    OBJECTS { 
              sdlc62-interface 
            }
    STATUS current
    DESCRIPTION
        "Notification of Event SDLC.62

        Message: 'Interface $1 - Configured POLL timeout value corrupted - fixed'

        Parameters list:
              $1: sdlc62-interface

        An invalid POLL timeout value was detected in the link configuration,
        possibly due to a software upgrade. It has been temporarily changed to
        a valid value. To avoid this message in the future, set the
        POLL timeout from the SDLC config prompt for this interface."
    ::= { sdlcNotificationsPrefix 62 }

sdlcNotification63 NOTIFICATION-TYPE
    OBJECTS { 
              sdlc63-interface 
            }
    STATUS current
    DESCRIPTION
        "Notification of Event SDLC.63

        Message: 'Interface $1 - Configured inter-POLL delay value corrupted - fixed'

        Parameters list:
              $1: sdlc63-interface

        An invalid inter-POLL delay value was detected in the link
        configuration, possibly due to a software upgrade. It has been
        temporarily changed to a valid value. To avoid this message in the
        future, set the inter-POLL delay from the SDLC config prompt for this
        interface."
    ::= { sdlcNotificationsPrefix 63 }

sdlcNotification64 NOTIFICATION-TYPE
    OBJECTS { 
              sdlc64-interface 
            }
    STATUS current
    DESCRIPTION
        "Notification of Event SDLC.64

        Message: 'Interface $1 - Configured POLL retry count corrupted - fixed'

        Parameters list:
              $1: sdlc64-interface

        An invalid POLL retry value was detected in the link configuration,
        possibly due to a software upgrade. It has been temporarily changed to
        a valid value. To avoid this message in the future, set
        the POLL retry count from the SDLC config prompt for this interface."
    ::= { sdlcNotificationsPrefix 64 }

sdlcNotification65 NOTIFICATION-TYPE
    OBJECTS { 
              sdlc65-interface 
            }
    STATUS current
    DESCRIPTION
        "Notification of Event SDLC.65

        Message: 'Interface $1 - Configured inactivity timeout value corrupted - fixed'

        Parameters list:
              $1: sdlc65-interface

        An invalid inactivity timeout value was detected in the link
        configuration, possibly due to a software upgrade. It has been
        temporarily changed to a valid value. To avoid this message in the
        future, set the inactivity timeout from the SDLC config prompt for this
        interface."
    ::= { sdlcNotificationsPrefix 65 }

sdlcNotification66 NOTIFICATION-TYPE
    OBJECTS { 
              sdlc66-interface 
            }
    STATUS current
    DESCRIPTION
        "Notification of Event SDLC.66

        Message: 'Interface $1 - Configured RTS hold duration value corrupted - fixed'

        Parameters list:
              $1: sdlc66-interface

        An invalid RTS hold value was detected in the link configuration,
        possibly due to a software upgrade. It has been temporarily changed to
        a valid value. To avoid this message in the future, set the RTS hold
        value from the SDLC config prompt for this interface."
    ::= { sdlcNotificationsPrefix 66 }

sdlcNotification67 NOTIFICATION-TYPE
    OBJECTS { 
              sdlc67-interface 
            }
    STATUS current
    DESCRIPTION
        "Notification of Event SDLC.67

        Message: 'Interface $1 - Configured max frame size value corrupted - fixed'

        Parameters list:
              $1: sdlc67-interface

        An invalid maximum frame size value was detected in the link
        configuration, possibly due to a software upgrade. It has been
        temporarily changed to a valid value. To avoid this message in the
        future, set the maximum frame size from the SDLC config prompt for
        this interface."
    ::= { sdlcNotificationsPrefix 67 }

sdlcNotification68 NOTIFICATION-TYPE
    OBJECTS { 
              sdlc68-interface 
            }
    STATUS current
    DESCRIPTION
        "Notification of Event SDLC.68

        Message: 'Interface $1 - SDLC link counters were reset by user'

        Parameters list:
              $1: sdlc68-interface

        The link counters have been reset from the SDLC console."
    ::= { sdlcNotificationsPrefix 68 }

sdlcNotification69 NOTIFICATION-TYPE
    OBJECTS { 
              sdlc69-interface 
            }
    STATUS current
    DESCRIPTION
        "Notification of Event SDLC.69

        Message: 'Interface $1 - SDLC link counters cannot be reset'

        Parameters list:
              $1: sdlc69-interface

        The link counters could not be reset from the SDLC console.
        This is usually a temporary condition. Retry the operation."
    ::= { sdlcNotificationsPrefix 69 }

sdlcNotification70 NOTIFICATION-TYPE
    OBJECTS { 
              sdlc70-interface, 
              sdlc70-address 
            }
    STATUS current
    DESCRIPTION
        "Notification of Event SDLC.70

        Message: 'Interface $1 Link Station $2 - SDLC link counters were reset by user'

        Parameters list:
              $1: sdlc70-interface
              $2: sdlc70-address

        The user reset the counters for a remote secondary station
        from the SDLC console."
    ::= { sdlcNotificationsPrefix 70 }

sdlcNotification71 NOTIFICATION-TYPE
    OBJECTS { 
              sdlc71-interface, 
              sdlc71-address 
            }
    STATUS current
    DESCRIPTION
        "Notification of Event SDLC.71

        Message: 'Interface $1 Link Station $2 - SDLC link counters cannot be reset'

        Parameters list:
              $1: sdlc71-interface
              $2: sdlc71-address

        The user could not reset the counters for a remote secondary station
        from the SDLC console. This is usually a temporary condition.
        Retry the operation."
    ::= { sdlcNotificationsPrefix 71 }

sdlcNotification72 NOTIFICATION-TYPE
    OBJECTS { 
              sdlc72-interface, 
              sdlc72-address 
            }
    STATUS current
    DESCRIPTION
        "Notification of Event SDLC.72

        Message: 'Interface $1 SDLC station $2: DLC-SAP-CLOSED'

        Parameters list:
              $1: sdlc72-interface
              $2: sdlc72-address

        The remote link station has been closed by the router and is no
        longer active."
    ::= { sdlcNotificationsPrefix 72 }

sdlcNotification73 NOTIFICATION-TYPE
    OBJECTS { 
              sdlc73-interface 
            }
    STATUS current
    DESCRIPTION
        "Notification of Event SDLC.73

        Message: 'Interface $1: low priority buffer request failed'

        Parameters list:
              $1: sdlc73-interface

        SDLC failed to allocate memory from the router's heap because it has
        already allocated its fair share. SDLC will recover from this usually
        temporary problem."
    ::= { sdlcNotificationsPrefix 73 }

sdlcNotification74 NOTIFICATION-TYPE
    OBJECTS { 
              sdlc74-interface 
            }
    STATUS current
    DESCRIPTION
        "Notification of Event SDLC.74

        Message: 'Interface $1: high priority buffer request failed'

        Parameters list:
              $1: sdlc74-interface

        SDLC failed to allocate a high-priority buffer from the router's heap.
        As a result, SDLC will temporarily experience a loss of performance.
        SDLC sessions could possibly be lost if the condition persists."
    ::= { sdlcNotificationsPrefix 74 }

sdlcNotification75 NOTIFICATION-TYPE
    OBJECTS { 
              sdlc75-interface 
            }
    STATUS current
    DESCRIPTION
        "Notification of Event SDLC.75

        Message: 'Interface $1: buffer alloc request failed, but credit is okay'

        Parameters list:
              $1: sdlc75-interface

        SDLC failed to allocate memory from the router's heap because the heap
        is exhausted. SDLC will recover from this usually temporary problem."
    ::= { sdlcNotificationsPrefix 75 }

sdlcNotification76 NOTIFICATION-TYPE
    OBJECTS { 
              sdlc76-interface 
            }
    STATUS current
    DESCRIPTION
        "Notification of Event SDLC.76

        Message: 'Interface $1: cannot transmit I-frame. Will re-transmit later'

        Parameters list:
              $1: sdlc76-interface

        SDLC could not send an Information (I) frame to the interface.
        SDLC will attempt to re-transmit it later."
    ::= { sdlcNotificationsPrefix 76 }

sdlcNotification77 NOTIFICATION-TYPE
    OBJECTS { 
              sdlc77-interface 
            }
    STATUS current
    DESCRIPTION
        "Notification of Event SDLC.77

        Message: 'Interface $1: cannot transmit S-frame - dropped'

        Parameters list:
              $1: sdlc77-interface

        SDLC could not send a Supervisory (S) frame to the interface.
        SDLC will attempt to re-transmit it later."
    ::= { sdlcNotificationsPrefix 77 }

sdlcNotification78 NOTIFICATION-TYPE
    OBJECTS { 
              sdlc78-interface 
            }
    STATUS current
    DESCRIPTION
        "Notification of Event SDLC.78

        Message: 'Interface $1: cannot transmit U-frame - SDLC will recover'

        Parameters list:
              $1: sdlc78-interface

        SDLC could not send an Unnumbered Information (UI) frame to
        the interface. SDLC will attempt to re-transmit it later."
    ::= { sdlcNotificationsPrefix 78 }

sdlcNotification79 NOTIFICATION-TYPE
    OBJECTS { 
              sdlc79-interface 
            }
    STATUS current
    DESCRIPTION
        "Notification of Event SDLC.79

        Message: 'Interface $1: cannot transmit U-frame - SDLC will re-transmit'

        Parameters list:
              $1: sdlc79-interface

        SDLC could not send an XID or TEST frame to the interface.
        SDLC will attempt to re-transmit it later."
    ::= { sdlcNotificationsPrefix 79 }

sdlcNotification80 NOTIFICATION-TYPE
    OBJECTS { 
              sdlc80-interface 
            }
    STATUS current
    DESCRIPTION
        "Notification of Event SDLC.80

        Message: 'Interface $1: received invalid frame type - dropped'

        Parameters list:
              $1: sdlc80-interface

        SDLC received an invalid frame type. This frame was ignored."
    ::= { sdlcNotificationsPrefix 80 }

sdlcNotification81 NOTIFICATION-TYPE
    OBJECTS { 
              sdlc81-interface 
            }
    STATUS current
    DESCRIPTION
        "Notification of Event SDLC.81

        Message: 'Interface $1: received a frame from a secondary station that was not polled - dropped'

        Parameters list:
              $1: sdlc81-interface

        SDLC received a frame from a remote link station that it had
        not polled. This frame was ignored. This error may also occur if
        the poll response timeout is too short."
    ::= { sdlcNotificationsPrefix 81 }

sdlcNotification82 NOTIFICATION-TYPE
    OBJECTS { 
              sdlc82-interface 
            }
    STATUS current
    DESCRIPTION
        "Notification of Event SDLC.82

        Message: 'Interface $1: received a UI frame from a secondary station without the Final bit set - dropped'

        Parameters list:
              $1: sdlc82-interface

        SDLC received an Unnumbered Information (UI) frame without the
        Final (F) bit set. This frame was dropped."
    ::= { sdlcNotificationsPrefix 82 }

sdlcNotification83 NOTIFICATION-TYPE
    OBJECTS { 
              sdlc83-interface 
            }
    STATUS current
    DESCRIPTION
        "Notification of Event SDLC.83

        Message: 'Interface $1: received a broadcast frame from a secondary station on a multipoint line - dropped'

        Parameters list:
              $1: sdlc83-interface

        SDLC received a frame to the broadcast address on a multipoint line.
        The frame was dropped."
    ::= { sdlcNotificationsPrefix 83 }

sdlcNotification84 NOTIFICATION-TYPE
    OBJECTS { 
              sdlc84-interface 
            }
    STATUS current
    DESCRIPTION
        "Notification of Event SDLC.84

        Message: 'Interface $1: SDLC not brought up because no LINK configuration is defined'

        Parameters list:
              $1: sdlc84-interface

        SDLC could not be initialized because there is no SDLC link
        configuration for this interface."
    ::= { sdlcNotificationsPrefix 84 }

sdlcNotification85 NOTIFICATION-TYPE
    OBJECTS { 
              sdlc85-interface, 
              sdlc85-reason 
            }
    STATUS current
    DESCRIPTION
        "Notification of Event SDLC.85

        Message: 'Interface $1: signal control request failed because $2'

        Parameters list:
              $1: sdlc85-interface
              $2: sdlc85-reason

        SDLC could not control one or more signals on the interface. This could
        occur if you attempt to run SDLC over an unsupported interface."
    ::= { sdlcNotificationsPrefix 85 }

sdlcNotification86 NOTIFICATION-TYPE
    OBJECTS { 
              sdlc86-interface 
            }
    STATUS current
    DESCRIPTION
        "Notification of Event SDLC.86

        Message: 'HDX, DCD went high during HDX transmit, on interface $1'

        Parameters list:
              $1: sdlc86-interface

        DCD went high during transmission of a frame in half duplex mode.
        This is a protocol violation, and the interface will go down shortly
        in order to correct the problem."
    ::= { sdlcNotificationsPrefix 86 }

sdlcNotification87 NOTIFICATION-TYPE
    OBJECTS { 
              sdlc87-interface 
            }
    STATUS current
    DESCRIPTION
        "Notification of Event SDLC.87

        Message: 'HDX, CTS now low. Premature DCD recovery complete, on interface $1'

        Parameters list:
              $1: sdlc87-interface

        The CTS signal has transitioned to low while the interface was
        recovering from a half-duplex protocol violation. The link is now in
        the correct state and data transfer may resume."
    ::= { sdlcNotificationsPrefix 87 }

sdlcNotification88 NOTIFICATION-TYPE
    OBJECTS { 
              sdlc88-interface 
            }
    STATUS current
    DESCRIPTION
        "Notification of Event SDLC.88

        Message: 'HDX, unsolicited signal while idle, on interface $1'

        Parameters list:
              $1: sdlc88-interface

        A signal was asserted by the connected device while the line was idle.
        When operating in half-duplex mode, only the DTR/DSR signal should be
        asserted on an idle interface."
    ::= { sdlcNotificationsPrefix 88 }

sdlcNotification89 NOTIFICATION-TYPE
    OBJECTS { 
              sdlc89-interface 
            }
    STATUS current
    DESCRIPTION
        "Notification of Event SDLC.89

        Message: 'HDX, DSR or CTS went low during HDX transmit, on interface $1'

        Parameters list:
              $1: sdlc89-interface

        The DSR or CTS signal went low during transmission. This is a protocol
        violation, and the interface will go down shortly in order to correct
        the problem."
    ::= { sdlcNotificationsPrefix 89 }

sdlcNotification90 NOTIFICATION-TYPE
    OBJECTS { 
              sdlc90-interface, 
              sdlc90-address 
            }
    STATUS current
    DESCRIPTION
        "Notification of Event SDLC.90

        Message: 'Interface $1: received inappropriate frame while closing link $2 - dropped'

        Parameters list:
              $1: sdlc90-interface
              $2: sdlc90-address

        SDLC received a frame other than a UA while trying to close
        the link station. The router ignored this frame."
    ::= { sdlcNotificationsPrefix 90 }

sdlcNotification91 NOTIFICATION-TYPE
    OBJECTS { 
              sdlc91-address, 
              sdlc91-interface 
            }
    STATUS current
    DESCRIPTION
        "Notification of Event SDLC.91

        Message: 'Secondary station $1 has been dynamically added, on interface $2'

        Parameters list:
              $1: sdlc91-address
              $2: sdlc91-interface

        An SDLC remote link station was added by the user from the
        SDLC console and is now available for use."
    ::= { sdlcNotificationsPrefix 91 }

sdlcNotification92 NOTIFICATION-TYPE
    OBJECTS { 
              sdlc92-address, 
              sdlc92-interface 
            }
    STATUS current
    DESCRIPTION
        "Notification of Event SDLC.92

        Message: 'Secondary station $1 has been dynamically deleted, on interface $2'

        Parameters list:
              $1: sdlc92-address
              $2: sdlc92-interface

        An SDLC remote link station was deleted by the user from the
        SDLC console and is no longer available for use."
    ::= { sdlcNotificationsPrefix 92 }

sdlcNotification93 NOTIFICATION-TYPE
    OBJECTS { 
              sdlc93-interface 
            }
    STATUS current
    DESCRIPTION
        "Notification of Event SDLC.93

        Message: 'Interface $1: received a frame from an invalid station address - dropped'

        Parameters list:
              $1: sdlc93-interface

        SDLC received a frame from a remote link station that contains an
        unrecognized station address. The router ignored this frame."
    ::= { sdlcNotificationsPrefix 93 }

sdlcNotification94 NOTIFICATION-TYPE
    OBJECTS { 
              sdlc94-interface, 
              sdlc94-address 
            }
    STATUS current
    DESCRIPTION
        "Notification of Event SDLC.94

        Message: 'Interface $1 Link Station $2 - station is disabled; frame ignored'

        Parameters list:
              $1: sdlc94-interface
              $2: sdlc94-address

        The router ignored the received frame for this station, because
        the target station is in a disabled state."
    ::= { sdlcNotificationsPrefix 94 }

sdlcNotification95 NOTIFICATION-TYPE
    OBJECTS { 
              sdlc95-interface, 
              sdlc95-address 
            }
    STATUS current
    DESCRIPTION
        "Notification of Event SDLC.95

        Message: 'Interface $1 SDLC station $2: DLC-RX-NXID-WHILE-IN-NRM'

        Parameters list:
              $1: sdlc95-interface
              $2: sdlc95-address

        The local SDLC secondary link station received a null XID frame from a
        remote link station while in NRM. We treat this as an indication that
        the link failed at the sending end and this is an attempt to reestablish
        the connection."
    ::= { sdlcNotificationsPrefix 95 }


END
