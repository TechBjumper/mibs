--
-- 	Copyright 1992, 1993, 1995, 1996 Shiva Corporation
--

-- Variables for configuring SNMP access to a device

SHIVA-COMM-MIB DEFINITIONS ::= BEGIN

IMPORTS
	OBJECT-TYPE
		FROM RFC-1212		-- Concise MIB Definitions
	DisplayString
		FROM RFC1213-MIB
	tCommunity
		FROM SHIVA-MIB;


    tCommunityTrapHostType OBJECT-TYPE
	SYNTAX	INTEGER {
		unconfigured(1),	-- address to be ignored
		ip(2),			-- address is a four byte IP address
		ipx(3)			-- address is a 12-byte IPX address
	}
	ACCESS  read-write
	STATUS  mandatory
	DESCRIPTION
		"This is the address type of the trap host.  The Trap Host
		is the host to which the device sends all traps."
	::= { tCommunity 1 }

    tCommunityTrapHostAddress OBJECT-TYPE
	SYNTAX	OCTET STRING
	ACCESS  read-write
	STATUS  mandatory
	DESCRIPTION
		"This is the Network Address of the host.  It is interpreted
		according to the value of tCommunityTrapHostType."
	::= { tCommunity 2 }

    tCommunitySetHostType OBJECT-TYPE
	SYNTAX	INTEGER {
		unconfigured(1),	-- address to be ignored
		ip(2),			-- address is a four byte IP address
		ipx(3),			-- address is a 12-byte IPX address
		netbios(4),		-- address is a 16-byte NetBIOS name
		ddprange(6)		-- address is 2 two byte ddp nets
	}
	ACCESS  read-write
	STATUS  mandatory
	DESCRIPTION
		"This is the address family of the set host.  The Set Host is
		a host which is privileged to change any MIB variable."
	::= { tCommunity 3 }

    tCommunitySetHostAddress OBJECT-TYPE
	SYNTAX	OCTET STRING
	ACCESS  read-write
	STATUS  mandatory
	DESCRIPTION
		"This is the Network Address of the Set Host.  It is
		interpreted  according to the value of
		tCommunityTrapHostType."
	::= { tCommunity 4 }

    tCommunityTable OBJECT-TYPE
	SYNTAX SEQUENCE OF TCommunityEntry
	ACCESS not-accessible
	STATUS mandatory
	DESCRIPTION
		"The Communities Table describes the various communities
		known to the the device."
	::= { tCommunity 5 }

     tCommunityEntry OBJECT-TYPE
	SYNTAX	TCommunityEntry
	ACCESS	not-accessible
	STATUS	mandatory
	DESCRIPTION
		"The type of a row object in the community table.  This
		represents a single SNMP Community.  Community entries
		are indexed by counting integers starting with 1."
	--Index is a simple INTEGER, not a row element
	--INDEX { INTEGER }
	::= { tCommunityTable 1 }

   TCommunityEntry ::= SEQUENCE {
	tCommunityName		DisplayString,
	tCommunityAccess	INTEGER
    }

    tCommunityName OBJECT-TYPE
	SYNTAX DisplayString
	ACCESS read-write
	STATUS mandatory
	DESCRIPTION
		"The name of this community."
	::= { tCommunityEntry 1 }

    tCommunityAccess OBJECT-TYPE
	SYNTAX INTEGER {
		no-access(1),		
		read-only-access(2),	-- name changed for Sun Net Manager!
		clear-statistics(3),
		configure(4)
	}
	ACCESS read-write
	STATUS mandatory
	DESCRIPTION
		"This defines the privilege of the community.  A 'read-only'
		community can examine any readable variable.  A
		'clear-statistics' community can reset non-critical counters.
		A 'configure' community has complete privileges.  By setting
		the community access to 'no-access', a management station
		can deny all access by that community."
	::= { tCommunityEntry 2 }

    tCommunityTrapTable OBJECT-TYPE
	SYNTAX SEQUENCE OF TCommunityTrapEntry
	ACCESS not-accessible
	STATUS mandatory
	DESCRIPTION
		"The Trap Table describes the list of hosts and the assosicated
		 host type  to be recepients of traps."
	::= { tCommunity 6 }

     tCommunityTrapEntry OBJECT-TYPE
	SYNTAX	TCommunityTrapEntry
	ACCESS	not-accessible
	STATUS	mandatory
	DESCRIPTION
		"The type of a row object in the community trap table.  This
		represents a single trap host type and its address.  
		Community trap entries are indexed by counting integers 
		starting with 1."
	--INDEX { INTEGER }
	::= { tCommunityTrapTable 1 }

   TCommunityTrapEntry ::= SEQUENCE {
	tCommunityTrapEntryHostAddress	OCTET STRING,
	tCommunityTrapEntryHostType	INTEGER
    }

    tCommunityTrapEntryHostAddress OBJECT-TYPE
	SYNTAX	OCTET STRING
	ACCESS  read-write
	STATUS  mandatory
	DESCRIPTION
		"Address of the trap host.  It is interpreted
		 according to the value of tCommunityTrapEntryHostType"
	::= { tCommunityTrapEntry 1 }
	
    tCommunityTrapEntryHostType OBJECT-TYPE
	SYNTAX	INTEGER {
		unconfigured(1),	-- address to be ignored
		ip(2),			-- address is a four byte IP address
		ipx(3)			-- address is a 12-byte IPX address
	}
	ACCESS  read-write
	STATUS  mandatory
	DESCRIPTION
		"Address type of the trap host"  
	::= { tCommunityTrapEntry 2 }

END
