-- file automatically created


TELDAT-TRAP-SNAT-MIB DEFINITIONS ::= BEGIN


IMPORTS
	MODULE-IDENTITY,OBJECT-TYPE,OBJECT-IDENTITY,NOTIFICATION-TYPE,Integer32,IpAddress
		FROM SNMPv2-SMI
	DisplayString
		FROM SNMPv2-TC
	telEventTraps
		FROM TELDAT-MIB;


snatTrapsMIB MODULE-IDENTITY
    LAST-UPDATED "201401200930Z"
    ORGANIZATION "Teldat, S.A."
    CONTACT-INFO 
        "Teldat, S.A.
        Customer Service

        Postal: Parque Tecnologico de Madrid
                Tres Cantos 28760
                Madrid, SPAIN

        Tel.: +34 918 076 565

        http://www.teldat.com"
    DESCRIPTION
        "This Module Information Base file is defined for managing received
        SNMP notifications generated by the SNAT event subsystem."
    REVISION "201401200930Z"
    DESCRIPTION "Initial implementation"
        ::= { telEventTraps 186 }


snatEventsGroup	OBJECT IDENTIFIER	::= { snatTrapsMIB 1 }

snatNotifications	OBJECT IDENTIFIER	::= { snatTrapsMIB 2 }
snatNotificationsPrefix	OBJECT IDENTIFIER	::= { snatNotifications 0 }

snatEventObjects1 OBJECT-IDENTITY
    STATUS current
    DESCRIPTION
        "Event SNAT.1
        This message is generated for each packet which has passed
        NAT in."
    ::= { snatEventsGroup 1 }

snat1-source-ip-address OBJECT-TYPE
    SYNTAX IpAddress
    MAX-ACCESS accessible-for-notify
    STATUS current
    DESCRIPTION
        "Parameter 'source-ip-address' in event SNAT.1"
    ::= { snatEventObjects1 1 }

snat1-destination-ip-address OBJECT-TYPE
    SYNTAX IpAddress
    MAX-ACCESS accessible-for-notify
    STATUS current
    DESCRIPTION
        "Parameter 'destination-ip-address' in event SNAT.1"
    ::= { snatEventObjects1 2 }

snat1-source-ip-address-nat OBJECT-TYPE
    SYNTAX IpAddress
    MAX-ACCESS accessible-for-notify
    STATUS current
    DESCRIPTION
        "Parameter 'source-ip-address-nat' in event SNAT.1"
    ::= { snatEventObjects1 3 }

snat1-destination-ip-address-nat OBJECT-TYPE
    SYNTAX IpAddress
    MAX-ACCESS accessible-for-notify
    STATUS current
    DESCRIPTION
        "Parameter 'destination-ip-address-nat' in event SNAT.1"
    ::= { snatEventObjects1 4 }

snatEventObjects2 OBJECT-IDENTITY
    STATUS current
    DESCRIPTION
        "Event SNAT.2
        This message is generated for each packet which has passed
        NAT out."
    ::= { snatEventsGroup 2 }

snat2-source-ip-address OBJECT-TYPE
    SYNTAX IpAddress
    MAX-ACCESS accessible-for-notify
    STATUS current
    DESCRIPTION
        "Parameter 'source-ip-address' in event SNAT.2"
    ::= { snatEventObjects2 1 }

snat2-destination-ip-address OBJECT-TYPE
    SYNTAX IpAddress
    MAX-ACCESS accessible-for-notify
    STATUS current
    DESCRIPTION
        "Parameter 'destination-ip-address' in event SNAT.2"
    ::= { snatEventObjects2 2 }

snat2-source-ip-address-nat OBJECT-TYPE
    SYNTAX IpAddress
    MAX-ACCESS accessible-for-notify
    STATUS current
    DESCRIPTION
        "Parameter 'source-ip-address-nat' in event SNAT.2"
    ::= { snatEventObjects2 3 }

snat2-destination-ip-address-nat OBJECT-TYPE
    SYNTAX IpAddress
    MAX-ACCESS accessible-for-notify
    STATUS current
    DESCRIPTION
        "Parameter 'destination-ip-address-nat' in event SNAT.2"
    ::= { snatEventObjects2 4 }

snatEventObjects3 OBJECT-IDENTITY
    STATUS current
    DESCRIPTION
        "Event SNAT.3
        This message is generated for each packet which has no been
        NATed in."
    ::= { snatEventsGroup 3 }

snat3-source-ip-address OBJECT-TYPE
    SYNTAX IpAddress
    MAX-ACCESS accessible-for-notify
    STATUS current
    DESCRIPTION
        "Parameter 'source-ip-address' in event SNAT.3"
    ::= { snatEventObjects3 1 }

snat3-destination-ip-address OBJECT-TYPE
    SYNTAX IpAddress
    MAX-ACCESS accessible-for-notify
    STATUS current
    DESCRIPTION
        "Parameter 'destination-ip-address' in event SNAT.3"
    ::= { snatEventObjects3 2 }

snatEventObjects4 OBJECT-IDENTITY
    STATUS current
    DESCRIPTION
        "Event SNAT.4
        This message is generated for each packet which has no been
        NATed out."
    ::= { snatEventsGroup 4 }

snat4-source-ip-address OBJECT-TYPE
    SYNTAX IpAddress
    MAX-ACCESS accessible-for-notify
    STATUS current
    DESCRIPTION
        "Parameter 'source-ip-address' in event SNAT.4"
    ::= { snatEventObjects4 1 }

snat4-destination-ip-address OBJECT-TYPE
    SYNTAX IpAddress
    MAX-ACCESS accessible-for-notify
    STATUS current
    DESCRIPTION
        "Parameter 'destination-ip-address' in event SNAT.4"
    ::= { snatEventObjects4 2 }

snatEventObjects5 OBJECT-IDENTITY
    STATUS current
    DESCRIPTION
        "Event SNAT.5
        This message is generated for each unvalid SNAT rule loaded
        that is not valid."
    ::= { snatEventsGroup 5 }

snat5-rule-num OBJECT-TYPE
    SYNTAX Integer32
    MAX-ACCESS accessible-for-notify
    STATUS current
    DESCRIPTION
        "Parameter 'rule-num' in event SNAT.5"
    ::= { snatEventObjects5 1 }

snat5-reason-txt OBJECT-TYPE
    SYNTAX DisplayString
    MAX-ACCESS accessible-for-notify
    STATUS current
    DESCRIPTION
        "Parameter 'reason-txt' in event SNAT.5"
    ::= { snatEventObjects5 2 }


snatNotification1 NOTIFICATION-TYPE
    OBJECTS { 
              snat1-source-ip-address, 
              snat1-destination-ip-address,
              snat1-source-ip-address-nat,
              snat1-destination-ip-address-nat 
            }
    STATUS current
    DESCRIPTION
        "Notification of Event SNAT.1

        Message: 'NAT-IN: ($1, $2)->($3, $4)'

        Parameters list:
              $1: snat1-source-ip-address
              $2: snat1-destination-ip-address
              $3: snat1-source-ip-address-nat
              $4: snat1-destination-ip-address-nat

        This message is generated for each packet which has passed
        NAT in."
    ::= { snatNotificationsPrefix 1 }

snatNotification2 NOTIFICATION-TYPE
    OBJECTS { 
              snat2-source-ip-address, 
              snat2-destination-ip-address,
              snat2-source-ip-address-nat,
              snat2-destination-ip-address-nat 
            }
    STATUS current
    DESCRIPTION
        "Notification of Event SNAT.2

        Message: 'NAT-OUT: ($1, $2)->($3, $4)'

        Parameters list:
              $1: snat2-source-ip-address
              $2: snat2-destination-ip-address
              $3: snat2-source-ip-address-nat
              $4: snat2-destination-ip-address-nat

        This message is generated for each packet which has passed
        NAT out."
    ::= { snatNotificationsPrefix 2 }

snatNotification3 NOTIFICATION-TYPE
    OBJECTS { 
              snat3-source-ip-address, 
              snat3-destination-ip-address 
            }
    STATUS current
    DESCRIPTION
        "Notification of Event SNAT.3

        Message: 'NAT-IN: ($1, $2)-> no nat'

        Parameters list:
              $1: snat3-source-ip-address
              $2: snat3-destination-ip-address

        This message is generated for each packet which has no been
        NATed in."
    ::= { snatNotificationsPrefix 3 }

snatNotification4 NOTIFICATION-TYPE
    OBJECTS { 
              snat4-source-ip-address, 
              snat4-destination-ip-address 
            }
    STATUS current
    DESCRIPTION
        "Notification of Event SNAT.4

        Message: 'NAT-OUT: ($1, $2)-> no nat'

        Parameters list:
              $1: snat4-source-ip-address
              $2: snat4-destination-ip-address

        This message is generated for each packet which has no been
        NATed out."
    ::= { snatNotificationsPrefix 4 }

snatNotification5 NOTIFICATION-TYPE
    OBJECTS { 
              snat5-rule-num, 
              snat5-reason-txt 
            }
    STATUS current
    DESCRIPTION
        "Notification of Event SNAT.5

        Message: 'Invalid SNAT rule (#$1): $2'

        Parameters list:
              $1: snat5-rule-num
              $2: snat5-reason-txt

        This message is generated for each unvalid SNAT rule loaded
        that is not valid."
    ::= { snatNotificationsPrefix 5 }


END
