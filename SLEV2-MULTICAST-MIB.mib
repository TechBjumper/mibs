--
-- slev2-multicast-mib.mib
-- MIB generated by MG-SOFT Visual MIB Builder Version 6.0  Build 88
-- Tuesday, March 29, 2016 at 14:32:14
--

--  SLEV2-MULTICAST-MIB.my
-- MIB generated by MG-SOFT Visual MIB Builder Version 6.0  Build 88
-- Friday, October 05, 2007 at 10:51:05
-- 

	SLEV2-MULTICAST-MIB DEFINITIONS ::= BEGIN
 
		IMPORTS
			sleV2Mgmt			
				FROM DASAN-SMI			
			IANAipMRouteProtocol, IANAipRouteProtocol			
				FROM IANA-RTPROTO-MIB			
			InetAddressIPv6			
				FROM INET-ADDRESS-MIB			
			SleControlStatusType, SleControlRequestResultType			
				FROM SLE-TC-MIB			
			OBJECT-GROUP, NOTIFICATION-GROUP			
				FROM SNMPv2-CONF			
			TimeTicks, IpAddress, Integer32, Unsigned32, Gauge32, 
			Counter32, Counter64, OBJECT-TYPE, MODULE-IDENTITY, 
			NOTIFICATION-TYPE			
				FROM SNMPv2-SMI			
			TimeStamp			
				FROM SNMPv2-TC;
	
	
--  1.3.6.1.4.1.6296.102.12
-- November 09, 2005 at 09:03 GMT
		sleV2Multicast MODULE-IDENTITY 
			LAST-UPDATED "200511090903Z"		-- November 09, 2005 at 09:03 GMT
			ORGANIZATION 
				"Dasan Co., Ltd."
			CONTACT-INFO 
				" "
			DESCRIPTION 
				" "
			::= { sleV2Mgmt 12 }

		
	
--
-- Type definitions
--
	
--  Type definitions
-- 
-- 1.3.6.1.4.1.6296.102.12
-- December 08, 2004 at 09:03 GMT
-- 
-- Type definitions
-- 
		Boolean ::= INTEGER
			{
			disable(0),
			enable(1)
			}

	
	
--
-- Node definitions
--
	
--  Node definitions
-- 
-- Multicast Common Configuration
-- 1.3.6.1.4.1.6296.102.12.1
		sleV2McastBase OBJECT IDENTIFIER ::= { sleV2Multicast 1 }

		
--  Multicast for IPv4
-- 1.3.6.1.4.1.6296.102.12.2
		sleV2Multicast4 OBJECT IDENTIFIER ::= { sleV2Multicast 2 }

		
--  Multicast Routing
-- 1.3.6.1.4.1.6296.102.12.2.1
		sleV2Mrib4 OBJECT IDENTIFIER ::= { sleV2Multicast4 1 }

		
--  Multicast Routing Configuration
-- 1.3.6.1.4.1.6296.102.12.2.1.1
		sleV2M4RouteBase OBJECT IDENTIFIER ::= { sleV2Mrib4 1 }

		
--  Multicast Routing Configuration Group
-- 1.3.6.1.4.1.6296.102.12.2.1.1.1
		sleV2M4RouteInfo OBJECT IDENTIFIER ::= { sleV2M4RouteBase 1 }

		
--  1.3.6.1.4.1.6296.102.12.2.1.1.1.1
		sleV2M4RouteInfoActivity OBJECT-TYPE
			SYNTAX Boolean
			MAX-ACCESS read-only
			STATUS current
			DESCRIPTION
				"Enable/disable status of multicast routing on this router."
			::= { sleV2M4RouteInfo 1 }

		
--  1.3.6.1.4.1.6296.102.12.2.1.1.1.2
		sleV2M4RouteInfoLimit OBJECT-TYPE
			SYNTAX INTEGER (0 | 1..2147483647)
			MAX-ACCESS read-only
			STATUS current
			DESCRIPTION
				"Limiting number of multicast routes that can be added to 
				a multicast routing table."
			::= { sleV2M4RouteInfo 2 }

		
--  1.3.6.1.4.1.6296.102.12.2.1.1.1.3
		sleV2M4RouteInfoThreshold OBJECT-TYPE
			SYNTAX INTEGER (1..2147483647)
			MAX-ACCESS read-only
			STATUS current
			DESCRIPTION
				"Threshold number at which to generate a warning message."
			::= { sleV2M4RouteInfo 3 }

		
--  1.3.6.1.4.1.6296.102.12.2.1.1.1.4
		sleV2M4RouteInfoUnknownFlood OBJECT-TYPE
			SYNTAX Boolean
			MAX-ACCESS read-only
			STATUS current
			DESCRIPTION
				"Flooding status of unknown multicast packets on this router."
			::= { sleV2M4RouteInfo 4 }

		
--  1.3.6.1.4.1.6296.102.12.2.1.1.1.5
		sleV2M4RouteInfoEntryCount OBJECT-TYPE
			SYNTAX Gauge32
			MAX-ACCESS read-only
			STATUS current
			DESCRIPTION
				"The number of rows in the sleV2MRoute4Table. 
				This can be used to monitor the multicast routing table size"
			::= { sleV2M4RouteInfo 5 }

		
--  1.3.6.1.4.1.6296.102.12.2.1.1.1.6
		sleV2M4RouteInfoNocacheRecvMsg OBJECT-TYPE
			SYNTAX Counter64
			MAX-ACCESS read-only
			STATUS current
			DESCRIPTION
				"The number of all NOCACHE event messages which this MRIB has received 
				from the Multicast Forwarder for all entries.
				The Multicast Forwarder generates the NOCACHE event when it receives 
				a data packet destined to (S,G), and does not have an (S,G) MRT entry."
			::= { sleV2M4RouteInfo 6 }

		
--  1.3.6.1.4.1.6296.102.12.2.1.1.1.7
		sleV2M4RouteInfoWholepktRecvMsg OBJECT-TYPE
			SYNTAX Counter64
			MAX-ACCESS read-only
			STATUS current
			DESCRIPTION
				"The number of all WHOLEPKT event messages which this MRIB has received 
				from the Multicast Forwarder for all entries.
				The Multicast Forwarder generates the WHOLEPKT event whenever 
				the special REGISTER VIF appears in the out interface list of an (S,G) MRT 
				in the multicast forwarder."
			::= { sleV2M4RouteInfo 7 }

		
--  1.3.6.1.4.1.6296.102.12.2.1.1.1.8
		sleV2M4RouteInfoWrongvifRecvMsg OBJECT-TYPE
			SYNTAX Counter64
			MAX-ACCESS read-only
			STATUS current
			DESCRIPTION
				"The number of all WRONGVIF event messages which this MRIB has received 
				from the Multicast Forwarder for all entries.
				The Multicast Forwarder generates a WRONGVIF event when it 
				receives a packet destined to (S,G) on an interface that 
				does not match the IIF of the (S,G) MRT in the Multicast Forwarder."
			::= { sleV2M4RouteInfo 8 }

		
--  1.3.6.1.4.1.6296.102.12.2.1.1.1.9
		sleV2M4RouteInfoNocacheSentMsg OBJECT-TYPE
			SYNTAX Counter64
			MAX-ACCESS read-only
			STATUS current
			DESCRIPTION
				"The number of all NSM_MSG_IPV4_MRT_NOCACHE(NSM_MSG_IPV6_MRT_NOCACHE) 
				messages which MRIB sent to multicast protocol for all entries.
				When the MRIB receives NOCACHE event message from Multicast Forwarder, 
				it relays it to all multicast protocols, ensuring that the correct 
				multicast protocol adds an (S,G) MRT to the MRIB."
			::= { sleV2M4RouteInfo 9 }

		
--  1.3.6.1.4.1.6296.102.12.2.1.1.1.10
		sleV2M4RouteInfoWholepktSentMsg OBJECT-TYPE
			SYNTAX Counter64
			MAX-ACCESS read-only
			STATUS current
			DESCRIPTION
				"The number of all NSM_MSG_IPV4_MRT_WHOLEPKT_REQUEST(NSM_MSG_IPV6_MRT_WHOLEPKT_REQUEST) 
				messages which MRIB sent to multicast protocol for all entries.
				When the MRIB receives WHOLEPKT event message from Multicast Forwarder, 
				it sends an message to the multicast protocol.
				
				It is inefficient and expensive to relay this whole message to the multicast 
				protocol, because IP packet can be as large as 64 KB.
				To avoid sending the WHOLEPKT message to the multicast protocol, 
				NSM_MSG_IPV4_MRT_WHOLEPKT_REQUEST message contains the (S,G) key, 
				the REGISTER VIF index, and a unique identifier for the instance of 
				the WHOLEPKT message from the Multicast Forwarder, whitout the all packet data."
			::= { sleV2M4RouteInfo 10 }

		
--  1.3.6.1.4.1.6296.102.12.2.1.1.1.11
		sleV2M4RouteInfoWrongvifSentMsg OBJECT-TYPE
			SYNTAX Counter64
			MAX-ACCESS read-only
			STATUS current
			DESCRIPTION
				"The number of all NSM_MSG_IPV4_MRT_WRONGVIF(NSM_MSG_IPV6_MRT_WRONGVIF) messages 
				which MRIB sent to multicast protocol for all entries.
				When the MRIB receives WRONGVIF event message from Multicast Forwarder, 
				it relays it to all multicast protocols that have requested PIM service."
			::= { sleV2M4RouteInfo 11 }

		
		sleV2M4RoutInfoIpMrouteJoinedCount OBJECT-TYPE
			SYNTAX Counter32
			MAX-ACCESS read-only
			STATUS current
			DESCRIPTION
				"The count of Mroute Joined channel"
			::= { sleV2M4RouteInfo 12 }

		
--  Multicast Routing Configuration Control
-- 1.3.6.1.4.1.6296.102.12.2.1.1.2
		sleV2M4RouteInfoControl OBJECT IDENTIFIER ::= { sleV2M4RouteBase 2 }

		
--  1.3.6.1.4.1.6296.102.12.2.1.1.2.1
		sleV2M4RouteInfoControlRequest OBJECT-TYPE
			SYNTAX INTEGER
				{
				setMRouteInfoActivity(1),
				setMRouteInfoLimitProfile(2),
				setMRouteInfoUnknownFlood(3)
				}
			MAX-ACCESS read-write
			STATUS current
			DESCRIPTION
				" The request of a user command"
			::= { sleV2M4RouteInfoControl 1 }

		
--  1.3.6.1.4.1.6296.102.12.2.1.1.2.2
		sleV2M4RouteInfoControlStatus OBJECT-TYPE
			SYNTAX SleControlStatusType
			MAX-ACCESS read-only
			STATUS current
			DESCRIPTION
				"The status of user command"
			::= { sleV2M4RouteInfoControl 2 }

		
--  1.3.6.1.4.1.6296.102.12.2.1.1.2.3
		sleV2M4RouteInfoControlTimer OBJECT-TYPE
			SYNTAX Gauge32
			MAX-ACCESS read-write
			STATUS current
			DESCRIPTION
				" The maximum time for the manager for a long running user command"
			::= { sleV2M4RouteInfoControl 3 }

		
--  1.3.6.1.4.1.6296.102.12.2.1.1.2.4
		sleV2M4RouteInfoControlTimeStamp OBJECT-TYPE
			SYNTAX TimeStamp
			MAX-ACCESS read-only
			STATUS current
			DESCRIPTION
				" The time stamp of the last command(end of command)"
			::= { sleV2M4RouteInfoControl 4 }

		
--  1.3.6.1.4.1.6296.102.12.2.1.1.2.5
		sleV2M4RouteInfoControlReqResult OBJECT-TYPE
			SYNTAX SleControlRequestResultType
			MAX-ACCESS read-only
			STATUS current
			DESCRIPTION
				" The result of the last user command"
			::= { sleV2M4RouteInfoControl 5 }

		
--  1.3.6.1.4.1.6296.102.12.2.1.1.2.6
		sleV2M4RouteInfoControlActivity OBJECT-TYPE
			SYNTAX Boolean
			MAX-ACCESS read-write
			STATUS current
			DESCRIPTION
				"CLI:(no) ip multicast-routing"
			::= { sleV2M4RouteInfoControl 6 }

		
--  1.3.6.1.4.1.6296.102.12.2.1.1.2.7
		sleV2M4RouteInfoControlLimit OBJECT-TYPE
			SYNTAX INTEGER (0 | 1..2147483647)
			MAX-ACCESS read-write
			STATUS current
			DESCRIPTION
				"CLI:(no) ip multicast route-limit LIMIT (THRESHOLD)
				value(-1) : (no)"
			::= { sleV2M4RouteInfoControl 7 }

		
--  1.3.6.1.4.1.6296.102.12.2.1.1.2.8
		sleV2M4RouteInfoControlThreshold OBJECT-TYPE
			SYNTAX INTEGER (-1 | 1..2147483647)
			MAX-ACCESS read-write
			STATUS current
			DESCRIPTION
				"CLI:(no) ip multicast route-limit LIMIT (THRESHOLD)
				value(-1) : (no)"
			::= { sleV2M4RouteInfoControl 8 }

		
--  1.3.6.1.4.1.6296.102.12.2.1.1.2.9
		sleV2M4RouteInfoControlUnknownFlood OBJECT-TYPE
			SYNTAX Boolean
			MAX-ACCESS read-write
			STATUS current
			DESCRIPTION
				"CLI: (no) ip multicast unknown-flood"
			::= { sleV2M4RouteInfoControl 9 }

		
--  Multicast Routing Configuration Notification
-- 1.3.6.1.4.1.6296.102.12.2.1.1.3
		sleV2M4RouteInfoNotification OBJECT IDENTIFIER ::= { sleV2M4RouteBase 3 }

		
--  1.3.6.1.4.1.6296.102.12.2.1.1.3.1
		sleV2M4RouteInfoActivityChanged NOTIFICATION-TYPE
			OBJECTS { sleV2M4RouteInfoControlRequest, sleV2M4RouteInfoControlReqResult, sleV2M4RouteInfoControlTimeStamp, sleV2M4RouteInfoActivity }
			STATUS current
			DESCRIPTION 
				" "
			::= { sleV2M4RouteInfoNotification 1 }

		
--  1.3.6.1.4.1.6296.102.12.2.1.1.3.2
		sleV2M4RouteInfoLimitChanged NOTIFICATION-TYPE
			OBJECTS { sleV2M4RouteInfoControlRequest, sleV2M4RouteInfoControlReqResult, sleV2M4RouteInfoControlTimeStamp, sleV2M4RouteInfoLimit, sleV2M4RouteInfoThreshold
				 }
			STATUS current
			DESCRIPTION 
				"Description."
			::= { sleV2M4RouteInfoNotification 2 }

		
--  1.3.6.1.4.1.6296.102.12.2.1.1.3.3
		sleV2M4RouteInfoUnkwonFloodChanged NOTIFICATION-TYPE
			OBJECTS { sleV2M4RouteInfoControlRequest, sleV2M4RouteInfoControlReqResult, sleV2M4RouteInfoControlTimeStamp, sleV2M4RouteInfoUnknownFlood }
			STATUS current
			DESCRIPTION 
				"Description."
			::= { sleV2M4RouteInfoNotification 3 }

		
--  Multicast Routing Information Base
-- 1.3.6.1.4.1.6296.102.12.2.1.2
		sleV2M4Route OBJECT IDENTIFIER ::= { sleV2Mrib4 2 }

		
--  Multicast Routing Information Base Table
-- 1.3.6.1.4.1.6296.102.12.2.1.2.1
		sleV2M4RouteTable OBJECT-TYPE
			SYNTAX SEQUENCE OF SleV2M4RouteEntry
			MAX-ACCESS not-accessible
			STATUS current
			DESCRIPTION
				"The (conceptual) table containing multicast routing
				information for IP datagrams sent by particular sources to
				the IP multicast groups known to this router.
				"
			::= { sleV2M4Route 1 }

		
--  Multicast Routing Information Base Entry
-- 1.3.6.1.4.1.6296.102.12.2.2.2.1.1
		sleV2M4RouteEntry OBJECT-TYPE
			SYNTAX SleV2M4RouteEntry
			MAX-ACCESS not-accessible
			STATUS current
			DESCRIPTION
				"An entry (conceptual row) containing the multicast routing
				information for IP datagrams from a particular source and
				addressed to a particular IP multicast group address.
				Discontinuities in counters in this entry can be detected by
				observing the value of sleV2M4RouteUpTime.
				key: sleV2M4RouteGroup, sleV2M4RouteSource, sleV2M4RouteSrcMask"
			INDEX { sleV2M4RouteGroup, sleV2M4RouteSource, sleV2M4RouteSrcMask }
			::= { sleV2M4RouteTable 1 }

		
		SleV2M4RouteEntry ::=
			SEQUENCE { 
				sleV2M4RouteGroup
					IpAddress,
				sleV2M4RouteSource
					IpAddress,
				sleV2M4RouteSrcMask
					IpAddress,
				sleV2M4RouteInInterface
					Integer32,
				sleV2M4RouteUpstreamNeighbor
					IpAddress,
				sleV2M4RouteUpTime
					TimeTicks,
				sleV2MRouteExpiryTime
					TimeTicks,
				sleV2M4RouteMcProtocol
					IANAipMRouteProtocol,
				sleV2M4RouteRtProtocol
					IANAipRouteProtocol,
				sleV2M4RouteRtAddress
					IpAddress,
				sleV2M4RouteRtMask
					INTEGER,
				sleV2M4RouteRtType
					INTEGER,
				sleV2M4RouteOutIfCount
					Integer32,
				sleV2M4RouteOutInterface
					OCTET STRING,
				sleV2M4RouteFlags
					BITS,
				sleV2M4RouteStsFwdPkts
					Counter64,
				sleV2M4RouteStsFwdBytes
					Counter64,
				sleV2M4RouteStsWrongIfPkts
					Counter64,
				sleV2M4RouteStsWholepktRecvMsg
					Counter64,
				sleV2M4RouteStsWrongvifRecvMsg
					Counter64,
				sleV2M4RouteStsWholepktSentMsg
					Counter64,
				sleV2M4RouteStsWrongvifSentMsg
					Counter64,
				sleV2M4RouteStsTimedSentMsg
					Counter64,
				sleV2M4RouteStsImmediateSentMsg
					Counter64,
				sleV2M4RouteStsRegAckRecvMsg
					Counter64,
				sleV2M4RouteStsRegNackRecvMsg
					Counter64,
				sleV2M4RouteStsRegSentPkts
					Counter64
			 }

--  1.3.6.1.4.1.6296.102.12.2.2.2.1.1.1
		sleV2M4RouteGroup OBJECT-TYPE
			SYNTAX IpAddress
			MAX-ACCESS read-only
			STATUS current
			DESCRIPTION
				"The IP multicast group address for which this entry 
				contains multicast routing information."
			::= { sleV2M4RouteEntry 1 }

		
--  1.3.6.1.4.1.6296.102.12.2.2.2.1.1.2
		sleV2M4RouteSource OBJECT-TYPE
			SYNTAX IpAddress
			MAX-ACCESS read-only
			STATUS current
			DESCRIPTION
				"The network address which when combined with the 
				corresponding value of ipMRouteSourceMask identifies the 
				sources for which this entry contains multicast routing 
				information. For (*,G) entry, value 0.0.0.0"
			::= { sleV2M4RouteEntry 2 }

		
--  1.3.6.1.4.1.6296.102.12.2.2.2.1.1.3
		sleV2M4RouteSrcMask OBJECT-TYPE
			SYNTAX IpAddress
			MAX-ACCESS read-only
			STATUS current
			DESCRIPTION
				"The network mask which when combined with the corresponding 
				value of  sleV2M4RouteSource identifies the sources for which 
				this entry contains multicast routing information.
				For (*,G) entry, value 0.0.0.0"
			::= { sleV2M4RouteEntry 3 }

		
--  1.3.6.1.4.1.6296.102.12.2.2.2.1.1.4
		sleV2M4RouteInInterface OBJECT-TYPE
			SYNTAX Integer32
			MAX-ACCESS read-only
			STATUS current
			DESCRIPTION
				"The value of ifIndex for the interface on which IP
				datagrams sent by these sources to this multicast address
				are received.  A value of 0 indicates that datagrams are not
				subject to an incoming interface check, but may be accepted
				on multiple interfaces (e.g., in CBT)."
			::= { sleV2M4RouteEntry 4 }

		
--  1.3.6.1.4.1.6296.102.12.2.2.2.1.1.5
		sleV2M4RouteUpstreamNeighbor OBJECT-TYPE
			SYNTAX IpAddress
			MAX-ACCESS read-only
			STATUS current
			DESCRIPTION
				"The address of the upstream neighbor (e.g., RPF neighbor) 
				from which IP datagrams from these sources to this multicast 
				address are received, or 0.0.0.0 if the upstream neighbor is 
				unknown (e.g., in CBT)."
			::= { sleV2M4RouteEntry 5 }

		
--  1.3.6.1.4.1.6296.102.12.2.2.2.1.1.6
		sleV2M4RouteUpTime OBJECT-TYPE
			SYNTAX TimeTicks
			MAX-ACCESS read-only
			STATUS current
			DESCRIPTION
				"The time since the multicast routing information 
				represented by this entry was learned by the router."
			::= { sleV2M4RouteEntry 6 }

		
--  1.3.6.1.4.1.6296.102.12.2.2.2.1.1.7
		sleV2MRouteExpiryTime OBJECT-TYPE
			SYNTAX TimeTicks
			MAX-ACCESS read-only
			STATUS current
			DESCRIPTION
				"The minimum amount of time remaining before this entry will
				be aged out.  The value 0 indicates that the entry is not
				subject to aging."
			::= { sleV2M4RouteEntry 7 }

		
--  1.3.6.1.4.1.6296.102.12.2.2.2.1.1.8
		sleV2M4RouteMcProtocol OBJECT-TYPE
			SYNTAX IANAipMRouteProtocol
			MAX-ACCESS read-only
			STATUS current
			DESCRIPTION
				"The multicast routing protocol via which this multicast
				forwarding entry was learned."
			::= { sleV2M4RouteEntry 8 }

		
--  1.3.6.1.4.1.6296.102.12.2.2.2.1.1.9
		sleV2M4RouteRtProtocol OBJECT-TYPE
			SYNTAX IANAipRouteProtocol
			MAX-ACCESS read-only
			STATUS current
			DESCRIPTION
				"The routing mechanism via which the route used to find the
				upstream or parent interface for this multicast forwarding
				entry was learned.  Inclusion of values for routing
				protocols is not intended to imply that those protocols need
				be supported."
			::= { sleV2M4RouteEntry 9 }

		
--  1.3.6.1.4.1.6296.102.12.2.2.2.1.1.10
		sleV2M4RouteRtAddress OBJECT-TYPE
			SYNTAX IpAddress
			MAX-ACCESS read-only
			STATUS current
			DESCRIPTION
				"The address portion of the route used to find the upstream
				or parent interface for this multicast forwarding entry."
			::= { sleV2M4RouteEntry 10 }

		
--  1.3.6.1.4.1.6296.102.12.2.2.2.1.1.11
		sleV2M4RouteRtMask OBJECT-TYPE
			SYNTAX INTEGER (1..32)
			MAX-ACCESS read-write
			STATUS current
			DESCRIPTION
				"The mask associated with the route used to find the upstream
				or parent interface for this multicast forwarding entry."
			::= { sleV2M4RouteEntry 11 }

		
--  1.3.6.1.4.1.6296.102.12.2.2.2.1.1.12
		sleV2M4RouteRtType OBJECT-TYPE
			SYNTAX INTEGER
				{
				unicast(1),
				multicast(2)
				}
			MAX-ACCESS read-only
			STATUS current
			DESCRIPTION
				"The reason the given route was placed in the (logical)
				multicast Routing Information Base (RIB).  A value of
				unicast means that the route would normally be placed only
				in the unicast RIB, but was placed in the multicast RIB
				(instead or in addition) due to local configuration, such as
				when running PIM over RIP.  A value of multicast means that
				the route was explicitly added to the multicast RIB by the
				routing protocol, such as DVMRP or Multiprotocol BGP."
			::= { sleV2M4RouteEntry 12 }

		
--  1.3.6.1.4.1.6296.102.12.2.2.2.1.1.13
		sleV2M4RouteOutIfCount OBJECT-TYPE
			SYNTAX Integer32
			MAX-ACCESS read-only
			STATUS current
			DESCRIPTION
				"The number of entry's outgoing interfaces."
			::= { sleV2M4RouteEntry 13 }

		
--  1.3.6.1.4.1.6296.102.12.2.2.2.1.1.14
		sleV2M4RouteOutInterface OBJECT-TYPE
			SYNTAX OCTET STRING (SIZE (1..512))
			MAX-ACCESS read-only
			STATUS current
			DESCRIPTION
				"The bitmap of entry's outgoing interfaces."
			::= { sleV2M4RouteEntry 14 }

		
--  1.3.6.1.4.1.6296.102.12.2.2.2.1.1.15
		sleV2M4RouteFlags OBJECT-TYPE
			SYNTAX BITS
				{
				immediateState(0),
				timedState(1),
				forworderInstalled(2)
				}
			MAX-ACCESS read-only
			STATUS current
			DESCRIPTION
				"MRIB entry's flags."
			::= { sleV2M4RouteEntry 15 }

		
--  1.3.6.1.4.1.6296.102.12.2.2.2.1.1.16
		sleV2M4RouteStsFwdPkts OBJECT-TYPE
			SYNTAX Counter64
			MAX-ACCESS read-only
			STATUS current
			DESCRIPTION
				"The number of packets which this router has received from
				these sources and addressed to this multicast group
				address, and which were forwarded by this router."
			::= { sleV2M4RouteEntry 16 }

		
--  1.3.6.1.4.1.6296.102.12.2.2.2.1.1.17
		sleV2M4RouteStsFwdBytes OBJECT-TYPE
			SYNTAX Counter64
			MAX-ACCESS read-only
			STATUS current
			DESCRIPTION
				"The number of octets contained in IP datagrams which were
				received from these sources and addressed to this multicast
				group address, and which were forwarded by this router."
			::= { sleV2M4RouteEntry 17 }

		
--  1.3.6.1.4.1.6296.102.12.2.2.2.1.1.18
		sleV2M4RouteStsWrongIfPkts OBJECT-TYPE
			SYNTAX Counter64
			MAX-ACCESS read-only
			STATUS current
			DESCRIPTION
				"The number of packets which this router has received from
				these sources and addressed to this multicast group address,
				which were dropped because they were not received on the
				interface indicated by sleV2M4RouteInInterface.  Packets which are
				not subject to an incoming interface check (e.g., using CBT)
				are not counted."
			::= { sleV2M4RouteEntry 18 }

		
--  1.3.6.1.4.1.6296.102.12.2.2.2.1.1.19
		sleV2M4RouteStsWholepktRecvMsg OBJECT-TYPE
			SYNTAX Counter64
			MAX-ACCESS read-only
			STATUS current
			DESCRIPTION
				"The number of WHOLEPKT event messages which this MRIB has received 
				from the Multicast Forwarder for this entry.
				The Multicast Forwarder generates the WHOLEPKT event whenever 
				the special REGISTER VIF appears in the out interface list of an (S,G) MRT 
				in the multicast forwarder."
			::= { sleV2M4RouteEntry 19 }

		
--  1.3.6.1.4.1.6296.102.12.2.2.2.1.1.20
		sleV2M4RouteStsWrongvifRecvMsg OBJECT-TYPE
			SYNTAX Counter64
			MAX-ACCESS read-only
			STATUS current
			DESCRIPTION
				"The number of WRONGVIF event messages which this MRIB has received 
				from the Multicast Forwarder for this entry.
				The Multicast Forwarder generates a WRONGVIF event when it 
				receives a packet destined to (S,G) on an interface that 
				does not match the IIF of the (S,G) MRT in the Multicast Forwarder."
			::= { sleV2M4RouteEntry 20 }

		
--  1.3.6.1.4.1.6296.102.12.2.2.2.1.1.21
		sleV2M4RouteStsWholepktSentMsg OBJECT-TYPE
			SYNTAX Counter64
			MAX-ACCESS read-only
			STATUS current
			DESCRIPTION
				"The number of NSM_MSG_IPV4_MRT_WHOLEPKT_REQUEST(NSM_MSG_IPV6_MRT_WHOLEPKT_REQUEST) 
				messages which MRIB sent to multicast protocol for this entry.
				When the MRIB receives WHOLEPKT event message from Multicast Forwarder, 
				it sends an message to the multicast protocol.
				
				It is inefficient and expensive to relay this whole message to the multicast 
				protocol, because IP packet can be as large as 64 KB.
				To avoid sending the WHOLEPKT message to the multicast protocol, 
				NSM_MSG_IPV4_MRT_WHOLEPKT_REQUEST message contains the (S,G) key, 
				the REGISTER VIF index, and a unique identifier for the instance of 
				the WHOLEPKT message from the Multicast Forwarder, whitout the all packet data."
			::= { sleV2M4RouteEntry 21 }

		
--  1.3.6.1.4.1.6296.102.12.2.2.2.1.1.22
		sleV2M4RouteStsWrongvifSentMsg OBJECT-TYPE
			SYNTAX Counter64
			MAX-ACCESS read-only
			STATUS current
			DESCRIPTION
				"The number of NSM_MSG_IPV4_MRT_WRONGVIF(NSM_MSG_IPV6_MRT_WRONGVIF) messages 
				which MRIB sent to multicast protocol for this entry.
				When the MRIB receives WRONGVIF event message from Multicast Forwarder, 
				it relays it to all multicast protocols that have requested PIM service."
			::= { sleV2M4RouteEntry 22 }

		
--  1.3.6.1.4.1.6296.102.12.2.2.2.1.1.23
		sleV2M4RouteStsTimedSentMsg OBJECT-TYPE
			SYNTAX Counter64
			MAX-ACCESS read-only
			STATUS current
			DESCRIPTION
				"The number of notification messages occured by timed event 
				of MRIB by which multicast protocols update own statistics 
				information."
			::= { sleV2M4RouteEntry 23 }

		
--  1.3.6.1.4.1.6296.102.12.2.2.2.1.1.24
		sleV2M4RouteStsImmediateSentMsg OBJECT-TYPE
			SYNTAX Counter64
			MAX-ACCESS read-only
			STATUS current
			DESCRIPTION
				"The number of notification messages occured by immediate event 
				of MRIB by which multicast protocols update own statistics 
				information."
			::= { sleV2M4RouteEntry 24 }

		
--  1.3.6.1.4.1.6296.102.12.2.2.2.1.1.25
		sleV2M4RouteStsRegAckRecvMsg OBJECT-TYPE
			SYNTAX Counter64
			MAX-ACCESS read-only
			STATUS current
			DESCRIPTION
				"The number of ACK messages which the MRIB has received from 
				multicast protocol for this MRIB entry, and by which MRIB 
				originates a Register packet to the destination RP provided 
				in this ACK reply."
			::= { sleV2M4RouteEntry 25 }

		
--  1.3.6.1.4.1.6296.102.12.2.2.2.1.1.26
		sleV2M4RouteStsRegNackRecvMsg OBJECT-TYPE
			SYNTAX Counter64
			MAX-ACCESS read-only
			STATUS current
			DESCRIPTION
				"The number of NACK messages which the MRIB has received from 
				multicast protocol for this MRIB entry, and by which MRIB don't 
				originates a Register packet to the destination RP provided 
				in this ACK reply."
			::= { sleV2M4RouteEntry 26 }

		
--  1.3.6.1.4.1.6296.102.12.2.2.2.1.1.27
		sleV2M4RouteStsRegSentPkts OBJECT-TYPE
			SYNTAX Counter64
			MAX-ACCESS read-only
			STATUS current
			DESCRIPTION
				"The number of Register packets which the MRIB sent to 
				the destination RP for this entry."
			::= { sleV2M4RouteEntry 27 }

		
--  Multicast Routing Information Base Control
-- 1.3.6.1.4.1.6296.102.12.2.1.2.2
		sleV2M4RouteControl OBJECT IDENTIFIER ::= { sleV2M4Route 2 }

		
--  1.3.6.1.4.1.6296.102.12.2.1.2.2.1
		sleV2M4RouteControlRequest OBJECT-TYPE
			SYNTAX INTEGER
				{
				destroyMRouteEntry(1),
				clearMRouteAllEntries(2),
				clearMRouteStatistics(3),
				clearMRouteAllStatistics(4)
				}
			MAX-ACCESS read-write
			STATUS current
			DESCRIPTION
				"The request of a user command"
			::= { sleV2M4RouteControl 1 }

		
--  1.3.6.1.4.1.6296.102.12.2.1.2.2.2
		sleV2M4RouteControlStatus OBJECT-TYPE
			SYNTAX SleControlStatusType
			MAX-ACCESS read-only
			STATUS current
			DESCRIPTION
				"The status of user command"
			::= { sleV2M4RouteControl 2 }

		
--  1.3.6.1.4.1.6296.102.12.2.1.2.2.3
		sleV2M4RouteControlTimer OBJECT-TYPE
			SYNTAX Gauge32
			MAX-ACCESS read-write
			STATUS current
			DESCRIPTION
				"The maximum time for the manager for a long running user command"
			::= { sleV2M4RouteControl 3 }

		
--  1.3.6.1.4.1.6296.102.12.2.1.2.2.4
		sleV2M4RouteControlTimeStamp OBJECT-TYPE
			SYNTAX TimeTicks
			MAX-ACCESS read-only
			STATUS current
			DESCRIPTION
				"The time stamp of the last command(end of command)"
			::= { sleV2M4RouteControl 4 }

		
--  1.3.6.1.4.1.6296.102.12.2.1.2.2.5
		sleV2M4RouteControlReqResult OBJECT-TYPE
			SYNTAX SleControlRequestResultType
			MAX-ACCESS read-only
			STATUS current
			DESCRIPTION
				"The result of the last user command"
			::= { sleV2M4RouteControl 5 }

		
--  1.3.6.1.4.1.6296.102.12.2.1.2.2.6
		sleV2M4RouteControlGroup OBJECT-TYPE
			SYNTAX IpAddress
			MAX-ACCESS read-write
			STATUS current
			DESCRIPTION
				"The IP multicast group address for which this entry 
				contains multicast routing information."
			::= { sleV2M4RouteControl 6 }

		
--  1.3.6.1.4.1.6296.102.12.2.1.2.2.7
		sleV2M4RouteControlSource OBJECT-TYPE
			SYNTAX IpAddress
			MAX-ACCESS read-write
			STATUS current
			DESCRIPTION
				"The network address which when combined with the 
				corresponding value of ipMRouteSourceMask identifies the 
				sources for which this entry contains multicast routing 
				information. For (*,G) entry, value 0.0.0.0"
			::= { sleV2M4RouteControl 7 }

		
--  1.3.6.1.4.1.6296.102.12.2.1.2.2.8
		sleV2M4RouteControlSrcMask OBJECT-TYPE
			SYNTAX IpAddress
			MAX-ACCESS read-write
			STATUS current
			DESCRIPTION
				"The network mask which when combined with the corresponding 
				value of  sleV2M4RouteSource identifies the sources for which 
				this entry contains multicast routing information.
				For (*,G) entry, value 0.0.0.0"
			::= { sleV2M4RouteControl 8 }

		
--  1.3.6.1.4.1.6296.102.12.2.1.2.2.9
		sleV2M4RouteControlMcastProtocol OBJECT-TYPE
			SYNTAX INTEGER
				{
				anyMRouteProtocol(0),
				pimSparseMode(8)
				}
			MAX-ACCESS read-write
			STATUS current
			DESCRIPTION
				"The multicast routing protocol via which this multicast
				forwarding entry was learned."
			::= { sleV2M4RouteControl 9 }

		
--  Multicast Routing Information Base Notification
-- 1.3.6.1.4.1.6296.102.12.2.1.2.3
		sleV2M4RouteNotification OBJECT IDENTIFIER ::= { sleV2M4Route 3 }

		
--  1.3.6.1.4.1.6296.102.12.2.1.2.3.1
		sleV2M4RouteEntryDestroyed NOTIFICATION-TYPE
			OBJECTS { sleV2M4RouteControlRequest, sleV2M4RouteControlReqResult, sleV2M4RouteControlTimeStamp, sleV2M4RouteControlGroup, sleV2M4RouteControlSource, 
				sleV2M4RouteControlSrcMask, sleV2M4RouteControlMcastProtocol }
			STATUS current
			DESCRIPTION 
				"Description."
			::= { sleV2M4RouteNotification 1 }

		
--  1.3.6.1.4.1.6296.102.12.2.1.2.3.2
		sleV2M4RoutAllEntriesCleared NOTIFICATION-TYPE
			OBJECTS { sleV2M4RouteControlRequest, sleV2M4RouteControlReqResult, sleV2M4RouteControlTimeStamp }
			STATUS current
			DESCRIPTION 
				"Description."
			::= { sleV2M4RouteNotification 2 }

		
--  1.3.6.1.4.1.6296.102.12.2.1.2.3.3
		sleV2M4RoutStatisticsCleared NOTIFICATION-TYPE
			OBJECTS { sleV2M4RouteControlRequest, sleV2M4RouteControlReqResult, sleV2M4RouteControlTimeStamp, sleV2M4RouteControlGroup, sleV2M4RouteControlSource, 
				sleV2M4RouteControlSrcMask }
			STATUS current
			DESCRIPTION 
				"Description."
			::= { sleV2M4RouteNotification 3 }

		
--  1.3.6.1.4.1.6296.102.12.2.1.2.3.4
		sleV2M4RoutAllStatisticsCleared NOTIFICATION-TYPE
			OBJECTS { sleV2M4RouteControlRequest, sleV2M4RouteControlReqResult, sleV2M4RouteControlTimeStamp }
			STATUS current
			DESCRIPTION 
				"Description."
			::= { sleV2M4RouteNotification 4 }

		
--  Multicast Routing Information Base Next-Hop
-- 1.3.6.1.4.1.6296.102.12.2.1.3
		sleV2M4RouteNextHop OBJECT IDENTIFIER ::= { sleV2Mrib4 3 }

		
--  Multicast Routing Information Base Next-Hop Table
-- 1.3.6.1.4.1.6296.102.12.2.1.3.1
		sleV2M4RouteNextHopTable OBJECT-TYPE
			SYNTAX SEQUENCE OF SleV2M4RouteNextHopEntry
			MAX-ACCESS not-accessible
			STATUS current
			DESCRIPTION
				"The (conceptual) table containing information on the 
				next-hops on outgoing interfaces for routing IP multicast
				datagrams.  Each entry is one of a list of next-hops on
				outgoing interfaces for particular sources sending to a
				particular multicast group address."
			::= { sleV2M4RouteNextHop 1 }

		
--  Multicast Routing Information Base Next-Hop Entry
-- 1.3.6.1.4.1.6296.102.12.2.2.3.1.1
		sleV2M4RouteNextHopEntry OBJECT-TYPE
			SYNTAX SleV2M4RouteNextHopEntry
			MAX-ACCESS not-accessible
			STATUS current
			DESCRIPTION
				"An entry (conceptual row) in the list of next-hops on
				outgoing interfaces to which IP multicast datagrams from
				particular sources to a IP multicast group address are
				routed.  Discontinuities in counters in this entry can be
				detected by observing the value of sleV2M4RouteUpTime.
				key: sleV2M4RouteGroup, sleV2M4RouteSource, sleV2M4RouteSrcMask, sleV2M4RouteNextHopIfIndex, sleV2M4RouteNextHopAddress"
			INDEX { sleV2M4RouteGroup, sleV2M4RouteSource, sleV2M4RouteSrcMask, sleV2M4RouteNextHopIfIndex, sleV2M4RouteNextHopAddress
				 }
			::= { sleV2M4RouteNextHopTable 1 }

		
		SleV2M4RouteNextHopEntry ::=
			SEQUENCE { 
				sleV2M4RouteNextHopIfIndex
					INTEGER,
				sleV2M4RouteNextHopAddress
					IpAddress,
				sleV2M4RouteNextHopState
					INTEGER,
				sleV2M4RouteNextHopUpTime
					TimeTicks,
				sleV2M4RouteNextHopExpiryTime
					TimeTicks,
				sleV2M4RouteNextHopProtocol
					IANAipMRouteProtocol,
				sleV2M4RouteNextHopClosestMemberHops
					Integer32,
				sleV2M4RouteNextHopPkts
					Counter64
			 }

--  1.3.6.1.4.1.6296.102.12.2.2.3.1.1.1
		sleV2M4RouteNextHopIfIndex OBJECT-TYPE
			SYNTAX INTEGER (1..4094)
			MAX-ACCESS read-only
			STATUS current
			DESCRIPTION
				"The ifIndex value of the interface for the outgoing 
				interface for this next-hop."
			::= { sleV2M4RouteNextHopEntry 1 }

		
--  1.3.6.1.4.1.6296.102.12.2.2.3.1.1.2
		sleV2M4RouteNextHopAddress OBJECT-TYPE
			SYNTAX IpAddress
			MAX-ACCESS read-only
			STATUS current
			DESCRIPTION
				"The address of the next-hop specific to this entry. For 
				most interfaces, this is identical to  sleV2M4RouteGroup. 
				NBMA interfaces, however, may have multiple next-hop 
				addresses out a single outgoing interface."
			::= { sleV2M4RouteNextHopEntry 2 }

		
--  1.3.6.1.4.1.6296.102.12.2.2.3.1.1.3
		sleV2M4RouteNextHopState OBJECT-TYPE
			SYNTAX INTEGER
				{
				pruned(1),
				forwarding(2)
				}
			MAX-ACCESS read-only
			STATUS current
			DESCRIPTION
				"An indication of whether the outgoing interface and next-
				hop represented by this entry is currently being used to
				forward IP datagrams.  The value 'forwarding' indicates it
				is currently being used; the value 'pruned' indicates it is
				not."
			::= { sleV2M4RouteNextHopEntry 3 }

		
--  1.3.6.1.4.1.6296.102.12.2.2.3.1.1.4
		sleV2M4RouteNextHopUpTime OBJECT-TYPE
			SYNTAX TimeTicks
			MAX-ACCESS read-only
			STATUS current
			DESCRIPTION
				"The time since the multicast routing information
				represented by this entry was learned by the router."
			::= { sleV2M4RouteNextHopEntry 4 }

		
--  1.3.6.1.4.1.6296.102.12.2.2.3.1.1.5
		sleV2M4RouteNextHopExpiryTime OBJECT-TYPE
			SYNTAX TimeTicks
			MAX-ACCESS read-only
			STATUS current
			DESCRIPTION
				"The minimum amount of time remaining before this entry will
				be aged out.  If ipMRouteNextHopState is pruned(1), the
				remaining time until the prune expires and the state reverts
				to forwarding(2).  Otherwise, the remaining time until this
				entry is removed from the table.  The time remaining may be
				copied from sleV2MRouteExpiryTime if the protocol in use for
				this entry does not specify next-hop timers.  The value 0
				indicates that the entry is not subject to aging."
			::= { sleV2M4RouteNextHopEntry 5 }

		
--  1.3.6.1.4.1.6296.102.12.2.2.3.1.1.6
		sleV2M4RouteNextHopProtocol OBJECT-TYPE
			SYNTAX IANAipMRouteProtocol
			MAX-ACCESS read-only
			STATUS current
			DESCRIPTION
				"The routing mechanism via which this next-hop was learned."
			::= { sleV2M4RouteNextHopEntry 6 }

		
--  1.3.6.1.4.1.6296.102.12.2.2.3.1.1.7
		sleV2M4RouteNextHopClosestMemberHops OBJECT-TYPE
			SYNTAX Integer32
			MAX-ACCESS read-only
			STATUS current
			DESCRIPTION
				"The minimum number of hops between this router and any
				member of this IP multicast group reached via this next-hop
				on this outgoing interface.  Any IP multicast datagrams for
				the group which have a TTL less than this number of hops
				will not be forwarded to this next-hop."
			::= { sleV2M4RouteNextHopEntry 7 }

		
--  1.3.6.1.4.1.6296.102.12.2.2.3.1.1.8
		sleV2M4RouteNextHopPkts OBJECT-TYPE
			SYNTAX Counter64
			MAX-ACCESS read-only
			STATUS current
			DESCRIPTION
				"The number of packets which have been forwarded using this
				route."
			::= { sleV2M4RouteNextHopEntry 8 }

		
--  Multicast Routing Information Base Interface
-- 1.3.6.1.4.1.6296.102.12.2.1.4
		sleV2M4RouteInterface OBJECT IDENTIFIER ::= { sleV2Mrib4 4 }

		
--  Multicast Routing Information Base Interface Table
-- 1.3.6.1.4.1.6296.102.12.2.1.4.1
		sleV2M4RouteIfTable OBJECT-TYPE
			SYNTAX SEQUENCE OF SleV2M4RouteIfEntry
			MAX-ACCESS not-accessible
			STATUS current
			DESCRIPTION
				"The (conceptual) table containing multicast routing
				information specific to interfaces."
			::= { sleV2M4RouteInterface 1 }

		
--  Multicast Routing Information Base Interface Entry
-- 1.3.6.1.4.1.6296.102.12.2.2.4.1.1
		sleV2M4RouteIfEntry OBJECT-TYPE
			SYNTAX SleV2M4RouteIfEntry
			MAX-ACCESS not-accessible
			STATUS current
			DESCRIPTION
				"An entry (conceptual row) containing the multicast routing
				information for a particular interface.
				key: sleV2M4RouteIfIndex"
			INDEX { sleV2M4RouteIfIndex }
			::= { sleV2M4RouteIfTable 1 }

		
		SleV2M4RouteIfEntry ::=
			SEQUENCE { 
				sleV2M4RouteIfIndex
					Integer32,
				sleV2M4RouteIfName
					OCTET STRING,
				sleV2M4RouteIfTtl
					Integer32,
				sleV2M4RouteIfRateLimit
					Integer32,
				sleV2M4RouteIfProtocol
					IANAipMRouteProtocol,
				sleV2M4RouteIfInMcastOctets
					Counter64,
				sleV2M4RouteIfOutMcastOctets
					Counter64
			 }

--  1.3.6.1.4.1.6296.102.12.2.2.4.1.1.1
		sleV2M4RouteIfIndex OBJECT-TYPE
			SYNTAX Integer32 (1..4094)
			MAX-ACCESS read-only
			STATUS current
			DESCRIPTION
				"The ifIndex value of the interface for which this entry
				contains information."
			::= { sleV2M4RouteIfEntry 1 }

		
--  1.3.6.1.4.1.6296.102.12.2.2.4.1.1.2
		sleV2M4RouteIfName OBJECT-TYPE
			SYNTAX OCTET STRING (SIZE (0..8))
			MAX-ACCESS read-only
			STATUS current
			DESCRIPTION
				"The ifName of the interface for which this entry
				contains information."
			::= { sleV2M4RouteIfEntry 2 }

		
--  1.3.6.1.4.1.6296.102.12.2.2.4.1.1.3
		sleV2M4RouteIfTtl OBJECT-TYPE
			SYNTAX Integer32 (0..255)
			MAX-ACCESS read-only
			STATUS current
			DESCRIPTION
				"The datagram TTL threshold for the interface. Any IP
				multicast datagrams with a TTL less than this threshold will
				not be forwarded out the interface. The default value of 0
				means all multicast packets are forwarded out the
				interface."
			::= { sleV2M4RouteIfEntry 3 }

		
--  1.3.6.1.4.1.6296.102.12.2.2.4.1.1.4
		sleV2M4RouteIfRateLimit OBJECT-TYPE
			SYNTAX Integer32
			MAX-ACCESS read-only
			STATUS current
			DESCRIPTION
				"The rate-limit, in kilobits per second, of forwarded
				multicast traffic on the interface.  A rate-limit of 0
				indicates that no rate limiting is done."
			DEFVAL { 0 }
			::= { sleV2M4RouteIfEntry 4 }

		
--  1.3.6.1.4.1.6296.102.12.2.2.4.1.1.5
		sleV2M4RouteIfProtocol OBJECT-TYPE
			SYNTAX IANAipMRouteProtocol
			MAX-ACCESS read-only
			STATUS current
			DESCRIPTION
				"The routing protocol running on this interface."
			::= { sleV2M4RouteIfEntry 5 }

		
--  1.3.6.1.4.1.6296.102.12.2.2.4.1.1.6
		sleV2M4RouteIfInMcastOctets OBJECT-TYPE
			SYNTAX Counter64
			MAX-ACCESS read-only
			STATUS current
			DESCRIPTION
				"The number of octets of multicast packets that have arrived
				on the interface, including framing characters.  This object
				is similar to ifInOctets in the Interfaces MIB, except that
				only multicast packets are counted."
			::= { sleV2M4RouteIfEntry 6 }

		
--  1.3.6.1.4.1.6296.102.12.2.2.4.1.1.7
		sleV2M4RouteIfOutMcastOctets OBJECT-TYPE
			SYNTAX Counter64
			MAX-ACCESS read-only
			STATUS current
			DESCRIPTION
				"The number of octets of multicast packets that have been
				sent on the interface."
			::= { sleV2M4RouteIfEntry 7 }

		
--  Multicast Routing Information Base Interface Control
-- 1.3.6.1.4.1.6296.102.12.2.1.4.2
		sleV2M4RouteIfControl OBJECT IDENTIFIER ::= { sleV2M4RouteInterface 2 }

		
--  1.3.6.1.4.1.6296.102.12.2.1.4.2.1
		sleV2M4RouteIfControlRequest OBJECT-TYPE
			SYNTAX INTEGER { setMRouteInterfaceProfile(1) }
			MAX-ACCESS read-write
			STATUS current
			DESCRIPTION
				"The request of a user command"
			::= { sleV2M4RouteIfControl 1 }

		
--  1.3.6.1.4.1.6296.102.12.2.1.4.2.2
		sleV2M4RouteIfControlStatus OBJECT-TYPE
			SYNTAX SleControlStatusType
			MAX-ACCESS read-only
			STATUS current
			DESCRIPTION
				"The status of user command"
			::= { sleV2M4RouteIfControl 2 }

		
--  1.3.6.1.4.1.6296.102.12.2.1.4.2.3
		sleV2M4RouteIfControlTimer OBJECT-TYPE
			SYNTAX Gauge32
			MAX-ACCESS read-write
			STATUS current
			DESCRIPTION
				"The maximum time for the manager for a long running user command"
			::= { sleV2M4RouteIfControl 3 }

		
--  1.3.6.1.4.1.6296.102.12.2.1.4.2.4
		sleV2M4RouteIfControlTimeStamp OBJECT-TYPE
			SYNTAX TimeTicks
			MAX-ACCESS read-only
			STATUS current
			DESCRIPTION
				"The time stamp of the last command(end of command)"
			::= { sleV2M4RouteIfControl 4 }

		
--  1.3.6.1.4.1.6296.102.12.2.1.4.2.5
		sleV2M4RouteIfControlReqResult OBJECT-TYPE
			SYNTAX SleControlRequestResultType
			MAX-ACCESS read-only
			STATUS current
			DESCRIPTION
				"The result of the last user command"
			::= { sleV2M4RouteIfControl 5 }

		
--  1.3.6.1.4.1.6296.102.12.2.1.4.2.6
		sleV2M4RouteIfControlIndex OBJECT-TYPE
			SYNTAX INTEGER (1..4094)
			MAX-ACCESS read-write
			STATUS current
			DESCRIPTION
				"The ifIndex value of the interface for which this control changes
				multicast configuration."
			::= { sleV2M4RouteIfControl 6 }

		
--  1.3.6.1.4.1.6296.102.12.2.1.4.2.7
		sleV2M4RouteIfControlTtl OBJECT-TYPE
			SYNTAX Integer32 (0..255)
			MAX-ACCESS read-write
			STATUS current
			DESCRIPTION
				"The datagram TTL threshold for the interface. Any IP
				multicast datagrams with a TTL less than this threshold will
				not be forwarded out the interface. The default value of 0
				means all multicast packets are forwarded out the
				interface."
			::= { sleV2M4RouteIfControl 7 }

		
--  1.3.6.1.4.1.6296.102.12.2.1.4.2.8
		sleV2M4RouteIfControlRateLimit OBJECT-TYPE
			SYNTAX Integer32
			MAX-ACCESS read-write
			STATUS current
			DESCRIPTION
				"The rate-limit, in kilobits per second, of forwarded
				multicast traffic on the interface.  A rate-limit of 0
				indicates that no rate limiting is done."
			::= { sleV2M4RouteIfControl 8 }

		
--  Multicast Routing Information Base Interface Notification
-- 1.3.6.1.4.1.6296.102.12.2.1.4.3
		sleV2M4RouteIfNotification OBJECT IDENTIFIER ::= { sleV2M4RouteInterface 3 }

		
--  1.3.6.1.4.1.6296.102.12.2.1.4.3.1
		sleV2M4RouteInterfaceProfileChanged NOTIFICATION-TYPE
			OBJECTS { sleV2M4RouteIfControlRequest, sleV2M4RouteIfControlReqResult, sleV2M4RouteIfControlTimeStamp, sleV2M4RouteIfTtl, sleV2M4RouteIfRateLimit
				 }
			STATUS current
			DESCRIPTION 
				"Description."
			::= { sleV2M4RouteIfNotification 1 }

		
--  Internet Group Management Protocol
-- 1.3.6.1.4.1.6296.102.12.2.2
		sleV2Igmp OBJECT IDENTIFIER ::= { sleV2Multicast4 2 }

		
--  IGMP Configuration
-- 1.3.6.1.4.1.6296.102.12.2.2.1
		sleV2IgmpBase OBJECT IDENTIFIER ::= { sleV2Igmp 1 }

		
--  IGMP Configuration Group
-- 1.3.6.1.4.1.6296.102.12.2.2.1.1
		sleV2IgmpInfo OBJECT IDENTIFIER ::= { sleV2IgmpBase 1 }

		
--  1.3.6.1.4.1.6296.102.12.2.2.1.1.1
		sleV2IgmpInfoSnoopActivity OBJECT-TYPE
			SYNTAX Boolean
			MAX-ACCESS read-only
			STATUS current
			DESCRIPTION
				"This object indicates whether IGMP Snooping has been enabled for the system."
			::= { sleV2IgmpInfo 1 }

		
--  1.3.6.1.4.1.6296.102.12.2.2.1.1.2
		sleV2IgmpInfoSnoopVersion OBJECT-TYPE
			SYNTAX INTEGER
				{
				igmpV1(1),
				igmpV2(2),
				igmpV3(3)
				}
			MAX-ACCESS read-only
			STATUS current
			DESCRIPTION
				"The maximum version of IGMP supported."
			::= { sleV2IgmpInfo 2 }

		
--  1.3.6.1.4.1.6296.102.12.2.2.1.1.3
		sleV2IgmpInfoSnoopVersionMode OBJECT-TYPE
			SYNTAX INTEGER
				{
				static(0),
				dynamic(1)
				}
			MAX-ACCESS read-only
			STATUS current
			DESCRIPTION
				"Global IGMP Snooping Version Mode"
			::= { sleV2IgmpInfo 3 }

		
--  1.3.6.1.4.1.6296.102.12.2.2.1.1.4
		sleV2IgmpInfoSnoopFastLeave OBJECT-TYPE
			SYNTAX Boolean
			MAX-ACCESS read-only
			STATUS current
			DESCRIPTION
				"This object indicates whether Fast-Leave mechanism has been configured to be enabled in the system. If Fast-Leave is enabled in the switch, IGMP Snooping will prune the port on which an IGMP leave message has been received without waiting for the Group Specific Query to timeout to determine whether there are any more hosts on that port for that group. If the value of sleV2IgmpInfoSnoopVersion is not 3, this object will not have any effect."
			::= { sleV2IgmpInfo 4 }

		
--  1.3.6.1.4.1.6296.102.12.2.2.1.1.5
		sleV2IgmpInfoSnoopFastBlock OBJECT-TYPE
			SYNTAX Boolean
			MAX-ACCESS read-only
			STATUS current
			DESCRIPTION
				"The object indicates whether Fast-Block mechanism has been enabled for the system. This object only has effect if the value of sleV2IgmpInfoSnoopVersion is 3."
			::= { sleV2IgmpInfo 5 }

		
--  1.3.6.1.4.1.6296.102.12.2.2.1.1.6
		sleV2IgmpInfoSnoopReportSuppression OBJECT-TYPE
			SYNTAX Boolean
			MAX-ACCESS read-only
			STATUS current
			DESCRIPTION
				"When this object is set to 'true', IGMP Snooping will suppress duplicate IGMP Reports.  When this object is set to 'false', all IGMP Reports are forwarded to all multicast routers. Alias is IGMP Snooping Proxy."
			::= { sleV2IgmpInfo 6 }

		
--  1.3.6.1.4.1.6296.102.12.2.2.1.1.7
		sleV2IgmpInfoSnoopQuerierActivity OBJECT-TYPE
			SYNTAX Boolean
			MAX-ACCESS read-only
			STATUS current
			DESCRIPTION
				"The object indicates whether the device will participate in the IGMP Querier election. If the object is set to 'true', the device will participate to an election process to be a Querier."
			::= { sleV2IgmpInfo 7 }

		
--  1.3.6.1.4.1.6296.102.12.2.2.1.1.8
		sleV2IgmpInfoSnoopQueryInterval OBJECT-TYPE
			SYNTAX Unsigned32 (0..31744)
			MAX-ACCESS read-only
			STATUS current
			DESCRIPTION
				"The frequency at which IGMP packets are transmitted on this interface."
			::= { sleV2IgmpInfo 8 }

		
--  1.3.6.1.4.1.6296.102.12.2.2.1.1.9
		sleV2IgmpInfoSnoopMaxResponseTime OBJECT-TYPE
			SYNTAX Integer32 (0..31744)
			MAX-ACCESS read-only
			STATUS current
			DESCRIPTION
				"The maximum query response time advertised in queries on this interface."
			::= { sleV2IgmpInfo 9 }

		
--  1.3.6.1.4.1.6296.102.12.2.2.1.1.10
		sleV2IgmpInfoSnoopLastMembQueryIntvl OBJECT-TYPE
			SYNTAX Unsigned32 (0..31744)
			MAX-ACCESS read-only
			STATUS current
			DESCRIPTION
				"The Last Member Qury Interval is the Max Response Time inserted into Group-Specific Queries sent in response to Leave Group messages, and is also the amount of time Between Group-Specific Query messages. This value may be tuned to modify the leave latency of the network. A reduced value results in reduced time to detect the loss of the last member of a group. The value of this object is irrelevant if mgmdRouterInterfaceVersion is 1"
			::= { sleV2IgmpInfo 10 }

		
--  1.3.6.1.4.1.6296.102.12.2.2.1.1.11
		sleV2IgmpInfoTcnFloodActivity OBJECT-TYPE
			SYNTAX Boolean
			MAX-ACCESS read-only
			STATUS current
			DESCRIPTION
				"TRUE is multicast traffic will be flooded on all ports of the VLAN for TcnFloodQueryCount of IGMP General Queries upon receiving a Topology Change Notification (TCN) for the VLAN. FALSE is not flooding."
			::= { sleV2IgmpInfo 11 }

		
--  1.3.6.1.4.1.6296.102.12.2.2.1.1.12
		sleV2IgmpInfoTcnQuerySolicitActivity OBJECT-TYPE
			SYNTAX Boolean
			MAX-ACCESS read-only
			STATUS current
			DESCRIPTION
				"This object specifies whether the device running IGMP Snooping will solicit IGMP General Queries from the Querier upon receiving a Topology Change Notification (TCN). The root device will always solicit IGMP General Queries on TCN irrespective of the value of this."
			::= { sleV2IgmpInfo 12 }

		
--  1.3.6.1.4.1.6296.102.12.2.2.1.1.13
		sleV2IgmpInfoTcnFloodQueryCount OBJECT-TYPE
			SYNTAX INTEGER (1..10)
			MAX-ACCESS read-only
			STATUS current
			DESCRIPTION
				"This object specifies the flooding period for multicast traffic upon receiving Topology Change Notifications (TCN). IGMP Snooping will flood multicast traffic until this count number of IGMP General Queries are received by IGMP Snooping."
			::= { sleV2IgmpInfo 13 }

		
--  1.3.6.1.4.1.6296.102.12.2.2.1.1.14
		sleV2IgmpInfoExplicitTracking OBJECT-TYPE
			SYNTAX Boolean
			MAX-ACCESS read-only
			STATUS current
			DESCRIPTION
				"In IGMPv3, it decide the device tracks reporters or not."
			::= { sleV2IgmpInfo 14 }

		
--  1.3.6.1.4.1.6296.102.12.2.2.1.1.15
		sleV2IgmpInfoMvrActivity OBJECT-TYPE
			SYNTAX Boolean
			MAX-ACCESS read-only
			STATUS current
			DESCRIPTION
				"The active state of MVR."
			::= { sleV2IgmpInfo 15 }

		
--  1.3.6.1.4.1.6296.102.12.2.2.1.1.16
		sleV2IgmpInfoTcnQueryInterval OBJECT-TYPE
			SYNTAX INTEGER (0 | 1..1800)
			MAX-ACCESS read-only
			STATUS current
			DESCRIPTION
				"TCN query interval"
			::= { sleV2IgmpInfo 16 }

		
--  1.3.6.1.4.1.6296.102.12.2.2.1.1.17
		sleV2IgmpInfoTcnQuerySolicitAddress OBJECT-TYPE
			SYNTAX IpAddress
			MAX-ACCESS read-only
			STATUS current
			DESCRIPTION
				"The source adddress of TCN solicit"
			::= { sleV2IgmpInfo 17 }

		
--  1.3.6.1.4.1.6296.102.12.2.2.1.1.18
		sleV2IgmpInfoVerifyTTL OBJECT-TYPE
			SYNTAX Boolean
			MAX-ACCESS read-only
			STATUS current
			DESCRIPTION
				"The activie state of Verify-TTL"
			::= { sleV2IgmpInfo 18 }

		
		sleV2IgmpInfoSnoopExplicitTrackingMacBased OBJECT-TYPE
			SYNTAX Boolean
			MAX-ACCESS read-only
			STATUS current
			DESCRIPTION
				"In IGMPv3, it decide the mac-based device tracks reporters or not."
			::= { sleV2IgmpInfo 19 }

		
		sleV2IgmpInfoSnoopTcnQueryGeneralStatus OBJECT-TYPE
			SYNTAX INTEGER
				{
				disable(0),
				enable(1)
				}
			MAX-ACCESS read-only
			STATUS current
			DESCRIPTION
				"The status is indicated Generating  an IGMPv2 gereral query. "
			::= { sleV2IgmpInfo 20 }

		
		sleV2IgmpInfoSnoopTcnQueryGeneralMaxResponseTime OBJECT-TYPE
			SYNTAX Integer32 (0..25)
			MAX-ACCESS read-only
			STATUS current
			DESCRIPTION
				"IGMP Snooping general query maximum response time (1-25sec, Default:1sec).
				when the TCN query general status is disable, max reponse time is 0."
			::= { sleV2IgmpInfo 21 }

		
--  1.3.6.1.4.1.6296.102.12.2.2.1.1.1
		sleV2IgmpinfoSnoopMrouterCpu OBJECT-TYPE
			SYNTAX INTEGER
				{
				disable(0),
				enable(1)
				}
			MAX-ACCESS read-only
			STATUS current
			DESCRIPTION
				"sleV2IgmpinfoSnoopMrouterCpu"
			::= { sleV2IgmpInfo 22 }

		
		sleV2IgmpInfoMaxGroupSystemCnt OBJECT-TYPE
			SYNTAX Unsigned32 (1..2147483647)
			MAX-ACCESS read-only
			STATUS current
			DESCRIPTION
				"The max group system count."
			::= { sleV2IgmpInfo 23 }

		
		sleV2IgmpInfoSnoopMRtLearningMode OBJECT-TYPE
			SYNTAX INTEGER
				{
				none(0),
				pim(1)
				}
			MAX-ACCESS read-only
			STATUS current
			DESCRIPTION
				"This object specifies the multicast router port learning method for IGMP Snooping
				
				    none(0): don't learning, Only use static router ports.
				
				    pim(1) : Protocol Independent Multicast.
				"
			::= { sleV2IgmpInfo 24 }

		
		sleV2IgmpInfoSnoopQuerierAddress OBJECT-TYPE
			SYNTAX IpAddress
			MAX-ACCESS read-only
			STATUS current
			DESCRIPTION
				"Description."
			::= { sleV2IgmpInfo 25 }

		
		sleV2IgmpInfoSsmMapActive OBJECT-TYPE
			SYNTAX Integer32
			MAX-ACCESS read-only
			STATUS current
			DESCRIPTION
				"Use this command to enable SSM mapping on the router."
			::= { sleV2IgmpInfo 26 }

		
		sleV2IgmpInfoLimit OBJECT-TYPE
			SYNTAX Integer32 (0 | 1..2097152)
			MAX-ACCESS read-only
			STATUS current
			DESCRIPTION
				"Use this command to set the maximum number of group membership states, at either the router level or at the interface level.
				range : 1 ~ 2097152
				0 : disable"
			::= { sleV2IgmpInfo 27 }

		
		sleV2IgmpInfoLimitExcept OBJECT-TYPE
			SYNTAX OCTET STRING
			MAX-ACCESS read-only
			STATUS current
			DESCRIPTION
				"Use this command to set the maximum number of group membership states, at either the router level or at the interface level."
			::= { sleV2IgmpInfo 28 }

		
--  IGMP Configuration Control
-- 1.3.6.1.4.1.6296.102.12.2.2.1.2
		sleV2IgmpInfoControl OBJECT IDENTIFIER ::= { sleV2IgmpBase 2 }

		
--  1.3.6.1.4.1.6296.102.12.2.2.1.2.1
		sleV2IgmpInfoControlRequest OBJECT-TYPE
			SYNTAX INTEGER
				{
				setIgmpInfoSnoopActivity(1),
				setIgmpInfoQuerierProfile(2),
				setIgmpInfoTcnProfile(3),
				setIgmpInfoMvrActivity(4),
				setIgmpInfoTcnProfileQueryInterval(5),
				setIgmpInfoTcnProfileSolicitAddr(6),
				setIgmpInfoVerifyTTL(7),
				setIgmpInfoSnoopExplicitTrackingMacBased(8),
				setIgmpInfoSnoopTcnGeneral(9),
				setIgmpInfoSnoopMrouterCpu(10),
				setIgmpInfoMaxGroupSystemCnt(11),
				delIgmpInfoMaxGroupSystemCnt(12),
				setIgmpInfoSnoopMrouterProfile(13)
				}
			MAX-ACCESS read-write
			STATUS current
			DESCRIPTION
				" The request of a user command"
			::= { sleV2IgmpInfoControl 1 }

		
--  1.3.6.1.4.1.6296.102.12.2.2.1.2.2
		sleV2IgmpInfoControlStatus OBJECT-TYPE
			SYNTAX SleControlStatusType
			MAX-ACCESS read-only
			STATUS current
			DESCRIPTION
				" The status of user command"
			::= { sleV2IgmpInfoControl 2 }

		
--  1.3.6.1.4.1.6296.102.12.2.2.1.2.3
		sleV2IgmpInfoControlTimer OBJECT-TYPE
			SYNTAX Gauge32
			MAX-ACCESS read-write
			STATUS current
			DESCRIPTION
				" The maximum time for the manager for a long running user command"
			::= { sleV2IgmpInfoControl 3 }

		
--  1.3.6.1.4.1.6296.102.12.2.2.1.2.4
		sleV2IgmpInfoControlTimeStamp OBJECT-TYPE
			SYNTAX TimeStamp
			MAX-ACCESS read-only
			STATUS current
			DESCRIPTION
				" The time stamp of the last command(end of command)"
			::= { sleV2IgmpInfoControl 4 }

		
--  1.3.6.1.4.1.6296.102.12.2.2.1.2.5
		sleV2IgmpInfoControlReqResult OBJECT-TYPE
			SYNTAX SleControlRequestResultType
			MAX-ACCESS read-only
			STATUS current
			DESCRIPTION
				" The result of the last user command
				"
			::= { sleV2IgmpInfoControl 5 }

		
--  1.3.6.1.4.1.6296.102.12.2.2.1.2.6
		sleV2IgmpInfoControlSnoopActivity OBJECT-TYPE
			SYNTAX Boolean
			MAX-ACCESS read-write
			STATUS current
			DESCRIPTION
				"This object indicates whether IGMP Snooping has been enabled for the system."
			::= { sleV2IgmpInfoControl 6 }

		
--  1.3.6.1.4.1.6296.102.12.2.2.1.2.7
		sleV2IgmpInfoControlSnoopVersion OBJECT-TYPE
			SYNTAX INTEGER
				{
				dynamic(0),
				igmpV1(1),
				igmpV2(2),
				igmpV3(3)
				}
			MAX-ACCESS read-write
			STATUS current
			DESCRIPTION
				"The maximum version of IGMP supported."
			::= { sleV2IgmpInfoControl 7 }

		
--  1.3.6.1.4.1.6296.102.12.2.2.1.2.8
		sleV2IgmpInfoControlSnoopFastLeave OBJECT-TYPE
			SYNTAX Boolean
			MAX-ACCESS read-write
			STATUS current
			DESCRIPTION
				"This object indicates whether Fast-Leave mechanism has been configured to be enabled in the system. If Fast-Leave is enabled in the switch, IGMP Snooping will prune the port on which an IGMP leave message has been received without waiting for the Group Specific Query to timeout to determine whether there are any more hosts on that port for that group. If the value of sleV2IgmpInfoSnoopVersion is not 3, this object will not have any effect."
			::= { sleV2IgmpInfoControl 8 }

		
--  1.3.6.1.4.1.6296.102.12.2.2.1.2.9
		sleV2IgmpInfoControlSnoopFastBlock OBJECT-TYPE
			SYNTAX Boolean
			MAX-ACCESS read-write
			STATUS current
			DESCRIPTION
				"The object indicates whether Fast-Block mechanism has been enabled for the system. This object only has effect if the value of sleV2IgmpInfoSnoopVersion is 3."
			::= { sleV2IgmpInfoControl 9 }

		
--  1.3.6.1.4.1.6296.102.12.2.2.1.2.10
		sleV2IgmpInfoControlSnoopReportSuppression OBJECT-TYPE
			SYNTAX Boolean
			MAX-ACCESS read-write
			STATUS current
			DESCRIPTION
				"When this object is set to 'true', IGMP Snooping will suppress duplicate IGMP Reports.  When this object is set to 'false', all IGMP Reports are forwarded to all multicast routers. Alias is IGMP Snooping Proxy."
			::= { sleV2IgmpInfoControl 10 }

		
--  1.3.6.1.4.1.6296.102.12.2.2.1.2.11
		sleV2IgmpInfoControlSnoopQuerierActivity OBJECT-TYPE
			SYNTAX Boolean
			MAX-ACCESS read-write
			STATUS current
			DESCRIPTION
				"The object indicates whether the device will participate in the IGMP Querier election. If the object is set to 'true', the device will participate to an election process to be a Querier."
			::= { sleV2IgmpInfoControl 11 }

		
--  1.3.6.1.4.1.6296.102.12.2.2.1.2.12
		sleV2IgmpInfoControlSnoopQueryInterval OBJECT-TYPE
			SYNTAX Unsigned32 (1..1800)
			MAX-ACCESS read-write
			STATUS current
			DESCRIPTION
				"The frequency at which IGMP packets are transmitted on this interface."
			::= { sleV2IgmpInfoControl 12 }

		
--  1.3.6.1.4.1.6296.102.12.2.2.1.2.13
		sleV2IgmpInfoControlSnoopMaxResponseTime OBJECT-TYPE
			SYNTAX Unsigned32 (1..25)
			MAX-ACCESS read-write
			STATUS current
			DESCRIPTION
				"The maximum query response time advertised in queries on this interface."
			::= { sleV2IgmpInfoControl 13 }

		
--  1.3.6.1.4.1.6296.102.12.2.2.1.2.14
		sleV2IgmpInfoControlSnoopLastMembQueryIntvl OBJECT-TYPE
			SYNTAX Unsigned32 (100..10000)
			MAX-ACCESS read-write
			STATUS current
			DESCRIPTION
				"The Last Member Qury Interval is the Max Response Time inserted into Group-Specific Queries sent in response to Leave Group messages, and is also the amount of time Between Group-Specific Query messages. This value may be tuned to modify the leave latency of the network. A reduced value results in reduced time to detect the loss of the last member of a group. The value of this object is irrelevant if mgmdRouterInterfaceVersion is 1"
			::= { sleV2IgmpInfoControl 14 }

		
--  1.3.6.1.4.1.6296.102.12.2.2.1.2.15
		sleV2IgmpInfoControlTcnFloodActivity OBJECT-TYPE
			SYNTAX Boolean
			MAX-ACCESS read-write
			STATUS current
			DESCRIPTION
				"TRUE is multicast traffic will be flooded on all ports of the VLAN for TcnFloodQueryCount of IGMP General Queries upon receiving a Topology Change Notification (TCN) for the VLAN. FALSE is not flooding."
			::= { sleV2IgmpInfoControl 15 }

		
--  1.3.6.1.4.1.6296.102.12.2.2.1.2.16
		sleV2IgmpInfoControlTcnQuerySolicitActivity OBJECT-TYPE
			SYNTAX Boolean
			MAX-ACCESS read-write
			STATUS current
			DESCRIPTION
				"This object specifies whether the device running IGMP Snooping will solicit IGMP General Queries from the Querier upon receiving a Topology Change Notification (TCN). The root device will always solicit IGMP General Queries on TCN irrespective of the value of this."
			::= { sleV2IgmpInfoControl 16 }

		
--  1.3.6.1.4.1.6296.102.12.2.2.1.2.17
		sleV2IgmpInfoControlTcnFloodQueryCount OBJECT-TYPE
			SYNTAX Integer32 (1..10)
			MAX-ACCESS read-write
			STATUS current
			DESCRIPTION
				"This object specifies the flooding period for multicast traffic upon receiving Topology Change Notifications (TCN). IGMP Snooping will flood multicast traffic until this count number of IGMP General Queries are received by IGMP Snooping."
			DEFVAL { 2 }
			::= { sleV2IgmpInfoControl 17 }

		
--  1.3.6.1.4.1.6296.102.12.2.2.1.2.18
		sleV2IgmpInfoControlExplicitTracking OBJECT-TYPE
			SYNTAX Boolean
			MAX-ACCESS read-write
			STATUS current
			DESCRIPTION
				"In IGMPv3, it decide the device tracks reporters or not."
			::= { sleV2IgmpInfoControl 18 }

		
--  1.3.6.1.4.1.6296.102.12.2.2.1.2.19
		sleV2IgmpInfoControlMvrActivity OBJECT-TYPE
			SYNTAX Boolean
			MAX-ACCESS read-write
			STATUS current
			DESCRIPTION
				"The active state of MVR."
			::= { sleV2IgmpInfoControl 19 }

		
--  1.3.6.1.4.1.6296.102.12.2.2.1.2.20
		sleV2IgmpInfoControlTcnQueryInterval OBJECT-TYPE
			SYNTAX INTEGER (0 | 1..1800)
			MAX-ACCESS read-write
			STATUS current
			DESCRIPTION
				"TCN query interval"
			::= { sleV2IgmpInfoControl 20 }

		
--  1.3.6.1.4.1.6296.102.12.2.2.1.2.21
		sleV2IgmpInfoControlTcnQuerySolicitAddress OBJECT-TYPE
			SYNTAX IpAddress
			MAX-ACCESS read-write
			STATUS current
			DESCRIPTION
				"The source adddress of TCN solicit"
			::= { sleV2IgmpInfoControl 21 }

		
--  1.3.6.1.4.1.6296.102.12.2.2.1.2.22
		sleV2IgmpInfoControlVerifyTTL OBJECT-TYPE
			SYNTAX Boolean
			MAX-ACCESS read-write
			STATUS current
			DESCRIPTION
				"The activie state of Verify-TTL"
			::= { sleV2IgmpInfoControl 22 }

		
		sleV2IgmpInfoControlSnoopExplicitTrackingMacBased OBJECT-TYPE
			SYNTAX Boolean
			MAX-ACCESS read-write
			STATUS current
			DESCRIPTION
				"In IGMPv3, it decide the mac-based device tracks reporters or not."
			::= { sleV2IgmpInfoControl 23 }

		
		sleV2IgmpInfoControlSnoopTcnQueryGeneralStatus OBJECT-TYPE
			SYNTAX INTEGER
				{
				disable(0),
				enable(1)
				}
			MAX-ACCESS read-write
			STATUS current
			DESCRIPTION
				"The status is indicated Generating  an IGMPv2 gereral query. "
			::= { sleV2IgmpInfoControl 24 }

		
		sleV2IgmpInfoControlSnoopTcnQueryGeneralMaxResponseTime OBJECT-TYPE
			SYNTAX Integer32 (1..25)
			MAX-ACCESS read-write
			STATUS current
			DESCRIPTION
				"IGMP Snooping general query maximum response time (1-25sec, Default:1sec)."
			::= { sleV2IgmpInfoControl 25 }

		
--  1.3.6.1.4.1.6296.102.12.2.2.1.1.1
		sleV2IgmpinfoControlSnoopMrouterCpu OBJECT-TYPE
			SYNTAX INTEGER
				{
				disable(0),
				enable(1)
				}
			MAX-ACCESS read-write
			STATUS current
			DESCRIPTION
				"sleV2IgmpinfoSnoopMrouterCpu"
			::= { sleV2IgmpInfoControl 26 }

		
		sleV2IgmpInfoControlMaxGroupSystemCnt OBJECT-TYPE
			SYNTAX Unsigned32 (1..2147483647)
			MAX-ACCESS read-write
			STATUS current
			DESCRIPTION
				"The max group system count."
			::= { sleV2IgmpInfoControl 27 }

		
		sleV2IgmpInfoControlSnoopMRtLearningMode OBJECT-TYPE
			SYNTAX INTEGER
				{
				none(0),
				pim(1)
				}
			MAX-ACCESS read-only
			STATUS current
			DESCRIPTION
				"This object specifies the multicast router port learning method for IGMP Snooping
				
				    none(0): don't learning, Only use static router ports.
				
				    pim(1) : Protocol Independent Multicast.
				"
			::= { sleV2IgmpInfoControl 28 }

		
		sleV2IgmpInfoControlSnoopQuerierAddress OBJECT-TYPE
			SYNTAX IpAddress
			MAX-ACCESS read-write
			STATUS current
			DESCRIPTION
				"Description."
			::= { sleV2IgmpInfoControl 29 }

		
		sleV2IgmpInfoControlSsmMapActive OBJECT-TYPE
			SYNTAX Integer32
			MAX-ACCESS read-write
			STATUS current
			DESCRIPTION
				"Use this command to enable SSM mapping on the router."
			::= { sleV2IgmpInfoControl 30 }

		
		sleV2IgmpInfoControlLimit OBJECT-TYPE
			SYNTAX Integer32 (0 | 1..2097152)
			MAX-ACCESS read-write
			STATUS current
			DESCRIPTION
				"Use this command to set the maximum number of group membership states, at either the router level or at the interface level.
				range : 1 ~ 2097152
				0 : disable"
			::= { sleV2IgmpInfoControl 31 }

		
		sleV2IgmpInfoControlLimitExcept OBJECT-TYPE
			SYNTAX OCTET STRING
			MAX-ACCESS read-write
			STATUS current
			DESCRIPTION
				"Use this command to set the maximum number of group membership states, at either the router level or at the interface level."
			::= { sleV2IgmpInfoControl 32 }

		
--  IGMP Configuration Notification
-- 1.3.6.1.4.1.6296.102.12.2.2.1.3
		sleV2IgmpInfoNotification OBJECT IDENTIFIER ::= { sleV2IgmpBase 3 }

		
--  1.3.6.1.4.1.6296.102.12.2.2.1.3.1
		sleV2IgmpInfoSnoopActivityChanged NOTIFICATION-TYPE
			OBJECTS { sleV2IgmpInfoControlRequest, sleV2IgmpInfoControlReqResult, sleV2IgmpInfoControlTimeStamp, sleV2IgmpInfoSnoopActivity, sleV2IgmpInfoSnoopVersion, 
				sleV2IgmpInfoSnoopVersionMode, sleV2IgmpInfoSnoopFastLeave, sleV2IgmpInfoSnoopFastBlock, sleV2IgmpInfoSnoopReportSuppression, sleV2IgmpInfoExplicitTracking
				 }
			STATUS current
			DESCRIPTION 
				"setMcastInfoMvrActivity"
			::= { sleV2IgmpInfoNotification 1 }

		
--  1.3.6.1.4.1.6296.102.12.2.2.1.3.2
		sleV2IgmpInfoQuerierProfileChanged NOTIFICATION-TYPE
			OBJECTS { sleV2IgmpInfoControlRequest, sleV2IgmpInfoControlTimeStamp, sleV2IgmpInfoControlReqResult, sleV2IgmpInfoSnoopQuerierActivity, sleV2IgmpInfoSnoopQueryInterval, 
				sleV2IgmpInfoSnoopMaxResponseTime, sleV2IgmpInfoSnoopLastMembQueryIntvl, sleV2IgmpInfoControlSnoopQuerierAddress }
			STATUS current
			DESCRIPTION 
				"Description."
			::= { sleV2IgmpInfoNotification 2 }

		
--  1.3.6.1.4.1.6296.102.12.2.2.1.3.3
		sleV2IgmpInfoTcnProfileChanged NOTIFICATION-TYPE
			OBJECTS { sleV2IgmpInfoControlRequest, sleV2IgmpInfoControlReqResult, sleV2IgmpInfoControlTimeStamp, sleV2IgmpInfoTcnFloodActivity, sleV2IgmpInfoTcnQuerySolicitActivity, 
				sleV2IgmpInfoTcnFloodQueryCount }
			STATUS current
			DESCRIPTION 
				"Description."
			::= { sleV2IgmpInfoNotification 3 }

		
--  1.3.6.1.4.1.6296.102.12.2.2.1.3.4
		sleV2IgmpInfoMvrActivityChanged NOTIFICATION-TYPE
			OBJECTS { sleV2IgmpInfoControlRequest, sleV2IgmpInfoControlReqResult, sleV2IgmpInfoControlTimeStamp, sleV2IgmpInfoMvrActivity }
			STATUS current
			DESCRIPTION 
				"setMcastInfoMvrActivity"
			::= { sleV2IgmpInfoNotification 4 }

		
--  1.3.6.1.4.1.6296.102.12.2.2.1.3.5
		sleV2IgmpInfoTcnProfileQueryIntervalChanged NOTIFICATION-TYPE
			OBJECTS { sleV2IgmpInfoControlRequest, sleV2IgmpInfoControlTimeStamp, sleV2IgmpInfoControlReqResult, sleV2IgmpInfoTcnQueryInterval }
			STATUS current
			DESCRIPTION 
				"Description."
			::= { sleV2IgmpInfoNotification 5 }

		
--  1.3.6.1.4.1.6296.102.12.2.2.1.3.6
		sleV2IgmpInfoTcnProfileSolicitAddressChanged NOTIFICATION-TYPE
			OBJECTS { sleV2IgmpInfoControlRequest, sleV2IgmpInfoControlTimeStamp, sleV2IgmpInfoControlReqResult, sleV2IgmpInfoTcnQuerySolicitAddress }
			STATUS current
			DESCRIPTION 
				"Description."
			::= { sleV2IgmpInfoNotification 6 }

		
--  1.3.6.1.4.1.6296.102.12.2.2.1.3.7
		sleV2IgmpInfoVerifyTTLChanged NOTIFICATION-TYPE
			OBJECTS { sleV2IgmpInfoControlRequest, sleV2IgmpInfoControlTimeStamp, sleV2IgmpInfoControlReqResult, sleV2IgmpInfoVerifyTTL }
			STATUS current
			DESCRIPTION 
				"Description."
			::= { sleV2IgmpInfoNotification 7 }

		
		sleV2IgmpInfoSnoopExplicitTrackingMacBasedChanged NOTIFICATION-TYPE
			OBJECTS { sleV2IgmpInfoControlRequest, sleV2IgmpInfoControlTimeStamp, sleV2IgmpInfoControlReqResult, sleV2IgmpInfoControlSnoopExplicitTrackingMacBased }
			STATUS current
			DESCRIPTION 
				"Description."
			::= { sleV2IgmpInfoNotification 8 }

		
		sleV2IgmpInfoSnoopTcnQueryGeneralChanged NOTIFICATION-TYPE
			OBJECTS { sleV2IgmpInfoControlRequest, sleV2IgmpInfoControlTimeStamp, sleV2IgmpInfoControlReqResult, sleV2IgmpInfoSnoopTcnQueryGeneralStatus, sleV2IgmpInfoSnoopTcnQueryGeneralMaxResponseTime
				 }
			STATUS current
			DESCRIPTION 
				"setIgmpInfoSnoopTcnGeneral"
			::= { sleV2IgmpInfoNotification 9 }

		
		sleV2IgmpinfoSnoopMrouterCpuChanged NOTIFICATION-TYPE
			OBJECTS { sleV2IgmpInfoControlRequest, sleV2IgmpInfoControlTimeStamp, sleV2IgmpInfoControlReqResult, sleV2IgmpinfoControlSnoopMrouterCpu }
			STATUS current
			DESCRIPTION 
				"setIgmpInfoSnoopMrouterCpu"
			::= { sleV2IgmpInfoNotification 10 }

		
		sleV2IgmpInfoMaxGroupSystemCntChanged NOTIFICATION-TYPE
			OBJECTS { sleV2IgmpInfoControlRequest, sleV2IgmpInfoControlTimeStamp, sleV2IgmpInfoControlReqResult, sleV2IgmpInfoControlMaxGroupSystemCnt }
			STATUS current
			DESCRIPTION 
				"setIgmpInfoMaxGroupSystemCnt"
			::= { sleV2IgmpInfoNotification 11 }

		
		sleV2IgmpInfoMaxGroupSystemCntDeleted NOTIFICATION-TYPE
			OBJECTS { sleV2IgmpInfoControlRequest, sleV2IgmpInfoControlTimeStamp, sleV2IgmpInfoControlReqResult }
			STATUS current
			DESCRIPTION 
				"delIgmpInfoMaxGroupSystemCnt"
			::= { sleV2IgmpInfoNotification 12 }

		
		sleV2IgmpInfoSnoopMRouteProfileChanged NOTIFICATION-TYPE
			OBJECTS { sleV2IgmpInfoControlRequest, sleV2IgmpInfoControlTimeStamp, sleV2IgmpInfoControlReqResult, sleV2IgmpInfoControlSnoopMRtLearningMode }
			STATUS current
			DESCRIPTION 
				"setIgmpInfoSnoopMrouterProfile"
			::= { sleV2IgmpInfoNotification 13 }

		
--  IGMP Helper
-- 1.3.6.1.4.1.6296.102.12.2.2.2
		sleV2IgmpHelper OBJECT IDENTIFIER ::= { sleV2Igmp 2 }

		
--  IGMP Helper VLAN
-- 1.3.6.1.4.1.6296.102.12.2.2.2.1
		sleV2IghVlan OBJECT IDENTIFIER ::= { sleV2IgmpHelper 1 }

		
--  IGMP Helper VLAN Table
-- 1.3.6.1.4.1.6296.102.12.2.2.2.1.1
		sleV2IghVlanTable OBJECT-TYPE
			SYNTAX SEQUENCE OF SleV2IghVlanEntry
			MAX-ACCESS not-accessible
			STATUS current
			DESCRIPTION
				"IGH vlan table."
			::= { sleV2IghVlan 1 }

		
--  IGMP Helper VLAN Entry
-- 1.3.6.1.4.1.6296.102.12.2.2.2.1.1.1
		sleV2IghVlanEntry OBJECT-TYPE
			SYNTAX SleV2IghVlanEntry
			MAX-ACCESS not-accessible
			STATUS current
			DESCRIPTION
				"key: sleV2IghVlanIndex"
			INDEX { sleV2IghVlanIndex }
			::= { sleV2IghVlanTable 1 }

		
		SleV2IghVlanEntry ::=
			SEQUENCE { 
				sleV2IghVlanIndex
					INTEGER,
				sleV2IghVlanHelperAddress
					IpAddress,
				sleV2IghVlanOperAddress
					IpAddress
			 }

--  1.3.6.1.4.1.6296.102.12.2.2.2.1.1.1.1
		sleV2IghVlanIndex OBJECT-TYPE
			SYNTAX INTEGER (1..4094)
			MAX-ACCESS read-only
			STATUS current
			DESCRIPTION
				"This object indicates the number of VLAN which is used in IGMP features.
				"
			::= { sleV2IghVlanEntry 1 }

		
--  1.3.6.1.4.1.6296.102.12.2.2.2.1.1.1.2
		sleV2IghVlanHelperAddress OBJECT-TYPE
			SYNTAX IpAddress
			MAX-ACCESS read-only
			STATUS current
			DESCRIPTION
				"This object indicates the helper address of the VLAN is used in IGMP snooping TCN, MVR, Static Host (sleV2IghGroup), etc."
			::= { sleV2IghVlanEntry 2 }

		
--  1.3.6.1.4.1.6296.102.12.2.2.2.1.1.1.3
		sleV2IghVlanOperAddress OBJECT-TYPE
			SYNTAX IpAddress
			MAX-ACCESS read-only
			STATUS current
			DESCRIPTION
				"Real source address used in IGMP report/leave message. It decided by sleV2IghVlanHelperAddress or interface address."
			::= { sleV2IghVlanEntry 3 }

		
--  IGMP Helper VLAN Control
-- 1.3.6.1.4.1.6296.102.12.2.2.2.1.2
		sleV2IghVlanControl OBJECT IDENTIFIER ::= { sleV2IghVlan 2 }

		
--  1.3.6.1.4.1.6296.102.12.2.2.2.1.2.1
		sleV2IghVlanControlRequest OBJECT-TYPE
			SYNTAX INTEGER { setIgmpHelperVlanProfile(1) }
			MAX-ACCESS read-write
			STATUS current
			DESCRIPTION
				"createMvrVlan(1), destroyMvrVlan(2) not supported because MVR VLANs is automatically added or/and deleted by adding or/and deleting MVR GROUPs."
			::= { sleV2IghVlanControl 1 }

		
--  1.3.6.1.4.1.6296.102.12.2.2.2.1.2.2
		sleV2IghVlanControlStatus OBJECT-TYPE
			SYNTAX SleControlStatusType
			MAX-ACCESS read-only
			STATUS current
			DESCRIPTION
				"The status of a user command. "
			::= { sleV2IghVlanControl 2 }

		
--  1.3.6.1.4.1.6296.102.12.2.2.2.1.2.3
		sleV2IghVlanControlTimer OBJECT-TYPE
			SYNTAX Gauge32
			MAX-ACCESS read-write
			STATUS current
			DESCRIPTION
				"The maximum wait time for the manager for a long running user command."
			::= { sleV2IghVlanControl 3 }

		
--  1.3.6.1.4.1.6296.102.12.2.2.2.1.2.4
		sleV2IghVlanControlTimeStamp OBJECT-TYPE
			SYNTAX TimeStamp
			MAX-ACCESS read-only
			STATUS current
			DESCRIPTION
				"The time stamp of the last command (end of command)."
			::= { sleV2IghVlanControl 4 }

		
--  1.3.6.1.4.1.6296.102.12.2.2.2.1.2.5
		sleV2IghVlanControlReqResult OBJECT-TYPE
			SYNTAX SleControlRequestResultType
			MAX-ACCESS read-only
			STATUS current
			DESCRIPTION
				"The result of the last user command."
			::= { sleV2IghVlanControl 5 }

		
--  1.3.6.1.4.1.6296.102.12.2.2.2.1.2.6
		sleV2IghVlanControlIndex OBJECT-TYPE
			SYNTAX INTEGER (1..4094)
			MAX-ACCESS read-write
			STATUS current
			DESCRIPTION
				"This object indicates the VLAN number on which MVR feature is configured."
			::= { sleV2IghVlanControl 6 }

		
--  1.3.6.1.4.1.6296.102.12.2.2.2.1.2.7
		sleV2IghVlanControlHelperAddress OBJECT-TYPE
			SYNTAX IpAddress
			MAX-ACCESS read-write
			STATUS current
			DESCRIPTION
				"This object indicates the helper address of VLAN number on which MVR feature is configured."
			::= { sleV2IghVlanControl 7 }

		
--  IGMP Helper VLAN Notification
-- 1.3.6.1.4.1.6296.102.12.2.2.2.1.3
		sleV2IghVlanNotification OBJECT IDENTIFIER ::= { sleV2IghVlan 3 }

		
--  1.3.6.1.4.1.6296.102.12.2.2.2.1.3.1
		sleV2IghVlanProfileChanged NOTIFICATION-TYPE
			OBJECTS { sleV2IghVlanControlRequest, sleV2IghVlanControlReqResult, sleV2IghVlanControlTimeStamp, sleV2IghVlanHelperAddress }
			STATUS current
			DESCRIPTION 
				"setMvr4VlanHelperAddress"
			::= { sleV2IghVlanNotification 1 }

		
--  IGMP Helper Group
-- 1.3.6.1.4.1.6296.102.12.2.2.2.2
		sleV2IghJoin OBJECT IDENTIFIER ::= { sleV2IgmpHelper 2 }

		
--  IGMP Helper Group Table
-- 1.3.6.1.4.1.6296.102.12.2.2.2.2.1
		sleV2IghJoinTable OBJECT-TYPE
			SYNTAX SEQUENCE OF SleV2IghJoinEntry
			MAX-ACCESS not-accessible
			STATUS current
			DESCRIPTION
				"IGH join table."
			::= { sleV2IghJoin 1 }

		
--  IGMP Helper Group Entry
-- 1.3.6.1.4.1.6296.102.12.2.2.2.2.1.1
		sleV2IghJoinEntry OBJECT-TYPE
			SYNTAX SleV2IghJoinEntry
			MAX-ACCESS not-accessible
			STATUS current
			DESCRIPTION
				"key: sleV2IghVlanIndex, sleV2IghJoinAddress, sleV2IghJoinSource, sleV2IghJoinReporter, sleV2IghJoinPortIndex"
			INDEX { sleV2IghVlanIndex, sleV2IghJoinAddress, sleV2IghJoinSource, sleV2IghJoinReporter, sleV2IghJoinPortIndex
				 }
			::= { sleV2IghJoinTable 1 }

		
		SleV2IghJoinEntry ::=
			SEQUENCE { 
				sleV2IghJoinAddress
					IpAddress,
				sleV2IghJoinSource
					IpAddress,
				sleV2IghJoinPortIndex
					INTEGER,
				sleV2IghJoinReporter
					IpAddress
			 }

--  1.3.6.1.4.1.6296.102.12.2.2.2.2.1.1.1
		sleV2IghJoinAddress OBJECT-TYPE
			SYNTAX IpAddress
			MAX-ACCESS read-only
			STATUS current
			DESCRIPTION
				"IP multicast address of multicast service (S,G) required by virtual (static or built-in) host to emulate."
			::= { sleV2IghJoinEntry 1 }

		
--  1.3.6.1.4.1.6296.102.12.2.2.2.2.1.1.2
		sleV2IghJoinSource OBJECT-TYPE
			SYNTAX IpAddress
			MAX-ACCESS read-only
			STATUS current
			DESCRIPTION
				"Source address of multicast service (S,G) required by virtual host to emulate. For (*,G) entry, value is 0.0.0.0"
			::= { sleV2IghJoinEntry 2 }

		
--  1.3.6.1.4.1.6296.102.12.2.2.2.2.1.1.3
		sleV2IghJoinPortIndex OBJECT-TYPE
			SYNTAX INTEGER (1..255)
			MAX-ACCESS read-only
			STATUS current
			DESCRIPTION
				"Index of port to what virtual host to emulate is connected."
			::= { sleV2IghJoinEntry 3 }

		
--  1.3.6.1.4.1.6296.102.12.2.2.2.2.1.1.4
		sleV2IghJoinReporter OBJECT-TYPE
			SYNTAX IpAddress
			MAX-ACCESS read-only
			STATUS current
			DESCRIPTION
				"IP address of virtual host to emulate. If value is 0.0.0.0, sleV2IghVlanOperAddress is used as source address of IGMP control message"
			::= { sleV2IghJoinEntry 4 }

		
		sleV2IghJoinControl OBJECT IDENTIFIER ::= { sleV2IghJoin 2 }

		
		sleV2IghJoinControlRequest OBJECT-TYPE
			SYNTAX INTEGER
				{
				createIgmpHelperJoin(1),
				destroyIgmpHelperJoin(2),
				clearIgmpHelperJoin(3)
				}
			MAX-ACCESS read-write
			STATUS current
			DESCRIPTION
				"The request of a user command"
			::= { sleV2IghJoinControl 1 }

		
		sleV2IghJoinControlStatus OBJECT-TYPE
			SYNTAX SleControlStatusType
			MAX-ACCESS read-only
			STATUS current
			DESCRIPTION
				"The status of a user command. "
			::= { sleV2IghJoinControl 2 }

		
		sleV2IghJoinControlTimer OBJECT-TYPE
			SYNTAX Gauge32
			MAX-ACCESS read-write
			STATUS current
			DESCRIPTION
				"The maximum wait time for the manager for a long running user command."
			::= { sleV2IghJoinControl 3 }

		
		sleV2IghJoinControlTimeStamp OBJECT-TYPE
			SYNTAX TimeStamp
			MAX-ACCESS read-only
			STATUS current
			DESCRIPTION
				"The time stamp of the last command (end of command)."
			::= { sleV2IghJoinControl 4 }

		
		sleV2IghJoinControlReqResult OBJECT-TYPE
			SYNTAX SleControlRequestResultType
			MAX-ACCESS read-only
			STATUS current
			DESCRIPTION
				"The result of the last user command."
			::= { sleV2IghJoinControl 5 }

		
		sleV2IghJoinControlVlanIndex OBJECT-TYPE
			SYNTAX INTEGER (0 | 1..4094)
			MAX-ACCESS read-write
			STATUS current
			DESCRIPTION
				"This object indicates the VLAN number on which MVR feature is configured.
				For all VLANs, the value is 0 (zero)"
			::= { sleV2IghJoinControl 6 }

		
		sleV2IghJoinControlAddress OBJECT-TYPE
			SYNTAX IpAddress
			MAX-ACCESS read-write
			STATUS current
			DESCRIPTION
				"This object indicates the helper address of VLAN number on which MVR feature is configured.
				For all GROUPs, the value is 0.0.0.0"
			::= { sleV2IghJoinControl 7 }

		
		sleV2IghJoinControlSource OBJECT-TYPE
			SYNTAX IpAddress
			MAX-ACCESS read-write
			STATUS current
			DESCRIPTION
				"Source address of multicast service (S,G) required by virtual host to emulate. For (*,G) entry, value is 0.0.0.0
				(not supported)"
			::= { sleV2IghJoinControl 8 }

		
		sleV2IghJoinControlPortIndex OBJECT-TYPE
			SYNTAX INTEGER (1..255)
			MAX-ACCESS read-write
			STATUS current
			DESCRIPTION
				"Index of port to what virtual host to emulate is connected."
			::= { sleV2IghJoinControl 9 }

		
		sleV2IghJoinControlReporter OBJECT-TYPE
			SYNTAX IpAddress
			MAX-ACCESS read-write
			STATUS current
			DESCRIPTION
				"IP address of virtual host to emulate. If value is 0.0.0.0, sleV2IghVlanOperAddress is used as source address of IGMP control message"
			::= { sleV2IghJoinControl 10 }

		
		sleV2IghJoinNotification OBJECT IDENTIFIER ::= { sleV2IghJoin 3 }

		
		sleV2IghJoinCreated NOTIFICATION-TYPE
			OBJECTS { sleV2IghJoinControlRequest, sleV2IghJoinControlTimeStamp, sleV2IghJoinControlReqResult, sleV2IghJoinControlVlanIndex, sleV2IghJoinControlAddress, 
				sleV2IghJoinControlSource, sleV2IghJoinControlReporter, sleV2IghJoinControlPortIndex }
			STATUS current
			DESCRIPTION 
				"Description."
			::= { sleV2IghJoinNotification 1 }

		
		sleV2IghJoinDestroyed NOTIFICATION-TYPE
			OBJECTS { sleV2IghJoinControlRequest, sleV2IghJoinControlTimeStamp, sleV2IghJoinControlReqResult, sleV2IghJoinControlVlanIndex, sleV2IghJoinControlAddress, 
				sleV2IghJoinControlSource, sleV2IghJoinControlReporter, sleV2IghJoinControlPortIndex }
			STATUS current
			DESCRIPTION 
				"Description."
			::= { sleV2IghJoinNotification 2 }

		
		sleV2IghJoinCleared NOTIFICATION-TYPE
			OBJECTS { sleV2IghJoinControlRequest, sleV2IghJoinControlTimeStamp, sleV2IghJoinControlReqResult, sleV2IghJoinControlVlanIndex, sleV2IghJoinControlAddress, 
				sleV2IghJoinControlSource }
			STATUS current
			DESCRIPTION 
				"Description."
			::= { sleV2IghJoinNotification 3 }

		
		sleV2IghGroup OBJECT IDENTIFIER ::= { sleV2IgmpHelper 3 }

		
		sleV2IghGroupTable OBJECT-TYPE
			SYNTAX SEQUENCE OF SleV2IghGroupEntry
			MAX-ACCESS not-accessible
			STATUS current
			DESCRIPTION
				"IGH group table."
			::= { sleV2IghGroup 1 }

		
		sleV2IghGroupEntry OBJECT-TYPE
			SYNTAX SleV2IghGroupEntry
			MAX-ACCESS not-accessible
			STATUS current
			DESCRIPTION
				"key: sleV2IghVlanIndex, sleV2IghGroupAddress, sleV2IghGroupSource, sleV2IghGroupPortIndex"
			INDEX { sleV2IghVlanIndex, sleV2IghGroupAddress, sleV2IghGroupSource, sleV2IghGroupPortIndex }
			::= { sleV2IghGroupTable 1 }

		
		SleV2IghGroupEntry ::=
			SEQUENCE { 
				sleV2IghGroupAddress
					IpAddress,
				sleV2IghGroupSource
					IpAddress,
				sleV2IghGroupPortIndex
					INTEGER
			 }

		sleV2IghGroupAddress OBJECT-TYPE
			SYNTAX IpAddress
			MAX-ACCESS read-only
			STATUS current
			DESCRIPTION
				"IP multicast address of multicast service (S,G) required by virtual 
				(static or built-in) host to emulate."
			::= { sleV2IghGroupEntry 1 }

		
		sleV2IghGroupSource OBJECT-TYPE
			SYNTAX IpAddress
			MAX-ACCESS read-only
			STATUS current
			DESCRIPTION
				"Source address of multicast service (S,G) required by virtual host to emulate. For (*,G) entry, value is 0.0.0.0"
			::= { sleV2IghGroupEntry 2 }

		
		sleV2IghGroupPortIndex OBJECT-TYPE
			SYNTAX INTEGER (1..255)
			MAX-ACCESS read-only
			STATUS current
			DESCRIPTION
				"Index of port to what virtual host to emulate is connected."
			::= { sleV2IghGroupEntry 3 }

		
		sleV2IghGroupControl OBJECT IDENTIFIER ::= { sleV2IghGroup 2 }

		
		sleV2IghGroupControlRequest OBJECT-TYPE
			SYNTAX INTEGER
				{
				createIgmpHelperGroup(1),
				destroyIgmpHelperGroup(2),
				clearIgmpHelperGroup(3)
				}
			MAX-ACCESS read-write
			STATUS current
			DESCRIPTION
				"createMvrVlan(1), destroyMvrVlan(2) not supported because MVR VLANs is automatically added or/and deleted by adding or/and deleting MVR GROUPs."
			::= { sleV2IghGroupControl 1 }

		
		sleV2IghGroupControlStatus OBJECT-TYPE
			SYNTAX SleControlStatusType
			MAX-ACCESS read-only
			STATUS current
			DESCRIPTION
				"The status of a user command. "
			::= { sleV2IghGroupControl 2 }

		
		sleV2IghGroupControlTimer OBJECT-TYPE
			SYNTAX Gauge32
			MAX-ACCESS read-write
			STATUS current
			DESCRIPTION
				"The maximum wait time for the manager for a long running user command."
			::= { sleV2IghGroupControl 3 }

		
		sleV2IghGroupControlTimeStamp OBJECT-TYPE
			SYNTAX TimeStamp
			MAX-ACCESS read-only
			STATUS current
			DESCRIPTION
				"The time stamp of the last command (end of command)."
			::= { sleV2IghGroupControl 4 }

		
		sleV2IghGroupControlReqResult OBJECT-TYPE
			SYNTAX SleControlRequestResultType
			MAX-ACCESS read-only
			STATUS current
			DESCRIPTION
				"The result of the last user command."
			::= { sleV2IghGroupControl 5 }

		
		sleV2IghGroupControlVlanIndex OBJECT-TYPE
			SYNTAX INTEGER (0 | 1..4094)
			MAX-ACCESS read-write
			STATUS current
			DESCRIPTION
				"This object indicates the VLAN number on which MVR feature is configured.
				For all VLANs, the value is 0 (zero)"
			::= { sleV2IghGroupControl 6 }

		
		sleV2IghGroupControlAddress OBJECT-TYPE
			SYNTAX IpAddress
			MAX-ACCESS read-write
			STATUS current
			DESCRIPTION
				"This object indicates the helper address of VLAN number on which MVR feature is configured.
				For all GROUPs, the value is 0.0.0.0"
			::= { sleV2IghGroupControl 7 }

		
		sleV2IghGroupControlSource OBJECT-TYPE
			SYNTAX IpAddress
			MAX-ACCESS read-write
			STATUS current
			DESCRIPTION
				"Source address of multicast service (S,G) required by virtual host to emulate. For (*,G) entry, value is 0.0.0.0
				(not supported)"
			::= { sleV2IghGroupControl 8 }

		
		sleV2IghGroupControlPortIndex OBJECT-TYPE
			SYNTAX INTEGER (1..255)
			MAX-ACCESS read-write
			STATUS current
			DESCRIPTION
				"Index of port to what virtual host to emulate is connected."
			::= { sleV2IghGroupControl 9 }

		
		sleV2IghGroupNotification OBJECT IDENTIFIER ::= { sleV2IghGroup 3 }

		
		sleV2IghGroupCreated NOTIFICATION-TYPE
			OBJECTS { sleV2IghGroupControlRequest, sleV2IghGroupControlTimeStamp, sleV2IghGroupControlReqResult, sleV2IghGroupControlVlanIndex, sleV2IghGroupControlAddress, 
				sleV2IghGroupControlSource, sleV2IghGroupControlPortIndex }
			STATUS current
			DESCRIPTION 
				"Description."
			::= { sleV2IghGroupNotification 1 }

		
		sleV2IghGroupDestroyed NOTIFICATION-TYPE
			OBJECTS { sleV2IghGroupControlRequest, sleV2IghGroupControlTimeStamp, sleV2IghGroupControlReqResult, sleV2IghGroupControlVlanIndex, sleV2IghGroupControlAddress, 
				sleV2IghGroupControlSource, sleV2IghGroupControlPortIndex }
			STATUS current
			DESCRIPTION 
				"Description."
			::= { sleV2IghGroupNotification 2 }

		
		sleV2IghGroupCleared NOTIFICATION-TYPE
			OBJECTS { sleV2IghGroupControlRequest, sleV2IghGroupControlTimeStamp, sleV2IghGroupControlReqResult, sleV2IghGroupControlVlanIndex, sleV2IghGroupControlAddress
				 }
			STATUS current
			DESCRIPTION 
				"Description."
			::= { sleV2IghGroupNotification 3 }

		
		sleV2IghJoinProfile OBJECT IDENTIFIER ::= { sleV2IgmpHelper 4 }

		
		sleV2IghJoinProfileTable OBJECT-TYPE
			SYNTAX SEQUENCE OF SleV2IghJoinProfileEntry
			MAX-ACCESS not-accessible
			STATUS current
			DESCRIPTION
				"IGH join profile table."
			::= { sleV2IghJoinProfile 1 }

		
		sleV2IghJoinProfileEntry OBJECT-TYPE
			SYNTAX SleV2IghJoinProfileEntry
			MAX-ACCESS not-accessible
			STATUS current
			DESCRIPTION
				"key: sleV2IghVlanIndex, sleV2IghJoinProfilePortIndex, sleV2IghJoinProfileId, sleV2IghJoinProfileReporter"
			INDEX { sleV2IghVlanIndex, sleV2IghJoinProfilePortIndex, sleV2IghJoinProfileId, sleV2IghJoinProfileReporter }
			::= { sleV2IghJoinProfileTable 1 }

		
		SleV2IghJoinProfileEntry ::=
			SEQUENCE { 
				sleV2IghJoinProfilePortIndex
					INTEGER,
				sleV2IghJoinProfileId
					Integer32,
				sleV2IghJoinProfileReporter
					IpAddress
			 }

		sleV2IghJoinProfilePortIndex OBJECT-TYPE
			SYNTAX INTEGER (1..255)
			MAX-ACCESS read-only
			STATUS current
			DESCRIPTION
				"Index of port to what virtual host to emulate is connected."
			::= { sleV2IghJoinProfileEntry 1 }

		
		sleV2IghJoinProfileId OBJECT-TYPE
			SYNTAX Integer32 (1..65535)
			MAX-ACCESS read-only
			STATUS current
			DESCRIPTION
				"IGMP profile ID. Same as sleV2IgfProfileIndex"
			::= { sleV2IghJoinProfileEntry 2 }

		
		sleV2IghJoinProfileReporter OBJECT-TYPE
			SYNTAX IpAddress
			MAX-ACCESS read-only
			STATUS current
			DESCRIPTION
				"IP address of virtual host to emulate. If value is 0.0.0.0, sleV2IghVlanOperAddress is used as source address of IGMP control message"
			::= { sleV2IghJoinProfileEntry 3 }

		
		sleV2IghJoinProfileControl OBJECT IDENTIFIER ::= { sleV2IghJoinProfile 2 }

		
		sleV2IghJoinProfileControlRequest OBJECT-TYPE
			SYNTAX INTEGER
				{
				createIgmpHelperJoinProfile(1),
				destroyIgmpHelperJoinProfile(2)
				}
			MAX-ACCESS read-write
			STATUS current
			DESCRIPTION
				"The request of a user command"
			::= { sleV2IghJoinProfileControl 1 }

		
		sleV2IghJoinProfileControlStatus OBJECT-TYPE
			SYNTAX SleControlStatusType
			MAX-ACCESS read-only
			STATUS current
			DESCRIPTION
				"The status of a user command. "
			::= { sleV2IghJoinProfileControl 2 }

		
		sleV2IghJoinProfileControlTimer OBJECT-TYPE
			SYNTAX Gauge32
			MAX-ACCESS read-write
			STATUS current
			DESCRIPTION
				"The maximum wait time for the manager for a long running user command."
			::= { sleV2IghJoinProfileControl 3 }

		
		sleV2IghJoinProfileControlTimeStamp OBJECT-TYPE
			SYNTAX TimeStamp
			MAX-ACCESS read-only
			STATUS current
			DESCRIPTION
				"The time stamp of the last command (end of command)."
			::= { sleV2IghJoinProfileControl 4 }

		
		sleV2IghJoinProfileControlReqResult OBJECT-TYPE
			SYNTAX SleControlRequestResultType
			MAX-ACCESS read-only
			STATUS current
			DESCRIPTION
				"The result of the last user command."
			::= { sleV2IghJoinProfileControl 5 }

		
		sleV2IghJoinProfileControlVlanIndex OBJECT-TYPE
			SYNTAX INTEGER (0 | 1..4094)
			MAX-ACCESS read-write
			STATUS current
			DESCRIPTION
				"This object indicates the VLAN number on which MVR feature is configured.
				For all VLANs, the value is 0 (zero)"
			::= { sleV2IghJoinProfileControl 6 }

		
		sleV2IghJoinProfileControlPortIndex OBJECT-TYPE
			SYNTAX INTEGER (1..255)
			MAX-ACCESS read-write
			STATUS current
			DESCRIPTION
				"port index"
			::= { sleV2IghJoinProfileControl 7 }

		
		sleV2IghJoinProfileControlId OBJECT-TYPE
			SYNTAX INTEGER (0..65535)
			MAX-ACCESS read-write
			STATUS current
			DESCRIPTION
				"IGMP profile ID. Same as sleV2IgfProfileIndex"
			::= { sleV2IghJoinProfileControl 8 }

		
		sleV2IghJoinProfileControlReporter OBJECT-TYPE
			SYNTAX IpAddress
			MAX-ACCESS read-write
			STATUS current
			DESCRIPTION
				"Join profile reporter"
			::= { sleV2IghJoinProfileControl 9 }

		
		sleV2IghJoinProfileNotification OBJECT IDENTIFIER ::= { sleV2IghJoinProfile 3 }

		
		sleV2IghJoinProfileCreated NOTIFICATION-TYPE
			OBJECTS { sleV2IghJoinProfileControlRequest, sleV2IghJoinProfileControlTimeStamp, sleV2IghJoinProfileControlReqResult, sleV2IghJoinProfileControlVlanIndex, sleV2IghJoinProfileControlPortIndex, 
				sleV2IghJoinProfileControlId, sleV2IghJoinProfileControlReporter }
			STATUS current
			DESCRIPTION 
				"Description."
			::= { sleV2IghJoinProfileNotification 1 }

		
		sleV2IghJoinProfileDestroyed NOTIFICATION-TYPE
			OBJECTS { sleV2IghJoinProfileControlRequest, sleV2IghJoinProfileControlTimeStamp, sleV2IghJoinProfileControlReqResult, sleV2IghJoinProfileControlVlanIndex, sleV2IghJoinProfileControlPortIndex, 
				sleV2IghJoinProfileControlId, sleV2IghJoinProfileControlReporter }
			STATUS current
			DESCRIPTION 
				"Description."
			::= { sleV2IghJoinProfileNotification 2 }

		
		sleV2IghGroupProfile OBJECT IDENTIFIER ::= { sleV2IgmpHelper 5 }

		
		sleV2IghGroupProfileTable OBJECT-TYPE
			SYNTAX SEQUENCE OF SleV2IghGroupProfileEntry
			MAX-ACCESS not-accessible
			STATUS current
			DESCRIPTION
				"IGH group profile table."
			::= { sleV2IghGroupProfile 1 }

		
		sleV2IghGroupProfileEntry OBJECT-TYPE
			SYNTAX SleV2IghGroupProfileEntry
			MAX-ACCESS not-accessible
			STATUS current
			DESCRIPTION
				"key: sleV2IghVlanIndex, sleV2IghGroupProfilePortIndex, sleV2IghGroupProfileId"
			INDEX { sleV2IghVlanIndex, sleV2IghGroupProfilePortIndex, sleV2IghGroupProfileId }
			::= { sleV2IghGroupProfileTable 1 }

		
		SleV2IghGroupProfileEntry ::=
			SEQUENCE { 
				sleV2IghGroupProfilePortIndex
					INTEGER,
				sleV2IghGroupProfileId
					Integer32
			 }

		sleV2IghGroupProfilePortIndex OBJECT-TYPE
			SYNTAX INTEGER (1..255)
			MAX-ACCESS read-only
			STATUS current
			DESCRIPTION
				"Index of port to what virtual host to emulate is connected."
			::= { sleV2IghGroupProfileEntry 1 }

		
		sleV2IghGroupProfileId OBJECT-TYPE
			SYNTAX Integer32 (1..65535)
			MAX-ACCESS read-only
			STATUS current
			DESCRIPTION
				"IGMP profile Id. Same as sleV2IgfProfileIndex"
			::= { sleV2IghGroupProfileEntry 2 }

		
		sleV2IghGroupProfileControl OBJECT IDENTIFIER ::= { sleV2IghGroupProfile 2 }

		
		sleV2IghGroupProfileControlRequest OBJECT-TYPE
			SYNTAX INTEGER
				{
				createIgmpHelperGroupProfile(1),
				destroyIgmpHelperGroupProfile(2)
				}
			MAX-ACCESS read-write
			STATUS current
			DESCRIPTION
				"The request of a user command"
			::= { sleV2IghGroupProfileControl 1 }

		
		sleV2IghGroupProfileControlStatus OBJECT-TYPE
			SYNTAX SleControlStatusType
			MAX-ACCESS read-only
			STATUS current
			DESCRIPTION
				"The status of a user command. "
			::= { sleV2IghGroupProfileControl 2 }

		
		sleV2IghGroupProfileControlTimer OBJECT-TYPE
			SYNTAX Gauge32
			MAX-ACCESS read-write
			STATUS current
			DESCRIPTION
				"The maximum wait time for the manager for a long running user command."
			::= { sleV2IghGroupProfileControl 3 }

		
		sleV2IghGroupProfileControlTimeStamp OBJECT-TYPE
			SYNTAX TimeStamp
			MAX-ACCESS read-only
			STATUS current
			DESCRIPTION
				"The time stamp of the last command (end of command)."
			::= { sleV2IghGroupProfileControl 4 }

		
		sleV2IghGroupProfileControlReqResult OBJECT-TYPE
			SYNTAX SleControlRequestResultType
			MAX-ACCESS read-only
			STATUS current
			DESCRIPTION
				"The result of the last user command."
			::= { sleV2IghGroupProfileControl 5 }

		
		sleV2IghGroupProfileControlVlanIndex OBJECT-TYPE
			SYNTAX INTEGER (0 | 1..4094)
			MAX-ACCESS read-write
			STATUS current
			DESCRIPTION
				"This object indicates the VLAN number on which MVR feature is configured.
				For all VLANs, the value is 0 (zero)"
			::= { sleV2IghGroupProfileControl 6 }

		
		sleV2IghGroupProfileControlPortIndex OBJECT-TYPE
			SYNTAX INTEGER (1..255)
			MAX-ACCESS read-write
			STATUS current
			DESCRIPTION
				"Port index"
			::= { sleV2IghGroupProfileControl 7 }

		
		sleV2IghGroupProfileControlId OBJECT-TYPE
			SYNTAX INTEGER (0..65535)
			MAX-ACCESS read-write
			STATUS current
			DESCRIPTION
				"IGMP profile Id. Same as sleV2IgfProfileIndex"
			::= { sleV2IghGroupProfileControl 8 }

		
		sleV2IghGroupProfileNotification OBJECT IDENTIFIER ::= { sleV2IghGroupProfile 3 }

		
		sleV2IghGroupProfileCreated NOTIFICATION-TYPE
			OBJECTS { sleV2IghGroupProfileControlRequest, sleV2IghGroupProfileControlTimeStamp, sleV2IghGroupProfileControlReqResult, sleV2IghGroupProfileControlVlanIndex, sleV2IghGroupProfileControlPortIndex, 
				sleV2IghGroupProfileControlId }
			STATUS current
			DESCRIPTION 
				"Description."
			::= { sleV2IghGroupProfileNotification 1 }

		
		sleV2IghGroupProfileDestroyed NOTIFICATION-TYPE
			OBJECTS { sleV2IghGroupProfileControlRequest, sleV2IghGroupProfileControlTimeStamp, sleV2IghGroupProfileControlReqResult, sleV2IghGroupProfileControlVlanIndex, sleV2IghGroupProfileControlPortIndex, 
				sleV2IghGroupProfileControlId }
			STATUS current
			DESCRIPTION 
				"Description."
			::= { sleV2IghGroupProfileNotification 2 }

		
--  IGMP Source-Specific Multicast(SSM) Mapping
-- 1.3.6.1.4.1.6296.102.12.2.2.3
		sleV2IgmpSsmMapping OBJECT IDENTIFIER ::= { sleV2Igmp 3 }

		
--  IGMP SSM Mapping Table
-- 1.3.6.1.4.1.6296.102.12.2.2.3.1
		sleV2IgmpSsmMapTable OBJECT-TYPE
			SYNTAX SEQUENCE OF SleV2IgmpSsmMapEntry
			MAX-ACCESS not-accessible
			STATUS current
			DESCRIPTION
				"IGMP SSM map tabel."
			::= { sleV2IgmpSsmMapping 1 }

		
--  IGMP SSM Mapping Entry
-- 1.3.6.1.4.1.6296.102.12.2.2.3.1.1
		sleV2IgmpSsmMapEntry OBJECT-TYPE
			SYNTAX SleV2IgmpSsmMapEntry
			MAX-ACCESS not-accessible
			STATUS current
			DESCRIPTION
				"key: sleV2IgmpSsmMapGroup, sleV2IgmpSsmMapSource"
			INDEX { sleV2IgmpSsmMapGroup, sleV2IgmpSsmMapSource }
			::= { sleV2IgmpSsmMapTable 1 }

		
		SleV2IgmpSsmMapEntry ::=
			SEQUENCE { 
				sleV2IgmpSsmMapGroup
					IpAddress,
				sleV2IgmpSsmMapSource
					IpAddress,
				sleV2IgmpSsmMapType
					INTEGER,
				sleV2IgmpSsmMapExpire
					TimeTicks
			 }

--  1.3.6.1.4.1.6296.102.12.2.2.3.1.1.1
		sleV2IgmpSsmMapGroup OBJECT-TYPE
			SYNTAX IpAddress
			MAX-ACCESS read-only
			STATUS current
			DESCRIPTION
				"The group address of (*,G) entry in Source-Specific Multicast (SSM)."
			::= { sleV2IgmpSsmMapEntry 1 }

		
--  1.3.6.1.4.1.6296.102.12.2.2.3.1.1.2
		sleV2IgmpSsmMapSource OBJECT-TYPE
			SYNTAX IpAddress
			MAX-ACCESS read-only
			STATUS current
			DESCRIPTION
				"The source address for group entry (*,G)."
			::= { sleV2IgmpSsmMapEntry 2 }

		
--  1.3.6.1.4.1.6296.102.12.2.2.3.1.1.3
		sleV2IgmpSsmMapType OBJECT-TYPE
			SYNTAX INTEGER
				{
				dynamic(1),
				static(2)
				}
			MAX-ACCESS read-only
			STATUS current
			DESCRIPTION
				"The type of this entry. Static(2) indicate that this 
				entry is setted by administative manner. Dynamic(1), 
				entry generated by remote SSM Mapping server (ex: DNS)."
			::= { sleV2IgmpSsmMapEntry 3 }

		
--  1.3.6.1.4.1.6296.102.12.2.2.3.1.1.4
		sleV2IgmpSsmMapExpire OBJECT-TYPE
			SYNTAX TimeTicks
			MAX-ACCESS read-only
			STATUS current
			DESCRIPTION
				"In static, this value is zero, otherwise time remaining 
				before ageing."
			::= { sleV2IgmpSsmMapEntry 4 }

		
--  IGMP SSM Mapping Control
-- 1.3.6.1.4.1.6296.102.12.2.2.3.2
		sleV2IgmpSsmMapControl OBJECT IDENTIFIER ::= { sleV2IgmpSsmMapping 2 }

		
--  1.3.6.1.4.1.6296.102.12.2.2.3.2.1
		sleV2IgmpSsmMapControlRequest OBJECT-TYPE
			SYNTAX INTEGER
				{
				createIgmpStaticSsmMapping(1),
				destroyIgmpStaticSsmMapping(2)
				}
			MAX-ACCESS read-write
			STATUS current
			DESCRIPTION
				" The request of a user command"
			::= { sleV2IgmpSsmMapControl 1 }

		
--  1.3.6.1.4.1.6296.102.12.2.2.3.2.2
		sleV2IgmpSsmMapControlStatus OBJECT-TYPE
			SYNTAX SleControlStatusType
			MAX-ACCESS read-only
			STATUS current
			DESCRIPTION
				" The status of user command"
			::= { sleV2IgmpSsmMapControl 2 }

		
--  1.3.6.1.4.1.6296.102.12.2.2.3.2.3
		sleV2IgmpSsmMapControlTimer OBJECT-TYPE
			SYNTAX TimeTicks
			MAX-ACCESS read-write
			STATUS current
			DESCRIPTION
				" The maximum time for the manager for a long running user command"
			::= { sleV2IgmpSsmMapControl 3 }

		
--  1.3.6.1.4.1.6296.102.12.2.2.3.2.4
		sleV2IgmpSsmMapControlTimeStamp OBJECT-TYPE
			SYNTAX TimeTicks
			MAX-ACCESS read-only
			STATUS current
			DESCRIPTION
				" The time stamp of the last command(end of command)"
			::= { sleV2IgmpSsmMapControl 4 }

		
--  1.3.6.1.4.1.6296.102.12.2.2.3.2.5
		sleV2IgmpSsmMapControlReqResult OBJECT-TYPE
			SYNTAX Integer32
			MAX-ACCESS read-only
			STATUS current
			DESCRIPTION
				" The result of the last user command"
			::= { sleV2IgmpSsmMapControl 5 }

		
--  1.3.6.1.4.1.6296.102.12.2.2.3.2.6
		sleV2IgmpSsmMapControlGroup OBJECT-TYPE
			SYNTAX IpAddress
			MAX-ACCESS read-write
			STATUS current
			DESCRIPTION
				" The group address of (*,G) entry in Source-Specific Multicast (SSM)."
			::= { sleV2IgmpSsmMapControl 6 }

		
--  1.3.6.1.4.1.6296.102.12.2.2.3.2.7
		sleV2IgmpSsmMapControlSource OBJECT-TYPE
			SYNTAX IpAddress
			MAX-ACCESS read-write
			STATUS current
			DESCRIPTION
				" The source address for group entry (*,G)."
			::= { sleV2IgmpSsmMapControl 7 }

		
--  IGMP SSM Mapping Notification
-- 1.3.6.1.4.1.6296.102.12.2.2.3.3
		sleV2IgmpSsmMapNotification OBJECT IDENTIFIER ::= { sleV2IgmpSsmMapping 3 }

		
--  1.3.6.1.4.1.6296.102.12.2.2.3.3.1
		sleV2IgmpSsmMapCreated NOTIFICATION-TYPE
			OBJECTS { sleV2IgmpSsmMapControlRequest, sleV2IgmpSsmMapControlReqResult, sleV2IgmpSsmMapControlTimeStamp, sleV2IgmpSsmMapType, sleV2IgmpSsmMapExpire
				 }
			STATUS current
			DESCRIPTION 
				" "
			::= { sleV2IgmpSsmMapNotification 1 }

		
--  1.3.6.1.4.1.6296.102.12.2.2.3.3.2
		sleV2IgmpSsmMapDestroyed NOTIFICATION-TYPE
			OBJECTS { sleV2IgmpSsmMapControlRequest, sleV2IgmpSsmMapControlReqResult, sleV2IgmpSsmMapControlTimeStamp, sleV2IgmpSsmMapControlGroup, sleV2IgmpSsmMapControlSource
				 }
			STATUS current
			DESCRIPTION 
				" "
			::= { sleV2IgmpSsmMapNotification 2 }

		
--  IGMP Agent (Layer 3)
-- 1.3.6.1.4.1.6296.102.12.2.2.4
		sleV2IgmpAgent OBJECT IDENTIFIER ::= { sleV2Igmp 4 }

		
--  IGMP Interface
-- 1.3.6.1.4.1.6296.102.12.2.2.4.1
		sleV2IgmpInterface OBJECT IDENTIFIER ::= { sleV2IgmpAgent 1 }

		
--  IGMP Interface Table
-- 1.3.6.1.4.1.6296.102.12.2.2.4.1.1
		sleV2IgmpIfTable OBJECT-TYPE
			SYNTAX SEQUENCE OF SleV2IgmpIfEntry
			MAX-ACCESS not-accessible
			STATUS current
			DESCRIPTION
				" IGMP interface table."
			::= { sleV2IgmpInterface 1 }

		
--  IGMP Interface Entry
-- 1.3.6.1.4.1.6296.102.12.2.2.4.1.1.1
		sleV2IgmpIfEntry OBJECT-TYPE
			SYNTAX SleV2IgmpIfEntry
			MAX-ACCESS not-accessible
			STATUS current
			DESCRIPTION
				"IGMP Interface Table Entries
				key: sleV2IgmpIfIndex"
			INDEX { sleV2IgmpIfIndex }
			::= { sleV2IgmpIfTable 1 }

		
		SleV2IgmpIfEntry ::=
			SEQUENCE { 
				sleV2IgmpIfIndex
					INTEGER,
				sleV2IgmpIfActivity
					Boolean,
				sleV2IgmpIfVersion
					INTEGER,
				sleV2IgmpIfQueryInterval
					Integer32,
				sleV2IgmpIfQuerierTimeOut
					Integer32,
				sleV2IgmpIfMaxResponseTime
					Integer32,
				sleV2IgmpIfLastMembQueryCount
					Integer32,
				sleV2IgmpIfLastMembQueryIntvl
					Integer32,
				sleV2IgmpIfFastLeaveGroupList
					OCTET STRING,
				sleV2IgmpIfQuerierState
					INTEGER,
				sleV2IgmpIfQuerierAddress
					IpAddress,
				sleV2IgmpIfQuerierUptime
					TimeTicks,
				sleV2IgmpIfQuerierExpireTime
					TimeTicks,
				sleV2IgmpIfWrongVersionQueriers
					Counter32,
				sleV2IgmpIfGroupMembIntvl
					Unsigned32,
				sleV2IgmpIfAccessGroup
					OCTET STRING,
				sleV2IgmpIfRobustness
					Integer32,
				sleV2IgmpIfJoins
					Counter32,
				sleV2IgmpIfGroups
					Gauge32,
				sleV2IgmpIfMRouteProxyIfIndex
					Integer32,
				sleV2IgmpIfMRouteProxyStatus
					Boolean,
				sleV2IgmpIfStartupQueryInterval
					Integer32,
				sleV2IgmpIfUnsolictedReportInterval
					Integer32,
				sleV2IgmpIfLeaves
					Counter32,
				sleV2IgmpIfLimit
					Integer32,
				sleV2IgmpIfExceptGroup
					OCTET STRING,
				sleV2IgmpIfVerifySrcIp
					Boolean,
				sleV2IgmpIfRaOption
					Boolean,
				sleV2IgmpIfStartupQueryCnt
					Unsigned32,
				sleV2IgmpIfOfflink
					Boolean
			 }

--  1.3.6.1.4.1.6296.102.12.2.2.4.1.1.1.1
		sleV2IgmpIfIndex OBJECT-TYPE
			SYNTAX INTEGER (1..4094)
			MAX-ACCESS read-only
			STATUS current
			DESCRIPTION
				" Network interface index.
				(= sleNetIfIndex)
				"
			::= { sleV2IgmpIfEntry 1 }

		
--  1.3.6.1.4.1.6296.102.12.2.2.4.1.1.1.2
		sleV2IgmpIfActivity OBJECT-TYPE
			SYNTAX Boolean
			MAX-ACCESS read-only
			STATUS current
			DESCRIPTION
				"TRUE is IGMP enabled on this interface, FALSE is not."
			::= { sleV2IgmpIfEntry 2 }

		
--  1.3.6.1.4.1.6296.102.12.2.2.4.1.1.1.3
		sleV2IgmpIfVersion OBJECT-TYPE
			SYNTAX INTEGER
				{
				one(1),
				two(2),
				three(3)
				}
			MAX-ACCESS read-only
			STATUS current
			DESCRIPTION
				"The maximum version of IGMP which the host
				can run on this interface."
			DEFVAL { 3 }
			::= { sleV2IgmpIfEntry 3 }

		
--  1.3.6.1.4.1.6296.102.12.2.2.4.1.1.1.4
		sleV2IgmpIfQueryInterval OBJECT-TYPE
			SYNTAX Integer32 (0..31744)
			UNITS "seconds"
			MAX-ACCESS read-only
			STATUS current
			DESCRIPTION
				"The frequency at which IGMP packets are 
				transmitted on this interface."
			DEFVAL { 125 }
			::= { sleV2IgmpIfEntry 4 }

		
--  1.3.6.1.4.1.6296.102.12.2.2.4.1.1.1.5
		sleV2IgmpIfQuerierTimeOut OBJECT-TYPE
			SYNTAX Integer32 (60..300)
			UNITS "seconds"
			MAX-ACCESS read-only
			STATUS current
			DESCRIPTION
				" Other Querier Present Interval. Default value is (QueryInterval * Robustness) + (MaxResponseTime / 2)"
			DEFVAL { 255 }
			::= { sleV2IgmpIfEntry 5 }

		
--  1.3.6.1.4.1.6296.102.12.2.2.4.1.1.1.6
		sleV2IgmpIfMaxResponseTime OBJECT-TYPE
			SYNTAX Integer32 (0..31744)
			UNITS "seconds"
			MAX-ACCESS read-only
			STATUS current
			DESCRIPTION
				"The maximum query response time advertised
				in queries on this interface."
			DEFVAL { 10 }
			::= { sleV2IgmpIfEntry 6 }

		
--  1.3.6.1.4.1.6296.102.12.2.2.4.1.1.1.7
		sleV2IgmpIfLastMembQueryCount OBJECT-TYPE
			SYNTAX Integer32 (1..255)
			MAX-ACCESS read-only
			STATUS current
			DESCRIPTION
				"Represents the number of Group-specific and 
				Group-and-Source-specific queries sent by the 
				router before it assumes there are no local members."
			::= { sleV2IgmpIfEntry 7 }

		
--  1.3.6.1.4.1.6296.102.12.2.2.4.1.1.1.8
		sleV2IgmpIfLastMembQueryIntvl OBJECT-TYPE
			SYNTAX Integer32 (0..31744)
			MAX-ACCESS read-only
			STATUS current
			DESCRIPTION
				"The Last Member Query Interval is the Max Response 
				Time inserted into Group-Specific Queries sent in 
				response to Leave Group messages, and is also the 
				amount of time Between Group-Specific Query messages.
				
				This value may be tuned to modify the leave latency 
				of the network. 
				
				A reduced value results in reduced time to detect 
				the loss of the last member of a group. 
				
				The value of this object is irrelevant if 
				mgmdRouterInterfaceVersion is 1."
			::= { sleV2IgmpIfEntry 8 }

		
--  1.3.6.1.4.1.6296.102.12.2.2.4.1.1.1.9
		sleV2IgmpIfFastLeaveGroupList OBJECT-TYPE
			SYNTAX OCTET STRING
			MAX-ACCESS read-only
			STATUS current
			DESCRIPTION
				" Other Querier Present Interval. Default value is (QueryInterval * Robustness) + (MaxResponseTime / 2)"
			::= { sleV2IgmpIfEntry 9 }

		
--  1.3.6.1.4.1.6296.102.12.2.2.4.1.1.1.10
		sleV2IgmpIfQuerierState OBJECT-TYPE
			SYNTAX INTEGER
				{
				querier(1),
				nonQuerier(2)
				}
			MAX-ACCESS read-only
			STATUS current
			DESCRIPTION
				"It indicates currnet status on IGMP querier in the interface.
				
				querier(1) is currently querier, nonQuerier(2) interface 
				is inactive or not querier now."
			::= { sleV2IgmpIfEntry 10 }

		
--  1.3.6.1.4.1.6296.102.12.2.2.4.1.1.1.11
		sleV2IgmpIfQuerierAddress OBJECT-TYPE
			SYNTAX IpAddress
			MAX-ACCESS read-only
			STATUS current
			DESCRIPTION
				"The address of IGMP Querier on the IP subnet to
				which this interface is attached."
			::= { sleV2IgmpIfEntry 11 }

		
--  1.3.6.1.4.1.6296.102.12.2.2.4.1.1.1.12
		sleV2IgmpIfQuerierUptime OBJECT-TYPE
			SYNTAX TimeTicks
			MAX-ACCESS read-only
			STATUS current
			DESCRIPTION
				"The time since sleV2IgmpIfQuerier was last changed."
			::= { sleV2IgmpIfEntry 12 }

		
--  1.3.6.1.4.1.6296.102.12.2.2.4.1.1.1.13
		sleV2IgmpIfQuerierExpireTime OBJECT-TYPE
			SYNTAX TimeTicks
			MAX-ACCESS read-only
			STATUS current
			DESCRIPTION
				"The amount of time remaining before the other querier
				present timer expires. If the local system is the 
				querier, the value of this object is zero."
			::= { sleV2IgmpIfEntry 13 }

		
--  1.3.6.1.4.1.6296.102.12.2.2.4.1.1.1.14
		sleV2IgmpIfWrongVersionQueriers OBJECT-TYPE
			SYNTAX Counter32
			MAX-ACCESS read-only
			STATUS current
			DESCRIPTION
				"The of general queries received whose IGMP version
				does not match the equivalent SleV2IgmpIfVersion,
				over the lifetime of the row entry.
				
				IGMP require that all routers on a LAN be configured 
				to run the same version.
				
				Thus, if any general queries are received with the 
				wrong version, this indicates a configuration error."
			::= { sleV2IgmpIfEntry 14 }

		
--  1.3.6.1.4.1.6296.102.12.2.2.4.1.1.1.15
		sleV2IgmpIfGroupMembIntvl OBJECT-TYPE
			SYNTAX Unsigned32
			MAX-ACCESS read-only
			STATUS current
			DESCRIPTION
				"Group Membership Interval. This value must be (sleV2IgmpIfQueryInterval * sleV2IgmpIfRobustness) + sleV2IgmpIfMaxResponseTime."
			::= { sleV2IgmpIfEntry 15 }

		
--  1.3.6.1.4.1.6296.102.12.2.2.4.1.1.1.16
		sleV2IgmpIfAccessGroup OBJECT-TYPE
			SYNTAX OCTET STRING
			MAX-ACCESS read-only
			STATUS current
			DESCRIPTION
				"List of IGMP Groups allowed to access."
			::= { sleV2IgmpIfEntry 16 }

		
--  1.3.6.1.4.1.6296.102.12.2.2.4.1.1.1.17
		sleV2IgmpIfRobustness OBJECT-TYPE
			SYNTAX Integer32 (1..255)
			MAX-ACCESS read-only
			STATUS current
			DESCRIPTION
				"The Robustness Variable allows tuning for the expected
				packet loss on a subnet.
				
				If a subnet is expected to be lossy, the Robustness 
				Variable may be increased.  
				
				IGMP is robust to (Robustness Variable-1) packet losses."
			DEFVAL { 2 }
			::= { sleV2IgmpIfEntry 17 }

		
--  1.3.6.1.4.1.6296.102.12.2.2.4.1.1.1.18
		sleV2IgmpIfJoins OBJECT-TYPE
			SYNTAX Counter32
			MAX-ACCESS read-only
			STATUS current
			DESCRIPTION
				"The number of times a group membership has been added
				on this interface; that is, the number of times an 
				entry for this interface has been added to the Cache Table.
				
				This object gives an indication of the amount of IGMP 
				activity over the lifetime of the row entry."
			::= { sleV2IgmpIfEntry 18 }

		
--  1.3.6.1.4.1.6296.102.12.2.2.4.1.1.1.19
		sleV2IgmpIfGroups OBJECT-TYPE
			SYNTAX Gauge32
			MAX-ACCESS read-only
			STATUS current
			DESCRIPTION
				"The current number of entries for this interface in the 
				RouterCache Table."
			::= { sleV2IgmpIfEntry 19 }

		
--  1.3.6.1.4.1.6296.102.12.2.2.4.1.1.1.20
		sleV2IgmpIfMRouteProxyIfIndex OBJECT-TYPE
			SYNTAX Integer32
			MAX-ACCESS read-only
			STATUS current
			DESCRIPTION
				"This value is the igmp-proxy hostside ifindex to multicast routing."
			::= { sleV2IgmpIfEntry 20 }

		
--  1.3.6.1.4.1.6296.102.12.2.2.4.1.1.1.21
		sleV2IgmpIfMRouteProxyStatus OBJECT-TYPE
			SYNTAX Boolean
			MAX-ACCESS read-only
			STATUS current
			DESCRIPTION
				"The true is Igmp Proxy service Enabled on this interface, the false is not."
			::= { sleV2IgmpIfEntry 21 }

		
--  1.3.6.1.4.1.6296.102.12.2.2.4.1.1.1.22
		sleV2IgmpIfStartupQueryInterval OBJECT-TYPE
			SYNTAX Integer32
			MAX-ACCESS read-only
			STATUS current
			DESCRIPTION
				"Startup Query Interval.
				This value is the interval between General Queries send by a Querier on startup.
				"
			::= { sleV2IgmpIfEntry 22 }

		
--  1.3.6.1.4.1.6296.102.12.2.2.4.1.1.1.23
		sleV2IgmpIfUnsolictedReportInterval OBJECT-TYPE
			SYNTAX Integer32
			MAX-ACCESS read-only
			STATUS current
			DESCRIPTION
				"Unsolicted Report Interval.
				This value is the time between repetitions of a host's initial report of membership in a group."
			::= { sleV2IgmpIfEntry 23 }

		
--  1.3.6.1.4.1.6296.102.12.2.2.4.1.1.1.24
		sleV2IgmpIfLeaves OBJECT-TYPE
			SYNTAX Counter32
			MAX-ACCESS read-only
			STATUS current
			DESCRIPTION
				"The number of times a group membership has been removed on this interface; that is, the number of times an entry for this interface has been removed to the Cache Table "
			::= { sleV2IgmpIfEntry 24 }

		
--  1.3.6.1.4.1.6296.102.12.2.2.4.1.1.1.25
		sleV2IgmpIfLimit OBJECT-TYPE
			SYNTAX Integer32
			MAX-ACCESS read-only
			STATUS current
			DESCRIPTION
				"This value is the tolerance limit of igmp groups in this interface"
			::= { sleV2IgmpIfEntry 25 }

		
--  1.3.6.1.4.1.6296.102.12.2.2.4.1.1.1.26
		sleV2IgmpIfExceptGroup OBJECT-TYPE
			SYNTAX OCTET STRING
			MAX-ACCESS read-only
			STATUS current
			DESCRIPTION
				"The permmited group list over the tolerance limit of igmp groups in this interface "
			::= { sleV2IgmpIfEntry 26 }

		
--  1.3.6.1.4.1.6296.102.12.2.2.4.1.1.1.27
		sleV2IgmpIfVerifySrcIp OBJECT-TYPE
			SYNTAX Boolean
			MAX-ACCESS read-only
			STATUS current
			DESCRIPTION
				"The activie state of Verify-SrcIp"
			::= { sleV2IgmpIfEntry 27 }

		
		sleV2IgmpIfRaOption OBJECT-TYPE
			SYNTAX Boolean
			MAX-ACCESS read-only
			STATUS current
			DESCRIPTION
				"The activie state of RA-Option(default disabled)"
			::= { sleV2IgmpIfEntry 28 }

		
		sleV2IgmpIfStartupQueryCnt OBJECT-TYPE
			SYNTAX Unsigned32 (2..10)
			MAX-ACCESS read-only
			STATUS current
			DESCRIPTION
				"Startup Query Count. 
				This value is the Count between General Queries send by a Querier on startup.(default 2)
				"
			::= { sleV2IgmpIfEntry 29 }

		
		sleV2IgmpIfOfflink OBJECT-TYPE
			SYNTAX Boolean
			MAX-ACCESS read-only
			STATUS current
			DESCRIPTION
				"Use this command to configure off-link for IGMP."
			::= { sleV2IgmpIfEntry 30 }

		
--  IGMP Interface Control
-- 1.3.6.1.4.1.6296.102.12.2.2.4.1.2
		sleV2IgmpIfControl OBJECT IDENTIFIER ::= { sleV2IgmpInterface 2 }

		
--  1.3.6.1.4.1.6296.102.12.2.2.4.1.2.1
		sleV2IgmpIfControlRequest OBJECT-TYPE
			SYNTAX INTEGER
				{
				setIgmpInterfaceActivity(1),
				setIgmpInterfaceProfile(2),
				setIgmpMrouteProxy(3),
				setIgmpProxyService(4),
				clearIgmpStatistics(5),
				setIgmpVerifySrcIp(6)
				}
			MAX-ACCESS read-write
			STATUS current
			DESCRIPTION
				" The request of a user command"
			::= { sleV2IgmpIfControl 1 }

		
--  1.3.6.1.4.1.6296.102.12.2.2.4.1.2.2
		sleV2IgmpIfControlStatus OBJECT-TYPE
			SYNTAX SleControlStatusType
			MAX-ACCESS read-only
			STATUS current
			DESCRIPTION
				" The status of user command"
			::= { sleV2IgmpIfControl 2 }

		
--  1.3.6.1.4.1.6296.102.12.2.2.4.1.2.3
		sleV2IgmpIfControlTimer OBJECT-TYPE
			SYNTAX Gauge32
			MAX-ACCESS read-write
			STATUS current
			DESCRIPTION
				" The maximum time for the manager for a long running user command"
			::= { sleV2IgmpIfControl 3 }

		
--  1.3.6.1.4.1.6296.102.12.2.2.4.1.2.4
		sleV2IgmpIfControlTimeStamp OBJECT-TYPE
			SYNTAX TimeStamp
			MAX-ACCESS read-only
			STATUS current
			DESCRIPTION
				" The time stamp of the last command(end of command)"
			::= { sleV2IgmpIfControl 4 }

		
--  1.3.6.1.4.1.6296.102.12.2.2.4.1.2.5
		sleV2IgmpIfControlReqResult OBJECT-TYPE
			SYNTAX SleControlRequestResultType
			MAX-ACCESS read-only
			STATUS current
			DESCRIPTION
				" The result of the last user command"
			::= { sleV2IgmpIfControl 5 }

		
--  1.3.6.1.4.1.6296.102.12.2.2.4.1.2.6
		sleV2IgmpIfControlIndex OBJECT-TYPE
			SYNTAX INTEGER (1..4094)
			MAX-ACCESS read-write
			STATUS current
			DESCRIPTION
				" Network interface index.
				(= sleNetIfIndex)
				"
			::= { sleV2IgmpIfControl 6 }

		
--  1.3.6.1.4.1.6296.102.12.2.2.4.1.2.7
		sleV2IgmpIfControlActivity OBJECT-TYPE
			SYNTAX Boolean
			MAX-ACCESS read-write
			STATUS current
			DESCRIPTION
				"Network interface index.
				(= sleNetIfIndex)
				"
			::= { sleV2IgmpIfControl 7 }

		
--  1.3.6.1.4.1.6296.102.12.2.2.4.1.2.8
		sleV2IgmpIfControlVersion OBJECT-TYPE
			SYNTAX INTEGER (-1 | 1..3)
			MAX-ACCESS read-write
			STATUS current
			DESCRIPTION
				"CLI : (no) ip igmp version <1-3>
				value(-1) : default"
			::= { sleV2IgmpIfControl 8 }

		
--  1.3.6.1.4.1.6296.102.12.2.2.4.1.2.9
		sleV2IgmpIfControlQueryInterval OBJECT-TYPE
			SYNTAX Integer32 (-1 | 1..18000)
			UNITS "seconds"
			MAX-ACCESS read-write
			STATUS current
			DESCRIPTION
				"CLI : (no) ip igmp query-interval <1-1800>
				value(-1) : (no)"
			::= { sleV2IgmpIfControl 9 }

		
--  1.3.6.1.4.1.6296.102.12.2.2.4.1.2.10
		sleV2IgmpIfControlQuerierTimeOut OBJECT-TYPE
			SYNTAX Integer32 (-1 | 60..300)
			UNITS "seconds"
			MAX-ACCESS read-write
			STATUS current
			DESCRIPTION
				"CLI : (no) ip igmp querier-timeout <60-300>
				value(-1) : (no)"
			DEFVAL { 255 }
			::= { sleV2IgmpIfControl 10 }

		
--  1.3.6.1.4.1.6296.102.12.2.2.4.1.2.11
		sleV2IgmpIfControlMaxResponseTime OBJECT-TYPE
			SYNTAX Integer32 (-1 | 1..240)
			UNITS "seconds"
			MAX-ACCESS read-write
			STATUS current
			DESCRIPTION
				"CLI: (no) ip igmp query-max-response-time <1-240>
				value(-1) : (no)"
			DEFVAL { 10 }
			::= { sleV2IgmpIfControl 11 }

		
--  1.3.6.1.4.1.6296.102.12.2.2.4.1.2.12
		sleV2IgmpIfControlLastMembQueryCount OBJECT-TYPE
			SYNTAX Integer32 (-1 | 2..7)
			MAX-ACCESS read-write
			STATUS current
			DESCRIPTION
				"CLI : (no) ip igmp last-member-query-count <2-7>
				value(-1) : (no)"
			DEFVAL { 2 }
			::= { sleV2IgmpIfControl 12 }

		
--  1.3.6.1.4.1.6296.102.12.2.2.4.1.2.13
		sleV2IgmpIfControlLastMembQueryIntvl OBJECT-TYPE
			SYNTAX Integer32 (-1 | 1000..25500)
			UNITS "milliseconds"
			MAX-ACCESS read-write
			STATUS current
			DESCRIPTION
				"CLI : (no) ip igmp last-member-query-interval <1000-25500>
				value(-1) : (no)"
			DEFVAL { 1000 }
			::= { sleV2IgmpIfControl 13 }

		
--  1.3.6.1.4.1.6296.102.12.2.2.4.1.2.14
		sleV2IgmpIfControlFastLeaveGroupList OBJECT-TYPE
			SYNTAX OCTET STRING
			MAX-ACCESS read-write
			STATUS current
			DESCRIPTION
				"CLI : (no) ip igmp immediate-leave group-list ACCESS-LIST
				value(0) : (no)"
			::= { sleV2IgmpIfControl 14 }

		
--  1.3.6.1.4.1.6296.102.12.2.2.4.1.2.15
		sleV2IgmpIfControlAccessGroup OBJECT-TYPE
			SYNTAX OCTET STRING
			MAX-ACCESS read-write
			STATUS current
			DESCRIPTION
				"CLI : (no) ip igm access-group ACCESS-LIST
				value(0) : (no)"
			::= { sleV2IgmpIfControl 15 }

		
--  1.3.6.1.4.1.6296.102.12.2.2.4.1.2.16
		sleV2IgmpIfControlRobustness OBJECT-TYPE
			SYNTAX Integer32 (-1 | 2..7)
			MAX-ACCESS read-write
			STATUS current
			DESCRIPTION
				"CLI : (no) ip igmp robustiness-variable <2-7>
				value(-1) : (no)"
			DEFVAL { 2 }
			::= { sleV2IgmpIfControl 16 }

		
--  1.3.6.1.4.1.6296.102.12.2.2.4.1.2.17
		sleV2IgmpIfControlMRouteProxyIfIndex OBJECT-TYPE
			SYNTAX INTEGER (-1 | 1..4094)
			MAX-ACCESS read-write
			STATUS current
			DESCRIPTION
				"CLI : (no) ip igmp mroute-proxy IFNAME 
				The value of -1 is (no)"
			::= { sleV2IgmpIfControl 17 }

		
--  1.3.6.1.4.1.6296.102.12.2.2.4.1.2.18
		sleV2IgmpIfControlProxyStatus OBJECT-TYPE
			SYNTAX Boolean
			MAX-ACCESS read-write
			STATUS current
			DESCRIPTION
				"CLI : (no) ip igmp proxy-service"
			::= { sleV2IgmpIfControl 18 }

		
--  1.3.6.1.4.1.6296.102.12.2.2.4.1.2.19
		sleV2IgmpIfControlStartupQueryInterval OBJECT-TYPE
			SYNTAX INTEGER (-1 | 1..18000)
			MAX-ACCESS read-write
			STATUS current
			DESCRIPTION
				"CLI : (no) ip igmp startup-query-interval <1-18000>
				The value of -1 is (no)"
			DEFVAL { 32 }
			::= { sleV2IgmpIfControl 19 }

		
--  1.3.6.1.4.1.6296.102.12.2.2.4.1.2.20
		sleV2IgmpIfControlUnsolictedReportInterval OBJECT-TYPE
			SYNTAX INTEGER (-1 | 1..18000)
			MAX-ACCESS read-write
			STATUS current
			DESCRIPTION
				"CLI : (no) ip igmp unsolicted-report-interval <1-18000>
				The value of -1 is (no)"
			DEFVAL { 10 }
			::= { sleV2IgmpIfControl 20 }

		
--  1.3.6.1.4.1.6296.102.12.2.2.4.1.2.21
		sleV2IgmpIfControlLimit OBJECT-TYPE
			SYNTAX Integer32
			MAX-ACCESS read-write
			STATUS current
			DESCRIPTION
				"This value is the tolerance limit of igmp groups in this interface
				(supported only model 5924N)
				"
			::= { sleV2IgmpIfControl 21 }

		
--  1.3.6.1.4.1.6296.102.12.2.2.4.1.2.22
		sleV2IgmpIfControlExceptGroup OBJECT-TYPE
			SYNTAX OCTET STRING
			MAX-ACCESS read-write
			STATUS current
			DESCRIPTION
				"The permmited group list over the tolerance limit of igmp groups in this interface
				(supported only model 5924N)
				"
			::= { sleV2IgmpIfControl 22 }

		
--  1.3.6.1.4.1.6296.102.12.2.2.4.1.2.23
		sleV2IgmpIfControlVerifySrcIp OBJECT-TYPE
			SYNTAX Boolean
			MAX-ACCESS read-write
			STATUS current
			DESCRIPTION
				"The activie state of Verify-SrcIp"
			::= { sleV2IgmpIfControl 23 }

		
		sleV2IgmpIfControlRaOption OBJECT-TYPE
			SYNTAX Boolean
			MAX-ACCESS read-write
			STATUS current
			DESCRIPTION
				"The activie state of RA-Option(default disabled)"
			::= { sleV2IgmpIfControl 24 }

		
		sleV2IgmpIfControlStartupQueryCnt OBJECT-TYPE
			SYNTAX Unsigned32 (2..10)
			MAX-ACCESS read-write
			STATUS current
			DESCRIPTION
				"Startup Query Count. 
				This value is the Count between General Queries send by a Querier on startup.(default 2)
				"
			::= { sleV2IgmpIfControl 25 }

		
		sleV2IgmpIfControlOfflink OBJECT-TYPE
			SYNTAX Boolean
			MAX-ACCESS read-write
			STATUS current
			DESCRIPTION
				"Use this command to configure off-link for IGMP."
			::= { sleV2IgmpIfControl 26 }

		
--  IGMP Interface Notification
-- 1.3.6.1.4.1.6296.102.12.2.2.4.1.3
		sleV2IgmpIfNotification OBJECT IDENTIFIER ::= { sleV2IgmpInterface 3 }

		
--  1.3.6.1.4.1.6296.102.12.2.2.4.1.3.1
		sleV2IgmpInterfaceActivityChanged NOTIFICATION-TYPE
			OBJECTS { sleV2IgmpIfControlRequest, sleV2IgmpIfControlTimeStamp, sleV2IgmpIfControlReqResult, sleV2IgmpIfActivity }
			STATUS current
			DESCRIPTION 
				" "
			::= { sleV2IgmpIfNotification 1 }

		
--  1.3.6.1.4.1.6296.102.12.2.2.4.1.3.2
		sleV2IgmpInterfaceProfileChanged NOTIFICATION-TYPE
			OBJECTS { sleV2IgmpIfControlTimeStamp, sleV2IgmpIfControlRequest, sleV2IgmpIfExceptGroup, sleV2IgmpIfLimit, sleV2IgmpIfControlRaOption, 
				sleV2IgmpIfControlStartupQueryCnt, sleV2IgmpIfControlReqResult, sleV2IgmpIfVersion, sleV2IgmpIfQueryInterval, sleV2IgmpIfQuerierTimeOut, 
				sleV2IgmpIfMaxResponseTime, sleV2IgmpIfLastMembQueryCount, sleV2IgmpIfLastMembQueryIntvl, sleV2IgmpIfFastLeaveGroupList, sleV2IgmpIfAccessGroup, 
				sleV2IgmpIfRobustness, sleV2IgmpIfStartupQueryInterval, sleV2IgmpIfUnsolictedReportInterval }
			STATUS current
			DESCRIPTION 
				"Description."
			::= { sleV2IgmpIfNotification 2 }

		
--  1.3.6.1.4.1.6296.102.12.2.2.4.1.3.3
		sleV2IgmpInterfaceMrouteChanged NOTIFICATION-TYPE
			OBJECTS { sleV2IgmpIfControlRequest, sleV2IgmpIfControlTimeStamp, sleV2IgmpIfControlReqResult, sleV2IgmpIfMRouteProxyIfIndex }
			STATUS current
			DESCRIPTION 
				"Description."
			::= { sleV2IgmpIfNotification 3 }

		
--  1.3.6.1.4.1.6296.102.12.2.2.4.1.3.4
		sleV2IgmpInterfaceProxyServiceChanged NOTIFICATION-TYPE
			OBJECTS { sleV2IgmpIfControlRequest, sleV2IgmpIfControlTimeStamp, sleV2IgmpIfControlReqResult, sleV2IgmpIfMRouteProxyStatus }
			STATUS current
			DESCRIPTION 
				"Description."
			::= { sleV2IgmpIfNotification 4 }

		
--  1.3.6.1.4.1.6296.102.12.2.2.4.1.3.5
		sleV2IgmpInterfaceStatsCleared NOTIFICATION-TYPE
			OBJECTS { sleV2IgmpIfControlRequest, sleV2IgmpIfControlTimeStamp, sleV2IgmpIfControlReqResult, sleV2IgmpIfJoins, sleV2IgmpIfLeaves
				 }
			STATUS current
			DESCRIPTION 
				"Description."
			::= { sleV2IgmpIfNotification 5 }

		
--  1.3.6.1.4.1.6296.102.12.2.2.4.1.3.6
		sleV2IgmpInterfaceVerifySrcIpChanged NOTIFICATION-TYPE
			OBJECTS { sleV2IgmpIfControlRequest, sleV2IgmpIfControlTimeStamp, sleV2IgmpIfControlReqResult, sleV2IgmpIfControlVerifySrcIp }
			STATUS current
			DESCRIPTION 
				"Description."
			::= { sleV2IgmpIfNotification 6 }

		
--  IGMP Cache (Group)
-- 1.3.6.1.4.1.6296.102.12.2.2.4.2
		sleV2IgmpCache OBJECT IDENTIFIER ::= { sleV2IgmpAgent 2 }

		
--  IGMP Cache Table
-- 1.3.6.1.4.1.6296.102.12.2.2.4.2.1
		sleV2IgmpCacheTable OBJECT-TYPE
			SYNTAX SEQUENCE OF SleV2IgmpCacheEntry
			MAX-ACCESS not-accessible
			STATUS current
			DESCRIPTION
				" IGMP cache table."
			::= { sleV2IgmpCache 1 }

		
--  IGMP Cache Entry
-- 1.3.6.1.4.1.6296.102.12.2.2.4.2.1.1
		sleV2IgmpCacheEntry OBJECT-TYPE
			SYNTAX SleV2IgmpCacheEntry
			MAX-ACCESS not-accessible
			STATUS current
			DESCRIPTION
				"key: sleV2IgmpIfIndex, sleV2IgmpCacheGroup"
			INDEX { sleV2IgmpIfIndex, sleV2IgmpCacheGroup }
			::= { sleV2IgmpCacheTable 1 }

		
		SleV2IgmpCacheEntry ::=
			SEQUENCE { 
				sleV2IgmpCacheGroup
					IpAddress,
				sleV2IgmpCacheLastReporter
					IpAddress,
				sleV2IgmpCacheVersion
					BITS,
				sleV2IgmpCacheSourceFilterMode
					INTEGER,
				sleV2IgmpCacheExcludeModeExpiryTimer
					TimeTicks,
				sleV2IgmpCacheUpTime
					TimeTicks,
				sleV2IgmpCacheExpiryTime
					TimeTicks,
				sleV2IgmpCacheVersion2HostTimer
					TimeTicks,
				sleV2IgmpCacheVersion1HostTimer
					TimeTicks
			 }

--  1.3.6.1.4.1.6296.102.12.2.2.4.2.1.1.1
		sleV2IgmpCacheGroup OBJECT-TYPE
			SYNTAX IpAddress
			MAX-ACCESS read-only
			STATUS current
			DESCRIPTION
				" It is a IP multicast address learned by IGMP."
			::= { sleV2IgmpCacheEntry 1 }

		
--  1.3.6.1.4.1.6296.102.12.2.2.4.2.1.1.2
		sleV2IgmpCacheLastReporter OBJECT-TYPE
			SYNTAX IpAddress
			MAX-ACCESS read-only
			STATUS current
			DESCRIPTION
				"The IP address of the source of the membership report received for this IP Multicast group address on this interface. If no membership report has been received, this object has the value 0.0.0.0."
			::= { sleV2IgmpCacheEntry 2 }

		
--  1.3.6.1.4.1.6296.102.12.2.2.4.2.1.1.3
		sleV2IgmpCacheVersion OBJECT-TYPE
			SYNTAX BITS
				{
				unused(0),
				igmpV1(1),
				igmpV2(2),
				igmpV3(3)
				}
			MAX-ACCESS read-only
			STATUS current
			DESCRIPTION
				"This object indicates the IGMP versions for the group. This is determined by the type of IGMP Membership Reports received by the device."
			::= { sleV2IgmpCacheEntry 3 }

		
--  1.3.6.1.4.1.6296.102.12.2.2.4.2.1.1.4
		sleV2IgmpCacheSourceFilterMode OBJECT-TYPE
			SYNTAX INTEGER
				{
				unknown(0),
				include(1),
				exclude(2)
				}
			MAX-ACCESS read-only
			STATUS current
			DESCRIPTION
				"The current cache state, applicable to IGMPv3 compatible nodes. The value indicates whether the state is INCLUDE or EXCLUDE."
			::= { sleV2IgmpCacheEntry 4 }

		
--  1.3.6.1.4.1.6296.102.12.2.2.4.2.1.1.5
		sleV2IgmpCacheExcludeModeExpiryTimer OBJECT-TYPE
			SYNTAX TimeTicks
			MAX-ACCESS read-only
			STATUS current
			DESCRIPTION
				"This value is applicable only to IGMPv3 compatible routers, and represents the time remaining before the interface EXCLUDE state expires and the interface state transitions to INCLUDE mode. This value can never be greater than sleV2IgmpCacheExpiryTime."
			::= { sleV2IgmpCacheEntry 5 }

		
--  1.3.6.1.4.1.6296.102.12.2.2.4.2.1.1.6
		sleV2IgmpCacheUpTime OBJECT-TYPE
			SYNTAX TimeTicks
			MAX-ACCESS read-only
			STATUS current
			DESCRIPTION
				"The time elapsed since this entry was created."
			::= { sleV2IgmpCacheEntry 6 }

		
--  1.3.6.1.4.1.6296.102.12.2.2.4.2.1.1.7
		sleV2IgmpCacheExpiryTime OBJECT-TYPE
			SYNTAX TimeTicks
			MAX-ACCESS read-only
			STATUS current
			DESCRIPTION
				"This value represents the time remaining before the Group Membership Interval state expires. The value must always be greater than 0."
			::= { sleV2IgmpCacheEntry 7 }

		
--  1.3.6.1.4.1.6296.102.12.2.2.4.2.1.1.8
		sleV2IgmpCacheVersion2HostTimer OBJECT-TYPE
			SYNTAX TimeTicks
			MAX-ACCESS read-only
			STATUS current
			DESCRIPTION
				"The time remaining until the local router will assume that there are no longer any IGMPv2 members on the IP subnet attached to this interface. This entry applies to IGMP hosts. Upon hearing any IGMPv2 Membership Report, this value is reset to the group membership timer. Assuming no IGMPv1 hosts have been detected, the local router does not ignore any IGMPv2 Leave messages for this group that it receives on this interface."
			::= { sleV2IgmpCacheEntry 8 }

		
--  1.3.6.1.4.1.6296.102.12.2.2.4.2.1.1.9
		sleV2IgmpCacheVersion1HostTimer OBJECT-TYPE
			SYNTAX TimeTicks
			MAX-ACCESS read-only
			STATUS current
			DESCRIPTION
				"The time remaining until the local router will assume that there are no longer any IGMP version 1 members on the IP subnet attached to this interface. This entry only applies to IGMPv1 hosts. Upon hearing any IGMPv1 Membership Report, this value is reset to the group membership timer. While this time remaining is non-zero, the local router ignores any IGMPv2 Leave messages (IGMPv2 only) for this group that it receives on this interface."
			::= { sleV2IgmpCacheEntry 9 }

		
--  IGMP Cache (Group)
-- 1.3.6.1.4.1.6296.102.12.2.2.4.3
		sleV2IgmpSource OBJECT IDENTIFIER ::= { sleV2IgmpAgent 3 }

		
--  IGMP Cache Table
-- 1.3.6.1.4.1.6296.102.12.2.2.4.3.1
		sleV2IgmpSourceTable OBJECT-TYPE
			SYNTAX SEQUENCE OF SleV2IgmpSourceEntry
			MAX-ACCESS not-accessible
			STATUS current
			DESCRIPTION
				"IGMP source table."
			::= { sleV2IgmpSource 1 }

		
--  IGMP Cache Entry
-- 1.3.6.1.4.1.6296.102.12.2.2.4.3.1.1
		sleV2IgmpSourceEntry OBJECT-TYPE
			SYNTAX SleV2IgmpSourceEntry
			MAX-ACCESS not-accessible
			STATUS current
			DESCRIPTION
				"key: sleV2IgmpIfIndex, sleV2IgmpCacheGroup, sleV2IgmpSourceAddress"
			INDEX { sleV2IgmpIfIndex, sleV2IgmpCacheGroup, sleV2IgmpSourceAddress }
			::= { sleV2IgmpSourceTable 1 }

		
		SleV2IgmpSourceEntry ::=
			SEQUENCE { 
				sleV2IgmpSourceAddress
					IpAddress,
				sleV2IgmpSourceType
					INTEGER,
				sleV2IgmpSourceUpTime
					TimeTicks,
				sleV2IgmpSourceExpiryTime
					TimeTicks,
				sleV2IgmpSourceSsmMapped
					Boolean
			 }

--  1.3.6.1.4.1.6296.102.12.2.2.4.3.1.1.1
		sleV2IgmpSourceAddress OBJECT-TYPE
			SYNTAX IpAddress
			MAX-ACCESS read-only
			STATUS current
			DESCRIPTION
				"Source of IP multicast group, sleV2IgmpCacheGroup.For (*,G) entry, value is 0.0.0.0"
			::= { sleV2IgmpSourceEntry 1 }

		
--  1.3.6.1.4.1.6296.102.12.2.2.4.3.1.1.2
		sleV2IgmpSourceType OBJECT-TYPE
			SYNTAX INTEGER
				{
				dynamic(1),
				static(2)
				}
			MAX-ACCESS read-only
			STATUS current
			DESCRIPTION
				"It indicates whether the multicast group (S/*,G) is learned by IGMP report messages or administrative maner."
			::= { sleV2IgmpSourceEntry 2 }

		
--  1.3.6.1.4.1.6296.102.12.2.2.4.3.1.1.3
		sleV2IgmpSourceUpTime OBJECT-TYPE
			SYNTAX TimeTicks
			MAX-ACCESS read-only
			STATUS current
			DESCRIPTION
				"The time elapsed since this entry was created. For (*,G) entry, it is equal to sleV2IgmpCacheUpTime"
			::= { sleV2IgmpSourceEntry 3 }

		
--  1.3.6.1.4.1.6296.102.12.2.2.4.3.1.1.4
		sleV2IgmpSourceExpiryTime OBJECT-TYPE
			SYNTAX TimeTicks
			MAX-ACCESS read-only
			STATUS current
			DESCRIPTION
				"This value represents the time remaining before the Group Membership Interval state expires. The value must always be greater than 0. For (*,G) entry, it is equal to sleV2IgmpCacheExpiryTime"
			::= { sleV2IgmpSourceEntry 4 }

		
--  1.3.6.1.4.1.6296.102.12.2.2.4.3.1.1.5
		sleV2IgmpSourceSsmMapped OBJECT-TYPE
			SYNTAX Boolean
			MAX-ACCESS read-only
			STATUS current
			DESCRIPTION
				"The value TRUE indicate that source of multicast group is decided by SSM Mapping Table, and FALSE is not."
			::= { sleV2IgmpSourceEntry 5 }

		
--  IGMP Cache Control
-- 1.3.6.1.4.1.6296.102.12.2.2.4.3.2
		sleV2IgmpSourceControl OBJECT IDENTIFIER ::= { sleV2IgmpSource 2 }

		
--   Not supported.
-- 
-- 1.3.6.1.4.1.6296.102.12.2.2.4.3.2.1
		sleV2IgmpSourceControlRequest OBJECT-TYPE
			SYNTAX INTEGER
				{
				createIgmpSourceStaticEntry(1),
				destroyIgmpSourceStaticEntry(2)
				}
			MAX-ACCESS read-write
			STATUS current
			DESCRIPTION
				" The request of a user command"
			::= { sleV2IgmpSourceControl 1 }

		
--  1.3.6.1.4.1.6296.102.12.2.2.4.3.2.2
		sleV2IgmpSourceControlStatus OBJECT-TYPE
			SYNTAX SleControlStatusType
			MAX-ACCESS read-only
			STATUS current
			DESCRIPTION
				"The status of user command"
			::= { sleV2IgmpSourceControl 2 }

		
--  1.3.6.1.4.1.6296.102.12.2.2.4.3.2.3
		sleV2IgmpSourceControlTimer OBJECT-TYPE
			SYNTAX Gauge32
			MAX-ACCESS read-write
			STATUS current
			DESCRIPTION
				"The maximum time for the manager for a long running user comman"
			::= { sleV2IgmpSourceControl 3 }

		
--  1.3.6.1.4.1.6296.102.12.2.2.4.3.2.4
		sleV2IgmpSourceControlTimeStamp OBJECT-TYPE
			SYNTAX TimeStamp
			MAX-ACCESS read-only
			STATUS current
			DESCRIPTION
				" The time stamp of the last command(end of command)"
			::= { sleV2IgmpSourceControl 4 }

		
--  1.3.6.1.4.1.6296.102.12.2.2.4.3.2.5
		sleV2IgmpSourceControlReqResult OBJECT-TYPE
			SYNTAX SleControlRequestResultType
			MAX-ACCESS read-only
			STATUS current
			DESCRIPTION
				" The result of the last user command"
			::= { sleV2IgmpSourceControl 5 }

		
--  1.3.6.1.4.1.6296.102.12.2.2.4.3.2.6
		sleV2IgmpSourceControlIfIndex OBJECT-TYPE
			SYNTAX Integer32
			MAX-ACCESS read-write
			STATUS current
			DESCRIPTION
				"interface index."
			::= { sleV2IgmpSourceControl 6 }

		
--  1.3.6.1.4.1.6296.102.12.2.2.4.3.2.7
		sleV2IgmpSourceControlGroup OBJECT-TYPE
			SYNTAX IpAddress
			MAX-ACCESS read-write
			STATUS current
			DESCRIPTION
				" The group IP address"
			::= { sleV2IgmpSourceControl 7 }

		
--  1.3.6.1.4.1.6296.102.12.2.2.4.3.2.8
		sleV2IgmpSourceControlAddress OBJECT-TYPE
			SYNTAX IpAddress
			MAX-ACCESS read-write
			STATUS current
			DESCRIPTION
				" The source IP address"
			::= { sleV2IgmpSourceControl 8 }

		
--  IGMP Cache Notification
-- 1.3.6.1.4.1.6296.102.12.2.2.4.3.3
		sleV2IgmpSourceNotification OBJECT IDENTIFIER ::= { sleV2IgmpSource 3 }

		
--  1.3.6.1.4.1.6296.102.12.2.2.4.3.3.1
		sleV2IgmpSourceCreated NOTIFICATION-TYPE
			OBJECTS { sleV2IgmpSourceControlRequest, sleV2IgmpSourceControlReqResult, sleV2IgmpSourceControlTimeStamp, sleV2IgmpSourceType }
			STATUS current
			DESCRIPTION 
				"In IGMPv3, Adding static (S,G) entry is imply that SourceFilterMode is 'allow'."
			::= { sleV2IgmpSourceNotification 1 }

		
--  1.3.6.1.4.1.6296.102.12.2.2.4.3.3.2
		sleV2IgmpSourceDestroyed NOTIFICATION-TYPE
			OBJECTS { sleV2IgmpSourceControlRequest, sleV2IgmpSourceControlReqResult, sleV2IgmpSourceControlTimeStamp, sleV2IgmpSourceType }
			STATUS current
			DESCRIPTION 
				"In IGMPv3, Removing static (S,G) entry is imply that SourceFilterMode is 'block'."
			::= { sleV2IgmpSourceNotification 2 }

		
--  1.3.6.1.4.1.6296.102.12.2.2.4.4
		sleV2IgmpGroupState OBJECT IDENTIFIER ::= { sleV2IgmpAgent 4 }

		
--  1.3.6.1.4.1.6296.102.12.2.2.4.4.1
		sleV2IgmpGRunningTable OBJECT-TYPE
			SYNTAX SEQUENCE OF SleV2IgmpGRunningEntry
			MAX-ACCESS not-accessible
			STATUS current
			DESCRIPTION
				"IGMP group running table."
			::= { sleV2IgmpGroupState 1 }

		
--  1.3.6.1.4.1.6296.102.12.2.2.4.4.1.1
		sleV2IgmpGRunningEntry OBJECT-TYPE
			SYNTAX SleV2IgmpGRunningEntry
			MAX-ACCESS not-accessible
			STATUS current
			DESCRIPTION
				"key: sleV2IgmpGRunningGroupAddr"
			INDEX { sleV2IgmpGRunningGroupAddr }
			::= { sleV2IgmpGRunningTable 1 }

		
		SleV2IgmpGRunningEntry ::=
			SEQUENCE { 
				sleV2IgmpGRunningGroupAddr
					IpAddress,
				sleV2IgmpGRunningTotalUptime
					OCTET STRING,
				sleV2IgmpGRunningLastJoined
					OCTET STRING,
				sleV2IgmpGRunningLastLeaved
					OCTET STRING,
				sleV2IgmpGRunningState
					INTEGER
			 }

--  1.3.6.1.4.1.6296.102.12.2.2.4.4.1.1.1
		sleV2IgmpGRunningGroupAddr OBJECT-TYPE
			SYNTAX IpAddress
			MAX-ACCESS read-only
			STATUS current
			DESCRIPTION
				"IP multicast address learned by IGMP"
			::= { sleV2IgmpGRunningEntry 1 }

		
--  1.3.6.1.4.1.6296.102.12.2.2.4.4.1.1.2
		sleV2IgmpGRunningTotalUptime OBJECT-TYPE
			SYNTAX OCTET STRING
			MAX-ACCESS read-only
			STATUS current
			DESCRIPTION
				"The total time of multicast service."
			::= { sleV2IgmpGRunningEntry 2 }

		
--  1.3.6.1.4.1.6296.102.12.2.2.4.4.1.1.3
		sleV2IgmpGRunningLastJoined OBJECT-TYPE
			SYNTAX OCTET STRING
			MAX-ACCESS read-only
			STATUS current
			DESCRIPTION
				"The time have elapsed since the receiving last join message "
			::= { sleV2IgmpGRunningEntry 3 }

		
--  1.3.6.1.4.1.6296.102.12.2.2.4.4.1.1.4
		sleV2IgmpGRunningLastLeaved OBJECT-TYPE
			SYNTAX OCTET STRING
			MAX-ACCESS read-only
			STATUS current
			DESCRIPTION
				"The time have elapsed since the receiving last leave message."
			::= { sleV2IgmpGRunningEntry 4 }

		
--  1.3.6.1.4.1.6296.102.12.2.2.4.4.1.1.5
		sleV2IgmpGRunningState OBJECT-TYPE
			SYNTAX INTEGER
				{
				joined(1),
				leaved(2)
				}
			MAX-ACCESS read-only
			STATUS current
			DESCRIPTION
				"The state of multicast group."
			::= { sleV2IgmpGRunningEntry 5 }

		
--  1.3.6.1.4.1.6296.102.12.2.2.4.4.2
		sleV2IgmpSRunningTable OBJECT-TYPE
			SYNTAX SEQUENCE OF SleV2IgmpSRunningEntry
			MAX-ACCESS not-accessible
			STATUS current
			DESCRIPTION
				"IGMP source running table."
			::= { sleV2IgmpGroupState 2 }

		
--  1.3.6.1.4.1.6296.102.12.2.2.4.4.2.1
		sleV2IgmpSRunningEntry OBJECT-TYPE
			SYNTAX SleV2IgmpSRunningEntry
			MAX-ACCESS not-accessible
			STATUS current
			DESCRIPTION
				"key: sleV2IgmpSRunningGroupAddr, sleV2IgmpSRunningSourceAddr"
			INDEX { sleV2IgmpSRunningGroupAddr, sleV2IgmpSRunningSourceAddr }
			::= { sleV2IgmpSRunningTable 1 }

		
		SleV2IgmpSRunningEntry ::=
			SEQUENCE { 
				sleV2IgmpSRunningGroupAddr
					IpAddress,
				sleV2IgmpSRunningSourceAddr
					IpAddress,
				sleV2IgmpSRunningTotalUptime
					OCTET STRING,
				sleV2IgmpSRunningLastJoined
					OCTET STRING,
				sleV2IgmpSRunningLastLeaved
					OCTET STRING,
				sleV2IgmpSRunningState
					INTEGER
			 }

--  1.3.6.1.4.1.6296.102.12.2.2.4.4.2.1.1
		sleV2IgmpSRunningGroupAddr OBJECT-TYPE
			SYNTAX IpAddress
			MAX-ACCESS read-only
			STATUS current
			DESCRIPTION
				"IP multicast address learned by IGMP."
			::= { sleV2IgmpSRunningEntry 1 }

		
--  1.3.6.1.4.1.6296.102.12.2.2.4.4.2.1.2
		sleV2IgmpSRunningSourceAddr OBJECT-TYPE
			SYNTAX IpAddress
			MAX-ACCESS read-only
			STATUS current
			DESCRIPTION
				"The source ip adderess of multicast server."
			::= { sleV2IgmpSRunningEntry 2 }

		
--  1.3.6.1.4.1.6296.102.12.2.2.4.4.2.1.3
		sleV2IgmpSRunningTotalUptime OBJECT-TYPE
			SYNTAX OCTET STRING
			MAX-ACCESS read-only
			STATUS current
			DESCRIPTION
				"The total time of multicast service."
			::= { sleV2IgmpSRunningEntry 3 }

		
--  1.3.6.1.4.1.6296.102.12.2.2.4.4.2.1.4
		sleV2IgmpSRunningLastJoined OBJECT-TYPE
			SYNTAX OCTET STRING
			MAX-ACCESS read-only
			STATUS current
			DESCRIPTION
				"The time have elapsed since the receiving last join message "
			::= { sleV2IgmpSRunningEntry 4 }

		
--  1.3.6.1.4.1.6296.102.12.2.2.4.4.2.1.5
		sleV2IgmpSRunningLastLeaved OBJECT-TYPE
			SYNTAX OCTET STRING
			MAX-ACCESS read-only
			STATUS current
			DESCRIPTION
				"The time have elapsed since the receiving last leave message."
			::= { sleV2IgmpSRunningEntry 5 }

		
--  1.3.6.1.4.1.6296.102.12.2.2.4.4.2.1.6
		sleV2IgmpSRunningState OBJECT-TYPE
			SYNTAX INTEGER
				{
				joined(1),
				leaved(2)
				}
			MAX-ACCESS read-only
			STATUS current
			DESCRIPTION
				"The state of multicast group."
			::= { sleV2IgmpSRunningEntry 6 }

		
--  1.3.6.1.4.1.6296.102.12.2.2.4.4.3
		sleV2IgmpGStateControl OBJECT IDENTIFIER ::= { sleV2IgmpGroupState 3 }

		
--  1.3.6.1.4.1.6296.102.12.2.2.4.4.3.1
		sleV2IgmpGStateControlRequest OBJECT-TYPE
			SYNTAX INTEGER
				{
				clearGroupEntry(1),
				clearSessionEntry(2),
				clearAllEntry(3)
				}
			MAX-ACCESS read-write
			STATUS current
			DESCRIPTION
				"The request of a user command"
			::= { sleV2IgmpGStateControl 1 }

		
--  1.3.6.1.4.1.6296.102.12.2.2.4.4.3.2
		sleV2IgmpGStateControlStatus OBJECT-TYPE
			SYNTAX SleControlStatusType
			MAX-ACCESS read-only
			STATUS current
			DESCRIPTION
				"The status of user command"
			::= { sleV2IgmpGStateControl 2 }

		
--  1.3.6.1.4.1.6296.102.12.2.2.4.4.3.3
		sleV2IgmpGStateControlTimer OBJECT-TYPE
			SYNTAX Gauge32
			MAX-ACCESS read-write
			STATUS current
			DESCRIPTION
				"The maximum time for the manager for a long running user command"
			::= { sleV2IgmpGStateControl 3 }

		
--  1.3.6.1.4.1.6296.102.12.2.2.4.4.3.4
		sleV2IgmpGStateControlTimeStamp OBJECT-TYPE
			SYNTAX TimeStamp
			MAX-ACCESS read-only
			STATUS current
			DESCRIPTION
				"The time stamp of the last command(end of command)"
			::= { sleV2IgmpGStateControl 4 }

		
--  1.3.6.1.4.1.6296.102.12.2.2.4.4.3.5
		sleV2IgmpGStateControlRequestResult OBJECT-TYPE
			SYNTAX SleControlRequestResultType
			MAX-ACCESS read-only
			STATUS current
			DESCRIPTION
				"The result of the last user command"
			::= { sleV2IgmpGStateControl 5 }

		
--  1.3.6.1.4.1.6296.102.12.2.2.4.4.3.6
		sleV2IgmpGStateControlGroupAddr OBJECT-TYPE
			SYNTAX IpAddress
			MAX-ACCESS read-write
			STATUS current
			DESCRIPTION
				"IP multicast address learned by IGMP."
			::= { sleV2IgmpGStateControl 6 }

		
--  1.3.6.1.4.1.6296.102.12.2.2.4.4.3.7
		sleV2IgmpGStateControlSourceAddr OBJECT-TYPE
			SYNTAX IpAddress
			MAX-ACCESS read-write
			STATUS current
			DESCRIPTION
				"IP multicast address learned by IGMP."
			::= { sleV2IgmpGStateControl 7 }

		
--  1.3.6.1.4.1.6296.102.12.2.2.4.4.4
		sleV2IgmpGStateNotification OBJECT IDENTIFIER ::= { sleV2IgmpGroupState 4 }

		
--  1.3.6.1.4.1.6296.102.12.2.2.4.4.4.1
		sleV2IgmpGStateGroupCleared NOTIFICATION-TYPE
			OBJECTS { sleV2IgmpGStateControlRequest, sleV2IgmpGStateControlTimeStamp, sleV2IgmpGStateControlRequestResult, sleV2IgmpGStateControlGroupAddr }
			STATUS current
			DESCRIPTION 
				"Description."
			::= { sleV2IgmpGStateNotification 1 }

		
--  1.3.6.1.4.1.6296.102.12.2.2.4.4.4.2
		sleV2IgmpGStateSessionCleared NOTIFICATION-TYPE
			OBJECTS { sleV2IgmpGStateControlRequest, sleV2IgmpGStateControlTimeStamp, sleV2IgmpGStateControlRequestResult, sleV2IgmpGStateControlGroupAddr, sleV2IgmpGStateControlSourceAddr
				 }
			STATUS current
			DESCRIPTION 
				"Description."
			::= { sleV2IgmpGStateNotification 2 }

		
--  1.3.6.1.4.1.6296.102.12.2.2.4.4.4.3
		sleV2IgmpGStateAllCleared NOTIFICATION-TYPE
			OBJECTS { sleV2IgmpGStateControlRequest, sleV2IgmpGStateControlTimeStamp, sleV2IgmpGStateControlRequestResult }
			STATUS current
			DESCRIPTION 
				"Description."
			::= { sleV2IgmpGStateNotification 3 }

		
		sleV2IgmpStaticGroup OBJECT IDENTIFIER ::= { sleV2IgmpAgent 5 }

		
		sleV2IgmpStaticGroupTable OBJECT-TYPE
			SYNTAX SEQUENCE OF SleV2IgmpStaticGroupEntry
			MAX-ACCESS not-accessible
			STATUS current
			DESCRIPTION
				"Description."
			::= { sleV2IgmpStaticGroup 1 }

		
		sleV2IgmpStaticGroupEntry OBJECT-TYPE
			SYNTAX SleV2IgmpStaticGroupEntry
			MAX-ACCESS not-accessible
			STATUS current
			DESCRIPTION
				"Description."
			INDEX { sleV2IgmpIfIndex, sleV2IgmpStaticGrpGroup }
			::= { sleV2IgmpStaticGroupTable 1 }

		
		SleV2IgmpStaticGroupEntry ::=
			SEQUENCE { 
				sleV2IgmpStaticGrpGroup
					IpAddress
			 }

		sleV2IgmpStaticGrpGroup OBJECT-TYPE
			SYNTAX IpAddress
			MAX-ACCESS read-only
			STATUS current
			DESCRIPTION
				"The ipv4 group address for static group"
			::= { sleV2IgmpStaticGroupEntry 1 }

		
		sleV2IgmpStaticSourceTable OBJECT-TYPE
			SYNTAX SEQUENCE OF SleV2IgmpStaticSourceEntry
			MAX-ACCESS not-accessible
			STATUS current
			DESCRIPTION
				"Description."
			::= { sleV2IgmpStaticGroup 2 }

		
		sleV2IgmpStaticSourceEntry OBJECT-TYPE
			SYNTAX SleV2IgmpStaticSourceEntry
			MAX-ACCESS not-accessible
			STATUS current
			DESCRIPTION
				"Description."
			INDEX { sleV2IgmpIfIndex, sleV2IgmpStaticGrpGroup, sleV2IgmpStaticGrpSource }
			::= { sleV2IgmpStaticSourceTable 1 }

		
		SleV2IgmpStaticSourceEntry ::=
			SEQUENCE { 
				sleV2IgmpStaticGrpSource
					IpAddress
			 }

		sleV2IgmpStaticGrpSource OBJECT-TYPE
			SYNTAX IpAddress
			MAX-ACCESS read-only
			STATUS current
			DESCRIPTION
				"Description."
			::= { sleV2IgmpStaticSourceEntry 1 }

		
		sleV2IgmpStaticSsmTable OBJECT-TYPE
			SYNTAX SEQUENCE OF SleV2IgmpStaticSsmEntry
			MAX-ACCESS not-accessible
			STATUS current
			DESCRIPTION
				"Description."
			::= { sleV2IgmpStaticGroup 3 }

		
		sleV2IgmpStaticSsmEntry OBJECT-TYPE
			SYNTAX SleV2IgmpStaticSsmEntry
			MAX-ACCESS not-accessible
			STATUS current
			DESCRIPTION
				"Description."
			INDEX { sleV2IgmpIfIndex, sleV2IgmpStaticGrpGroup }
			::= { sleV2IgmpStaticSsmTable 1 }

		
		SleV2IgmpStaticSsmEntry ::=
			SEQUENCE { 
				sleV2IgmpStaticGrpSsm
					Boolean
			 }

		sleV2IgmpStaticGrpSsm OBJECT-TYPE
			SYNTAX Boolean
			MAX-ACCESS read-only
			STATUS current
			DESCRIPTION
				"Description."
			::= { sleV2IgmpStaticSsmEntry 1 }

		
		sleV2IgmpIStaticGroupControl OBJECT IDENTIFIER ::= { sleV2IgmpStaticGroup 4 }

		
		sleV2IgmpStaticGrpControlRequest OBJECT-TYPE
			SYNTAX INTEGER
				{
				createIgmpIfStaticGroup(1),
				destroyIgmpIfStaticGroup(2),
				createIgmpIfStaticSource(3),
				destroyIgmpIfStaticSource(4),
				createIgmpIfStaticSsm(5),
				destroyIgmpIfStaticSsm(6)
				}
			MAX-ACCESS read-write
			STATUS current
			DESCRIPTION
				"Description."
			::= { sleV2IgmpIStaticGroupControl 1 }

		
		sleV2IgmpStaticGrpControlStatus OBJECT-TYPE
			SYNTAX SleControlStatusType
			MAX-ACCESS read-write
			STATUS current
			DESCRIPTION
				"Description."
			::= { sleV2IgmpIStaticGroupControl 2 }

		
		sleV2IgmpStaticGrpControlTimer OBJECT-TYPE
			SYNTAX Gauge32
			MAX-ACCESS read-write
			STATUS current
			DESCRIPTION
				"Description."
			::= { sleV2IgmpIStaticGroupControl 3 }

		
		sleV2IgmpIStaticGrpControlTimeStamp OBJECT-TYPE
			SYNTAX TimeStamp
			MAX-ACCESS read-write
			STATUS current
			DESCRIPTION
				"Description."
			::= { sleV2IgmpIStaticGroupControl 4 }

		
		sleV2IgmpStaticGrpControlReqResult OBJECT-TYPE
			SYNTAX SleControlRequestResultType
			MAX-ACCESS read-write
			STATUS current
			DESCRIPTION
				"Description."
			::= { sleV2IgmpIStaticGroupControl 5 }

		
		sleV2IgmpStaticGrpControlIndex OBJECT-TYPE
			SYNTAX Integer32
			MAX-ACCESS read-write
			STATUS current
			DESCRIPTION
				"Description."
			::= { sleV2IgmpIStaticGroupControl 6 }

		
		sleV2IgmpStaticGrpControlGroup OBJECT-TYPE
			SYNTAX IpAddress
			MAX-ACCESS read-write
			STATUS current
			DESCRIPTION
				"Description."
			::= { sleV2IgmpIStaticGroupControl 7 }

		
		sleV2IgmpStaticGrpControlSource OBJECT-TYPE
			SYNTAX IpAddress
			MAX-ACCESS read-write
			STATUS current
			DESCRIPTION
				"Description."
			::= { sleV2IgmpIStaticGroupControl 8 }

		
		sleV2IgmpStaticGrpControlSsm OBJECT-TYPE
			SYNTAX Boolean
			MAX-ACCESS read-write
			STATUS current
			DESCRIPTION
				"Description."
			::= { sleV2IgmpIStaticGroupControl 9 }

		
--  IGMP Snooping
-- 1.3.6.1.4.1.6296.102.12.2.2.5
		sleV2IgmpSnooping OBJECT IDENTIFIER ::= { sleV2Igmp 5 }

		
--  IGMP Snooping VLAN
-- 1.3.6.1.4.1.6296.102.12.2.2.5.1
		sleV2IgsVlan OBJECT IDENTIFIER ::= { sleV2IgmpSnooping 1 }

		
--  IGMP Snooping VLAN Table
-- 1.3.6.1.4.1.6296.102.12.2.2.5.1.1
		sleV2IgsVlanTable OBJECT-TYPE
			SYNTAX SEQUENCE OF SleV2IgsVlanEntry
			MAX-ACCESS not-accessible
			STATUS current
			DESCRIPTION
				" IGS vlan table."
			::= { sleV2IgsVlan 1 }

		
--  IGMP Snooping VLAN Entry
-- 1.3.6.1.4.1.6296.102.12.2.2.5.1.1.1
		sleV2IgsVlanEntry OBJECT-TYPE
			SYNTAX SleV2IgsVlanEntry
			MAX-ACCESS not-accessible
			STATUS current
			DESCRIPTION
				"Index field will be added by Na, Hojin
				key: sleV2IgsVlanIndex"
			INDEX { sleV2IgsVlanIndex }
			::= { sleV2IgsVlanTable 1 }

		
		SleV2IgsVlanEntry ::=
			SEQUENCE { 
				sleV2IgsVlanIndex
					INTEGER,
				sleV2IgsVlanActivity
					Boolean,
				sleV2IgsVlanVersion
					INTEGER,
				sleV2IgsVlanVersionMode
					INTEGER,
				sleV2IgsVlanFastLeave
					Boolean,
				sleV2IgsVlanFastBlock
					Boolean,
				sleV2IgsVlanMRtLearningMode
					INTEGER,
				sleV2IgsVlanMRtDynamicPortMap
					OCTET STRING,
				sleV2IgsVlanMRtStaticPortMap
					OCTET STRING,
				sleV2IgsVlanReportSuppression
					Boolean,
				sleV2IgsVlanQuerierActivity
					Boolean,
				sleV2IgsVlanQueryInterval
					Unsigned32,
				sleV2IgsVlanRobustness
					Unsigned32,
				sleV2IgsVlanMaxResponseTime
					Unsigned32,
				sleV2IgsVlanQuerierTimeOut
					Unsigned32,
				sleV2IgsVlanLastMembQueryIntvl
					Unsigned32,
				sleV2IgsVlanLastMembQueryCount
					Unsigned32,
				sleV2IgsVlanQuerierState
					INTEGER,
				sleV2IgsVlanQuerierVersion
					INTEGER,
				sleV2IgsVlanQuerierAddress
					IpAddress,
				sleV2IgsVlanQuerierPortIndex
					INTEGER,
				sleV2IgsVlanQuerierUptime
					TimeTicks,
				sleV2IgsVlanQuerierExpireTime
					TimeTicks,
				sleV2IgsVlanTcnFloodActivity
					Boolean,
				sleV2IgsVlanExplicitTracking
					Boolean,
				sleV2IgsVlanTxGeneralQueries
					Counter32,
				sleV2IgsVlanTxSpecialQueries
					Counter32,
				sleV2IgsVlanTxReportMessages
					Counter32,
				sleV2IgsVlanTxLeaveMessages
					Counter32,
				sleV2IgsVlanRxGeneralQueries
					Counter32,
				sleV2IgsVlanRxSpecialQueries
					Counter32,
				sleV2IgsVlanRxReportMessages
					Counter32,
				sleV2IgsVlanRxLeaveMessages
					Counter32,
				sleV2IgsVlanRxValidMessages
					Counter32,
				sleV2IgsVlanRxWrongMessages
					Counter32
			 }

--  1.3.6.1.4.1.6296.102.12.2.2.5.1.1.1.1
		sleV2IgsVlanIndex OBJECT-TYPE
			SYNTAX INTEGER (1..4094)
			MAX-ACCESS read-only
			STATUS current
			DESCRIPTION
				"This object indicates the VLAN in which IGMP Snooping is configured. (= sleNetIfIndex)"
			::= { sleV2IgsVlanEntry 1 }

		
--  1.3.6.1.4.1.6296.102.12.2.2.5.1.1.1.2
		sleV2IgsVlanActivity OBJECT-TYPE
			SYNTAX Boolean
			MAX-ACCESS read-only
			STATUS current
			DESCRIPTION
				"When this object is set to 'true' IGMP Snooping is enabled on this VLAN else disabled."
			::= { sleV2IgsVlanEntry 2 }

		
--  1.3.6.1.4.1.6296.102.12.2.2.5.1.1.1.3
		sleV2IgsVlanVersion OBJECT-TYPE
			SYNTAX INTEGER
				{
				igmpV1(1),
				igmpV2(2),
				igmpV3(3)
				}
			MAX-ACCESS read-only
			STATUS current
			DESCRIPTION
				"This object indicate IGMP version on the VLAN that IGMP Snooping is enabled."
			::= { sleV2IgsVlanEntry 3 }

		
--  1.3.6.1.4.1.6296.102.12.2.2.5.1.1.1.4
		sleV2IgsVlanVersionMode OBJECT-TYPE
			SYNTAX INTEGER
				{
				static(0),
				dynamic(1)
				}
			MAX-ACCESS read-write
			STATUS current
			DESCRIPTION
				"IGMP Snooping Version Mode on the VLAN."
			::= { sleV2IgsVlanEntry 4 }

		
--  1.3.6.1.4.1.6296.102.12.2.2.5.1.1.1.5
		sleV2IgsVlanFastLeave OBJECT-TYPE
			SYNTAX Boolean
			MAX-ACCESS read-only
			STATUS current
			DESCRIPTION
				"This object specifies whether Fast-Leave mechanism (also known as Immediate-Leave) is to be performed by IGMP Snooping or not. When enabled, IGMP Snooping will remove the interface from the group mentioned in the IGMP Leave message received on that interface without waiting for the IGMP Group-Specific Query to timeout to determine whether there are any more hosts on that interface for that group."
			::= { sleV2IgsVlanEntry 5 }

		
--  1.3.6.1.4.1.6296.102.12.2.2.5.1.1.1.6
		sleV2IgsVlanFastBlock OBJECT-TYPE
			SYNTAX Boolean
			MAX-ACCESS read-only
			STATUS current
			DESCRIPTION
				"The object indicates whether Fast-Block mechanism has been enabled for the VLAN. This object only has effect if the value of sleV2IgsVlanVersion is 3."
			::= { sleV2IgsVlanEntry 6 }

		
--  1.3.6.1.4.1.6296.102.12.2.2.5.1.1.1.7
		sleV2IgsVlanMRtLearningMode OBJECT-TYPE
			SYNTAX INTEGER
				{
				none(0),
				pim(1)
				}
			MAX-ACCESS read-only
			STATUS current
			DESCRIPTION
				"This object specifies the multicast router port learning method for IGMP Snooping as described below:none(0) : don't learning, Only use static router ports.pim(1) : Protocol Independent Multicast."
			::= { sleV2IgsVlanEntry 7 }

		
--  1.3.6.1.4.1.6296.102.12.2.2.5.1.1.1.8
		sleV2IgsVlanMRtDynamicPortMap OBJECT-TYPE
			SYNTAX OCTET STRING (SIZE (0..64))
			MAX-ACCESS read-only
			STATUS current
			DESCRIPTION
				"Multicast router ports learned by dynamic method (ex: PIM when MRouterLearningMode is 'pim'"
			::= { sleV2IgsVlanEntry 8 }

		
--  1.3.6.1.4.1.6296.102.12.2.2.5.1.1.1.9
		sleV2IgsVlanMRtStaticPortMap OBJECT-TYPE
			SYNTAX OCTET STRING (SIZE (0..64))
			MAX-ACCESS read-only
			STATUS current
			DESCRIPTION
				"Multicast router ports setted by administrative maner. Bit 0 is CPU port."
			::= { sleV2IgsVlanEntry 9 }

		
--  1.3.6.1.4.1.6296.102.12.2.2.5.1.1.1.10
		sleV2IgsVlanReportSuppression OBJECT-TYPE
			SYNTAX Boolean
			MAX-ACCESS read-only
			STATUS current
			DESCRIPTION
				"It's TRUE, IGMP Snooping will suppress duplicate IGMP Reports on the VLAN. FALSE, all IGMP Reports are forwarded to multicast routers on the VLAN. Alias of this is IGMP Snooping Proxy."
			::= { sleV2IgsVlanEntry 10 }

		
--  1.3.6.1.4.1.6296.102.12.2.2.5.1.1.1.11
		sleV2IgsVlanQuerierActivity OBJECT-TYPE
			SYNTAX Boolean
			MAX-ACCESS read-only
			STATUS current
			DESCRIPTION
				"The object indicates whether the device will participate in the IGMP Querier election in a VLAN. If the object is set to 'true', the device will participate to an election process to be a Querier. If this is set to 'false' while the device is acting as the Querier in a VLAN, a new election will be activated to choose a different Querier."
			::= { sleV2IgsVlanEntry 11 }

		
--  1.3.6.1.4.1.6296.102.12.2.2.5.1.1.1.12
		sleV2IgsVlanQueryInterval OBJECT-TYPE
			SYNTAX Unsigned32 (0..31744)
			MAX-ACCESS read-only
			STATUS current
			DESCRIPTION
				"The frequency at which IGMP packets are transmitted on this interface."
			::= { sleV2IgsVlanEntry 12 }

		
--  1.3.6.1.4.1.6296.102.12.2.2.5.1.1.1.13
		sleV2IgsVlanRobustness OBJECT-TYPE
			SYNTAX Unsigned32 (1..255)
			MAX-ACCESS read-only
			STATUS current
			DESCRIPTION
				"The Robustness Variable allows tuning for the expected packet loss on a subnet. If a subnet is expected to be lossy, the Robustness Variable may be increased. IGMP is robust to (Robustness Variable-1) packet losses."
			::= { sleV2IgsVlanEntry 13 }

		
--  1.3.6.1.4.1.6296.102.12.2.2.5.1.1.1.14
		sleV2IgsVlanMaxResponseTime OBJECT-TYPE
			SYNTAX Unsigned32 (0..31744)
			MAX-ACCESS read-only
			STATUS current
			DESCRIPTION
				"The maximum query response time advertised in queries on this interface."
			::= { sleV2IgsVlanEntry 14 }

		
--  1.3.6.1.4.1.6296.102.12.2.2.5.1.1.1.15
		sleV2IgsVlanQuerierTimeOut OBJECT-TYPE
			SYNTAX Unsigned32 (0..31744)
			MAX-ACCESS read-only
			STATUS current
			DESCRIPTION
				"Other Querier Present Interval. Default value is (QueryInterval * Robustness) + (MaxResponseTime / 2)"
			::= { sleV2IgsVlanEntry 15 }

		
--  1.3.6.1.4.1.6296.102.12.2.2.5.1.1.1.16
		sleV2IgsVlanLastMembQueryIntvl OBJECT-TYPE
			SYNTAX Unsigned32 (0..31744)
			MAX-ACCESS read-only
			STATUS current
			DESCRIPTION
				"The Last Member Query Interval is the Max Response Time inserted into Group-Specific Queries sent in response to Leave Group messages, and is also the amount of time Between Group-Specific Query messages. This value may be tuned to modify the leave latency of the network. A reduced value results in reduced time to detect the loss of the last member of a group. The value of this object is irrelevant if mgmdRouterInterfaceVersion is 1"
			::= { sleV2IgsVlanEntry 16 }

		
--  1.3.6.1.4.1.6296.102.12.2.2.5.1.1.1.17
		sleV2IgsVlanLastMembQueryCount OBJECT-TYPE
			SYNTAX Unsigned32 (1..255)
			MAX-ACCESS read-only
			STATUS current
			DESCRIPTION
				"Represents the number of Group-specific and Group-and-Source-specific queries sent by the router before it assumes there are no local members."
			::= { sleV2IgsVlanEntry 17 }

		
--  1.3.6.1.4.1.6296.102.12.2.2.5.1.1.1.18
		sleV2IgsVlanQuerierState OBJECT-TYPE
			SYNTAX INTEGER
				{
				disabled(1),
				electing(2),
				querier(3),
				candidate(4),
				inactive(5)
				}
			MAX-ACCESS read-only
			STATUS current
			DESCRIPTION
				"The object indicates the current state of the device as an IGMP Querier in a VLAN.disabled(1) : Querier function is disabled for this device in this VLAN.electing(2) : It is in the election process of the Querier.querier(3) : It is the current Querier in this VLAN.candidate (4): It is a alternative Querier in this VLAN.inactive(5) : VLAN is inactive or not an Ethernet"
			::= { sleV2IgsVlanEntry 18 }

		
--  1.3.6.1.4.1.6296.102.12.2.2.5.1.1.1.19
		sleV2IgsVlanQuerierVersion OBJECT-TYPE
			SYNTAX INTEGER
				{
				one(1),
				two(2),
				three(3)
				}
			MAX-ACCESS read-only
			STATUS current
			DESCRIPTION
				"The object indicates IGMP version of the Querier for the VLAN. IGMP version of the Querier is determined by the type of IGMP General Query received by the device."
			::= { sleV2IgsVlanEntry 19 }

		
--  1.3.6.1.4.1.6296.102.12.2.2.5.1.1.1.20
		sleV2IgsVlanQuerierAddress OBJECT-TYPE
			SYNTAX IpAddress
			MAX-ACCESS read-only
			STATUS current
			DESCRIPTION
				"It is IP address of the IGMP Querier for the VLAN."
			::= { sleV2IgsVlanEntry 20 }

		
--  1.3.6.1.4.1.6296.102.12.2.2.5.1.1.1.21
		sleV2IgsVlanQuerierPortIndex OBJECT-TYPE
			SYNTAX INTEGER (0..255)
			MAX-ACCESS read-only
			STATUS current
			DESCRIPTION
				"It is the port on which IGMP Querier is detected for the VLAN. It is zero if the device itself is acting as IGMP Querier for the VLAN."
			::= { sleV2IgsVlanEntry 21 }

		
--  1.3.6.1.4.1.6296.102.12.2.2.5.1.1.1.22
		sleV2IgsVlanQuerierUptime OBJECT-TYPE
			SYNTAX TimeTicks
			MAX-ACCESS read-only
			STATUS current
			DESCRIPTION
				"The time since Querier on the VLAN was last changed."
			::= { sleV2IgsVlanEntry 22 }

		
--  1.3.6.1.4.1.6296.102.12.2.2.5.1.1.1.23
		sleV2IgsVlanQuerierExpireTime OBJECT-TYPE
			SYNTAX TimeTicks
			MAX-ACCESS read-only
			STATUS current
			DESCRIPTION
				"The amount of time remaining before the Other Querier Present Timer expires. If the local system is the querier, the value of this object is zero."
			::= { sleV2IgsVlanEntry 23 }

		
--  1.3.6.1.4.1.6296.102.12.2.2.5.1.1.1.24
		sleV2IgsVlanTcnFloodActivity OBJECT-TYPE
			SYNTAX Boolean
			MAX-ACCESS read-only
			STATUS current
			DESCRIPTION
				"TRUE is multicast traffic will be flooded on all ports of the VLAN for TcnFloodQueryCount of IGMP General Queries upon receiving a Topology Change Notification (TCN) for the VLAN. FALSE is not flooding."
			::= { sleV2IgsVlanEntry 24 }

		
--  1.3.6.1.4.1.6296.102.12.2.2.5.1.1.1.25
		sleV2IgsVlanExplicitTracking OBJECT-TYPE
			SYNTAX Boolean
			MAX-ACCESS read-only
			STATUS current
			DESCRIPTION
				"In IGMPv3, it decide the device tracks reporters or not."
			::= { sleV2IgsVlanEntry 25 }

		
--  1.3.6.1.4.1.6296.102.12.2.2.5.1.1.1.26
		sleV2IgsVlanTxGeneralQueries OBJECT-TYPE
			SYNTAX Counter32
			MAX-ACCESS read-only
			STATUS current
			DESCRIPTION
				"Total IGMP General Queries that have been transmitted through an interface."
			::= { sleV2IgsVlanEntry 26 }

		
--  1.3.6.1.4.1.6296.102.12.2.2.5.1.1.1.27
		sleV2IgsVlanTxSpecialQueries OBJECT-TYPE
			SYNTAX Counter32
			MAX-ACCESS read-only
			STATUS current
			DESCRIPTION
				"Total IGMP Group-Specific Queries that have been transmitted through an interface."
			::= { sleV2IgsVlanEntry 27 }

		
--  1.3.6.1.4.1.6296.102.12.2.2.5.1.1.1.28
		sleV2IgsVlanTxReportMessages OBJECT-TYPE
			SYNTAX Counter32
			MAX-ACCESS read-only
			STATUS current
			DESCRIPTION
				"Total IGMP Membership Reports that have been transmitted through an interface."
			::= { sleV2IgsVlanEntry 28 }

		
--  1.3.6.1.4.1.6296.102.12.2.2.5.1.1.1.29
		sleV2IgsVlanTxLeaveMessages OBJECT-TYPE
			SYNTAX Counter32
			MAX-ACCESS read-only
			STATUS current
			DESCRIPTION
				"Total IGMP Leave messages that have been transmitted through an interface."
			::= { sleV2IgsVlanEntry 29 }

		
--  1.3.6.1.4.1.6296.102.12.2.2.5.1.1.1.30
		sleV2IgsVlanRxGeneralQueries OBJECT-TYPE
			SYNTAX Counter32
			MAX-ACCESS read-only
			STATUS current
			DESCRIPTION
				"Total IGMP General Queries that have been received at an interface."
			::= { sleV2IgsVlanEntry 30 }

		
--  1.3.6.1.4.1.6296.102.12.2.2.5.1.1.1.31
		sleV2IgsVlanRxSpecialQueries OBJECT-TYPE
			SYNTAX Counter32
			MAX-ACCESS read-only
			STATUS current
			DESCRIPTION
				"Total IGMP Group-Specific Queries that have been received at an interface."
			::= { sleV2IgsVlanEntry 31 }

		
--  1.3.6.1.4.1.6296.102.12.2.2.5.1.1.1.32
		sleV2IgsVlanRxReportMessages OBJECT-TYPE
			SYNTAX Counter32
			MAX-ACCESS read-only
			STATUS current
			DESCRIPTION
				"Total IGMP Membership Reports that have been received at an interface."
			::= { sleV2IgsVlanEntry 32 }

		
--  1.3.6.1.4.1.6296.102.12.2.2.5.1.1.1.33
		sleV2IgsVlanRxLeaveMessages OBJECT-TYPE
			SYNTAX Counter32
			MAX-ACCESS read-only
			STATUS current
			DESCRIPTION
				"Total IGMP Leave messages that have been received at an interface."
			::= { sleV2IgsVlanEntry 33 }

		
--  1.3.6.1.4.1.6296.102.12.2.2.5.1.1.1.34
		sleV2IgsVlanRxValidMessages OBJECT-TYPE
			SYNTAX Counter32
			MAX-ACCESS read-only
			STATUS current
			DESCRIPTION
				"Total valid IGMP packets have been received at an interface."
			::= { sleV2IgsVlanEntry 34 }

		
--  1.3.6.1.4.1.6296.102.12.2.2.5.1.1.1.35
		sleV2IgsVlanRxWrongMessages OBJECT-TYPE
			SYNTAX Counter32
			MAX-ACCESS read-only
			STATUS current
			DESCRIPTION
				"Total packets those are not valid IGMP messages received at an interface."
			::= { sleV2IgsVlanEntry 35 }

		
--  IGMP Snooping VLAN Control
-- 1.3.6.1.4.1.6296.102.12.2.2.5.1.2
		sleV2IgsVlanControl OBJECT IDENTIFIER ::= { sleV2IgsVlan 2 }

		
--  1.3.6.1.4.1.6296.102.12.2.2.5.1.2.1
		sleV2IgsVlanControlRequest OBJECT-TYPE
			SYNTAX INTEGER
				{
				createIgmpSnoopVlan(1),
				destroyIgmpSnoopVlan(2),
				setIgmpSnoopVlanProfile(3),
				setIgmpSnoopMRouteProfile(4),
				setIgmpSnoopQuerierProfile(5),
				setIgmpSnoopTcnProfile(6),
				clearIgmpSnoopStatistics(7)
				}
			MAX-ACCESS read-write
			STATUS current
			DESCRIPTION
				" The request of a user command"
			::= { sleV2IgsVlanControl 1 }

		
--  1.3.6.1.4.1.6296.102.12.2.2.5.1.2.2
		sleV2IgsVlanControlStatus OBJECT-TYPE
			SYNTAX SleControlStatusType
			MAX-ACCESS read-only
			STATUS current
			DESCRIPTION
				" The status of user command"
			::= { sleV2IgsVlanControl 2 }

		
--  1.3.6.1.4.1.6296.102.12.2.2.5.1.2.3
		sleV2IgsVlanControlTimer OBJECT-TYPE
			SYNTAX Gauge32
			MAX-ACCESS read-write
			STATUS current
			DESCRIPTION
				" The maximum time for the manager for a long running user command"
			::= { sleV2IgsVlanControl 3 }

		
--  1.3.6.1.4.1.6296.102.12.2.2.5.1.2.4
		sleV2IgsVlanControlTimeStamp OBJECT-TYPE
			SYNTAX TimeStamp
			MAX-ACCESS read-only
			STATUS current
			DESCRIPTION
				" The time stamp of the last command(end of command)"
			::= { sleV2IgsVlanControl 4 }

		
--  1.3.6.1.4.1.6296.102.12.2.2.5.1.2.5
		sleV2IgsVlanControlReqResult OBJECT-TYPE
			SYNTAX SleControlRequestResultType
			MAX-ACCESS read-only
			STATUS current
			DESCRIPTION
				" The result of the last user command"
			::= { sleV2IgsVlanControl 5 }

		
--  1.3.6.1.4.1.6296.102.12.2.2.5.1.2.6
		sleV2IgsVlanControlIndex OBJECT-TYPE
			SYNTAX INTEGER (1..4094)
			MAX-ACCESS read-write
			STATUS current
			DESCRIPTION
				"value(0) : all vlan"
			::= { sleV2IgsVlanControl 6 }

		
--  1.3.6.1.4.1.6296.102.12.2.2.5.1.2.7
		sleV2IgsVlanControlActivity OBJECT-TYPE
			SYNTAX Boolean
			MAX-ACCESS read-write
			STATUS current
			DESCRIPTION
				"When this object is set to 'true' IGMP Snooping is enabled on this VLAN else disabled."
			::= { sleV2IgsVlanControl 7 }

		
--  1.3.6.1.4.1.6296.102.12.2.2.5.1.2.8
		sleV2IgsVlanControlVersion OBJECT-TYPE
			SYNTAX INTEGER
				{
				dynamic(0),
				igmpV1(1),
				igmpV2(2),
				igmpV3(3)
				}
			MAX-ACCESS read-write
			STATUS current
			DESCRIPTION
				"default = igmpV3"
			::= { sleV2IgsVlanControl 8 }

		
--  1.3.6.1.4.1.6296.102.12.2.2.5.1.2.9
		sleV2IgsVlanControlFastLeave OBJECT-TYPE
			SYNTAX Boolean
			MAX-ACCESS read-write
			STATUS current
			DESCRIPTION
				"This object specifies whether Fast-Leave mechanism (also known as Immediate-Leave) is to be performed by IGMP Snooping or not. When enabled, IGMP Snooping will remove the interface from the group mentioned in the IGMP Leave message received on that interface without waiting for the IGMP Group-Specific Query to timeout to determine whether there are any more hosts on that interface for that group."
			::= { sleV2IgsVlanControl 9 }

		
--  1.3.6.1.4.1.6296.102.12.2.2.5.1.2.10
		sleV2IgsVlanControlFastBlock OBJECT-TYPE
			SYNTAX Boolean
			MAX-ACCESS read-write
			STATUS current
			DESCRIPTION
				"The object indicates whether Fast-Block mechanism has been enabled for the VLAN. This object only has effect if the value of sleV2IgsVlanVersion is 3."
			::= { sleV2IgsVlanControl 10 }

		
--  1.3.6.1.4.1.6296.102.12.2.2.5.1.2.11
		sleV2IgsVlanControlMRtLearningMode OBJECT-TYPE
			SYNTAX INTEGER
				{
				none(0),
				pim(1)
				}
			MAX-ACCESS read-write
			STATUS current
			DESCRIPTION
				"This object specifies the multicast router port learning method for IGMP Snooping as described below:
				none(0) : dont learning, Only use static router ports.
				pim(1) : Protocol Independent Multicast.
				"
			::= { sleV2IgsVlanControl 11 }

		
--  1.3.6.1.4.1.6296.102.12.2.2.5.1.2.12
		sleV2IgsVlanControlMRtStaticPortMap OBJECT-TYPE
			SYNTAX OCTET STRING (SIZE (0..64))
			MAX-ACCESS read-write
			STATUS current
			DESCRIPTION
				"Multicast router ports learned by dynamic method (ex: PIM when MRouterLearningMode is pim"
			::= { sleV2IgsVlanControl 12 }

		
--  1.3.6.1.4.1.6296.102.12.2.2.5.1.2.13
		sleV2IgsVlanControlReportSuppression OBJECT-TYPE
			SYNTAX Boolean
			MAX-ACCESS read-write
			STATUS current
			DESCRIPTION
				"Its TRUE, IGMP Snooping will suppress duplicate IGMP Reports on the VLAN. FALSE, all IGMP Reports are forwarded to multicast routers on the VLAN. Alias of this is IGMP Snooping Proxy."
			::= { sleV2IgsVlanControl 13 }

		
--  1.3.6.1.4.1.6296.102.12.2.2.5.1.2.14
		sleV2IgsVlanControlQuerierActivity OBJECT-TYPE
			SYNTAX Boolean
			MAX-ACCESS read-write
			STATUS current
			DESCRIPTION
				"The object indicates whether the device will participate in the IGMP Querier election in a VLAN. If the object is set to 'true', the device will participate to an election process to be a Querier. If this is set to 'false' while the device is acting as the Querier in a VLAN, a new election will be activated to choose a different Querier."
			::= { sleV2IgsVlanControl 14 }

		
--  1.3.6.1.4.1.6296.102.12.2.2.5.1.2.15
		sleV2IgsVlanControlQueryInterval OBJECT-TYPE
			SYNTAX Unsigned32 (0..31744)
			MAX-ACCESS read-write
			STATUS current
			DESCRIPTION
				"The frequency at which IGMP packets are transmitted on this interface."
			::= { sleV2IgsVlanControl 15 }

		
--  1.3.6.1.4.1.6296.102.12.2.2.5.1.2.16
		sleV2IgsVlanControlRobustness OBJECT-TYPE
			SYNTAX Unsigned32 (1..7)
			MAX-ACCESS read-write
			STATUS current
			DESCRIPTION
				"The Robustness Variable allows tuning for the expected packet loss on a subnet. If a subnet is expected to be lossy, the Robustness Variable may be increased. IGMP is robust to (Robustness Variable-1) packet losses."
			::= { sleV2IgsVlanControl 16 }

		
--  1.3.6.1.4.1.6296.102.12.2.2.5.1.2.17
		sleV2IgsVlanControlMaxResponseTime OBJECT-TYPE
			SYNTAX Unsigned32 (0..31744)
			MAX-ACCESS read-write
			STATUS current
			DESCRIPTION
				"The maximum query response time advertised in queries on this interface."
			::= { sleV2IgsVlanControl 17 }

		
--  1.3.6.1.4.1.6296.102.12.2.2.5.1.2.18
		sleV2IgsVlanControlQuerierTimeOut OBJECT-TYPE
			SYNTAX Unsigned32 (60..300)
			MAX-ACCESS read-write
			STATUS current
			DESCRIPTION
				"Other Querier Present Interval. Default value is (QueryInterval * Robustness) + (MaxResponseTime / 2)"
			::= { sleV2IgsVlanControl 18 }

		
--  1.3.6.1.4.1.6296.102.12.2.2.5.1.2.19
		sleV2IgsVlanControlLastMembQueryIntvl OBJECT-TYPE
			SYNTAX Unsigned32 (0..31744)
			MAX-ACCESS read-write
			STATUS current
			DESCRIPTION
				"The Last Member Query Interval is the Max Response Time inserted into Group-Specific Queries sent in response to Leave Group messages, and is also the amount of time Between Group-Specific Query messages. This value may be tuned to modify the leave latency of the network. A reduced value results in reduced time to detect the loss of the last member of a group. The value of this object is irrelevant if mgmdRouterInterfaceVersion is 1"
			::= { sleV2IgsVlanControl 19 }

		
--  1.3.6.1.4.1.6296.102.12.2.2.5.1.2.20
		sleV2IgsVlanControlTcnFloodActivity OBJECT-TYPE
			SYNTAX Boolean
			MAX-ACCESS read-write
			STATUS current
			DESCRIPTION
				"TRUE is multicast traffic will be flooded on all ports of the VLAN for TcnFloodQueryCount of IGMP General Queries upon receiving a Topology Change Notification (TCN) for the VLAN. FALSE is not flooding."
			::= { sleV2IgsVlanControl 20 }

		
--  1.3.6.1.4.1.6296.102.12.2.2.5.1.2.21
		sleV2IgsVlanControlExplicitTracking OBJECT-TYPE
			SYNTAX Boolean
			MAX-ACCESS read-write
			STATUS current
			DESCRIPTION
				"In IGMPv3, it decide the device tracks reporters or not."
			::= { sleV2IgsVlanControl 21 }

		
		sleV2IgsVlanControlQuerierAddress OBJECT-TYPE
			SYNTAX IpAddress
			MAX-ACCESS read-write
			STATUS current
			DESCRIPTION
				"Description."
			::= { sleV2IgsVlanControl 22 }

		
--  IGMP Snooping VLAN Notification
-- 1.3.6.1.4.1.6296.102.12.2.2.5.1.3
		sleV2IgsVlanNotification OBJECT IDENTIFIER ::= { sleV2IgsVlan 3 }

		
--  1.3.6.1.4.1.6296.102.12.2.2.5.1.3.1
		sleV2IgsVlanCreated NOTIFICATION-TYPE
			OBJECTS { sleV2IgsVlanControlRequest, sleV2IgsVlanControlTimeStamp, sleV2IgsVlanControlReqResult, sleV2IgsVlanActivity }
			STATUS current
			DESCRIPTION 
				"createIgmpSnoopVlan"
			::= { sleV2IgsVlanNotification 1 }

		
--  1.3.6.1.4.1.6296.102.12.2.2.5.1.3.2
		sleV2IgsVlanDestroyed NOTIFICATION-TYPE
			OBJECTS { sleV2IgsVlanControlRequest, sleV2IgsVlanControlTimeStamp, sleV2IgsVlanControlReqResult, sleV2IgsVlanControlIndex }
			STATUS current
			DESCRIPTION 
				"destroyIgmpSnoopVlan"
			::= { sleV2IgsVlanNotification 2 }

		
--  1.3.6.1.4.1.6296.102.12.2.2.5.1.3.3
		sleV2IgsVlanProfileChanged NOTIFICATION-TYPE
			OBJECTS { sleV2IgsVlanControlRequest, sleV2IgsVlanControlTimeStamp, sleV2IgsVlanControlReqResult, sleV2IgsVlanVersion, sleV2IgsVlanVersionMode, 
				sleV2IgsVlanFastLeave, sleV2IgsVlanFastBlock, sleV2IgsVlanReportSuppression, sleV2IgsVlanExplicitTracking }
			STATUS current
			DESCRIPTION 
				"setIgmpSnoopVlanProfile"
			::= { sleV2IgsVlanNotification 3 }

		
--  1.3.6.1.4.1.6296.102.12.2.2.5.1.3.4
		sleV2IgsVlanMRouteProfileChanged NOTIFICATION-TYPE
			OBJECTS { sleV2IgsVlanControlRequest, sleV2IgsVlanControlTimeStamp, sleV2IgsVlanControlReqResult, sleV2IgsVlanMRtLearningMode, sleV2IgsVlanMRtStaticPortMap
				 }
			STATUS current
			DESCRIPTION 
				"setIgmpSnoopMRouteProfile"
			::= { sleV2IgsVlanNotification 4 }

		
--  1.3.6.1.4.1.6296.102.12.2.2.5.1.3.5
		sleV2IgsVlanQuerierProfileChanced NOTIFICATION-TYPE
			OBJECTS { sleV2IgsVlanControlRequest, sleV2IgsVlanControlTimeStamp, sleV2IgsVlanControlReqResult, sleV2IgsVlanQuerierActivity, sleV2IgsVlanQueryInterval, 
				sleV2IgsVlanRobustness, sleV2IgsVlanMaxResponseTime, sleV2IgsVlanQuerierTimeOut, sleV2IgsVlanLastMembQueryIntvl, sleV2IgsVlanQuerierAddress
				 }
			STATUS current
			DESCRIPTION 
				"setIgmpSnoopQuerierProfile"
			::= { sleV2IgsVlanNotification 5 }

		
--  1.3.6.1.4.1.6296.102.12.2.2.5.1.3.6
		sleV2IgsVlanTcnProfileChanced NOTIFICATION-TYPE
			OBJECTS { sleV2IgsVlanControlRequest, sleV2IgsVlanControlTimeStamp, sleV2IgsVlanControlReqResult, sleV2IgsVlanTcnFloodActivity }
			STATUS current
			DESCRIPTION 
				"setIgmpSnoopTcnProfile"
			::= { sleV2IgsVlanNotification 6 }

		
--  1.3.6.1.4.1.6296.102.12.2.2.5.1.3.7
		sleV2IgsVlanStatisticsCleared NOTIFICATION-TYPE
			OBJECTS { sleV2IgsVlanControlRequest, sleV2IgsVlanControlTimeStamp, sleV2IgsVlanControlReqResult, sleV2IgsVlanControlIndex }
			STATUS current
			DESCRIPTION 
				"clearIgmpSnoopStatistics"
			::= { sleV2IgsVlanNotification 7 }

		
--  IGMP Snooping Group
-- 1.3.6.1.4.1.6296.102.12.2.2.5.2
		sleV2IgsGroup OBJECT IDENTIFIER ::= { sleV2IgmpSnooping 2 }

		
--  IGMP Snooping Group Table
-- 1.3.6.1.4.1.6296.102.12.2.2.5.2.1
		sleV2IgsGroupTable OBJECT-TYPE
			SYNTAX SEQUENCE OF SleV2IgsGroupEntry
			MAX-ACCESS not-accessible
			STATUS current
			DESCRIPTION
				"IGS group table."
			::= { sleV2IgsGroup 1 }

		
--  IGMP Snooping Group Entry
-- 1.3.6.1.4.1.6296.102.12.2.2.5.2.2.1
		sleV2IgsGroupEntry OBJECT-TYPE
			SYNTAX SleV2IgsGroupEntry
			MAX-ACCESS not-accessible
			STATUS current
			DESCRIPTION
				"key: sleV2IgsVlanIndex, sleV2IgsGroupAddress, sleV2IgsGroupPortIndex"
			INDEX { sleV2IgsVlanIndex, sleV2IgsGroupAddress, sleV2IgsGroupPortIndex }
			::= { sleV2IgsGroupTable 1 }

		
		SleV2IgsGroupEntry ::=
			SEQUENCE { 
				sleV2IgsGroupAddress
					IpAddress,
				sleV2IgsGroupPortIndex
					INTEGER,
				sleV2IgsGroupSourceFilterMode
					INTEGER,
				sleV2IgsGroupExcludeModeExpiryTimer
					TimeTicks,
				sleV2IgsGroupUpTime
					TimeTicks,
				sleV2IgsGroupExpiryTime
					TimeTicks,
				sleV2IgsGroupPortInfo
					Integer32
			 }

--  1.3.6.1.4.1.6296.102.12.2.2.5.2.2.1.1
		sleV2IgsGroupAddress OBJECT-TYPE
			SYNTAX IpAddress
			MAX-ACCESS read-only
			STATUS current
			DESCRIPTION
				"It is a IP multicast address learned by IGMP Snooping."
			::= { sleV2IgsGroupEntry 1 }

		
--  1.3.6.1.4.1.6296.102.12.2.2.5.2.2.1.2
		sleV2IgsGroupPortIndex OBJECT-TYPE
			SYNTAX INTEGER (1..512)
			MAX-ACCESS read-only
			STATUS current
			DESCRIPTION
				"This object indicates the port on VLAN in which the group is learned."
			::= { sleV2IgsGroupEntry 2 }

		
--  1.3.6.1.4.1.6296.102.12.2.2.5.2.2.1.3
		sleV2IgsGroupSourceFilterMode OBJECT-TYPE
			SYNTAX INTEGER
				{
				unknown(0),
				include(1),
				exclude(2)
				}
			MAX-ACCESS read-only
			STATUS current
			DESCRIPTION
				"The current group state, applicable to IGMPv3 compatible nodes. The value indicates whether the state is INCLUDE or EXCLUDE."
			::= { sleV2IgsGroupEntry 3 }

		
--  1.3.6.1.4.1.6296.102.12.2.2.5.2.2.1.4
		sleV2IgsGroupExcludeModeExpiryTimer OBJECT-TYPE
			SYNTAX TimeTicks
			MAX-ACCESS read-only
			STATUS current
			DESCRIPTION
				"This value is applicable only to IGMPv3 compatible routers, and represents the time remaining before the interface EXCLUDE state expires and the interface state transitions to INCLUDE mode. This value can never be greater than sleV2IgmpCacheExpiryTime."
			::= { sleV2IgsGroupEntry 4 }

		
--  1.3.6.1.4.1.6296.102.12.2.2.5.2.2.1.5
		sleV2IgsGroupUpTime OBJECT-TYPE
			SYNTAX TimeTicks
			MAX-ACCESS read-only
			STATUS current
			DESCRIPTION
				"The time elapsed since this entry was created."
			::= { sleV2IgsGroupEntry 5 }

		
--  1.3.6.1.4.1.6296.102.12.2.2.5.2.2.1.6
		sleV2IgsGroupExpiryTime OBJECT-TYPE
			SYNTAX TimeTicks
			MAX-ACCESS read-only
			STATUS current
			DESCRIPTION
				"This value represents the time remaining before the Group Membership Interval state expires. The value must always be greater than 0."
			::= { sleV2IgsGroupEntry 6 }

		
		sleV2IgsGroupPortInfo OBJECT-TYPE
			SYNTAX Integer32
			MAX-ACCESS read-only
			STATUS current
			DESCRIPTION
				"Port information."
			::= { sleV2IgsGroupEntry 7 }

		
--  IGMP Snooping Group
-- 1.3.6.1.4.1.6296.102.12.2.2.5.3
		sleV2IgsSource OBJECT IDENTIFIER ::= { sleV2IgmpSnooping 3 }

		
--  IGMP Snooping Group Table
-- 1.3.6.1.4.1.6296.102.12.2.2.5.3.1
		sleV2IgsSourceTable OBJECT-TYPE
			SYNTAX SEQUENCE OF SleV2IgsSourceEntry
			MAX-ACCESS not-accessible
			STATUS current
			DESCRIPTION
				"IGS source table."
			::= { sleV2IgsSource 1 }

		
--  IGMP Snooping Group Entry
-- 1.3.6.1.4.1.6296.102.12.2.2.5.3.1.1
		sleV2IgsSourceEntry OBJECT-TYPE
			SYNTAX SleV2IgsSourceEntry
			MAX-ACCESS not-accessible
			STATUS current
			DESCRIPTION
				"key: sleV2IgsVlanIndex, sleV2IgsGroupAddress, sleV2IgsGroupPortIndex, sleV2IgsSourceAddress"
			INDEX { sleV2IgsVlanIndex, sleV2IgsGroupAddress, sleV2IgsGroupPortIndex, sleV2IgsSourceAddress }
			::= { sleV2IgsSourceTable 1 }

		
		SleV2IgsSourceEntry ::=
			SEQUENCE { 
				sleV2IgsSourceAddress
					IpAddress,
				sleV2IgsSourceType
					INTEGER,
				sleV2IgsSourceUpTime
					TimeTicks,
				sleV2IgsSourceExpiryTime
					TimeTicks,
				sleV2IgsSourceSsmMapped
					Boolean,
				sleV2IgsSourceVId
					Integer32,
				sleV2IgsSourcenGrpAddr
					IpAddress,
				sleV2IgsSourcePort
					Integer32,
				sleV2IgsSourcePortInfo
					Integer32
			 }

--  1.3.6.1.4.1.6296.102.12.2.2.5.3.1.1.1
		sleV2IgsSourceAddress OBJECT-TYPE
			SYNTAX IpAddress
			MAX-ACCESS read-only
			STATUS current
			DESCRIPTION
				"Source of IP multicast group, sleV2IgsGroupAddress.For (*,G) entry, value is 0.0.0.0"
			::= { sleV2IgsSourceEntry 1 }

		
--  1.3.6.1.4.1.6296.102.12.2.2.5.3.1.1.2
		sleV2IgsSourceType OBJECT-TYPE
			SYNTAX INTEGER
				{
				dynamic(1),
				static(2)
				}
			MAX-ACCESS read-only
			STATUS current
			DESCRIPTION
				"It indicates whether the multicast group (S/*,G) is learned by snooping of IGMP report messages or administrative maner."
			::= { sleV2IgsSourceEntry 2 }

		
--  1.3.6.1.4.1.6296.102.12.2.2.5.3.1.1.3
		sleV2IgsSourceUpTime OBJECT-TYPE
			SYNTAX TimeTicks
			MAX-ACCESS read-only
			STATUS current
			DESCRIPTION
				"The time elapsed since this entry was created."
			::= { sleV2IgsSourceEntry 3 }

		
--  1.3.6.1.4.1.6296.102.12.2.2.5.3.1.1.4
		sleV2IgsSourceExpiryTime OBJECT-TYPE
			SYNTAX TimeTicks
			MAX-ACCESS read-only
			STATUS current
			DESCRIPTION
				"This value represents the time remaining before the Group Membership Interval state expires. The value must always be greater than 0."
			::= { sleV2IgsSourceEntry 4 }

		
--  1.3.6.1.4.1.6296.102.12.2.2.5.3.1.1.5
		sleV2IgsSourceSsmMapped OBJECT-TYPE
			SYNTAX Boolean
			MAX-ACCESS read-only
			STATUS current
			DESCRIPTION
				"The value TRUE indicate that source of multicast group is decided by SSM Mapping Table, and FALSE is not."
			::= { sleV2IgsSourceEntry 5 }

		
		sleV2IgsSourceVId OBJECT-TYPE
			SYNTAX Integer32 (1..4094)
			MAX-ACCESS read-only
			STATUS current
			DESCRIPTION
				"This object indicates the VLAN in which IGMP Snooping is configured. (= sleNetIfIndex)"
			::= { sleV2IgsSourceEntry 6 }

		
		sleV2IgsSourcenGrpAddr OBJECT-TYPE
			SYNTAX IpAddress
			MAX-ACCESS read-only
			STATUS current
			DESCRIPTION
				"It is a IP multicast address learned by IGMP Snooping."
			::= { sleV2IgsSourceEntry 7 }

		
		sleV2IgsSourcePort OBJECT-TYPE
			SYNTAX Integer32
			MAX-ACCESS read-only
			STATUS current
			DESCRIPTION
				"This object indicates the port on VLAN in which the group is learned."
			::= { sleV2IgsSourceEntry 8 }

		
		sleV2IgsSourcePortInfo OBJECT-TYPE
			SYNTAX Integer32
			MAX-ACCESS read-only
			STATUS current
			DESCRIPTION
				"Port information."
			::= { sleV2IgsSourceEntry 9 }

		
--  IGMP Snooping Group Control
-- 1.3.6.1.4.1.6296.102.12.2.2.5.3.2
		sleV2IgsSourceControl OBJECT IDENTIFIER ::= { sleV2IgsSource 2 }

		
--  1.3.6.1.4.1.6296.102.12.2.2.5.3.2.1
		sleV2IgsSourceControlRequest OBJECT-TYPE
			SYNTAX INTEGER
				{
				createIgmpSnoopSourceStatic(1),
				destroyIgmpSnoopSourceStatic(2)
				}
			MAX-ACCESS read-write
			STATUS current
			DESCRIPTION
				" The request of a user command"
			::= { sleV2IgsSourceControl 1 }

		
--  1.3.6.1.4.1.6296.102.12.2.2.5.3.2.2
		sleV2IgsSourceControlStatus OBJECT-TYPE
			SYNTAX SleControlStatusType
			MAX-ACCESS read-only
			STATUS current
			DESCRIPTION
				"The status of user command"
			::= { sleV2IgsSourceControl 2 }

		
--  1.3.6.1.4.1.6296.102.12.2.2.5.3.2.3
		sleV2IgsSourceControlTimer OBJECT-TYPE
			SYNTAX Gauge32
			MAX-ACCESS read-write
			STATUS current
			DESCRIPTION
				" The maximum time for the manager for a long running user command"
			::= { sleV2IgsSourceControl 3 }

		
--  1.3.6.1.4.1.6296.102.12.2.2.5.3.2.4
		sleV2IgsSourceControlTimeStamp OBJECT-TYPE
			SYNTAX TimeStamp
			MAX-ACCESS read-only
			STATUS current
			DESCRIPTION
				" The time stamp of the last command(end of command)"
			::= { sleV2IgsSourceControl 4 }

		
--  1.3.6.1.4.1.6296.102.12.2.2.5.3.2.5
		sleV2IgsSourceControlReqResult OBJECT-TYPE
			SYNTAX SleControlRequestResultType
			MAX-ACCESS read-only
			STATUS current
			DESCRIPTION
				" The result of the last user command"
			::= { sleV2IgsSourceControl 5 }

		
--  1.3.6.1.4.1.6296.102.12.2.2.5.3.2.6
		sleV2IgsSourceControlVlanIndex OBJECT-TYPE
			SYNTAX INTEGER (1..4094)
			MAX-ACCESS read-write
			STATUS current
			DESCRIPTION
				"value(0) : all vlan"
			::= { sleV2IgsSourceControl 6 }

		
--  1.3.6.1.4.1.6296.102.12.2.2.5.3.2.7
		sleV2IgsSourceControlGroup OBJECT-TYPE
			SYNTAX IpAddress
			MAX-ACCESS read-write
			STATUS current
			DESCRIPTION
				"Group IP address"
			::= { sleV2IgsSourceControl 7 }

		
--  1.3.6.1.4.1.6296.102.12.2.2.5.3.2.8
		sleV2IgsSourceControlPortIndex OBJECT-TYPE
			SYNTAX INTEGER (1..512)
			MAX-ACCESS read-write
			STATUS current
			DESCRIPTION
				"Port index"
			::= { sleV2IgsSourceControl 8 }

		
--  1.3.6.1.4.1.6296.102.12.2.2.5.3.2.9
		sleV2IgsSourceControlAddress OBJECT-TYPE
			SYNTAX IpAddress
			MAX-ACCESS read-write
			STATUS current
			DESCRIPTION
				"Source IP address"
			::= { sleV2IgsSourceControl 9 }

		
--  IGMP Snooping Group Notification
-- 1.3.6.1.4.1.6296.102.12.2.2.5.3.3
		sleV2IgsSourceNotification OBJECT IDENTIFIER ::= { sleV2IgsSource 3 }

		
--  1.3.6.1.4.1.6296.102.12.2.2.5.3.3.1
		sleV2IgsSourceCreated NOTIFICATION-TYPE
			OBJECTS { sleV2IgsSourceControlRequest, sleV2IgsSourceControlReqResult, sleV2IgsSourceControlTimeStamp, sleV2IgsSourceType }
			STATUS current
			DESCRIPTION 
				"In IGMPv3, Adding (S,G) entry is imply that SourceFilterMode is 'allow'."
			::= { sleV2IgsSourceNotification 1 }

		
--  1.3.6.1.4.1.6296.102.12.2.2.5.3.3.2
		sleV2IgsSourceDestroyed NOTIFICATION-TYPE
			OBJECTS { sleV2IgsSourceControlRequest, sleV2IgsSourceControlReqResult, sleV2IgsSourceControlTimeStamp, sleV2IgsSourceType }
			STATUS current
			DESCRIPTION 
				"In IGMPv3, Removing static (S,G) entry is imply that SourceFilterMode is 'block'."
			::= { sleV2IgsSourceNotification 2 }

		
--  IGMP Snooping Reporter
-- 1.3.6.1.4.1.6296.102.12.2.2.5.4
		sleV2IgsReporter OBJECT IDENTIFIER ::= { sleV2IgmpSnooping 4 }

		
--  IGMP Snooping Reporter Table
-- 1.3.6.1.4.1.6296.102.12.2.2.5.4.1
		sleV2IgsReporterTable OBJECT-TYPE
			SYNTAX SEQUENCE OF SleV2IgsReporterEntry
			MAX-ACCESS not-accessible
			STATUS current
			DESCRIPTION
				"IGS reporter table."
			::= { sleV2IgsReporter 1 }

		
--  IGMP Snooping Reporter Entry
-- 1.3.6.1.4.1.6296.102.12.2.2.5.4.1.1
		sleV2IgsReporterEntry OBJECT-TYPE
			SYNTAX SleV2IgsReporterEntry
			MAX-ACCESS not-accessible
			STATUS current
			DESCRIPTION
				"key: sleV2IgsVlanIndex, sleV2IgsGroupAddress, sleV2IgsGroupPortIndex, sleV2IgsSourceAddress, sleV2IgsReporterAddress"
			INDEX { sleV2IgsVlanIndex, sleV2IgsGroupAddress, sleV2IgsGroupPortIndex, sleV2IgsSourceAddress, sleV2IgsReporterAddress
				 }
			::= { sleV2IgsReporterTable 1 }

		
		SleV2IgsReporterEntry ::=
			SEQUENCE { 
				sleV2IgsReporterAddress
					IpAddress,
				sleV2IgsReporterExpiryTime
					TimeTicks,
				sleV2IgsReporterMac
					OCTET STRING,
				sleV2IgsReporterVersion
					INTEGER,
				sleV2IgsReporterMode
					INTEGER,
				sleV2IgsReporterPortInfo
					Integer32
			 }

--  1.3.6.1.4.1.6296.102.12.2.2.5.4.1.1.1
		sleV2IgsReporterAddress OBJECT-TYPE
			SYNTAX IpAddress
			MAX-ACCESS read-only
			STATUS current
			DESCRIPTION
				"IP address of reporter."
			::= { sleV2IgsReporterEntry 1 }

		
--  1.3.6.1.4.1.6296.102.12.2.2.5.4.1.1.2
		sleV2IgsReporterExpiryTime OBJECT-TYPE
			SYNTAX TimeTicks
			MAX-ACCESS read-only
			STATUS current
			DESCRIPTION
				"This value represents the time remaining before the reporter has expire."
			::= { sleV2IgsReporterEntry 2 }

		
--  1.3.6.1.4.1.6296.102.12.2.2.5.4.1.1.3
		sleV2IgsReporterMac OBJECT-TYPE
			SYNTAX OCTET STRING (SIZE (6))
			MAX-ACCESS read-only
			STATUS current
			DESCRIPTION
				"Hardware address of reporter."
			::= { sleV2IgsReporterEntry 3 }

		
--  1.3.6.1.4.1.6296.102.12.2.2.5.4.1.1.4
		sleV2IgsReporterVersion OBJECT-TYPE
			SYNTAX INTEGER
				{
				igmpV1(1),
				igmpV2(2),
				igmpV3(3)
				}
			MAX-ACCESS read-only
			STATUS current
			DESCRIPTION
				"IGMP version"
			::= { sleV2IgsReporterEntry 4 }

		
--  1.3.6.1.4.1.6296.102.12.2.2.5.4.1.1.5
		sleV2IgsReporterMode OBJECT-TYPE
			SYNTAX INTEGER
				{
				unknown(0),
				includeAllow(1),
				includeBlock(2),
				excludeAllow(3),
				excludeBlock(4)
				}
			MAX-ACCESS read-only
			STATUS current
			DESCRIPTION
				"Filter mode"
			::= { sleV2IgsReporterEntry 5 }

		
		sleV2IgsReporterPortInfo OBJECT-TYPE
			SYNTAX Integer32
			MAX-ACCESS read-only
			STATUS current
			DESCRIPTION
				"Port information."
			::= { sleV2IgsReporterEntry 6 }

		
--  1.3.6.1.4.1.6296.102.12.2.2.5.5
		sleV2IgsPort OBJECT IDENTIFIER ::= { sleV2IgmpSnooping 5 }

		
--  1.3.6.1.4.1.6296.102.12.2.2.5.5.1
		sleV2IgsPortTable OBJECT-TYPE
			SYNTAX SEQUENCE OF SleV2IgsPortEntry
			MAX-ACCESS not-accessible
			STATUS current
			DESCRIPTION
				"IGS port table."
			::= { sleV2IgsPort 1 }

		
--  1.3.6.1.4.1.6296.102.12.2.2.5.5.1.1
		sleV2IgsPortEntry OBJECT-TYPE
			SYNTAX SleV2IgsPortEntry
			MAX-ACCESS not-accessible
			STATUS current
			DESCRIPTION
				"key: sleV2IgsPortIndex"
			INDEX { sleV2IgsPortIndex }
			::= { sleV2IgsPortTable 1 }

		
		SleV2IgsPortEntry ::=
			SEQUENCE { 
				sleV2IgsPortIndex
					INTEGER,
				sleV2IgsPortFastLeave
					Boolean,
				sleV2IgsPortExplicitTrackingMaxHosts
					INTEGER,
				sleV2IgsPortExplicitTrackingMacBased
					Boolean,
				sleV2IgsPortDot1qSelection
					INTEGER,
				sleV2IgsPortMrouter
					INTEGER
			 }

--  1.3.6.1.4.1.6296.102.12.2.2.5.5.1.1.1
		sleV2IgsPortIndex OBJECT-TYPE
			SYNTAX INTEGER (1..512)
			MAX-ACCESS read-only
			STATUS current
			DESCRIPTION
				"This object indicates the port index
				"
			::= { sleV2IgsPortEntry 1 }

		
--  1.3.6.1.4.1.6296.102.12.2.2.5.5.1.1.2
		sleV2IgsPortFastLeave OBJECT-TYPE
			SYNTAX Boolean
			MAX-ACCESS read-only
			STATUS current
			DESCRIPTION
				"This object specifies whether Fast-Leave mechanism (also known as Immediate-Leave) is to be performed by IGMP Snooping or not. When enabled, IGMP Snooping will remove the interface from the group mentioned in the IGMP Leave message received on that interface without waiting for the IGMP Group-Specific Query to timeout to determine whether there are any more hosts on that interface for that port
				"
			::= { sleV2IgsPortEntry 2 }

		
--  1.3.6.1.4.1.6296.102.12.2.2.5.5.1.1.3
		sleV2IgsPortExplicitTrackingMaxHosts OBJECT-TYPE
			SYNTAX INTEGER (1..65535)
			MAX-ACCESS read-only
			STATUS current
			DESCRIPTION
				"This object indicates the maximum number of hosts in the specified port"
			::= { sleV2IgsPortEntry 3 }

		
		sleV2IgsPortExplicitTrackingMacBased OBJECT-TYPE
			SYNTAX Boolean
			MAX-ACCESS read-only
			STATUS current
			DESCRIPTION
				"Tracking mac based"
			::= { sleV2IgsPortEntry 4 }

		
		sleV2IgsPortDot1qSelection OBJECT-TYPE
			SYNTAX INTEGER
				{
				inner(1),
				outer(2)
				}
			MAX-ACCESS read-only
			STATUS current
			DESCRIPTION
				"Dot1q selection
				1: inner
				2: outer
				"
			::= { sleV2IgsPortEntry 5 }

		
		sleV2IgsPortMrouter OBJECT-TYPE
			SYNTAX INTEGER
				{
				disable(0),
				enable(1)
				}
			MAX-ACCESS read-only
			STATUS current
			DESCRIPTION
				"Mrouter Interface. "
			::= { sleV2IgsPortEntry 6 }

		
--  1.3.6.1.4.1.6296.102.12.2.2.5.5.2
		sleV2IgsPortControl OBJECT IDENTIFIER ::= { sleV2IgsPort 2 }

		
--  1.3.6.1.4.1.6296.102.12.2.2.5.5.2.1
		sleV2IgsPortControlRequest OBJECT-TYPE
			SYNTAX INTEGER
				{
				setIgmpSnoopPortProfile(1),
				setIgsExplicitTrackingMaxHosts(2),
				setIgsExplicitTrackingMacBased(3),
				setIgsPortDot1q(4),
				setIgsPortMrouter(5)
				}
			MAX-ACCESS read-write
			STATUS current
			DESCRIPTION
				"The request of a user command"
			::= { sleV2IgsPortControl 1 }

		
--  1.3.6.1.4.1.6296.102.12.2.2.5.5.2.2
		sleV2IgsPortControlStatus OBJECT-TYPE
			SYNTAX SleControlStatusType
			MAX-ACCESS read-only
			STATUS current
			DESCRIPTION
				"The status of user command"
			::= { sleV2IgsPortControl 2 }

		
--  1.3.6.1.4.1.6296.102.12.2.2.5.5.2.3
		sleV2IgsPortControlTimer OBJECT-TYPE
			SYNTAX Gauge32
			MAX-ACCESS read-write
			STATUS current
			DESCRIPTION
				"The maximum time for the manager for a long running user command"
			::= { sleV2IgsPortControl 3 }

		
--  1.3.6.1.4.1.6296.102.12.2.2.5.5.2.4
		sleV2IgsPortControlTimeStamp OBJECT-TYPE
			SYNTAX TimeTicks
			MAX-ACCESS read-only
			STATUS current
			DESCRIPTION
				"The time stamp of the last command(end of command)"
			::= { sleV2IgsPortControl 4 }

		
--  1.3.6.1.4.1.6296.102.12.2.2.5.5.2.5
		sleV2IgsPortControlReqResult OBJECT-TYPE
			SYNTAX SleControlRequestResultType
			MAX-ACCESS read-only
			STATUS current
			DESCRIPTION
				"The result of the last user command"
			::= { sleV2IgsPortControl 5 }

		
--  1.3.6.1.4.1.6296.102.12.2.2.5.5.2.6
		sleV2IgsPortControlIndex OBJECT-TYPE
			SYNTAX INTEGER (1..512)
			MAX-ACCESS read-write
			STATUS current
			DESCRIPTION
				"This object indicates the port index
				"
			::= { sleV2IgsPortControl 6 }

		
--  1.3.6.1.4.1.6296.102.12.2.2.5.5.2.7
		sleV2IgsPortControlFastLeave OBJECT-TYPE
			SYNTAX Boolean
			MAX-ACCESS read-write
			STATUS current
			DESCRIPTION
				"This object specifies whether Fast-Leave mechanism
				"
			::= { sleV2IgsPortControl 7 }

		
--  1.3.6.1.4.1.6296.102.12.2.2.5.5.2.8
		sleV2IgsPortControlExplicitTrackingMaxHosts OBJECT-TYPE
			SYNTAX INTEGER (1..65535)
			MAX-ACCESS read-write
			STATUS current
			DESCRIPTION
				"This object indicates the maximum number of hosts in the specified port"
			::= { sleV2IgsPortControl 8 }

		
		sleV2IgsPortControlExplicitTrackingMacBased OBJECT-TYPE
			SYNTAX Boolean
			MAX-ACCESS read-write
			STATUS current
			DESCRIPTION
				"Tracking mac based"
			::= { sleV2IgsPortControl 9 }

		
		sleV2IgsPortControlDot1qSelection OBJECT-TYPE
			SYNTAX INTEGER
				{
				inner(1),
				outer(2)
				}
			MAX-ACCESS read-write
			STATUS current
			DESCRIPTION
				"Dot1q selection
				1: inner
				2: outer
				"
			::= { sleV2IgsPortControl 10 }

		
		sleV2IgsPortControlMrouter OBJECT-TYPE
			SYNTAX INTEGER
				{
				disable(0),
				enable(1)
				}
			MAX-ACCESS read-write
			STATUS current
			DESCRIPTION
				"Mrouter Interface. "
			::= { sleV2IgsPortControl 11 }

		
--  1.3.6.1.4.1.6296.102.12.2.2.5.5.3
		sleV2IgsPortNotifications OBJECT IDENTIFIER ::= { sleV2IgsPort 3 }

		
--  1.3.6.1.4.1.6296.102.12.2.2.5.5.3.1
		sleV2IgsPortrofileChanged NOTIFICATION-TYPE
			OBJECTS { sleV2IgsPortControlRequest, sleV2IgsPortControlTimeStamp, sleV2IgsPortControlReqResult, sleV2IgsPortFastLeave }
			STATUS current
			DESCRIPTION 
				"Description."
			::= { sleV2IgsPortNotifications 1 }

		
--  1.3.6.1.4.1.6296.102.12.2.2.5.5.3.2
		sleV2IgsPortExplicitTrackingMaxHostsChanged NOTIFICATION-TYPE
			OBJECTS { sleV2IgsPortControlRequest, sleV2IgsPortControlTimeStamp, sleV2IgsPortControlReqResult, sleV2IgsPortControlIndex, sleV2IgsPortControlExplicitTrackingMaxHosts
				 }
			STATUS current
			DESCRIPTION 
				"Description."
			::= { sleV2IgsPortNotifications 2 }

		
		sleV2IgsPortExplicitTrackingMacBasedChanged NOTIFICATION-TYPE
			OBJECTS { sleV2IgsPortControlRequest, sleV2IgsPortControlTimeStamp, sleV2IgsPortControlReqResult, sleV2IgsPortControlIndex, sleV2IgsPortControlExplicitTrackingMacBased
				 }
			STATUS current
			DESCRIPTION 
				"Description."
			::= { sleV2IgsPortNotifications 3 }

		
		sleV2IgsPortDot1qChanged NOTIFICATION-TYPE
			OBJECTS { sleV2IgsPortControlRequest, sleV2IgsPortControlTimeStamp, sleV2IgsPortControlReqResult, sleV2IgsPortControlIndex, sleV2IgsPortControlDot1qSelection
				 }
			STATUS current
			DESCRIPTION 
				"Description."
			::= { sleV2IgsPortNotifications 4 }

		
--  1.3.6.1.4.1.6296.102.12.2.2.5.5.3.1
		sleV2IgsPortMrouterchanged NOTIFICATION-TYPE
			OBJECTS { sleV2IgsPortControlRequest, sleV2IgsPortControlTimeStamp, sleV2IgsPortControlReqResult, sleV2IgsPortControlIndex, sleV2IgsPortControlMrouter
				 }
			STATUS current
			DESCRIPTION 
				"setIgsMrouter"
			::= { sleV2IgsPortNotifications 5 }

		
--  1.3.6.1.4.1.6296.102.12.2.2.5.6
		sleV2IgsPortStats OBJECT IDENTIFIER ::= { sleV2IgmpSnooping 6 }

		
--  1.3.6.1.4.1.6296.102.12.2.2.5.6.1
		sleV2IgsStatsTable OBJECT-TYPE
			SYNTAX SEQUENCE OF SleV2IgsStatsEntry
			MAX-ACCESS not-accessible
			STATUS current
			DESCRIPTION
				"IGS stats table."
			::= { sleV2IgsPortStats 1 }

		
--  1.3.6.1.4.1.6296.102.12.2.2.5.6.1.1
		sleV2IgsStatsEntry OBJECT-TYPE
			SYNTAX SleV2IgsStatsEntry
			MAX-ACCESS not-accessible
			STATUS current
			DESCRIPTION
				"key: sleV2IgsPortIndex"
			INDEX { sleV2IgsPortIndex }
			::= { sleV2IgsStatsTable 1 }

		
		SleV2IgsStatsEntry ::=
			SEQUENCE { 
				sleV2IgsStatsPortIndex
					INTEGER,
				sleV2IgsStatsTxGeneralQueries
					Unsigned32,
				sleV2IgsStatsTxGroupSpecificQueies
					Unsigned32,
				sleV2IgsStatsTxReports
					Unsigned32,
				sleV2IgsStatsTxLeaves
					Unsigned32,
				sleV2IgsStatsRxGeneralQueries
					Unsigned32,
				sleV2IgsStatsRxGroupSpecificQueies
					Unsigned32,
				sleV2IgsStatsRxReports
					Unsigned32,
				sleV2IgsStatsRxLeaves
					Unsigned32,
				sleV2IgsStatsRxValidPackets
					Unsigned32,
				sleV2IgsStatsRxInvalidPackets
					Unsigned32,
				sleV2IgsStatsRxOtherPackets
					Unsigned32,
				sleV2IgsStatsRxMacGeneralQueries
					Unsigned32,
				sleV2IgsStatsRxTopoNotifications
					Unsigned32,
				sleV2IgsStatsv3Allows
					Unsigned32,
				sleV2IgsStatsv3Blocks
					Unsigned32,
				sleV2IgsStatsv3IsIncluded
					Unsigned32,
				sleV2IgsStatsv3IsExcluded
					Unsigned32,
				sleV2IgsStatsv3ToIncluded
					Unsigned32,
				sleV2IgsStatsv3ToExcluded
					Unsigned32,
				sleV2IgsStatsRxFilteredPackets
					Unsigned32
			 }

--  1.3.6.1.4.1.6296.102.12.2.2.5.6.1.1.1
		sleV2IgsStatsPortIndex OBJECT-TYPE
			SYNTAX INTEGER (1..512)
			MAX-ACCESS read-only
			STATUS current
			DESCRIPTION
				"The Port index to access IGS IGMP Snooping Statistics Information"
			::= { sleV2IgsStatsEntry 1 }

		
--  1.3.6.1.4.1.6296.102.12.2.2.5.6.1.1.2
		sleV2IgsStatsTxGeneralQueries OBJECT-TYPE
			SYNTAX Unsigned32
			MAX-ACCESS read-only
			STATUS current
			DESCRIPTION
				"The count of sending the General Query Messages to the specific port"
			::= { sleV2IgsStatsEntry 2 }

		
--  1.3.6.1.4.1.6296.102.12.2.2.5.6.1.1.3
		sleV2IgsStatsTxGroupSpecificQueies OBJECT-TYPE
			SYNTAX Unsigned32
			MAX-ACCESS read-only
			STATUS current
			DESCRIPTION
				"The count of sending the Group Specific Query Messages to the specific port"
			::= { sleV2IgsStatsEntry 3 }

		
--  1.3.6.1.4.1.6296.102.12.2.2.5.6.1.1.4
		sleV2IgsStatsTxReports OBJECT-TYPE
			SYNTAX Unsigned32
			MAX-ACCESS read-only
			STATUS current
			DESCRIPTION
				"The count of sending the Membership Report Messages to the secific port"
			::= { sleV2IgsStatsEntry 4 }

		
--  1.3.6.1.4.1.6296.102.12.2.2.5.6.1.1.5
		sleV2IgsStatsTxLeaves OBJECT-TYPE
			SYNTAX Unsigned32
			MAX-ACCESS read-only
			STATUS current
			DESCRIPTION
				"The count of sending the Leave Membership Messages to the specific port"
			::= { sleV2IgsStatsEntry 5 }

		
--  1.3.6.1.4.1.6296.102.12.2.2.5.6.1.1.6
		sleV2IgsStatsRxGeneralQueries OBJECT-TYPE
			SYNTAX Unsigned32
			MAX-ACCESS read-only
			STATUS current
			DESCRIPTION
				"The count of receiving the General Query Messages from the specific port"
			::= { sleV2IgsStatsEntry 6 }

		
--  1.3.6.1.4.1.6296.102.12.2.2.5.6.1.1.7
		sleV2IgsStatsRxGroupSpecificQueies OBJECT-TYPE
			SYNTAX Unsigned32
			MAX-ACCESS read-only
			STATUS current
			DESCRIPTION
				"The count of receiving the Group Specific Query Messages from the specific port"
			::= { sleV2IgsStatsEntry 7 }

		
--  1.3.6.1.4.1.6296.102.12.2.2.5.6.1.1.8
		sleV2IgsStatsRxReports OBJECT-TYPE
			SYNTAX Unsigned32
			MAX-ACCESS read-only
			STATUS current
			DESCRIPTION
				"The count of recieving the Membership Report Messages from the specific ports"
			::= { sleV2IgsStatsEntry 8 }

		
--  1.3.6.1.4.1.6296.102.12.2.2.5.6.1.1.9
		sleV2IgsStatsRxLeaves OBJECT-TYPE
			SYNTAX Unsigned32
			MAX-ACCESS read-only
			STATUS current
			DESCRIPTION
				"The count of receiving the Leave Membership Messages from the specific port"
			::= { sleV2IgsStatsEntry 9 }

		
--  1.3.6.1.4.1.6296.102.12.2.2.5.6.1.1.10
		sleV2IgsStatsRxValidPackets OBJECT-TYPE
			SYNTAX Unsigned32
			MAX-ACCESS read-only
			STATUS current
			DESCRIPTION
				"The count of receiving the valid IGMP Packets from the specific port"
			::= { sleV2IgsStatsEntry 10 }

		
--  1.3.6.1.4.1.6296.102.12.2.2.5.6.1.1.11
		sleV2IgsStatsRxInvalidPackets OBJECT-TYPE
			SYNTAX Unsigned32
			MAX-ACCESS read-only
			STATUS current
			DESCRIPTION
				"The count of receiving the Invalid Packets from the specific port"
			::= { sleV2IgsStatsEntry 11 }

		
--  1.3.6.1.4.1.6296.102.12.2.2.5.6.1.1.12
		sleV2IgsStatsRxOtherPackets OBJECT-TYPE
			SYNTAX Unsigned32
			MAX-ACCESS read-only
			STATUS current
			DESCRIPTION
				"The count of receiving the valid IGMP Packets but not defined from the specific port"
			::= { sleV2IgsStatsEntry 12 }

		
--  1.3.6.1.4.1.6296.102.12.2.2.5.6.1.1.13
		sleV2IgsStatsRxMacGeneralQueries OBJECT-TYPE
			SYNTAX Unsigned32
			MAX-ACCESS read-only
			STATUS current
			DESCRIPTION
				"The count of receiving the MAC General Query Messages from the specific port"
			::= { sleV2IgsStatsEntry 13 }

		
--  1.3.6.1.4.1.6296.102.12.2.2.5.6.1.1.14
		sleV2IgsStatsRxTopoNotifications OBJECT-TYPE
			SYNTAX Unsigned32
			MAX-ACCESS read-only
			STATUS current
			DESCRIPTION
				"The count of receiving the Topology Change Notification Messages from the specific port"
			::= { sleV2IgsStatsEntry 14 }

		
--  1.3.6.1.4.1.6296.102.12.2.2.5.6.1.1.15
		sleV2IgsStatsv3Allows OBJECT-TYPE
			SYNTAX Unsigned32
			MAX-ACCESS read-only
			STATUS current
			DESCRIPTION
				"The count of receiving the IGMP Version-3 Allow Messages from the specific port"
			::= { sleV2IgsStatsEntry 15 }

		
--  1.3.6.1.4.1.6296.102.12.2.2.5.6.1.1.16
		sleV2IgsStatsv3Blocks OBJECT-TYPE
			SYNTAX Unsigned32
			MAX-ACCESS read-only
			STATUS current
			DESCRIPTION
				"The count of receiving the IGMP Version-3 Block Messages from the specific port"
			::= { sleV2IgsStatsEntry 16 }

		
--  1.3.6.1.4.1.6296.102.12.2.2.5.6.1.1.17
		sleV2IgsStatsv3IsIncluded OBJECT-TYPE
			SYNTAX Unsigned32
			MAX-ACCESS read-only
			STATUS current
			DESCRIPTION
				"The count of recieving the IGMP version-3 Membership Report Messages Whose Type is ISINCLUDE from the specific port"
			::= { sleV2IgsStatsEntry 17 }

		
--  1.3.6.1.4.1.6296.102.12.2.2.5.6.1.1.18
		sleV2IgsStatsv3IsExcluded OBJECT-TYPE
			SYNTAX Unsigned32
			MAX-ACCESS read-only
			STATUS current
			DESCRIPTION
				"The count of receiving the IGMP version-3 Membership Report Messages Whose type is ISEXCLUDE from the specific port"
			::= { sleV2IgsStatsEntry 18 }

		
--  1.3.6.1.4.1.6296.102.12.2.2.5.6.1.1.19
		sleV2IgsStatsv3ToIncluded OBJECT-TYPE
			SYNTAX Unsigned32
			MAX-ACCESS read-only
			STATUS current
			DESCRIPTION
				"The count of receiving the IGMP version-3 Membership Report Messages Whose type is TOINCLUDE from the specific port"
			::= { sleV2IgsStatsEntry 19 }

		
--  1.3.6.1.4.1.6296.102.12.2.2.5.6.1.1.20
		sleV2IgsStatsv3ToExcluded OBJECT-TYPE
			SYNTAX Unsigned32
			MAX-ACCESS read-only
			STATUS current
			DESCRIPTION
				"The count of receiving the IGMP version-3 Membership Report Messages Whose type is TOEXCLUDE from the specific port"
			::= { sleV2IgsStatsEntry 20 }

		
--  1.3.6.1.4.1.6296.102.12.2.2.5.6.1.1.21
		sleV2IgsStatsRxFilteredPackets OBJECT-TYPE
			SYNTAX Unsigned32
			MAX-ACCESS read-only
			STATUS current
			DESCRIPTION
				"The count of receiving the valid IGMP Packet that is blocked  by IGMP Filter from the specific port"
			::= { sleV2IgsStatsEntry 21 }

		
--  1.3.6.1.4.1.6296.102.12.2.2.5.6.2
		sleV2IgsStatsControl OBJECT IDENTIFIER ::= { sleV2IgsPortStats 2 }

		
--  1.3.6.1.4.1.6296.102.12.2.2.5.6.2.1
		sleV2IgsStatsControlRequest OBJECT-TYPE
			SYNTAX INTEGER { clearIgsStats(1) }
			MAX-ACCESS read-write
			STATUS current
			DESCRIPTION
				"The request of a user command"
			::= { sleV2IgsStatsControl 1 }

		
--  1.3.6.1.4.1.6296.102.12.2.2.5.6.2.2
		sleV2IgsStatsControlStatus OBJECT-TYPE
			SYNTAX SleControlStatusType
			MAX-ACCESS read-write
			STATUS current
			DESCRIPTION
				"The status of user command"
			::= { sleV2IgsStatsControl 2 }

		
--  1.3.6.1.4.1.6296.102.12.2.2.5.6.2.3
		sleV2IgsStatsControlControlTimer OBJECT-TYPE
			SYNTAX Gauge32
			MAX-ACCESS read-write
			STATUS current
			DESCRIPTION
				"The maximum time for the manager for a long running user command"
			::= { sleV2IgsStatsControl 3 }

		
--  1.3.6.1.4.1.6296.102.12.2.2.5.6.2.4
		sleV2IgsStatsControlTimeStamp OBJECT-TYPE
			SYNTAX TimeTicks
			MAX-ACCESS read-write
			STATUS current
			DESCRIPTION
				"The time stamp of the last command(end of command)"
			::= { sleV2IgsStatsControl 4 }

		
--  1.3.6.1.4.1.6296.102.12.2.2.5.6.2.5
		sleV2IgsStatsControlReqResult OBJECT-TYPE
			SYNTAX SleControlRequestResultType
			MAX-ACCESS read-write
			STATUS current
			DESCRIPTION
				"The result of the last user command
				"
			::= { sleV2IgsStatsControl 5 }

		
--  1.3.6.1.4.1.6296.102.12.2.2.5.6.2.6
		sleV2IgsStatsControlIndex OBJECT-TYPE
			SYNTAX Integer32
			MAX-ACCESS read-write
			STATUS current
			DESCRIPTION
				"IGS stats index."
			::= { sleV2IgsStatsControl 6 }

		
--  1.3.6.1.4.1.6296.102.12.2.2.5.6.3
		sleV2IgsStatsNotification OBJECT IDENTIFIER ::= { sleV2IgsPortStats 3 }

		
--  1.3.6.1.4.1.6296.102.12.2.2.5.6.3.1
		sleV2IgsStatsCleared NOTIFICATION-TYPE
			OBJECTS { sleV2IgsStatsControlRequest, sleV2IgsStatsControlTimeStamp, sleV2IgsStatsControlReqResult, sleV2IgsStatsPortIndex }
			STATUS current
			DESCRIPTION 
				"Description."
			::= { sleV2IgsStatsNotification 1 }

		
--  1.3.6.1.4.1.6296.102.12.2.2.5.6
		sleV2IgsVlanStats OBJECT IDENTIFIER ::= { sleV2IgmpSnooping 7 }

		
--  1.3.6.1.4.1.6296.102.12.2.2.5.6.1
		sleV2IgsVlanStatsTable OBJECT-TYPE
			SYNTAX SEQUENCE OF SleV2IgsVlanStatsEntry
			MAX-ACCESS not-accessible
			STATUS current
			DESCRIPTION
				"IGS stats table."
			::= { sleV2IgsVlanStats 1 }

		
--  1.3.6.1.4.1.6296.102.12.2.2.5.6.1.1
		sleV2IgsVlanStatsEntry OBJECT-TYPE
			SYNTAX SleV2IgsVlanStatsEntry
			MAX-ACCESS not-accessible
			STATUS current
			DESCRIPTION
				"key: sleV2IgsPortIndex"
			INDEX { sleV2IgsVlanStatsVlanIndex }
			::= { sleV2IgsVlanStatsTable 1 }

		
		SleV2IgsVlanStatsEntry ::=
			SEQUENCE { 
				sleV2IgsVlanStatsVlanIndex
					INTEGER,
				sleV2IgsVlanStatsTxGeneralQueries
					Unsigned32,
				sleV2IgsVlanStatsTxGroupSpecificQueies
					Unsigned32,
				sleV2IgsVlanStatsTxReports
					Unsigned32,
				sleV2IgsVlanStatsTxLeaves
					Unsigned32,
				sleV2IgsVlanStatsRxGeneralQueries
					Unsigned32,
				sleV2IgsVlanStatsRxGroupSpecificQueies
					Unsigned32,
				sleV2IgsVlanStatsRxReports
					Unsigned32,
				sleV2IgsVlanStatsRxLeaves
					Unsigned32,
				sleV2IgsVlanStatsRxValidPackets
					Unsigned32,
				sleV2IgsVlanStatsRxInvalidPackets
					Unsigned32,
				sleV2IgsVlanStatsRxOtherPackets
					Unsigned32,
				sleV2IgsVlanStatsRxMacGeneralQueries
					Unsigned32,
				sleV2IgsVlanStatsRxTopoNotifications
					Unsigned32,
				sleV2IgsVlanStatsv3Allows
					Unsigned32,
				sleV2IgsVlanStatsv3Blocks
					Unsigned32,
				sleV2IgsVlanStatsv3IsIncluded
					Unsigned32,
				sleV2IgsVlanStatsv3IsExcluded
					Unsigned32,
				sleV2IgsVlanStatsv3ToIncluded
					Unsigned32,
				sleV2IgsVlanStatsv3ToExcluded
					Unsigned32,
				sleV2IgsVlanStatsRxFilteredPackets
					Unsigned32,
				sleV2IgsVlanStatsTotalRxReports
					Unsigned32,
				sleV2IgsVlanStatsUnsuccessRxReports
					Unsigned32
			 }

--  1.3.6.1.4.1.6296.102.12.2.2.5.6.1.1.1
		sleV2IgsVlanStatsVlanIndex OBJECT-TYPE
			SYNTAX INTEGER (1..512)
			MAX-ACCESS read-only
			STATUS current
			DESCRIPTION
				"The Port index to access IGS IGMP Snooping Statistics Information"
			::= { sleV2IgsVlanStatsEntry 1 }

		
--  1.3.6.1.4.1.6296.102.12.2.2.5.6.1.1.2
		sleV2IgsVlanStatsTxGeneralQueries OBJECT-TYPE
			SYNTAX Unsigned32
			MAX-ACCESS read-only
			STATUS current
			DESCRIPTION
				"The count of sending the General Query Messages to the specific port"
			::= { sleV2IgsVlanStatsEntry 2 }

		
--  1.3.6.1.4.1.6296.102.12.2.2.5.6.1.1.3
		sleV2IgsVlanStatsTxGroupSpecificQueies OBJECT-TYPE
			SYNTAX Unsigned32
			MAX-ACCESS read-only
			STATUS current
			DESCRIPTION
				"The count of sending the Group Specific Query Messages to the specific port"
			::= { sleV2IgsVlanStatsEntry 3 }

		
--  1.3.6.1.4.1.6296.102.12.2.2.5.6.1.1.4
		sleV2IgsVlanStatsTxReports OBJECT-TYPE
			SYNTAX Unsigned32
			MAX-ACCESS read-only
			STATUS current
			DESCRIPTION
				"The count of sending the Membership Report Messages to the secific port"
			::= { sleV2IgsVlanStatsEntry 4 }

		
--  1.3.6.1.4.1.6296.102.12.2.2.5.6.1.1.5
		sleV2IgsVlanStatsTxLeaves OBJECT-TYPE
			SYNTAX Unsigned32
			MAX-ACCESS read-only
			STATUS current
			DESCRIPTION
				"The count of sending the Leave Membership Messages to the specific port"
			::= { sleV2IgsVlanStatsEntry 5 }

		
--  1.3.6.1.4.1.6296.102.12.2.2.5.6.1.1.6
		sleV2IgsVlanStatsRxGeneralQueries OBJECT-TYPE
			SYNTAX Unsigned32
			MAX-ACCESS read-only
			STATUS current
			DESCRIPTION
				"The count of receiving the General Query Messages from the specific port"
			::= { sleV2IgsVlanStatsEntry 6 }

		
--  1.3.6.1.4.1.6296.102.12.2.2.5.6.1.1.7
		sleV2IgsVlanStatsRxGroupSpecificQueies OBJECT-TYPE
			SYNTAX Unsigned32
			MAX-ACCESS read-only
			STATUS current
			DESCRIPTION
				"The count of receiving the Group Specific Query Messages from the specific port"
			::= { sleV2IgsVlanStatsEntry 7 }

		
--  1.3.6.1.4.1.6296.102.12.2.2.5.6.1.1.8
		sleV2IgsVlanStatsRxReports OBJECT-TYPE
			SYNTAX Unsigned32
			MAX-ACCESS read-only
			STATUS current
			DESCRIPTION
				"The count of recieving the Membership Report Messages from the specific ports. (SuccessRxReports)"
			::= { sleV2IgsVlanStatsEntry 8 }

		
--  1.3.6.1.4.1.6296.102.12.2.2.5.6.1.1.9
		sleV2IgsVlanStatsRxLeaves OBJECT-TYPE
			SYNTAX Unsigned32
			MAX-ACCESS read-only
			STATUS current
			DESCRIPTION
				"The count of receiving the Leave Membership Messages from the specific port"
			::= { sleV2IgsVlanStatsEntry 9 }

		
--  1.3.6.1.4.1.6296.102.12.2.2.5.6.1.1.10
		sleV2IgsVlanStatsRxValidPackets OBJECT-TYPE
			SYNTAX Unsigned32
			MAX-ACCESS read-only
			STATUS current
			DESCRIPTION
				"The count of receiving the valid IGMP Packets from the specific port"
			::= { sleV2IgsVlanStatsEntry 10 }

		
--  1.3.6.1.4.1.6296.102.12.2.2.5.6.1.1.11
		sleV2IgsVlanStatsRxInvalidPackets OBJECT-TYPE
			SYNTAX Unsigned32
			MAX-ACCESS read-only
			STATUS current
			DESCRIPTION
				"The count of receiving the Invalid Packets from the specific port"
			::= { sleV2IgsVlanStatsEntry 11 }

		
--  1.3.6.1.4.1.6296.102.12.2.2.5.6.1.1.12
		sleV2IgsVlanStatsRxOtherPackets OBJECT-TYPE
			SYNTAX Unsigned32
			MAX-ACCESS read-only
			STATUS current
			DESCRIPTION
				"The count of receiving the valid IGMP Packets but not defined from the specific port"
			::= { sleV2IgsVlanStatsEntry 12 }

		
--  1.3.6.1.4.1.6296.102.12.2.2.5.6.1.1.13
		sleV2IgsVlanStatsRxMacGeneralQueries OBJECT-TYPE
			SYNTAX Unsigned32
			MAX-ACCESS read-only
			STATUS current
			DESCRIPTION
				"The count of receiving the MAC General Query Messages from the specific port"
			::= { sleV2IgsVlanStatsEntry 13 }

		
--  1.3.6.1.4.1.6296.102.12.2.2.5.6.1.1.14
		sleV2IgsVlanStatsRxTopoNotifications OBJECT-TYPE
			SYNTAX Unsigned32
			MAX-ACCESS read-only
			STATUS current
			DESCRIPTION
				"The count of receiving the Topology Change Notification Messages from the specific port"
			::= { sleV2IgsVlanStatsEntry 14 }

		
--  1.3.6.1.4.1.6296.102.12.2.2.5.6.1.1.15
		sleV2IgsVlanStatsv3Allows OBJECT-TYPE
			SYNTAX Unsigned32
			MAX-ACCESS read-only
			STATUS current
			DESCRIPTION
				"The count of receiving the IGMP Version-3 Allow Messages from the specific port"
			::= { sleV2IgsVlanStatsEntry 15 }

		
--  1.3.6.1.4.1.6296.102.12.2.2.5.6.1.1.16
		sleV2IgsVlanStatsv3Blocks OBJECT-TYPE
			SYNTAX Unsigned32
			MAX-ACCESS read-only
			STATUS current
			DESCRIPTION
				"The count of receiving the IGMP Version-3 Block Messages from the specific port"
			::= { sleV2IgsVlanStatsEntry 16 }

		
--  1.3.6.1.4.1.6296.102.12.2.2.5.6.1.1.17
		sleV2IgsVlanStatsv3IsIncluded OBJECT-TYPE
			SYNTAX Unsigned32
			MAX-ACCESS read-only
			STATUS current
			DESCRIPTION
				"The count of recieving the IGMP version-3 Membership Report Messages Whose Type is ISINCLUDE from the specific port"
			::= { sleV2IgsVlanStatsEntry 17 }

		
--  1.3.6.1.4.1.6296.102.12.2.2.5.6.1.1.18
		sleV2IgsVlanStatsv3IsExcluded OBJECT-TYPE
			SYNTAX Unsigned32
			MAX-ACCESS read-only
			STATUS current
			DESCRIPTION
				"The count of receiving the IGMP version-3 Membership Report Messages Whose type is ISEXCLUDE from the specific port"
			::= { sleV2IgsVlanStatsEntry 18 }

		
--  1.3.6.1.4.1.6296.102.12.2.2.5.6.1.1.19
		sleV2IgsVlanStatsv3ToIncluded OBJECT-TYPE
			SYNTAX Unsigned32
			MAX-ACCESS read-only
			STATUS current
			DESCRIPTION
				"The count of receiving the IGMP version-3 Membership Report Messages Whose type is TOINCLUDE from the specific port"
			::= { sleV2IgsVlanStatsEntry 19 }

		
--  1.3.6.1.4.1.6296.102.12.2.2.5.6.1.1.20
		sleV2IgsVlanStatsv3ToExcluded OBJECT-TYPE
			SYNTAX Unsigned32
			MAX-ACCESS read-only
			STATUS current
			DESCRIPTION
				"The count of receiving the IGMP version-3 Membership Report Messages Whose type is TOEXCLUDE from the specific port"
			::= { sleV2IgsVlanStatsEntry 20 }

		
--  1.3.6.1.4.1.6296.102.12.2.2.5.6.1.1.21
		sleV2IgsVlanStatsRxFilteredPackets OBJECT-TYPE
			SYNTAX Unsigned32
			MAX-ACCESS read-only
			STATUS current
			DESCRIPTION
				"The count of receiving the valid IGMP Packet that is blocked  by IGMP Filter from the specific port"
			::= { sleV2IgsVlanStatsEntry 21 }

		
		sleV2IgsVlanStatsTotalRxReports OBJECT-TYPE
			SYNTAX Unsigned32
			MAX-ACCESS read-only
			STATUS current
			DESCRIPTION
				"Total RX reports."
			::= { sleV2IgsVlanStatsEntry 22 }

		
		sleV2IgsVlanStatsUnsuccessRxReports OBJECT-TYPE
			SYNTAX Unsigned32
			MAX-ACCESS read-only
			STATUS current
			DESCRIPTION
				"Total RX reports."
			::= { sleV2IgsVlanStatsEntry 23 }

		
--  1.3.6.1.4.1.6296.102.12.2.2.5.6.2
		sleV2IgsVlanStatsControl OBJECT IDENTIFIER ::= { sleV2IgsVlanStats 2 }

		
--  1.3.6.1.4.1.6296.102.12.2.2.5.6.2.1
		sleV2IgsVlanStatsControlRequest OBJECT-TYPE
			SYNTAX INTEGER { clearIgsVlanStats(1) }
			MAX-ACCESS read-write
			STATUS current
			DESCRIPTION
				"The request of a user command"
			::= { sleV2IgsVlanStatsControl 1 }

		
--  1.3.6.1.4.1.6296.102.12.2.2.5.6.2.2
		sleV2IgsVlanStatsControlStatus OBJECT-TYPE
			SYNTAX SleControlStatusType
			MAX-ACCESS read-write
			STATUS current
			DESCRIPTION
				"The status of user command"
			::= { sleV2IgsVlanStatsControl 2 }

		
--  1.3.6.1.4.1.6296.102.12.2.2.5.6.2.3
		sleV2IgsVlanStatsControlControlTimer OBJECT-TYPE
			SYNTAX Gauge32
			MAX-ACCESS read-write
			STATUS current
			DESCRIPTION
				"The maximum time for the manager for a long running user command"
			::= { sleV2IgsVlanStatsControl 3 }

		
--  1.3.6.1.4.1.6296.102.12.2.2.5.6.2.4
		sleV2IgsVlanStatsControlTimeStamp OBJECT-TYPE
			SYNTAX TimeTicks
			MAX-ACCESS read-write
			STATUS current
			DESCRIPTION
				"The time stamp of the last command(end of command)"
			::= { sleV2IgsVlanStatsControl 4 }

		
--  1.3.6.1.4.1.6296.102.12.2.2.5.6.2.5
		sleV2IgsVlanStatsControlReqResult OBJECT-TYPE
			SYNTAX SleControlRequestResultType
			MAX-ACCESS read-write
			STATUS current
			DESCRIPTION
				"The result of the last user command
				"
			::= { sleV2IgsVlanStatsControl 5 }

		
--  1.3.6.1.4.1.6296.102.12.2.2.5.6.2.6
		sleV2IgsVlanStatsControlIndex OBJECT-TYPE
			SYNTAX Integer32
			MAX-ACCESS read-write
			STATUS current
			DESCRIPTION
				"IGS stats index."
			::= { sleV2IgsVlanStatsControl 6 }

		
--  1.3.6.1.4.1.6296.102.12.2.2.5.6.3
		sleV2IgsVlanStatsNotification OBJECT IDENTIFIER ::= { sleV2IgsVlanStats 3 }

		
--  1.3.6.1.4.1.6296.102.12.2.2.5.6.3.1
		sleV2IgsVlanStatsCleared NOTIFICATION-TYPE
			OBJECTS { sleV2IgsVlanStatsControlRequest, sleV2IgsVlanStatsControlTimeStamp, sleV2IgsVlanStatsControlReqResult, sleV2IgsVlanStatsControlIndex }
			STATUS current
			DESCRIPTION 
				"Description."
			::= { sleV2IgsVlanStatsNotification 1 }

		
--  IGMP Filter
		sleV2IgmpFilter OBJECT IDENTIFIER ::= { sleV2Igmp 6 }

		
--  IGMP Profile
-- 1.3.6.1.4.1.6296.102.12.2.2.6.1
		sleV2IgfProfile OBJECT IDENTIFIER ::= { sleV2IgmpFilter 1 }

		
--  IGMP Profile Table
-- 1.3.6.1.4.1.6296.102.12.2.2.6.1.1
		sleV2IgfProfileTable OBJECT-TYPE
			SYNTAX SEQUENCE OF SleV2IgfProfileEntry
			MAX-ACCESS not-accessible
			STATUS current
			DESCRIPTION
				" IGF profile table."
			::= { sleV2IgfProfile 1 }

		
--  IGMP Profile Entry
-- 1.3.6.1.4.1.6296.102.12.2.2.6.1.1.1
		sleV2IgfProfileEntry OBJECT-TYPE
			SYNTAX SleV2IgfProfileEntry
			MAX-ACCESS not-accessible
			STATUS current
			DESCRIPTION
				"key: sleV2IgfProfileIndex"
			INDEX { sleV2IgfProfileIndex }
			::= { sleV2IgfProfileTable 1 }

		
		SleV2IgfProfileEntry ::=
			SEQUENCE { 
				sleV2IgfProfileIndex
					INTEGER,
				sleV2IgfProfilePermission
					INTEGER,
				sleV2IgfProfileName
					OCTET STRING
			 }

--  1.3.6.1.4.1.6296.102.12.2.2.6.1.1.1.1
		sleV2IgfProfileIndex OBJECT-TYPE
			SYNTAX INTEGER (1..2147483647)
			MAX-ACCESS read-only
			STATUS current
			DESCRIPTION
				" Unique index of IGMP profile"
			::= { sleV2IgfProfileEntry 1 }

		
--  1.3.6.1.4.1.6296.102.12.2.2.6.1.1.1.2
		sleV2IgfProfilePermission OBJECT-TYPE
			SYNTAX INTEGER
				{
				permit(1),
				deny(2)
				}
			MAX-ACCESS read-only
			STATUS current
			DESCRIPTION
				" It is a policy (permission) of the IGMP profile."
			::= { sleV2IgfProfileEntry 2 }

		
--  1.3.6.1.4.1.6296.102.12.2.2.6.1.1.1.3
		sleV2IgfProfileName OBJECT-TYPE
			SYNTAX OCTET STRING
			MAX-ACCESS read-only
			STATUS current
			DESCRIPTION
				"Name of IGMP profile"
			::= { sleV2IgfProfileEntry 3 }

		
--  IGMP Profile Control
-- 1.3.6.1.4.1.6296.102.12.2.2.6.1.2
		sleV2IgfProfileControl OBJECT IDENTIFIER ::= { sleV2IgfProfile 2 }

		
--  1.3.6.1.4.1.6296.102.12.2.2.6.1.2.1
		sleV2IgfProfileControlRequest OBJECT-TYPE
			SYNTAX INTEGER
				{
				createIgmpProfile(1),
				destroyIgmpProfile(2),
				setIgmpProfile(3),
				createIgmpProfileByName(4)
				}
			MAX-ACCESS read-write
			STATUS current
			DESCRIPTION
				" The request of a user command"
			::= { sleV2IgfProfileControl 1 }

		
--  1.3.6.1.4.1.6296.102.12.2.2.6.1.2.2
		sleV2IgfProfileControlStatus OBJECT-TYPE
			SYNTAX SleControlStatusType
			MAX-ACCESS read-only
			STATUS current
			DESCRIPTION
				" The status of user command"
			::= { sleV2IgfProfileControl 2 }

		
--  1.3.6.1.4.1.6296.102.12.2.2.6.1.2.3
		sleV2IgfProfileControlTimer OBJECT-TYPE
			SYNTAX Gauge32
			MAX-ACCESS read-write
			STATUS current
			DESCRIPTION
				" The maximum time for the manager for a long running user command"
			::= { sleV2IgfProfileControl 3 }

		
--  1.3.6.1.4.1.6296.102.12.2.2.6.1.2.4
		sleV2IgfProfileControlTimeStamp OBJECT-TYPE
			SYNTAX TimeStamp
			MAX-ACCESS read-only
			STATUS current
			DESCRIPTION
				" The time stamp of the last command(end of command)"
			::= { sleV2IgfProfileControl 4 }

		
--  1.3.6.1.4.1.6296.102.12.2.2.6.1.2.5
		sleV2IgfProfileControlReqResult OBJECT-TYPE
			SYNTAX SleControlRequestResultType
			MAX-ACCESS read-only
			STATUS current
			DESCRIPTION
				" The result of the last user command
				"
			::= { sleV2IgfProfileControl 5 }

		
--  1.3.6.1.4.1.6296.102.12.2.2.6.1.2.6
		sleV2IgfProfileControlIndex OBJECT-TYPE
			SYNTAX Unsigned32
			MAX-ACCESS read-write
			STATUS current
			DESCRIPTION
				"CLI : (no) ip igmp profile <1-4294967295>
				value(0) : (no)"
			::= { sleV2IgfProfileControl 6 }

		
--  1.3.6.1.4.1.6296.102.12.2.2.6.1.2.7
		sleV2IgfProfileControlPermission OBJECT-TYPE
			SYNTAX INTEGER
				{
				permit(1),
				deny(2)
				}
			MAX-ACCESS read-write
			STATUS current
			DESCRIPTION
				"CLI : permit
				deny"
			DEFVAL { 1 }
			::= { sleV2IgfProfileControl 7 }

		
--  1.3.6.1.4.1.6296.102.12.2.2.6.1.2.8
		sleV2IgfProfileControlName OBJECT-TYPE
			SYNTAX OCTET STRING
			MAX-ACCESS read-write
			STATUS current
			DESCRIPTION
				"Name of IGMP profile
				(Supported only model 5924N)
				"
			::= { sleV2IgfProfileControl 8 }

		
--  IGMP Profile Notification
-- 1.3.6.1.4.1.6296.102.12.2.2.6.1.3
		sleV2IgfProfileNotification OBJECT IDENTIFIER ::= { sleV2IgfProfile 3 }

		
--  1.3.6.1.4.1.6296.102.12.2.2.6.1.3.1
		sleV2IgfProfileCreated NOTIFICATION-TYPE
			OBJECTS { sleV2IgfProfileControlRequest, sleV2IgfProfileControlReqResult, sleV2IgfProfileControlTimeStamp, sleV2IgfProfilePermission }
			STATUS current
			DESCRIPTION 
				" "
			::= { sleV2IgfProfileNotification 1 }

		
--  1.3.6.1.4.1.6296.102.12.2.2.6.1.3.2
		sleV2IgfProfileDestroyed NOTIFICATION-TYPE
			OBJECTS { sleV2IgfProfileControlRequest, sleV2IgfProfileControlReqResult, sleV2IgfProfileControlTimeStamp, sleV2IgfProfilePermission }
			STATUS current
			DESCRIPTION 
				"Description."
			::= { sleV2IgfProfileNotification 2 }

		
--  1.3.6.1.4.1.6296.102.12.2.2.6.1.3.3
		sleV2IgfProfileChanged NOTIFICATION-TYPE
			OBJECTS { sleV2IgfProfileControlRequest, sleV2IgfProfileControlReqResult, sleV2IgfProfileControlTimeStamp, sleV2IgfProfilePermission }
			STATUS current
			DESCRIPTION 
				"Description."
			::= { sleV2IgfProfileNotification 3 }

		
--  1.3.6.1.4.1.6296.102.12.2.2.6.1.3.4
		sleV2IgfProfileByNameCreated NOTIFICATION-TYPE
			OBJECTS { sleV2IgfProfileControlRequest, sleV2IgfProfileControlTimeStamp, sleV2IgfProfileControlReqResult, sleV2IgfProfilePermission, sleV2IgfProfileName
				 }
			STATUS current
			DESCRIPTION 
				"Description."
			::= { sleV2IgfProfileNotification 4 }

		
--  IGMP Profile Range
-- 1.3.6.1.4.1.6296.102.12.2.2.6.2
		sleV2IgfpRange OBJECT IDENTIFIER ::= { sleV2IgmpFilter 2 }

		
--  IGMP Profile Range Table
-- 1.3.6.1.4.1.6296.102.12.2.2.6.2.1
		sleV2IgfpRangeTable OBJECT-TYPE
			SYNTAX SEQUENCE OF SleV2IgfpRangeEntry
			MAX-ACCESS not-accessible
			STATUS current
			DESCRIPTION
				"IGFP ranger talbe."
			::= { sleV2IgfpRange 1 }

		
--  IGMP Profile Range Entry
-- 1.3.6.1.4.1.6296.102.12.2.2.6.2.1.1
		sleV2IgfpRangeEntry OBJECT-TYPE
			SYNTAX SleV2IgfpRangeEntry
			MAX-ACCESS not-accessible
			STATUS current
			DESCRIPTION
				"key: sleV2IgfProfileIndex, sleV2IgfpRangeStartAddress, sleV2IgfpRangeEndAddress"
			INDEX { sleV2IgfProfileIndex, sleV2IgfpRangeStartAddress, sleV2IgfpRangeEndAddress }
			::= { sleV2IgfpRangeTable 1 }

		
		SleV2IgfpRangeEntry ::=
			SEQUENCE { 
				sleV2IgfpRangeStartAddress
					IpAddress,
				sleV2IgfpRangeEndAddress
					IpAddress
			 }

--  1.3.6.1.4.1.6296.102.12.2.2.6.2.1.1.1
		sleV2IgfpRangeStartAddress OBJECT-TYPE
			SYNTAX IpAddress
			MAX-ACCESS read-only
			STATUS current
			DESCRIPTION
				" Start IP multicast address in a range of IGMP profile."
			::= { sleV2IgfpRangeEntry 1 }

		
--  1.3.6.1.4.1.6296.102.12.2.2.6.2.1.1.2
		sleV2IgfpRangeEndAddress OBJECT-TYPE
			SYNTAX IpAddress
			MAX-ACCESS read-only
			STATUS current
			DESCRIPTION
				"End IP multicast address in a range of IGMP profile."
			::= { sleV2IgfpRangeEntry 2 }

		
--  IGMP Profile Range Control
-- 1.3.6.1.4.1.6296.102.12.2.2.6.2.2
		sleV2IgfpRangeControl OBJECT IDENTIFIER ::= { sleV2IgfpRange 2 }

		
--  1.3.6.1.4.1.6296.102.12.2.2.6.2.2.1
		sleV2IgfpRangeControlRequest OBJECT-TYPE
			SYNTAX INTEGER
				{
				addIgmpProfileRange(1),
				delIgmpProfileRange(2)
				}
			MAX-ACCESS read-write
			STATUS current
			DESCRIPTION
				" The request of a user command"
			::= { sleV2IgfpRangeControl 1 }

		
--  1.3.6.1.4.1.6296.102.12.2.2.6.2.2.2
		sleV2IgfpRangeControlStatus OBJECT-TYPE
			SYNTAX SleControlStatusType
			MAX-ACCESS read-only
			STATUS current
			DESCRIPTION
				" The status of user command"
			::= { sleV2IgfpRangeControl 2 }

		
--  1.3.6.1.4.1.6296.102.12.2.2.6.2.2.3
		sleV2IgfpRangeControlTimer OBJECT-TYPE
			SYNTAX Gauge32
			MAX-ACCESS read-write
			STATUS current
			DESCRIPTION
				" The maximum time for the manager for a long running user command"
			::= { sleV2IgfpRangeControl 3 }

		
--  1.3.6.1.4.1.6296.102.12.2.2.6.2.2.4
		sleV2IgfpRangeControlTimeStamp OBJECT-TYPE
			SYNTAX TimeStamp
			MAX-ACCESS read-only
			STATUS current
			DESCRIPTION
				" The time stamp of the last command(end of command)"
			::= { sleV2IgfpRangeControl 4 }

		
--  1.3.6.1.4.1.6296.102.12.2.2.6.2.2.5
		sleV2IgfpRangeControlReqResult OBJECT-TYPE
			SYNTAX SleControlRequestResultType
			MAX-ACCESS read-only
			STATUS current
			DESCRIPTION
				" The result of the last user command"
			::= { sleV2IgfpRangeControl 5 }

		
--  1.3.6.1.4.1.6296.102.12.2.2.6.2.2.6
		sleV2IgfpRangeControlProfileIndex OBJECT-TYPE
			SYNTAX Unsigned32
			MAX-ACCESS read-write
			STATUS current
			DESCRIPTION
				"CLI : (no) ip igmp profile <1-4294967295>
				value(0) : (no)"
			::= { sleV2IgfpRangeControl 6 }

		
--  1.3.6.1.4.1.6296.102.12.2.2.6.2.2.7
		sleV2IgfpRangeControlStartAddress OBJECT-TYPE
			SYNTAX IpAddress
			MAX-ACCESS read-write
			STATUS current
			DESCRIPTION
				"CLI : range A.B.C.D A.B.C.D"
			::= { sleV2IgfpRangeControl 7 }

		
--  1.3.6.1.4.1.6296.102.12.2.2.6.2.2.8
		sleV2IgfpRangeControlEndAddress OBJECT-TYPE
			SYNTAX IpAddress
			MAX-ACCESS read-write
			STATUS current
			DESCRIPTION
				"CLI : range A.B.C.D A.B.C.D"
			::= { sleV2IgfpRangeControl 8 }

		
--  IGMP Profile Range Notification
-- 1.3.6.1.4.1.6296.102.12.2.2.6.2.3
		sleV2IgfpRangeNotification OBJECT IDENTIFIER ::= { sleV2IgfpRange 3 }

		
--  1.3.6.1.4.1.6296.102.12.2.2.6.2.3.1
		sleV2IgfpRangeAdded NOTIFICATION-TYPE
			OBJECTS { sleV2IgfpRangeControlRequest, sleV2IgfpRangeControlReqResult, sleV2IgfpRangeControlTimeStamp, sleV2IgfpRangeControlProfileIndex, sleV2IgfpRangeControlStartAddress, 
				sleV2IgfpRangeControlEndAddress }
			STATUS current
			DESCRIPTION 
				"Description."
			::= { sleV2IgfpRangeNotification 1 }

		
--  1.3.6.1.4.1.6296.102.12.2.2.6.2.3.2
		sleV2IgfpRangeDeleted NOTIFICATION-TYPE
			OBJECTS { sleV2IgfpRangeControlRequest, sleV2IgfpRangeControlReqResult, sleV2IgfpRangeControlTimeStamp, sleV2IgfpRangeControlProfileIndex, sleV2IgfpRangeControlStartAddress, 
				sleV2IgfpRangeControlEndAddress }
			STATUS current
			DESCRIPTION 
				"Description."
			::= { sleV2IgfpRangeNotification 2 }

		
--  IGMP Filter Port
-- 1.3.6.1.4.1.6296.102.12.2.2.6.3
		sleV2IgfPort OBJECT IDENTIFIER ::= { sleV2IgmpFilter 3 }

		
--  IGMP Filter Port Table
-- 1.3.6.1.4.1.6296.102.12.2.2.6.3.1
		sleV2IgfPortTable OBJECT-TYPE
			SYNTAX SEQUENCE OF SleV2IgfPortEntry
			MAX-ACCESS not-accessible
			STATUS current
			DESCRIPTION
				" IGF port table."
			::= { sleV2IgfPort 1 }

		
--  IGMP Filter Port Entry
-- 1.3.6.1.4.1.6296.102.12.2.2.6.3.1.1
		sleV2IgfPortEntry OBJECT-TYPE
			SYNTAX SleV2IgfPortEntry
			MAX-ACCESS not-accessible
			STATUS current
			DESCRIPTION
				"key: sleV2IgfPortIndex"
			INDEX { sleV2IgfPortIndex }
			::= { sleV2IgfPortTable 1 }

		
		SleV2IgfPortEntry ::=
			SEQUENCE { 
				sleV2IgfPortIndex
					Integer32,
				sleV2IgfPortProfileIndex
					Unsigned32,
				sleV2IgfPortMaxGroupCount
					Unsigned32,
				sleV2IgfPortMaxGroupAction
					INTEGER,
				sleV2IgfPortDhcpSnoopBindingPermission
					INTEGER,
				sleV2IgfPortPacketType
					BITS
			 }

--  1.3.6.1.4.1.6296.102.12.2.2.6.3.1.1.1
		sleV2IgfPortIndex OBJECT-TYPE
			SYNTAX Integer32 (1..255)
			MAX-ACCESS read-only
			STATUS current
			DESCRIPTION
				" A port index to apply IGMP profile"
			::= { sleV2IgfPortEntry 1 }

		
--  1.3.6.1.4.1.6296.102.12.2.2.6.3.1.1.2
		sleV2IgfPortProfileIndex OBJECT-TYPE
			SYNTAX Unsigned32 (0..2147483647)
			MAX-ACCESS read-only
			STATUS current
			DESCRIPTION
				" A port index to apply IGMP profile"
			::= { sleV2IgfPortEntry 2 }

		
--  1.3.6.1.4.1.6296.102.12.2.2.6.3.1.1.3
		sleV2IgfPortMaxGroupCount OBJECT-TYPE
			SYNTAX Unsigned32 (0..2147483647)
			MAX-ACCESS read-only
			STATUS current
			DESCRIPTION
				" Maximum group count on the port."
			::= { sleV2IgfPortEntry 3 }

		
--  1.3.6.1.4.1.6296.102.12.2.2.6.3.1.1.4
		sleV2IgfPortMaxGroupAction OBJECT-TYPE
			SYNTAX INTEGER
				{
				unknown(0),
				deny(1),
				replace(2)
				}
			MAX-ACCESS read-only
			STATUS current
			DESCRIPTION
				" Policy applied when exceeds the maximum group count. default value deny(1)."
			::= { sleV2IgfPortEntry 4 }

		
--  1.3.6.1.4.1.6296.102.12.2.2.6.3.1.1.5
		sleV2IgfPortDhcpSnoopBindingPermission OBJECT-TYPE
			SYNTAX INTEGER
				{
				unused(0),
				permit(1),
				deny(2)
				}
			MAX-ACCESS read-only
			STATUS current
			DESCRIPTION
				"DHCP snoop binding permission
				0 : unused
				1 : permit
				2 : deny
				"
			::= { sleV2IgfPortEntry 5 }

		
		sleV2IgfPortPacketType OBJECT-TYPE
			SYNTAX BITS
				{
				all(0),
				v1report(1),
				v2report(2),
				v3report(3),
				query(4),
				leave(5)
				}
			MAX-ACCESS read-only
			STATUS current
			DESCRIPTION
				"The packet-filter type."
			::= { sleV2IgfPortEntry 6 }

		
--  IGMP Filter Port Control
-- 1.3.6.1.4.1.6296.102.12.2.2.6.3.2
		sleV2IgfPortControl OBJECT IDENTIFIER ::= { sleV2IgfPort 2 }

		
--  1.3.6.1.4.1.6296.102.12.2.2.6.3.2.1
		sleV2IgfPortControlRequest OBJECT-TYPE
			SYNTAX INTEGER
				{
				setIgmpFilterPortProfileIndex(1),
				setIgmpFilterPortMaxGroupProfile(2),
				setIgmpFilterPortDhcpSnoopBindingPermission(3),
				setIgmpFilterPortPacketType(4)
				}
			MAX-ACCESS read-write
			STATUS current
			DESCRIPTION
				" The request of a user command"
			::= { sleV2IgfPortControl 1 }

		
--  1.3.6.1.4.1.6296.102.12.2.2.6.3.2.2
		sleV2IgfPortControlStatus OBJECT-TYPE
			SYNTAX SleControlStatusType
			MAX-ACCESS read-only
			STATUS current
			DESCRIPTION
				" The status of user command"
			::= { sleV2IgfPortControl 2 }

		
--  1.3.6.1.4.1.6296.102.12.2.2.6.3.2.3
		sleV2IgfPortControlTimer OBJECT-TYPE
			SYNTAX Gauge32
			MAX-ACCESS read-write
			STATUS current
			DESCRIPTION
				"The maximum time for the manager for a long running user command"
			::= { sleV2IgfPortControl 3 }

		
--  1.3.6.1.4.1.6296.102.12.2.2.6.3.2.4
		sleV2IgfPortControlTimeStamp OBJECT-TYPE
			SYNTAX TimeStamp
			MAX-ACCESS read-only
			STATUS current
			DESCRIPTION
				" The time stamp of the last command(end of command)"
			::= { sleV2IgfPortControl 4 }

		
--  1.3.6.1.4.1.6296.102.12.2.2.6.3.2.5
		sleV2IgfPortControlReqResult OBJECT-TYPE
			SYNTAX SleControlRequestResultType
			MAX-ACCESS read-only
			STATUS current
			DESCRIPTION
				" The time stamp of the last command(end of command)
				The result of the last user command"
			::= { sleV2IgfPortControl 5 }

		
--  1.3.6.1.4.1.6296.102.12.2.2.6.3.2.6
		sleV2IgfPortControlIndex OBJECT-TYPE
			SYNTAX INTEGER (1..512)
			MAX-ACCESS read-write
			STATUS current
			DESCRIPTION
				" A port index to apply IGMP profile"
			::= { sleV2IgfPortControl 6 }

		
--  1.3.6.1.4.1.6296.102.12.2.2.6.3.2.7
		sleV2IgfPortControlProfileIndex OBJECT-TYPE
			SYNTAX Unsigned32 (0..2147483647)
			MAX-ACCESS read-write
			STATUS current
			DESCRIPTION
				"CLI : (no) ip igmp filter port PORT profile <1-4294967295>
				value(0) : (no)"
			::= { sleV2IgfPortControl 7 }

		
--  1.3.6.1.4.1.6296.102.12.2.2.6.3.2.8
		sleV2IgfPortControlMaxGroupCount OBJECT-TYPE
			SYNTAX Unsigned32 (0..2147483647)
			MAX-ACCESS read-write
			STATUS current
			DESCRIPTION
				"CLI : (no) ip igmp max-groups port PORT count <1-4294967295> action (deny|replace)"
			::= { sleV2IgfPortControl 8 }

		
--  1.3.6.1.4.1.6296.102.12.2.2.6.3.2.9
		sleV2IgfPortControlMaxGroupAction OBJECT-TYPE
			SYNTAX INTEGER
				{
				deny(1),
				replace(2)
				}
			MAX-ACCESS read-write
			STATUS current
			DESCRIPTION
				"CLI : (no) ip igmp max-groups port PORT count <1-4294967295> action (deny|replace)"
			::= { sleV2IgfPortControl 9 }

		
--  1.3.6.1.4.1.6296.102.12.2.2.6.3.2.10
		sleV2IgfPortControlDhcpSnoopBindingPermission OBJECT-TYPE
			SYNTAX INTEGER
				{
				unused(0),
				permit(1),
				deny(2)
				}
			MAX-ACCESS read-write
			STATUS current
			DESCRIPTION
				"DHCP snoop binding permission
				0 : unused
				1 : permit
				2 : deny
				"
			::= { sleV2IgfPortControl 10 }

		
		sleV2IgfPortControlPacketType OBJECT-TYPE
			SYNTAX BITS
				{
				all(0),
				v1report(1),
				v2report(2),
				v3report(3),
				query(4),
				leave(5)
				}
			MAX-ACCESS read-write
			STATUS current
			DESCRIPTION
				"The packet-filter type."
			::= { sleV2IgfPortControl 11 }

		
--  IGMP Filter Port Notification
-- 1.3.6.1.4.1.6296.102.12.2.2.6.3.3
		sleV2IgfPortNotification OBJECT IDENTIFIER ::= { sleV2IgfPort 3 }

		
--  1.3.6.1.4.1.6296.102.12.2.2.6.3.3.1
		sleV2IgfPortProfileChanged NOTIFICATION-TYPE
			OBJECTS { sleV2IgfPortControlRequest, sleV2IgfPortControlReqResult, sleV2IgfPortControlTimeStamp, sleV2IgfPortProfileIndex }
			STATUS current
			DESCRIPTION 
				" "
			::= { sleV2IgfPortNotification 1 }

		
--  1.3.6.1.4.1.6296.102.12.2.2.6.3.3.2
		sleV2IgfPortMaxGroupChanged NOTIFICATION-TYPE
			OBJECTS { sleV2IgfPortControlRequest, sleV2IgfPortControlReqResult, sleV2IgfPortControlTimeStamp, sleV2IgfPortMaxGroupCount, sleV2IgfPortMaxGroupAction
				 }
			STATUS current
			DESCRIPTION 
				" "
			::= { sleV2IgfPortNotification 2 }

		
--  1.3.6.1.4.1.6296.102.12.2.2.6.3.3.3
		sleV2IgfPortDhcpSnoopBindingPermissionChanged NOTIFICATION-TYPE
			OBJECTS { sleV2IgfPortControlRequest, sleV2IgfPortControlTimeStamp, sleV2IgfPortControlReqResult, sleV2IgfPortDhcpSnoopBindingPermission }
			STATUS current
			DESCRIPTION 
				"Description."
			::= { sleV2IgfPortNotification 3 }

		
		sleV2IgfPortPacketTypeChanged NOTIFICATION-TYPE
			OBJECTS { sleV2IgfPortControlRequest, sleV2IgfPortControlTimeStamp, sleV2IgfPortControlReqResult, sleV2IgfPortControlPacketType }
			STATUS current
			DESCRIPTION 
				"Description."
			::= { sleV2IgfPortNotification 4 }

		
--  Multicast VLAN Registration
-- 1.3.6.1.4.1.6296.102.12.2.2.7
		sleV2Mvr4 OBJECT IDENTIFIER ::= { sleV2Igmp 7 }

		
--  MVR Port
-- 1.3.6.1.4.1.6296.102.12.2.2.7.1
		sleV2Mvr4Port OBJECT IDENTIFIER ::= { sleV2Mvr4 1 }

		
--  MVR Port Table
-- 1.3.6.1.4.1.6296.102.12.2.2.7.1.1
		sleV2Mvr4PortTable OBJECT-TYPE
			SYNTAX SEQUENCE OF SleV2Mvr4PortEntry
			MAX-ACCESS not-accessible
			STATUS current
			DESCRIPTION
				"port table."
			::= { sleV2Mvr4Port 1 }

		
--  MVR Port Entry
-- 1.3.6.1.4.1.6296.102.12.2.2.7.1.1.1
		sleV2Mvr4PortEntry OBJECT-TYPE
			SYNTAX SleV2Mvr4PortEntry
			MAX-ACCESS not-accessible
			STATUS current
			DESCRIPTION
				"key: sleV2Mvr4PortIndex"
			INDEX { sleV2Mvr4PortIndex }
			::= { sleV2Mvr4PortTable 1 }

		
		SleV2Mvr4PortEntry ::=
			SEQUENCE { 
				sleV2Mvr4PortIndex
					INTEGER,
				sleV2Mvr4PortType
					INTEGER
			 }

--  1.3.6.1.4.1.6296.102.12.2.2.7.1.1.1.1
		sleV2Mvr4PortIndex OBJECT-TYPE
			SYNTAX INTEGER (1..512)
			MAX-ACCESS read-only
			STATUS current
			DESCRIPTION
				"Same as ifIndex (for all ifTable entries)."
			::= { sleV2Mvr4PortEntry 1 }

		
--  1.3.6.1.4.1.6296.102.12.2.2.7.1.1.1.2
		sleV2Mvr4PortType OBJECT-TYPE
			SYNTAX INTEGER
				{
				none(0),
				source(1),
				receiver(2)
				}
			MAX-ACCESS read-only
			STATUS current
			DESCRIPTION
				"It indicates the port's MVR operation type."
			DEFVAL { none }
			::= { sleV2Mvr4PortEntry 2 }

		
--  MVR Port Control
-- 1.3.6.1.4.1.6296.102.12.2.2.7.1.2
		sleV2Mvr4PortControl OBJECT IDENTIFIER ::= { sleV2Mvr4Port 2 }

		
--  1.3.6.1.4.1.6296.102.12.2.2.7.1.2.1
		sleV2Mvr4PortControlRequest OBJECT-TYPE
			SYNTAX INTEGER { setMvrPortProfile(1) }
			MAX-ACCESS read-write
			STATUS current
			DESCRIPTION
				" The request of a user command"
			::= { sleV2Mvr4PortControl 1 }

		
--  1.3.6.1.4.1.6296.102.12.2.2.7.1.2.2
		sleV2Mvr4PortControlStatus OBJECT-TYPE
			SYNTAX SleControlStatusType
			MAX-ACCESS read-only
			STATUS current
			DESCRIPTION
				" The status of user command"
			::= { sleV2Mvr4PortControl 2 }

		
--  1.3.6.1.4.1.6296.102.12.2.2.7.1.2.3
		sleV2Mvr4PortControlTimer OBJECT-TYPE
			SYNTAX Gauge32
			MAX-ACCESS read-write
			STATUS current
			DESCRIPTION
				" The maximum time for the manager for a long running user command"
			::= { sleV2Mvr4PortControl 3 }

		
--  1.3.6.1.4.1.6296.102.12.2.2.7.1.2.4
		sleV2Mvr4PortControlTimeStamp OBJECT-TYPE
			SYNTAX TimeStamp
			MAX-ACCESS read-only
			STATUS current
			DESCRIPTION
				" The time stamp of the last command(end of command)"
			::= { sleV2Mvr4PortControl 4 }

		
--  1.3.6.1.4.1.6296.102.12.2.2.7.1.2.5
		sleV2Mvr4PortControlReqResult OBJECT-TYPE
			SYNTAX SleControlRequestResultType
			MAX-ACCESS read-only
			STATUS current
			DESCRIPTION
				" The result of the last user command"
			::= { sleV2Mvr4PortControl 5 }

		
--  1.3.6.1.4.1.6296.102.12.2.2.7.1.2.6
		sleV2Mvr4PortControlIndex OBJECT-TYPE
			SYNTAX INTEGER (1..512)
			MAX-ACCESS read-write
			STATUS current
			DESCRIPTION
				"Same as ifIndex (for all ifTable entries)."
			::= { sleV2Mvr4PortControl 6 }

		
--  1.3.6.1.4.1.6296.102.12.2.2.7.1.2.7
		sleV2Mvr4PortControlType OBJECT-TYPE
			SYNTAX INTEGER
				{
				none(0),
				source(1),
				receiver(2)
				}
			MAX-ACCESS read-write
			STATUS current
			DESCRIPTION
				"It indicates the port's MVR operation type."
			::= { sleV2Mvr4PortControl 7 }

		
--  MVR Port Notification
-- 1.3.6.1.4.1.6296.102.12.2.2.7.1.3
		sleV2Mvr4PortNotification OBJECT IDENTIFIER ::= { sleV2Mvr4Port 3 }

		
--  1.3.6.1.4.1.6296.102.12.2.2.7.1.3.1
		sleV2Mvr4PortProfileChanged NOTIFICATION-TYPE
			OBJECTS { sleV2Mvr4PortControlRequest, sleV2Mvr4PortControlReqResult, sleV2Mvr4PortControlTimeStamp, sleV2Mvr4PortType }
			STATUS current
			DESCRIPTION 
				"setMvrPort"
			::= { sleV2Mvr4PortNotification 1 }

		
--  MVR Group
-- 1.3.6.1.4.1.6296.102.12.2.2.7.2
		sleV2Mvr4Group OBJECT IDENTIFIER ::= { sleV2Mvr4 2 }

		
--  MVR Group Table
-- 1.3.6.1.4.1.6296.102.12.2.2.7.2.1
		sleV2Mvr4GroupTable OBJECT-TYPE
			SYNTAX SEQUENCE OF SleV2Mvr4GroupEntry
			MAX-ACCESS not-accessible
			STATUS current
			DESCRIPTION
				"MVR group table."
			::= { sleV2Mvr4Group 1 }
-- group table.
		
--  MVR Group Entry
-- 1.3.6.1.4.1.6296.102.12.2.2.7.2.1.1
		sleV2Mvr4GroupEntry OBJECT-TYPE
			SYNTAX SleV2Mvr4GroupEntry
			MAX-ACCESS not-accessible
			STATUS current
			DESCRIPTION
				"key: sleV2Mvr4GroupAddress"
			INDEX { sleV2Mvr4GroupAddress }
			::= { sleV2Mvr4GroupTable 1 }
-- key: sleV2Mvr4GroupAddress
		
		SleV2Mvr4GroupEntry ::=
			SEQUENCE { 
				sleV2Mvr4GroupAddress
					IpAddress,
				sleV2Mvr4GroupVlanIndex
					INTEGER
			 }

--  1.3.6.1.4.1.6296.102.12.2.2.7.2.1.1.1
		sleV2Mvr4GroupAddress OBJECT-TYPE
			SYNTAX IpAddress
			MAX-ACCESS read-only
			STATUS current
			DESCRIPTION
				"This object indicates group address for MVR."
			::= { sleV2Mvr4GroupEntry 1 }

		
--  1.3.6.1.4.1.6296.102.12.2.2.7.2.1.1.2
		sleV2Mvr4GroupVlanIndex OBJECT-TYPE
			SYNTAX INTEGER (1..4094)
			MAX-ACCESS read-only
			STATUS current
			DESCRIPTION
				"This object indicates the VLAN for MVR."
			::= { sleV2Mvr4GroupEntry 2 }

		
--  MVR Group Control
-- 1.3.6.1.4.1.6296.102.12.2.2.7.2.2
		sleV2Mvr4GroupControl OBJECT IDENTIFIER ::= { sleV2Mvr4Group 2 }

		
--  1.3.6.1.4.1.6296.102.12.2.2.7.2.2.1
		sleV2Mvr4GroupControlRequest OBJECT-TYPE
			SYNTAX INTEGER
				{
				createMvrGroup(1),
				destroyMvrGroup(2)
				}
			MAX-ACCESS read-write
			STATUS current
			DESCRIPTION
				" The request of a user command"
			::= { sleV2Mvr4GroupControl 1 }

		
--  1.3.6.1.4.1.6296.102.12.2.2.7.2.2.2
		sleV2Mvr4GroupControlStatus OBJECT-TYPE
			SYNTAX SleControlStatusType
			MAX-ACCESS read-only
			STATUS current
			DESCRIPTION
				" The status of user command"
			::= { sleV2Mvr4GroupControl 2 }

		
--  1.3.6.1.4.1.6296.102.12.2.2.7.2.2.3
		sleV2Mvr4GroupControlTimer OBJECT-TYPE
			SYNTAX Gauge32
			MAX-ACCESS read-write
			STATUS current
			DESCRIPTION
				" The maximum time for the manager for a long running user command"
			::= { sleV2Mvr4GroupControl 3 }

		
--  1.3.6.1.4.1.6296.102.12.2.2.7.2.2.4
		sleV2Mvr4GroupControlTimeStamp OBJECT-TYPE
			SYNTAX TimeStamp
			MAX-ACCESS read-only
			STATUS current
			DESCRIPTION
				" The time stamp of the last command(end of command)"
			::= { sleV2Mvr4GroupControl 4 }

		
--  1.3.6.1.4.1.6296.102.12.2.2.7.2.2.5
		sleV2Mvr4GroupControlReqResult OBJECT-TYPE
			SYNTAX SleControlRequestResultType
			MAX-ACCESS read-only
			STATUS current
			DESCRIPTION
				" The result of the last user command"
			::= { sleV2Mvr4GroupControl 5 }

		
--  1.3.6.1.4.1.6296.102.12.2.2.7.2.2.6
		sleV2Mvr4GroupControlAddress OBJECT-TYPE
			SYNTAX IpAddress
			MAX-ACCESS read-write
			STATUS current
			DESCRIPTION
				"This object indicates group address for MVR."
			::= { sleV2Mvr4GroupControl 6 }

		
--  1.3.6.1.4.1.6296.102.12.2.2.7.2.2.7
		sleV2Mvr4GroupControlVlanIndex OBJECT-TYPE
			SYNTAX INTEGER (1..4094)
			MAX-ACCESS read-write
			STATUS current
			DESCRIPTION
				"This object indicates the VLAN for MVR."
			::= { sleV2Mvr4GroupControl 7 }

		
--  MVR Group Notification
-- 1.3.6.1.4.1.6296.102.12.2.2.7.2.3
		sleV2Mvr4GroupNotification OBJECT IDENTIFIER ::= { sleV2Mvr4Group 3 }

		
--  1.3.6.1.4.1.6296.102.12.2.2.7.2.3.1
		sleV2Mvr4GroupCreated NOTIFICATION-TYPE
			OBJECTS { sleV2Mvr4GroupControlRequest, sleV2Mvr4GroupControlReqResult, sleV2Mvr4GroupControlTimeStamp, sleV2Mvr4GroupVlanIndex }
			STATUS current
			DESCRIPTION 
				"It indicates that the group has been created on the VLAN."
			::= { sleV2Mvr4GroupNotification 1 }

		
--  1.3.6.1.4.1.6296.102.12.2.2.7.2.3.2
		sleV2Mvr4GroupDestroyed NOTIFICATION-TYPE
			OBJECTS { sleV2Mvr4GroupControlRequest, sleV2Mvr4GroupControlReqResult, sleV2Mvr4GroupControlTimeStamp, sleV2Mvr4GroupVlanIndex }
			STATUS current
			DESCRIPTION 
				"It indicates that the group has been destroyed from the VLAN."
			::= { sleV2Mvr4GroupNotification 2 }

		
--  IGMP Counter
		sleV2IgmpCounterInfo OBJECT IDENTIFIER ::= { sleV2Igmp 8 }

		
		sleV2IgmpCounterInfoGroupCount OBJECT-TYPE
			SYNTAX Counter32
			MAX-ACCESS read-only
			STATUS current
			DESCRIPTION
				"Count of IGMP Group entry."
			::= { sleV2IgmpCounterInfo 1 }

		
		sleV2IgmpCounterInfoSnoopingCount OBJECT-TYPE
			SYNTAX Counter32
			MAX-ACCESS read-only
			STATUS current
			DESCRIPTION
				"Count of IGMP Snooping Group entry."
			::= { sleV2IgmpCounterInfo 2 }

		
		sleV2IgsMaxBWLimit OBJECT IDENTIFIER ::= { sleV2Igmp 9 }

		
		sleV2IgsMaxBWLimitInfo OBJECT IDENTIFIER ::= { sleV2IgsMaxBWLimit 1 }

		
		sleV2IgsMaxBWLimitSystemMax OBJECT-TYPE
			SYNTAX Gauge32
			MAX-ACCESS read-only
			STATUS current
			DESCRIPTION
				"The maximum bandwidth per system of MAXBW Limit
				"
			::= { sleV2IgsMaxBWLimitInfo 1 }

		
		sleV2IgsMaxBWLimitChannelDefault OBJECT-TYPE
			SYNTAX Gauge32
			MAX-ACCESS read-only
			STATUS current
			DESCRIPTION
				"The default bandwidth per channel of MAXBW Limit
				"
			::= { sleV2IgsMaxBWLimitInfo 2 }

		
		sleV2IgsMaxBWLimitSystemCurrentBw OBJECT-TYPE
			SYNTAX Gauge32
			MAX-ACCESS read-only
			STATUS current
			DESCRIPTION
				"Description."
			::= { sleV2IgsMaxBWLimitInfo 3 }

		
		sleV2IgsMaxBWLimitPortTable OBJECT-TYPE
			SYNTAX SEQUENCE OF SleV2IgsMaxBWLimitPortEntry
			MAX-ACCESS not-accessible
			STATUS current
			DESCRIPTION
				"Description."
			::= { sleV2IgsMaxBWLimit 2 }

		
		sleV2IgsMaxBWLimitPortEntry OBJECT-TYPE
			SYNTAX SleV2IgsMaxBWLimitPortEntry
			MAX-ACCESS not-accessible
			STATUS current
			DESCRIPTION
				"Description."
			INDEX { sleV2IgsMaxBWLimitPortIndex }
			::= { sleV2IgsMaxBWLimitPortTable 1 }

		
		SleV2IgsMaxBWLimitPortEntry ::=
			SEQUENCE { 
				sleV2IgsMaxBWLimitPortIndex
					Integer32,
				sleV2IgsMaxBWLimitPortMax
					Gauge32,
				sleV2IgsMaxBWLimitPortCurrentBW
					Gauge32
			 }

		sleV2IgsMaxBWLimitPortIndex OBJECT-TYPE
			SYNTAX Integer32 (1..65535)
			MAX-ACCESS read-only
			STATUS current
			DESCRIPTION
				"The portIndex.
				"
			::= { sleV2IgsMaxBWLimitPortEntry 1 }

		
		sleV2IgsMaxBWLimitPortMax OBJECT-TYPE
			SYNTAX Gauge32
			MAX-ACCESS read-only
			STATUS current
			DESCRIPTION
				"The maximum bandwidth per port of MAXBW Limit
				"
			::= { sleV2IgsMaxBWLimitPortEntry 2 }

		
		sleV2IgsMaxBWLimitPortCurrentBW OBJECT-TYPE
			SYNTAX Gauge32
			MAX-ACCESS read-only
			STATUS current
			DESCRIPTION
				"The current bandwidth per port of MAXBW Limit
				"
			::= { sleV2IgsMaxBWLimitPortEntry 3 }

		
		sleV2IgsMaxBWLimitChannelTable OBJECT-TYPE
			SYNTAX SEQUENCE OF SleV2IgsMaxBWLimitChannelEntry
			MAX-ACCESS not-accessible
			STATUS current
			DESCRIPTION
				"Description."
			::= { sleV2IgsMaxBWLimit 3 }

		
		sleV2IgsMaxBWLimitChannelEntry OBJECT-TYPE
			SYNTAX SleV2IgsMaxBWLimitChannelEntry
			MAX-ACCESS not-accessible
			STATUS current
			DESCRIPTION
				"Description."
			INDEX { sleV2IgsMaxBWLimitChannelStart, sleV2IgsMaxBWLimitChannelEnd }
			::= { sleV2IgsMaxBWLimitChannelTable 1 }

		
		SleV2IgsMaxBWLimitChannelEntry ::=
			SEQUENCE { 
				sleV2IgsMaxBWLimitChannelStart
					IpAddress,
				sleV2IgsMaxBWLimitChannelEnd
					IpAddress,
				sleV2IgsMaxBWLimitChannelBW
					Gauge32
			 }

		sleV2IgsMaxBWLimitChannelStart OBJECT-TYPE
			SYNTAX IpAddress
			MAX-ACCESS read-only
			STATUS current
			DESCRIPTION
				"The start address of channel
				"
			::= { sleV2IgsMaxBWLimitChannelEntry 1 }

		
		sleV2IgsMaxBWLimitChannelEnd OBJECT-TYPE
			SYNTAX IpAddress
			MAX-ACCESS read-only
			STATUS current
			DESCRIPTION
				"The end address of channel
				"
			::= { sleV2IgsMaxBWLimitChannelEntry 2 }

		
		sleV2IgsMaxBWLimitChannelBW OBJECT-TYPE
			SYNTAX Gauge32
			MAX-ACCESS read-only
			STATUS current
			DESCRIPTION
				"The maximum bandwidth per channel of MAXBW Limit
				"
			::= { sleV2IgsMaxBWLimitChannelEntry 3 }

		
--  IGMP Profile Range Control
-- 1.3.6.1.4.1.6296.102.12.2.2.6.2.2
		sleV2IgsMaxBWLimitControl OBJECT IDENTIFIER ::= { sleV2IgsMaxBWLimit 4 }

		
		sleV2IgsMaxBWLimitControlRequest OBJECT-TYPE
			SYNTAX INTEGER
				{
				setSystemMaxBW(1),
				setChannelDefaultBW(2),
				setPortMaxBW(3),
				addChannelBW(4),
				deleteChannelBW(5),
				clearCurrentBW(6),
				clearCurrentPortBW(7)
				}
			MAX-ACCESS read-write
			STATUS current
			DESCRIPTION
				" The request of a user command"
			::= { sleV2IgsMaxBWLimitControl 1 }

		
		sleV2IgsMaxBWLimitControlStatus OBJECT-TYPE
			SYNTAX SleControlStatusType
			MAX-ACCESS read-only
			STATUS current
			DESCRIPTION
				" The status of user command"
			::= { sleV2IgsMaxBWLimitControl 2 }

		
		sleV2IgsMaxBWLimitControlTimer OBJECT-TYPE
			SYNTAX Gauge32
			MAX-ACCESS read-write
			STATUS current
			DESCRIPTION
				" The maximum time for the manager for a long running user command"
			::= { sleV2IgsMaxBWLimitControl 3 }

		
--  1.3.6.1.4.1.6296.102.12.2.2.6.2.2.4
		sleV2IgsMaxBWLimitControlTimeStamp OBJECT-TYPE
			SYNTAX TimeStamp
			MAX-ACCESS read-only
			STATUS current
			DESCRIPTION
				" The time stamp of the last command(end of command)"
			::= { sleV2IgsMaxBWLimitControl 4 }

		
--  1.3.6.1.4.1.6296.102.12.2.2.6.2.2.5
		sleV2IgsMaxBWLimitControlReqResult OBJECT-TYPE
			SYNTAX SleControlRequestResultType
			MAX-ACCESS read-only
			STATUS current
			DESCRIPTION
				" The result of the last user command"
			::= { sleV2IgsMaxBWLimitControl 5 }

		
		sleV2IgsMaxBWLimitControlSystemMax OBJECT-TYPE
			SYNTAX Gauge32
			MAX-ACCESS read-write
			STATUS current
			DESCRIPTION
				"The maximum bandwidth per system of MAXBW Limit
				"
			::= { sleV2IgsMaxBWLimitControl 6 }

		
		sleV2IgsMaxBWLimitControlChannelDefault OBJECT-TYPE
			SYNTAX Gauge32
			MAX-ACCESS read-write
			STATUS current
			DESCRIPTION
				"The default bandwidth per channel of MAXBW Limit
				"
			::= { sleV2IgsMaxBWLimitControl 7 }

		
-- \
		sleV2IgsMaxBWLimitControlPortIndex OBJECT-TYPE
			SYNTAX Integer32
			MAX-ACCESS read-write
			STATUS current
			DESCRIPTION
				"The portIndex.
				"
			::= { sleV2IgsMaxBWLimitControl 8 }

		
		sleV2IgsMaxBWLimitControlPortEnd OBJECT-TYPE
			SYNTAX Integer32
			MAX-ACCESS read-write
			STATUS current
			DESCRIPTION
				"Description."
			::= { sleV2IgsMaxBWLimitControl 9 }

		
		sleV2IgsMaxBWLimitControlPortMax OBJECT-TYPE
			SYNTAX Gauge32
			MAX-ACCESS read-write
			STATUS current
			DESCRIPTION
				"The maximum bandwidth per port of MAXBW Limit
				"
			::= { sleV2IgsMaxBWLimitControl 10 }

		
		sleV2IgsMaxBWLimitControlChannelStart OBJECT-TYPE
			SYNTAX IpAddress
			MAX-ACCESS read-write
			STATUS current
			DESCRIPTION
				"The start address of channel
				"
			::= { sleV2IgsMaxBWLimitControl 11 }

		
--  
		sleV2IgsMaxBWLimitControlChannelEnd OBJECT-TYPE
			SYNTAX IpAddress
			MAX-ACCESS read-write
			STATUS current
			DESCRIPTION
				"The end address of channel
				"
			::= { sleV2IgsMaxBWLimitControl 12 }

		
		sleV2IgsMaxBWLimitControlChannelBW OBJECT-TYPE
			SYNTAX Gauge32
			MAX-ACCESS read-write
			STATUS current
			DESCRIPTION
				"The maximum bandwidth per channel of MAXBW Limit
				"
			::= { sleV2IgsMaxBWLimitControl 13 }

		
		sleV2IgsMaxBWLimitNotification OBJECT IDENTIFIER ::= { sleV2IgsMaxBWLimit 5 }

		
		sleV2IgsMaxBWLimitSystemMaxChanged NOTIFICATION-TYPE
			OBJECTS { sleV2IgsMaxBWLimitControlRequest, sleV2IgsMaxBWLimitControlTimeStamp, sleV2IgsMaxBWLimitControlReqResult, sleV2IgsMaxBWLimitSystemMax }
			STATUS current
			DESCRIPTION 
				"Description."
			::= { sleV2IgsMaxBWLimitNotification 1 }

		
		sleV2IgsMaxBWLimitChannelDefaultChanged NOTIFICATION-TYPE
			OBJECTS { sleV2IgsMaxBWLimitControlRequest, sleV2IgsMaxBWLimitControlTimeStamp, sleV2IgsMaxBWLimitControlReqResult, sleV2IgsMaxBWLimitChannelDefault }
			STATUS current
			DESCRIPTION 
				"Description."
			::= { sleV2IgsMaxBWLimitNotification 2 }

		
		sleV2IgsMaxBWLimitPortMaxChanged NOTIFICATION-TYPE
			OBJECTS { sleV2IgsMaxBWLimitControlRequest, sleV2IgsMaxBWLimitControlTimeStamp, sleV2IgsMaxBWLimitControlReqResult, sleV2IgsMaxBWLimitControlPortIndex, sle2IgsMaxBWLimitControlPortEnd, 
				sleV2IgsMaxBWLimitControlPortMax }
			STATUS current
			DESCRIPTION 
				"Description."
			::= { sleV2IgsMaxBWLimitNotification 3 }

		
		sleV2IgsMaxBWLimitChannelAdded NOTIFICATION-TYPE
			OBJECTS { sleV2IgsMaxBWLimitControlRequest, sleV2IgsMaxBWLimitControlTimeStamp, sleV2IgsMaxBWLimitControlReqResult, sleV2IgsMaxBWLimitChannelStart, sleV2IgsMaxBWLimitChannelEnd, 
				sleV2IgsMaxBWLimitChannelBW }
			STATUS current
			DESCRIPTION 
				"Description."
			::= { sleV2IgsMaxBWLimitNotification 4 }

		
		sleV2IgsMaxBWLimitChannelDeleted NOTIFICATION-TYPE
			OBJECTS { sleV2IgsMaxBWLimitControlRequest, sleV2IgsMaxBWLimitControlTimeStamp, sleV2IgsMaxBWLimitControlReqResult, sleV2IgsMaxBWLimitControlChannelStart, sleV2IgsMaxBWLimitControlChannelEnd
				 }
			STATUS current
			DESCRIPTION 
				"Description."
			::= { sleV2IgsMaxBWLimitNotification 5 }

		
		sleV2IgsMaxBWLimitCurrentBWCleared NOTIFICATION-TYPE
			OBJECTS { sleV2IgsMaxBWLimitControlRequest, sleV2IgsMaxBWLimitControlTimeStamp, sleV2IgsMaxBWLimitControlReqResult }
			STATUS current
			DESCRIPTION 
				"Description."
			::= { sleV2IgsMaxBWLimitNotification 6 }

		
		sleV2IgsMaxBWLimitPortCurrentBWCleared NOTIFICATION-TYPE
			OBJECTS { sleV2IgsMaxBWLimitControlRequest, sleV2IgsMaxBWLimitControlTimeStamp, sleV2IgsMaxBWLimitControlReqResult, sleV2IgsMaxBWLimitControlPortIndex }
			STATUS current
			DESCRIPTION 
				"Description."
			::= { sleV2IgsMaxBWLimitNotification 7 }

		
		sleV2IgmpSsmMapStatic OBJECT IDENTIFIER ::= { sleV2Igmp 10 }

		
		sleV2IgmpSsmMapStaticTable OBJECT-TYPE
			SYNTAX SEQUENCE OF SleV2IgmpSsmMapStaticEntry
			MAX-ACCESS not-accessible
			STATUS current
			DESCRIPTION
				"Description."
			::= { sleV2IgmpSsmMapStatic 1 }

		
		sleV2IgmpSsmMapStaticEntry OBJECT-TYPE
			SYNTAX SleV2IgmpSsmMapStaticEntry
			MAX-ACCESS not-accessible
			STATUS current
			DESCRIPTION
				"Description."
			INDEX { sleV2IgmpSsmMapStaticAcl, sleV2IgmpSsmMapStaticSource }
			::= { sleV2IgmpSsmMapStaticTable 1 }

		
		SleV2IgmpSsmMapStaticEntry ::=
			SEQUENCE { 
				sleV2IgmpSsmMapStaticAcl
					OCTET STRING,
				sleV2IgmpSsmMapStaticSource
					IpAddress
			 }

		sleV2IgmpSsmMapStaticAcl OBJECT-TYPE
			SYNTAX OCTET STRING
			MAX-ACCESS read-only
			STATUS current
			DESCRIPTION
				"Use this command to specify the static mode of defining SSM mapping."
			::= { sleV2IgmpSsmMapStaticEntry 1 }

		
		sleV2IgmpSsmMapStaticSource OBJECT-TYPE
			SYNTAX IpAddress
			MAX-ACCESS read-only
			STATUS current
			DESCRIPTION
				"Use this command to specify the static mode of defining SSM mapping."
			::= { sleV2IgmpSsmMapStaticEntry 2 }

		
		sleV2IgmpSsmMapStaticControl OBJECT IDENTIFIER ::= { sleV2IgmpSsmMapStatic 2 }

		
		sleV2IgmpSsmMapStaticControlRequest OBJECT-TYPE
			SYNTAX INTEGER
				{
				createIgmpSsmMapStatic(1),
				destroyIgmpSsmMapStatic(2)
				}
			MAX-ACCESS read-write
			STATUS current
			DESCRIPTION
				"Description."
			::= { sleV2IgmpSsmMapStaticControl 1 }

		
		sleV2IgmpSsmMapStaticControlStatus OBJECT-TYPE
			SYNTAX SleControlStatusType
			MAX-ACCESS read-write
			STATUS current
			DESCRIPTION
				"Description."
			::= { sleV2IgmpSsmMapStaticControl 2 }

		
		sleV2IgmpSsmMapStaticControlTimer OBJECT-TYPE
			SYNTAX Gauge32
			MAX-ACCESS read-write
			STATUS current
			DESCRIPTION
				"Description."
			::= { sleV2IgmpSsmMapStaticControl 3 }

		
		sleV2IgmpSsmMapStaticControlTimeStamp OBJECT-TYPE
			SYNTAX TimeStamp
			MAX-ACCESS read-write
			STATUS current
			DESCRIPTION
				"Description."
			::= { sleV2IgmpSsmMapStaticControl 4 }

		
		sleV2IgmpSsmMapStaticControlReqResult OBJECT-TYPE
			SYNTAX SleControlRequestResultType
			MAX-ACCESS read-write
			STATUS current
			DESCRIPTION
				"Description."
			::= { sleV2IgmpSsmMapStaticControl 5 }

		
		sleV2IgmpSsmMapStaticControlAcl OBJECT-TYPE
			SYNTAX OCTET STRING
			MAX-ACCESS read-write
			STATUS current
			DESCRIPTION
				"Use this command to specify the static mode of defining SSM mapping."
			::= { sleV2IgmpSsmMapStaticControl 6 }

		
		sleV2IgmpSsmMapStaticControlSource OBJECT-TYPE
			SYNTAX IpAddress
			MAX-ACCESS read-write
			STATUS current
			DESCRIPTION
				"Use this command to specify the static mode of defining SSM mapping."
			::= { sleV2IgmpSsmMapStaticControl 7 }

		
--  Protocol Independent Multicast
-- 1.3.6.1.4.1.6296.102.12.2.3
		sleV2Pim4 OBJECT IDENTIFIER ::= { sleV2Multicast4 3 }

		
--  PIM Configuration
-- 1.3.6.1.4.1.6296.102.12.2.3.1
		sleV2Pim4Base OBJECT IDENTIFIER ::= { sleV2Pim4 1 }

		
		sleV2Pim4Info OBJECT IDENTIFIER ::= { sleV2Pim4Base 1 }

		
		sleV2Pim4InfoSnoopActivity OBJECT-TYPE
			SYNTAX Boolean
			MAX-ACCESS read-only
			STATUS current
			DESCRIPTION
				"The active state of PIM snooping."
			::= { sleV2Pim4Info 1 }

		
		sleV2Pim4InfoMultiPath OBJECT-TYPE
			SYNTAX INTEGER
				{
				disable(1),
				src(2),
				srcgrp(3)
				}
			MAX-ACCESS read-only
			STATUS current
			DESCRIPTION
				"Description."
			::= { sleV2Pim4Info 2 }

		
		sleV2Pim4InfoMessageInterval OBJECT-TYPE
			SYNTAX INTEGER (1..65535)
			MAX-ACCESS read-only
			STATUS current
			DESCRIPTION
				"Description."
			::= { sleV2Pim4Info 3 }

		
		sleV2Pim4InfoSPTThreshold OBJECT-TYPE
			SYNTAX Boolean
			MAX-ACCESS read-only
			STATUS current
			DESCRIPTION
				"Description."
			::= { sleV2Pim4Info 4 }

		
		sleV2Pim4InfoSPTThresholdACL OBJECT-TYPE
			SYNTAX OCTET STRING
			MAX-ACCESS read-only
			STATUS current
			DESCRIPTION
				"Description."
			::= { sleV2Pim4Info 5 }

		
		sleV2Pim4InfoSSMDefault OBJECT-TYPE
			SYNTAX Boolean
			MAX-ACCESS read-only
			STATUS current
			DESCRIPTION
				"Description."
			::= { sleV2Pim4Info 6 }

		
		sleV2Pim4InfoSSMRangeACL OBJECT-TYPE
			SYNTAX OCTET STRING
			MAX-ACCESS read-only
			STATUS current
			DESCRIPTION
				"Description."
			::= { sleV2Pim4Info 7 }

		
		sleV2Pim4InfoCRPCiscoPrefix OBJECT-TYPE
			SYNTAX Boolean
			MAX-ACCESS read-only
			STATUS current
			DESCRIPTION
				"Description."
			::= { sleV2Pim4Info 8 }

		
		sleV2Pim4InfoIgnoreRPSetPriority OBJECT-TYPE
			SYNTAX Boolean
			MAX-ACCESS read-only
			STATUS current
			DESCRIPTION
				"Description."
			::= { sleV2Pim4Info 9 }

		
		sleV2Pim4InfoBSRCandidateInterface OBJECT-TYPE
			SYNTAX INTEGER (1..65535)
			MAX-ACCESS read-only
			STATUS current
			DESCRIPTION
				"Description."
			::= { sleV2Pim4Info 10 }

		
		sleV2Pim4InfoBSRCandidateHash OBJECT-TYPE
			SYNTAX INTEGER (0..32)
			MAX-ACCESS read-only
			STATUS current
			DESCRIPTION
				"Description."
			::= { sleV2Pim4Info 11 }

		
		sleV2Pim4InfoBSRCandidatePriority OBJECT-TYPE
			SYNTAX INTEGER (0..255)
			MAX-ACCESS read-only
			STATUS current
			DESCRIPTION
				"Description."
			::= { sleV2Pim4Info 12 }

		
		sleV2Pim4InfoBSRRole OBJECT-TYPE
			SYNTAX INTEGER
				{
				nonCandidateBSR(1),
				candidateBSR(2)
				}
			MAX-ACCESS read-only
			STATUS current
			DESCRIPTION
				"Description."
			::= { sleV2Pim4Info 13 }

		
		sleV2Pim4InfoBSRStatus OBJECT-TYPE
			SYNTAX INTEGER
				{
				noInfo(1),
				acceptAny(2),
				acceptPreferred(3),
				candidateBSR(4),
				pendingBSR(5),
				elsectedBSR(6)
				}
			MAX-ACCESS read-only
			STATUS current
			DESCRIPTION
				"Description."
			::= { sleV2Pim4Info 14 }

		
		sleV2Pim4InfoBSRUptime OBJECT-TYPE
			SYNTAX TimeTicks
			MAX-ACCESS read-only
			STATUS current
			DESCRIPTION
				"Description."
			::= { sleV2Pim4Info 15 }

		
		sleV2Pim4InfoRegisterRateLimit OBJECT-TYPE
			SYNTAX INTEGER (1..65535)
			MAX-ACCESS read-only
			STATUS current
			DESCRIPTION
				"Description."
			::= { sleV2Pim4Info 16 }

		
		sleV2Pim4InfoRegisterSourceIPAddr OBJECT-TYPE
			SYNTAX IpAddress
			MAX-ACCESS read-only
			STATUS current
			DESCRIPTION
				"Description."
			::= { sleV2Pim4Info 17 }

		
		sleV2Pim4InfoRegisterSourceInterface OBJECT-TYPE
			SYNTAX INTEGER (1..65535)
			MAX-ACCESS read-only
			STATUS current
			DESCRIPTION
				"Description."
			::= { sleV2Pim4Info 18 }

		
		sleV2Pim4InfoRegisterRPReachability OBJECT-TYPE
			SYNTAX Boolean
			MAX-ACCESS read-only
			STATUS current
			DESCRIPTION
				"Description."
			::= { sleV2Pim4Info 19 }

		
		sleV2Pim4InfoRegisterSuppression OBJECT-TYPE
			SYNTAX INTEGER (1..65535)
			MAX-ACCESS read-only
			STATUS current
			DESCRIPTION
				"Description."
			::= { sleV2Pim4Info 20 }

		
		sleV2Pim4InfoAcceptRegisterACL OBJECT-TYPE
			SYNTAX OCTET STRING
			MAX-ACCESS read-only
			STATUS current
			DESCRIPTION
				"Description."
			::= { sleV2Pim4Info 21 }

		
		sleV2Pim4InfoRPRegisterKAT OBJECT-TYPE
			SYNTAX INTEGER (1..65535)
			MAX-ACCESS read-only
			STATUS current
			DESCRIPTION
				"Description."
			::= { sleV2Pim4Info 22 }

		
		sleV2Pim4InfoCiscoRegisterChecksum OBJECT-TYPE
			SYNTAX Boolean
			MAX-ACCESS read-only
			STATUS current
			DESCRIPTION
				"Description."
			::= { sleV2Pim4Info 23 }

		
		sleV2Pim4InfoCiscoRegisterChecksumACL OBJECT-TYPE
			SYNTAX OCTET STRING
			MAX-ACCESS read-only
			STATUS current
			DESCRIPTION
				"Description."
			::= { sleV2Pim4Info 24 }

		
		sleV2Pim4InfoVIFFlapDiscredit OBJECT-TYPE
			SYNTAX Boolean
			MAX-ACCESS read-only
			STATUS current
			DESCRIPTION
				"Description."
			::= { sleV2Pim4Info 25 }

		
		sleV2Pim4InfoVIFFlapDiscreditUnit OBJECT-TYPE
			SYNTAX INTEGER (10..50)
			MAX-ACCESS read-only
			STATUS current
			DESCRIPTION
				"Description."
			::= { sleV2Pim4Info 26 }

		
		sleV2Pim4InfoVIFFlapDiscreditHalfTime OBJECT-TYPE
			SYNTAX INTEGER (0..3600)
			MAX-ACCESS read-only
			STATUS current
			DESCRIPTION
				"Description."
			::= { sleV2Pim4Info 27 }

		
		sleV2Pim4InfoControl OBJECT IDENTIFIER ::= { sleV2Pim4Base 2 }

		
		sleV2Pim4InfoControlRequest OBJECT-TYPE
			SYNTAX INTEGER
				{
				setPimSnoopingActivity(1),
				setPIM4InfoProfile(2),
				setPIM4InfoRPProfile(3),
				setPIM4InfoBSRProfile(4),
				setPIM4InfoRegisterProfile(5),
				setPIM4InfoVIFFlapDiscreditProfile(6),
				clearPIM4InfoMRT(7),
				clearPIM4InfoRPSet(8),
				clearPIM4InfoFlapVIF(9)
				}
			MAX-ACCESS read-write
			STATUS current
			DESCRIPTION
				" The request of a user command"
			::= { sleV2Pim4InfoControl 1 }

		
		sleV2Pim4InfoControlStatus OBJECT-TYPE
			SYNTAX SleControlStatusType
			MAX-ACCESS read-only
			STATUS current
			DESCRIPTION
				"The status of user command"
			::= { sleV2Pim4InfoControl 2 }

		
		sleV2Pim4InfoControlTimer OBJECT-TYPE
			SYNTAX Gauge32
			MAX-ACCESS read-write
			STATUS current
			DESCRIPTION
				" The maximum time for the manager for a long running user command"
			::= { sleV2Pim4InfoControl 3 }

		
		sleV2Pim4InfoControlTimeStamp OBJECT-TYPE
			SYNTAX TimeStamp
			MAX-ACCESS read-only
			STATUS current
			DESCRIPTION
				"The time stamp of the last command(end of command)"
			::= { sleV2Pim4InfoControl 4 }

		
		sleV2Pim4InfoControlReqResult OBJECT-TYPE
			SYNTAX SleControlRequestResultType
			MAX-ACCESS read-only
			STATUS current
			DESCRIPTION
				" The result of the last user command"
			::= { sleV2Pim4InfoControl 5 }

		
		sleV2Pim4InfoControlSnoopActivity OBJECT-TYPE
			SYNTAX Boolean
			MAX-ACCESS read-write
			STATUS current
			DESCRIPTION
				"The active state of PIM snooping."
			::= { sleV2Pim4InfoControl 6 }

		
		sleV2Pim4InfoControlMultipath OBJECT-TYPE
			SYNTAX INTEGER
				{
				disable(1),
				src(2),
				srcgrp(3)
				}
			MAX-ACCESS read-write
			STATUS current
			DESCRIPTION
				"Description."
			::= { sleV2Pim4InfoControl 7 }

		
		sleV2Pim4InfoControlMessageInterval OBJECT-TYPE
			SYNTAX INTEGER (-1 | 1..65535)
			MAX-ACCESS read-write
			STATUS current
			DESCRIPTION
				"Description."
			::= { sleV2Pim4InfoControl 8 }

		
		sleV2Pim4InfoControlSPTThreshold OBJECT-TYPE
			SYNTAX Boolean
			MAX-ACCESS read-write
			STATUS current
			DESCRIPTION
				"Description."
			::= { sleV2Pim4InfoControl 9 }

		
		sleV2Pim4InfoControlSPTThresholdACL OBJECT-TYPE
			SYNTAX OCTET STRING
			MAX-ACCESS read-write
			STATUS current
			DESCRIPTION
				"Description."
			::= { sleV2Pim4InfoControl 10 }

		
		sleV2Pim4InfoControlSSMDefault OBJECT-TYPE
			SYNTAX Boolean
			MAX-ACCESS read-write
			STATUS current
			DESCRIPTION
				"Description."
			::= { sleV2Pim4InfoControl 11 }

		
		sleV2Pim4InfoControlSSMRangeACL OBJECT-TYPE
			SYNTAX OCTET STRING
			MAX-ACCESS read-write
			STATUS current
			DESCRIPTION
				"Description."
			::= { sleV2Pim4InfoControl 12 }

		
		sleV2Pim4InfoControlCRPCiscoPrefix OBJECT-TYPE
			SYNTAX Boolean
			MAX-ACCESS read-write
			STATUS current
			DESCRIPTION
				"Description."
			::= { sleV2Pim4InfoControl 13 }

		
		sleV2Pim4InfoControlIgnoreRPSetPriority OBJECT-TYPE
			SYNTAX Boolean
			MAX-ACCESS read-write
			STATUS current
			DESCRIPTION
				"Description."
			::= { sleV2Pim4InfoControl 14 }

		
		sleV2Pim4InfoControlBSRCandidateInterface OBJECT-TYPE
			SYNTAX INTEGER (-1 | 1..65535)
			MAX-ACCESS read-write
			STATUS current
			DESCRIPTION
				"Description."
			::= { sleV2Pim4InfoControl 15 }

		
		sleV2Pim4InfoControlBSRCnadidateHash OBJECT-TYPE
			SYNTAX INTEGER (-1 | 0..32)
			MAX-ACCESS read-write
			STATUS current
			DESCRIPTION
				"Description."
			::= { sleV2Pim4InfoControl 16 }

		
		sleV2Pim4InfoControlBSRCandidatePriority OBJECT-TYPE
			SYNTAX INTEGER (-1 | 0..255)
			MAX-ACCESS read-write
			STATUS current
			DESCRIPTION
				"Description."
			::= { sleV2Pim4InfoControl 17 }

		
		sleV2Pim4InfoControlRegisterRateLimit OBJECT-TYPE
			SYNTAX INTEGER (-1 | 0..65535)
			MAX-ACCESS read-write
			STATUS current
			DESCRIPTION
				"Description."
			::= { sleV2Pim4InfoControl 18 }

		
		sleV2Pim4InfoControlRegisterSourceIPAddr OBJECT-TYPE
			SYNTAX IpAddress
			MAX-ACCESS read-write
			STATUS current
			DESCRIPTION
				"Description."
			::= { sleV2Pim4InfoControl 19 }

		
		sleV2Pim4InfoControlRegisterSourceInterface OBJECT-TYPE
			SYNTAX INTEGER (-1 | 1..65535)
			MAX-ACCESS read-write
			STATUS current
			DESCRIPTION
				"Description."
			::= { sleV2Pim4InfoControl 20 }

		
		sleV2Pim4InfoControlRegisterRPReachability OBJECT-TYPE
			SYNTAX Boolean
			MAX-ACCESS read-write
			STATUS current
			DESCRIPTION
				"Description."
			::= { sleV2Pim4InfoControl 21 }

		
		sleV2Pim4InfoControlRegisterSuppression OBJECT-TYPE
			SYNTAX INTEGER (-1 | 1..65535)
			MAX-ACCESS read-write
			STATUS current
			DESCRIPTION
				"Description."
			::= { sleV2Pim4InfoControl 22 }

		
		sleV2Pim4InfoControlAcceptRegisterACL OBJECT-TYPE
			SYNTAX OCTET STRING
			MAX-ACCESS read-write
			STATUS current
			DESCRIPTION
				"Description."
			::= { sleV2Pim4InfoControl 23 }

		
		sleV2Pim4InfoControlRPRegisterKAT OBJECT-TYPE
			SYNTAX INTEGER (-1 | 1..65535)
			MAX-ACCESS read-write
			STATUS current
			DESCRIPTION
				"Description."
			::= { sleV2Pim4InfoControl 24 }

		
		sleV2Pim4InfoControlCiscoRegisterChecksum OBJECT-TYPE
			SYNTAX Boolean
			MAX-ACCESS read-write
			STATUS current
			DESCRIPTION
				"Description."
			::= { sleV2Pim4InfoControl 25 }

		
		sleV2Pim4InfoControlCiscoRegisterChecksumACL OBJECT-TYPE
			SYNTAX OCTET STRING
			MAX-ACCESS read-write
			STATUS current
			DESCRIPTION
				"Description."
			::= { sleV2Pim4InfoControl 26 }

		
		sleV2Pim4InfoControlVIFFlapDiscredit OBJECT-TYPE
			SYNTAX Boolean
			MAX-ACCESS read-write
			STATUS current
			DESCRIPTION
				"Description."
			::= { sleV2Pim4InfoControl 27 }

		
		sleV2Pim4InfoControlVIFFlapDiscreditUnit OBJECT-TYPE
			SYNTAX INTEGER (-1 | 10..50)
			MAX-ACCESS read-write
			STATUS current
			DESCRIPTION
				"Description."
			::= { sleV2Pim4InfoControl 28 }

		
		sleV2Pim4InfoControlVIFFlapDiscreditHalfTime OBJECT-TYPE
			SYNTAX INTEGER (-1 | 0..3600)
			MAX-ACCESS read-write
			STATUS current
			DESCRIPTION
				"Description."
			::= { sleV2Pim4InfoControl 29 }

		
		sleV2Pim4InfoControlGroup OBJECT-TYPE
			SYNTAX IpAddress
			MAX-ACCESS read-write
			STATUS current
			DESCRIPTION
				"Description."
			::= { sleV2Pim4InfoControl 30 }

		
		sleV2Pim4InfoControlSource OBJECT-TYPE
			SYNTAX IpAddress
			MAX-ACCESS read-write
			STATUS current
			DESCRIPTION
				"Description."
			::= { sleV2Pim4InfoControl 31 }

		
		sleV2Pim4InfoControlClearVIF OBJECT-TYPE
			SYNTAX INTEGER (-1 | 0..127)
			MAX-ACCESS read-write
			STATUS current
			DESCRIPTION
				"Description."
			::= { sleV2Pim4InfoControl 32 }

		
		sleV2Pim4InfoNotification OBJECT IDENTIFIER ::= { sleV2Pim4Base 3 }

		
		sleV2Pim4InfoSnoopingActivityChanged NOTIFICATION-TYPE
			OBJECTS { sleV2Pim4InfoControlRequest, sleV2Pim4InfoControlReqResult, sleV2Pim4InfoControlTimeStamp, sleV2Pim4InfoSnoopActivity }
			STATUS current
			DESCRIPTION 
				"sleV2Pim4InfoSnoopingActivityChanged"
			::= { sleV2Pim4InfoNotification 1 }

		
		sleV2Pim4InfoProfileChanged NOTIFICATION-TYPE
			OBJECTS { sleV2Pim4InfoControlRequest, sleV2Pim4InfoControlTimeStamp, sleV2Pim4InfoControlReqResult, sleV2Pim4InfoMultiPath, sleV2Pim4InfoMessageInterval, 
				sleV2Pim4InfoSPTThreshold, sleV2Pim4InfoSPTThresholdACL, sleV2Pim4InfoSSMDefault, sleV2Pim4InfoSSMRangeACL }
			STATUS current
			DESCRIPTION 
				"Description."
			::= { sleV2Pim4InfoNotification 2 }

		
		sleV2Pim4InfoRPProfileChanged NOTIFICATION-TYPE
			OBJECTS { sleV2Pim4InfoControlRequest, sleV2Pim4InfoControlTimeStamp, sleV2Pim4InfoControlReqResult, sleV2Pim4InfoControlCRPCiscoPrefix, sleV2Pim4InfoControlIgnoreRPSetPriority
				 }
			STATUS current
			DESCRIPTION 
				"Description."
			::= { sleV2Pim4InfoNotification 3 }

		
		sleV2Pim4InfoBSRProfileChanged NOTIFICATION-TYPE
			OBJECTS { sleV2Pim4InfoControlRequest, sleV2Pim4InfoControlTimeStamp, sleV2Pim4InfoControlReqResult, sleV2Pim4InfoBSRCandidateInterface, sleV2Pim4InfoBSRCandidateHash, 
				sleV2Pim4InfoBSRCandidatePriority }
			STATUS current
			DESCRIPTION 
				"Description."
			::= { sleV2Pim4InfoNotification 4 }

		
		sleV2Pim4InfoRegisterProfileChanged NOTIFICATION-TYPE
			OBJECTS { sleV2Pim4InfoControlRequest, sleV2Pim4InfoControlTimeStamp, sleV2Pim4InfoControlReqResult, sleV2Pim4InfoRegisterRateLimit, sleV2Pim4InfoRegisterSourceIPAddr, 
				sleV2Pim4InfoRegisterSourceInterface, sleV2Pim4InfoRegisterRPReachability, sleV2Pim4InfoRegisterSuppression, sleV2Pim4InfoAcceptRegisterACL, sleV2Pim4InfoRPRegisterKAT, 
				sleV2Pim4InfoCiscoRegisterChecksum, sleV2Pim4InfoCiscoRegisterChecksumACL }
			STATUS current
			DESCRIPTION 
				"Description."
			::= { sleV2Pim4InfoNotification 5 }

		
		sleV2Pim4InfoVIFFlapDiscreditProfileChanged NOTIFICATION-TYPE
			OBJECTS { sleV2Pim4InfoControlRequest, sleV2Pim4InfoControlTimeStamp, sleV2Pim4InfoControlReqResult, sleV2Pim4InfoVIFFlapDiscredit, sleV2Pim4InfoVIFFlapDiscreditUnit, 
				sleV2Pim4InfoVIFFlapDiscreditHalfTime }
			STATUS current
			DESCRIPTION 
				"Description."
			::= { sleV2Pim4InfoNotification 6 }

		
		sleV2Pim4InfoMRTCleared NOTIFICATION-TYPE
			OBJECTS { sleV2Pim4InfoControlRequest, sleV2Pim4InfoControlTimeStamp, sleV2Pim4InfoControlReqResult, sleV2Pim4InfoControlGroup, sleV2Pim4InfoControlSource
				 }
			STATUS current
			DESCRIPTION 
				"Description."
			::= { sleV2Pim4InfoNotification 7 }

		
		sleV2Pim4InfoRPSetCleared NOTIFICATION-TYPE
			OBJECTS { sleV2Pim4InfoControlRequest, sleV2Pim4InfoControlTimeStamp, sleV2Pim4InfoControlReqResult }
			STATUS current
			DESCRIPTION 
				"Description."
			::= { sleV2Pim4InfoNotification 8 }

		
		sleV2Pim4InfoFlapVIFCleared NOTIFICATION-TYPE
			OBJECTS { sleV2Pim4InfoControlRequest, sleV2Pim4InfoControlTimeStamp, sleV2Pim4InfoControlReqResult, sleV2Pim4InfoControlClearVIF }
			STATUS current
			DESCRIPTION 
				"Description."
			::= { sleV2Pim4InfoNotification 9 }

		
--  PIM Agent (Daemon)
-- 1.3.6.1.4.1.6296.102.12.2.3.2
		sleV2Pim4Agent OBJECT IDENTIFIER ::= { sleV2Pim4 2 }

		
		sleV2Pim4Interface OBJECT IDENTIFIER ::= { sleV2Pim4Agent 1 }

		
		sleV2Pim4IfTable OBJECT-TYPE
			SYNTAX SEQUENCE OF SleV2Pim4IfEntry
			MAX-ACCESS not-accessible
			STATUS current
			DESCRIPTION
				"Description."
			::= { sleV2Pim4Interface 1 }

		
		sleV2Pim4IfEntry OBJECT-TYPE
			SYNTAX SleV2Pim4IfEntry
			MAX-ACCESS not-accessible
			STATUS current
			DESCRIPTION
				"Description."
			INDEX { sleV2Pim4IfVid }
			::= { sleV2Pim4IfTable 1 }

		
		SleV2Pim4IfEntry ::=
			SEQUENCE { 
				sleV2Pim4IfVid
					INTEGER,
				sleV2Pim4IfVifIndex
					INTEGER,
				sleV2Pim4IfAddress
					IpAddress,
				sleV2Pim4IfDrAddress
					IpAddress,
				sleV2Pim4IfTriggedHelloPeriod
					INTEGER,
				sleV2Pim4IfFlapCredit
					INTEGER,
				sleV2Pim4IfFlapTotalTimes
					INTEGER,
				sleV2Pim4IfFlapFirstTime
					TimeTicks,
				sleV2Pim4IfFlapLastTime
					TimeTicks,
				sleV2Pim4IfNextHelloTime
					TimeTicks,
				sleV2Pim4IfSparseMode
					Boolean,
				sleV2Pim4IfSparseModePassive
					Boolean,
				sleV2Pim4IfQueryHoldtime
					INTEGER,
				sleV2Pim4IfQueryInterval
					INTEGER,
				sleV2Pim4IfDrPriority
					Gauge32,
				sleV2Pim4IfExcludeGenID
					Boolean,
				sleV2Pim4IfNeighborFilterACL
					OCTET STRING,
				sleV2Pim4IfGroupFilterACL
					OCTET STRING,
				sleV2Pim4IfGroupFilterRangeACL
					OCTET STRING,
				sleV2Pim4IfPropagationDelay
					Integer32,
				sleV2Pim4IfBsrBorder
					Boolean,
				sleV2Pim4IfUnicastBsm
					Boolean
			 }

		sleV2Pim4IfVid OBJECT-TYPE
			SYNTAX INTEGER (1..4094)
			MAX-ACCESS read-only
			STATUS current
			DESCRIPTION
				"Description."
			::= { sleV2Pim4IfEntry 1 }

		
		sleV2Pim4IfVifIndex OBJECT-TYPE
			SYNTAX INTEGER
			MAX-ACCESS read-only
			STATUS current
			DESCRIPTION
				"Description."
			::= { sleV2Pim4IfEntry 2 }

		
		sleV2Pim4IfAddress OBJECT-TYPE
			SYNTAX IpAddress
			MAX-ACCESS read-only
			STATUS current
			DESCRIPTION
				"Description."
			::= { sleV2Pim4IfEntry 3 }

		
		sleV2Pim4IfDrAddress OBJECT-TYPE
			SYNTAX IpAddress
			MAX-ACCESS read-only
			STATUS current
			DESCRIPTION
				"Description."
			::= { sleV2Pim4IfEntry 4 }

		
		sleV2Pim4IfTriggedHelloPeriod OBJECT-TYPE
			SYNTAX INTEGER (1..18724)
			MAX-ACCESS read-only
			STATUS current
			DESCRIPTION
				"Description."
			::= { sleV2Pim4IfEntry 5 }

		
		sleV2Pim4IfFlapCredit OBJECT-TYPE
			SYNTAX INTEGER (0..100)
			MAX-ACCESS read-only
			STATUS current
			DESCRIPTION
				"Description."
			::= { sleV2Pim4IfEntry 6 }

		
		sleV2Pim4IfFlapTotalTimes OBJECT-TYPE
			SYNTAX INTEGER
			MAX-ACCESS read-only
			STATUS current
			DESCRIPTION
				"Description."
			::= { sleV2Pim4IfEntry 7 }

		
		sleV2Pim4IfFlapFirstTime OBJECT-TYPE
			SYNTAX TimeTicks
			MAX-ACCESS read-only
			STATUS current
			DESCRIPTION
				"Description."
			::= { sleV2Pim4IfEntry 8 }

		
		sleV2Pim4IfFlapLastTime OBJECT-TYPE
			SYNTAX TimeTicks
			MAX-ACCESS read-only
			STATUS current
			DESCRIPTION
				"Description."
			::= { sleV2Pim4IfEntry 9 }

		
		sleV2Pim4IfNextHelloTime OBJECT-TYPE
			SYNTAX TimeTicks
			MAX-ACCESS read-only
			STATUS current
			DESCRIPTION
				"Description."
			::= { sleV2Pim4IfEntry 10 }

		
		sleV2Pim4IfSparseMode OBJECT-TYPE
			SYNTAX Boolean
			MAX-ACCESS read-only
			STATUS current
			DESCRIPTION
				"Description."
			::= { sleV2Pim4IfEntry 11 }

		
		sleV2Pim4IfSparseModePassive OBJECT-TYPE
			SYNTAX Boolean
			MAX-ACCESS read-only
			STATUS current
			DESCRIPTION
				"Description."
			::= { sleV2Pim4IfEntry 12 }

		
		sleV2Pim4IfQueryHoldtime OBJECT-TYPE
			SYNTAX INTEGER (1..65535)
			MAX-ACCESS read-only
			STATUS current
			DESCRIPTION
				"Description."
			::= { sleV2Pim4IfEntry 13 }

		
		sleV2Pim4IfQueryInterval OBJECT-TYPE
			SYNTAX INTEGER (1..18724)
			MAX-ACCESS read-only
			STATUS current
			DESCRIPTION
				"Description."
			::= { sleV2Pim4IfEntry 14 }

		
		sleV2Pim4IfDrPriority OBJECT-TYPE
			SYNTAX Gauge32 (0..4294967294)
			MAX-ACCESS read-only
			STATUS current
			DESCRIPTION
				"Description."
			::= { sleV2Pim4IfEntry 15 }

		
		sleV2Pim4IfExcludeGenID OBJECT-TYPE
			SYNTAX Boolean
			MAX-ACCESS read-only
			STATUS current
			DESCRIPTION
				"Description."
			::= { sleV2Pim4IfEntry 16 }

		
		sleV2Pim4IfNeighborFilterACL OBJECT-TYPE
			SYNTAX OCTET STRING
			MAX-ACCESS read-only
			STATUS current
			DESCRIPTION
				"Description."
			::= { sleV2Pim4IfEntry 17 }

		
		sleV2Pim4IfGroupFilterACL OBJECT-TYPE
			SYNTAX OCTET STRING
			MAX-ACCESS read-only
			STATUS current
			DESCRIPTION
				"Description."
			::= { sleV2Pim4IfEntry 18 }

		
		sleV2Pim4IfGroupFilterRangeACL OBJECT-TYPE
			SYNTAX OCTET STRING
			MAX-ACCESS read-only
			STATUS current
			DESCRIPTION
				"Description."
			::= { sleV2Pim4IfEntry 19 }

		
		sleV2Pim4IfPropagationDelay OBJECT-TYPE
			SYNTAX Integer32 (1000..5000)
			MAX-ACCESS read-only
			STATUS current
			DESCRIPTION
				"Description."
			::= { sleV2Pim4IfEntry 20 }

		
		sleV2Pim4IfBsrBorder OBJECT-TYPE
			SYNTAX Boolean
			MAX-ACCESS read-only
			STATUS current
			DESCRIPTION
				"0 : disable 1: enable"
			::= { sleV2Pim4IfEntry 21 }

		
		sleV2Pim4IfUnicastBsm OBJECT-TYPE
			SYNTAX Boolean
			MAX-ACCESS read-only
			STATUS current
			DESCRIPTION
				"0: disable 1: enable"
			::= { sleV2Pim4IfEntry 22 }

		
		sleV2Pim4IfControl OBJECT IDENTIFIER ::= { sleV2Pim4Interface 2 }

		
		sleV2Pim4IfControlRequest OBJECT-TYPE
			SYNTAX INTEGER
				{
				setPIM4IfInfoProfile(1),
				setPIM4IfStaticProfile(2)
				}
			MAX-ACCESS read-write
			STATUS current
			DESCRIPTION
				"Description."
			::= { sleV2Pim4IfControl 1 }

		
		sleV2Pim4IfControlStatus OBJECT-TYPE
			SYNTAX SleControlStatusType
			MAX-ACCESS read-write
			STATUS current
			DESCRIPTION
				"Description."
			::= { sleV2Pim4IfControl 2 }

		
		sleV2Pim4IfControlTimer OBJECT-TYPE
			SYNTAX Gauge32
			MAX-ACCESS read-write
			STATUS current
			DESCRIPTION
				"Description."
			::= { sleV2Pim4IfControl 3 }

		
		sleV2Pim4IfControlTimeStamp OBJECT-TYPE
			SYNTAX TimeTicks
			MAX-ACCESS read-write
			STATUS current
			DESCRIPTION
				"Description."
			::= { sleV2Pim4IfControl 4 }

		
		sleV2Pim4IfControlReqResult OBJECT-TYPE
			SYNTAX SleControlRequestResultType
			MAX-ACCESS read-write
			STATUS current
			DESCRIPTION
				"Description."
			::= { sleV2Pim4IfControl 5 }

		
		sleV2Pim4IfControlVid OBJECT-TYPE
			SYNTAX INTEGER (1..4094)
			MAX-ACCESS read-write
			STATUS current
			DESCRIPTION
				"Description."
			::= { sleV2Pim4IfControl 6 }

		
		sleV2Pim4IfControlSparseMode OBJECT-TYPE
			SYNTAX Boolean
			MAX-ACCESS read-write
			STATUS current
			DESCRIPTION
				"Description."
			::= { sleV2Pim4IfControl 7 }

		
		sleV2Pim4IfControlSparseModePassive OBJECT-TYPE
			SYNTAX Boolean
			MAX-ACCESS read-write
			STATUS current
			DESCRIPTION
				"Description."
			::= { sleV2Pim4IfControl 8 }

		
		sleV2Pim4IfControlQueryHoldtime OBJECT-TYPE
			SYNTAX INTEGER (-1 | 1..65535)
			MAX-ACCESS read-write
			STATUS current
			DESCRIPTION
				"Description."
			::= { sleV2Pim4IfControl 9 }

		
		sleV2Pim4IfControlQueryInterval OBJECT-TYPE
			SYNTAX INTEGER (-1 | 1..18724)
			MAX-ACCESS read-write
			STATUS current
			DESCRIPTION
				"Description."
			::= { sleV2Pim4IfControl 10 }

		
		sleV2Pim4IfControlDrPriority OBJECT-TYPE
			SYNTAX Gauge32 (0..4294967294)
			MAX-ACCESS read-write
			STATUS current
			DESCRIPTION
				"Description."
			::= { sleV2Pim4IfControl 11 }

		
		sleV2Pim4IfControlExcludeGenID OBJECT-TYPE
			SYNTAX Boolean
			MAX-ACCESS read-write
			STATUS current
			DESCRIPTION
				"Description."
			::= { sleV2Pim4IfControl 12 }

		
		sleV2Pim4IfControlNeighborFilterACL OBJECT-TYPE
			SYNTAX OCTET STRING
			MAX-ACCESS read-write
			STATUS current
			DESCRIPTION
				"Description."
			::= { sleV2Pim4IfControl 13 }

		
		sleV2Pim4IfControlGroupFilterACL OBJECT-TYPE
			SYNTAX OCTET STRING
			MAX-ACCESS read-write
			STATUS current
			DESCRIPTION
				"Description."
			::= { sleV2Pim4IfControl 14 }

		
		sleV2Pim4IfControlGroupFilterRangeACL OBJECT-TYPE
			SYNTAX OCTET STRING
			MAX-ACCESS read-write
			STATUS current
			DESCRIPTION
				"Description."
			::= { sleV2Pim4IfControl 15 }

		
		sleV2Pim4IfControlPropagationDelay OBJECT-TYPE
			SYNTAX Integer32 (1000..5000)
			MAX-ACCESS read-write
			STATUS current
			DESCRIPTION
				"Description."
			::= { sleV2Pim4IfControl 16 }

		
		sleV2Pim4IfControlBsrBorder OBJECT-TYPE
			SYNTAX Boolean
			MAX-ACCESS read-write
			STATUS current
			DESCRIPTION
				"0 : disable 1: enable"
			::= { sleV2Pim4IfControl 17 }

		
		sleV2Pim4IfControlUnicastBsm OBJECT-TYPE
			SYNTAX Boolean
			MAX-ACCESS read-write
			STATUS current
			DESCRIPTION
				"0 : disable 1: enable"
			::= { sleV2Pim4IfControl 18 }

		
		sleV2Pim4IfNotification OBJECT IDENTIFIER ::= { sleV2Pim4Interface 3 }

		
		sleV2Pim4IfProfileChanged NOTIFICATION-TYPE
			OBJECTS { sleV2Pim4IfControlRequest, sleV2Pim4IfControlTimeStamp, sleV2Pim4IfControlUnicastBsm, sleV2Pim4IfControlBsrBorder, sleV2Pim4IfControlPropagationDelay, 
				sleV2Pim4IfControlReqResult, sleV2Pim4IfVid, sleV2Pim4IfSparseMode, sleV2Pim4IfSparseModePassive, sleV2Pim4IfQueryHoldtime, 
				sleV2Pim4IfQueryInterval, sleV2Pim4IfDrPriority, sleV2Pim4IfExcludeGenID, sleV2Pim4IfNeighborFilterACL, sleV2Pim4IfGroupFilterACL, 
				sleV2Pim4IfGroupFilterRangeACL }
			STATUS current
			DESCRIPTION 
				"Description."
			::= { sleV2Pim4IfNotification 1 }

		
		sleV2Pim4Neighbor OBJECT IDENTIFIER ::= { sleV2Pim4Agent 2 }

		
--  PIM Snooping VLAN Table
-- 1.3.6.1.4.1.6296.102.12.2.3.3.1.1
		sleV2Pim4NeighborTable OBJECT-TYPE
			SYNTAX SEQUENCE OF SleV2Pim4NeighborEntry
			MAX-ACCESS not-accessible
			STATUS current
			DESCRIPTION
				"PIM vlan table."
			::= { sleV2Pim4Neighbor 1 }

		
--  PIM Snooping VLAN Entry
-- 1.3.6.1.4.1.6296.102.12.2.4.3.1.1.1
		sleV2Pim4NeighborEntry OBJECT-TYPE
			SYNTAX SleV2Pim4NeighborEntry
			MAX-ACCESS not-accessible
			STATUS current
			DESCRIPTION
				"key: sleV2Pim4VlanIndex"
			INDEX { sleV2Pim4NeighborAddress }
			::= { sleV2Pim4NeighborTable 1 }

		
		SleV2Pim4NeighborEntry ::=
			SEQUENCE { 
				sleV2Pim4NeighborAddress
					IpAddress,
				sleV2Pim4NeighborUptime
					TimeTicks,
				sleV2Pim4NeighborExpireTime
					TimeTicks,
				sleV2Pim4NeighborVersion
					Integer32,
				sleV2Pim4NeighborDr
					INTEGER,
				sleV2Pim4NeighborDrPriority
					Integer32
			 }

-- The IP address of the PIM neighbor for which this entry
--  	contains information.
		sleV2Pim4NeighborAddress OBJECT-TYPE
			SYNTAX IpAddress
			MAX-ACCESS read-only
			STATUS current
			DESCRIPTION
				"This object indicates the VLAN for PIM snooping."
			::= { sleV2Pim4NeighborEntry 1 }

		
-- The time since this PIM neighbor (last) became a neighbor of the local router.
		sleV2Pim4NeighborUptime OBJECT-TYPE
			SYNTAX TimeTicks
			MAX-ACCESS read-only
			STATUS current
			DESCRIPTION
				"It indicates the activity status of  the corresponding VLAN's PIM snooping, this is set by administrator."
			::= { sleV2Pim4NeighborEntry 2 }

		
-- The minimum time remaining before this PIM neighbor will be aged out.
		sleV2Pim4NeighborExpireTime OBJECT-TYPE
			SYNTAX TimeTicks
			MAX-ACCESS read-only
			STATUS current
			DESCRIPTION
				"It indicates the operating status of  the corresponding VLAN's PIM snooping."
			::= { sleV2Pim4NeighborEntry 3 }

		
-- The neighbor version
		sleV2Pim4NeighborVersion OBJECT-TYPE
			SYNTAX Integer32 (2)
			MAX-ACCESS read-only
			STATUS current
			DESCRIPTION
				"This object indicates the VLAN for PIM snooping."
			::= { sleV2Pim4NeighborEntry 4 }

		
-- The DR status
		sleV2Pim4NeighborDr OBJECT-TYPE
			SYNTAX INTEGER
				{
				noneDr(0),
				dr(1)
				}
			MAX-ACCESS read-only
			STATUS current
			DESCRIPTION
				"This object indicates the VLAN for PIM snooping."
			::= { sleV2Pim4NeighborEntry 5 }

		
-- The DR priority
		sleV2Pim4NeighborDrPriority OBJECT-TYPE
			SYNTAX Integer32
			MAX-ACCESS read-only
			STATUS current
			DESCRIPTION
				"This object indicates the VLAN for PIM snooping."
			::= { sleV2Pim4NeighborEntry 6 }

		
		sleV2Pim4Nexthop OBJECT IDENTIFIER ::= { sleV2Pim4Agent 3 }

		
		sleV2Pim4NexthopTable OBJECT-TYPE
			SYNTAX SEQUENCE OF SleV2Pim4NexthopEntry
			MAX-ACCESS not-accessible
			STATUS current
			DESCRIPTION
				"Description."
			::= { sleV2Pim4Nexthop 1 }

		
		sleV2Pim4NexthopEntry OBJECT-TYPE
			SYNTAX SleV2Pim4NexthopEntry
			MAX-ACCESS not-accessible
			STATUS current
			DESCRIPTION
				"Description."
			INDEX { sleV2Pim4NexthopSourceAddress, sleV2Pim4NexthopGroupAddress }
			::= { sleV2Pim4NexthopTable 1 }

		
		SleV2Pim4NexthopEntry ::=
			SEQUENCE { 
				sleV2Pim4NexthopSourceAddress
					IpAddress,
				sleV2Pim4NexthopGroupAddress
					IpAddress,
				sleV2Pim4NexthopNum
					INTEGER,
				sleV2Pim4NexthopType
					BITS,
				sleV2Pim4NexthopAddress
					IpAddress,
				sleV2Pim4NexthopVid
					INTEGER,
				sleV2Pim4NexthopMetric
					INTEGER,
				sleV2Pim4NexthopPref
					INTEGER,
				sleV2Pim4NexthopRefcnt
					INTEGER
			 }

		sleV2Pim4NexthopSourceAddress OBJECT-TYPE
			SYNTAX IpAddress
			MAX-ACCESS read-only
			STATUS current
			DESCRIPTION
				"Description."
			::= { sleV2Pim4NexthopEntry 1 }

		
		sleV2Pim4NexthopGroupAddress OBJECT-TYPE
			SYNTAX IpAddress
			MAX-ACCESS read-only
			STATUS current
			DESCRIPTION
				"Description."
			::= { sleV2Pim4NexthopEntry 2 }

		
		sleV2Pim4NexthopNum OBJECT-TYPE
			SYNTAX INTEGER
			MAX-ACCESS read-only
			STATUS current
			DESCRIPTION
				"Description."
			::= { sleV2Pim4NexthopEntry 3 }

		
		sleV2Pim4NexthopType OBJECT-TYPE
			SYNTAX BITS
				{
				new(0),
				rp(1),
				source(2),
				unreachable(3),
				activePath(4)
				}
			MAX-ACCESS read-only
			STATUS current
			DESCRIPTION
				"Description."
			::= { sleV2Pim4NexthopEntry 4 }

		
		sleV2Pim4NexthopAddress OBJECT-TYPE
			SYNTAX IpAddress
			MAX-ACCESS read-only
			STATUS current
			DESCRIPTION
				"Description."
			::= { sleV2Pim4NexthopEntry 5 }

		
		sleV2Pim4NexthopVid OBJECT-TYPE
			SYNTAX INTEGER (1..4094)
			MAX-ACCESS read-only
			STATUS current
			DESCRIPTION
				"Description."
			::= { sleV2Pim4NexthopEntry 6 }

		
		sleV2Pim4NexthopMetric OBJECT-TYPE
			SYNTAX INTEGER
			MAX-ACCESS read-only
			STATUS current
			DESCRIPTION
				"Description."
			::= { sleV2Pim4NexthopEntry 7 }

		
		sleV2Pim4NexthopPref OBJECT-TYPE
			SYNTAX INTEGER
			MAX-ACCESS read-only
			STATUS current
			DESCRIPTION
				"Description."
			::= { sleV2Pim4NexthopEntry 8 }

		
		sleV2Pim4NexthopRefcnt OBJECT-TYPE
			SYNTAX INTEGER
			MAX-ACCESS read-only
			STATUS current
			DESCRIPTION
				"Description."
			::= { sleV2Pim4NexthopEntry 9 }

		
		sleV2Pim4CandidateRP OBJECT IDENTIFIER ::= { sleV2Pim4Agent 4 }

		
		sleV2Pim4CRPTable OBJECT-TYPE
			SYNTAX SEQUENCE OF SleV2Pim4CRPEntry
			MAX-ACCESS not-accessible
			STATUS current
			DESCRIPTION
				"Description."
			::= { sleV2Pim4CandidateRP 1 }

		
		sleV2Pim4CRPEntry OBJECT-TYPE
			SYNTAX SleV2Pim4CRPEntry
			MAX-ACCESS not-accessible
			STATUS current
			DESCRIPTION
				"Description."
			INDEX { sleV2Pim4CRPVid, sleV2Pim4CRPACL }
			::= { sleV2Pim4CRPTable 1 }

		
		SleV2Pim4CRPEntry ::=
			SEQUENCE { 
				sleV2Pim4CRPVid
					INTEGER,
				sleV2Pim4CRPACL
					OCTET STRING,
				sleV2Pim4RPActive
					INTEGER,
				sleV2Pim4CRPInterval
					INTEGER,
				sleV2Pim4CRPPriority
					INTEGER,
				sleV2Pim4CRPNextAdver
					TimeTicks
			 }

		sleV2Pim4CRPVid OBJECT-TYPE
			SYNTAX INTEGER (1..4094)
			MAX-ACCESS read-only
			STATUS current
			DESCRIPTION
				"Description."
			::= { sleV2Pim4CRPEntry 1 }

		
		sleV2Pim4CRPACL OBJECT-TYPE
			SYNTAX OCTET STRING
			MAX-ACCESS read-only
			STATUS current
			DESCRIPTION
				"Description."
			::= { sleV2Pim4CRPEntry 2 }

		
		sleV2Pim4RPActive OBJECT-TYPE
			SYNTAX INTEGER
				{
				disable(0),
				enable(1)
				}
			MAX-ACCESS read-only
			STATUS current
			DESCRIPTION
				"Description."
			::= { sleV2Pim4CRPEntry 3 }

		
		sleV2Pim4CRPInterval OBJECT-TYPE
			SYNTAX INTEGER (0..16383)
			MAX-ACCESS read-only
			STATUS current
			DESCRIPTION
				"Description."
			::= { sleV2Pim4CRPEntry 4 }

		
		sleV2Pim4CRPPriority OBJECT-TYPE
			SYNTAX INTEGER
			MAX-ACCESS read-only
			STATUS current
			DESCRIPTION
				"Description."
			::= { sleV2Pim4CRPEntry 5 }

		
		sleV2Pim4CRPNextAdver OBJECT-TYPE
			SYNTAX TimeTicks
			MAX-ACCESS read-only
			STATUS current
			DESCRIPTION
				"Description."
			::= { sleV2Pim4CRPEntry 6 }

		
		sleV2Pim4CRPControl OBJECT IDENTIFIER ::= { sleV2Pim4CandidateRP 2 }

		
		sleV2Pim4CRPControlRequest OBJECT-TYPE
			SYNTAX INTEGER
				{
				createPIM4CandidateRP(1),
				destroyPIM4CandidateRP(2)
				}
			MAX-ACCESS read-write
			STATUS current
			DESCRIPTION
				"Description."
			::= { sleV2Pim4CRPControl 1 }

		
		sleV2Pim4CRPControlStatus OBJECT-TYPE
			SYNTAX SleControlStatusType
			MAX-ACCESS read-write
			STATUS current
			DESCRIPTION
				"Description."
			::= { sleV2Pim4CRPControl 2 }

		
		sleV2Pim4CRPControlTimer OBJECT-TYPE
			SYNTAX Gauge32
			MAX-ACCESS read-write
			STATUS current
			DESCRIPTION
				"Description."
			::= { sleV2Pim4CRPControl 3 }

		
		sleV2Pim4CRPControlTimeStamp OBJECT-TYPE
			SYNTAX TimeTicks
			MAX-ACCESS read-write
			STATUS current
			DESCRIPTION
				"Description."
			::= { sleV2Pim4CRPControl 4 }

		
		sleV2Pim4CRPControlReqResult OBJECT-TYPE
			SYNTAX SleControlRequestResultType
			MAX-ACCESS read-write
			STATUS current
			DESCRIPTION
				"Description."
			::= { sleV2Pim4CRPControl 5 }

		
		sleV2Pim4CRPControlVid OBJECT-TYPE
			SYNTAX INTEGER (1..4094)
			MAX-ACCESS read-write
			STATUS current
			DESCRIPTION
				"Description."
			::= { sleV2Pim4CRPControl 6 }

		
		sleV2Pim4CRPControlACL OBJECT-TYPE
			SYNTAX OCTET STRING
			MAX-ACCESS read-write
			STATUS current
			DESCRIPTION
				"Description."
			::= { sleV2Pim4CRPControl 7 }

		
		sleV2Pim4CRPControlInterval OBJECT-TYPE
			SYNTAX INTEGER (-1 | 1..16383)
			MAX-ACCESS read-write
			STATUS current
			DESCRIPTION
				"Description."
			::= { sleV2Pim4CRPControl 8 }

		
		sleV2Pim4CRPControlPriority OBJECT-TYPE
			SYNTAX INTEGER (-1 | 0..255)
			MAX-ACCESS read-write
			STATUS current
			DESCRIPTION
				"Description."
			::= { sleV2Pim4CRPControl 9 }

		
		sleV2Pim4CRPNotification OBJECT IDENTIFIER ::= { sleV2Pim4CandidateRP 3 }

		
		sleV2Pim4CreateCRPProfileChanged NOTIFICATION-TYPE
			OBJECTS { sleV2Pim4CRPVid, sleV2Pim4CRPACL, sleV2Pim4RPActive, sleV2Pim4CRPInterval, sleV2Pim4CRPPriority
				 }
			STATUS current
			DESCRIPTION 
				"Description."
			::= { sleV2Pim4CRPNotification 1 }

		
		sleV2Pim4DestroyCRPProfileChanged NOTIFICATION-TYPE
			OBJECTS { sleV2Pim4CRPControlVid, sleV2Pim4CRPControlACL }
			STATUS current
			DESCRIPTION 
				"Description."
			::= { sleV2Pim4CRPNotification 2 }

		
		sleV2Pim4StaticRP OBJECT IDENTIFIER ::= { sleV2Pim4Agent 5 }

		
		sleV2Pim4SRPTable OBJECT-TYPE
			SYNTAX SEQUENCE OF SleV2Pim4SRPEntry
			MAX-ACCESS not-accessible
			STATUS current
			DESCRIPTION
				"Description."
			::= { sleV2Pim4StaticRP 1 }

		
		sleV2Pim4SRPEntry OBJECT-TYPE
			SYNTAX SleV2Pim4SRPEntry
			MAX-ACCESS not-accessible
			STATUS current
			DESCRIPTION
				"Description."
			INDEX { sleV2Pim4SRPAddr, sleV2Pim4SRPACL }
			::= { sleV2Pim4SRPTable 1 }

		
		SleV2Pim4SRPEntry ::=
			SEQUENCE { 
				sleV2Pim4SRPAddr
					IpAddress,
				sleV2Pim4SRPACL
					OCTET STRING,
				sleV2Pim4SRPOverride
					INTEGER
			 }

		sleV2Pim4SRPAddr OBJECT-TYPE
			SYNTAX IpAddress
			MAX-ACCESS read-only
			STATUS current
			DESCRIPTION
				"Description."
			::= { sleV2Pim4SRPEntry 1 }

		
		sleV2Pim4SRPACL OBJECT-TYPE
			SYNTAX OCTET STRING
			MAX-ACCESS read-only
			STATUS current
			DESCRIPTION
				"Description."
			::= { sleV2Pim4SRPEntry 2 }

		
		sleV2Pim4SRPOverride OBJECT-TYPE
			SYNTAX INTEGER
				{
				disable(0),
				enable(1)
				}
			MAX-ACCESS read-only
			STATUS current
			DESCRIPTION
				"Description."
			::= { sleV2Pim4SRPEntry 3 }

		
		sleV2Pim4SRPControl OBJECT IDENTIFIER ::= { sleV2Pim4StaticRP 2 }

		
		sleV2Pim4SRPControlRequest OBJECT-TYPE
			SYNTAX INTEGER
				{
				createPIM4StaticRP(1),
				destroyPIM4StaticRP(2)
				}
			MAX-ACCESS read-write
			STATUS current
			DESCRIPTION
				"Description."
			::= { sleV2Pim4SRPControl 1 }

		
		sleV2Pim4SRPControlStatus OBJECT-TYPE
			SYNTAX SleControlStatusType
			MAX-ACCESS read-write
			STATUS current
			DESCRIPTION
				"Description."
			::= { sleV2Pim4SRPControl 2 }

		
		sleV2Pim4SRPControlTimer OBJECT-TYPE
			SYNTAX Gauge32
			MAX-ACCESS read-write
			STATUS current
			DESCRIPTION
				"Description."
			::= { sleV2Pim4SRPControl 3 }

		
		sleV2Pim4SRPControlTimeStamp OBJECT-TYPE
			SYNTAX TimeTicks
			MAX-ACCESS read-write
			STATUS current
			DESCRIPTION
				"Description."
			::= { sleV2Pim4SRPControl 4 }

		
		sleV2Pim4SRPControlReqResult OBJECT-TYPE
			SYNTAX SleControlRequestResultType
			MAX-ACCESS read-write
			STATUS current
			DESCRIPTION
				"Description."
			::= { sleV2Pim4SRPControl 5 }

		
		sleV2Pim4SRPControlAddr OBJECT-TYPE
			SYNTAX IpAddress
			MAX-ACCESS read-write
			STATUS current
			DESCRIPTION
				"Description."
			::= { sleV2Pim4SRPControl 6 }

		
		sleV2Pim4SRPControlACL OBJECT-TYPE
			SYNTAX OCTET STRING
			MAX-ACCESS read-write
			STATUS current
			DESCRIPTION
				"Description."
			::= { sleV2Pim4SRPControl 7 }

		
		sleV2Pim4SRPControlOverride OBJECT-TYPE
			SYNTAX INTEGER
				{
				disable(0),
				enable(1)
				}
			MAX-ACCESS read-write
			STATUS current
			DESCRIPTION
				"Description."
			::= { sleV2Pim4SRPControl 8 }

		
		sleV2Pim4SRPNotification OBJECT IDENTIFIER ::= { sleV2Pim4StaticRP 3 }

		
		sleV2Pim4CreateSRPProfileChanged NOTIFICATION-TYPE
			OBJECTS { sleV2Pim4SRPACL, sleV2Pim4SRPAddr, sleV2Pim4SRPOverride }
			STATUS current
			DESCRIPTION 
				"Description."
			::= { sleV2Pim4SRPNotification 1 }

		
		sleV2Pim4DestroySRPProfileChanged NOTIFICATION-TYPE
			OBJECTS { sleV2Pim4SRPControlAddr }
			STATUS current
			DESCRIPTION 
				"Description."
			::= { sleV2Pim4SRPNotification 2 }

		
		sleV2Pim4RPSet OBJECT IDENTIFIER ::= { sleV2Pim4Agent 6 }

		
		sleV2Pim4RPSetTable OBJECT-TYPE
			SYNTAX SEQUENCE OF SleV2Pim4RPSetEntry
			MAX-ACCESS not-accessible
			STATUS current
			DESCRIPTION
				"Description."
			::= { sleV2Pim4RPSet 1 }

		
		sleV2Pim4RPSetEntry OBJECT-TYPE
			SYNTAX SleV2Pim4RPSetEntry
			MAX-ACCESS not-accessible
			STATUS current
			DESCRIPTION
				"Description."
			INDEX { sleV2Pim4RPSetGroupAddress, sleV2Pim4RPSetGroupMask, sleV2Pim4RPSetRPAddress }
			::= { sleV2Pim4RPSetTable 1 }

		
		SleV2Pim4RPSetEntry ::=
			SEQUENCE { 
				sleV2Pim4RPSetGroupAddress
					IpAddress,
				sleV2Pim4RPSetGroupMask
					Integer32,
				sleV2Pim4RPSetRPAddress
					IpAddress,
				sleV2Pim4RPSetSourceAddress
					IpAddress,
				sleV2Pim4RPSetPriority
					INTEGER,
				sleV2Pim4RPSetUptime
					TimeTicks,
				sleV2Pim4RPSetExpire
					TimeTicks
			 }

		sleV2Pim4RPSetGroupAddress OBJECT-TYPE
			SYNTAX IpAddress
			MAX-ACCESS read-only
			STATUS current
			DESCRIPTION
				"Description."
			::= { sleV2Pim4RPSetEntry 1 }

		
		sleV2Pim4RPSetGroupMask OBJECT-TYPE
			SYNTAX Integer32 (0..65535)
			MAX-ACCESS read-only
			STATUS current
			DESCRIPTION
				"Description."
			::= { sleV2Pim4RPSetEntry 2 }

		
		sleV2Pim4RPSetRPAddress OBJECT-TYPE
			SYNTAX IpAddress
			MAX-ACCESS read-only
			STATUS current
			DESCRIPTION
				"Description."
			::= { sleV2Pim4RPSetEntry 3 }

		
		sleV2Pim4RPSetSourceAddress OBJECT-TYPE
			SYNTAX IpAddress
			MAX-ACCESS read-only
			STATUS current
			DESCRIPTION
				"Description."
			::= { sleV2Pim4RPSetEntry 4 }

		
		sleV2Pim4RPSetPriority OBJECT-TYPE
			SYNTAX INTEGER (0..255)
			MAX-ACCESS read-only
			STATUS current
			DESCRIPTION
				"Description."
			::= { sleV2Pim4RPSetEntry 5 }

		
		sleV2Pim4RPSetUptime OBJECT-TYPE
			SYNTAX TimeTicks
			MAX-ACCESS read-only
			STATUS current
			DESCRIPTION
				"Description."
			::= { sleV2Pim4RPSetEntry 6 }

		
		sleV2Pim4RPSetExpire OBJECT-TYPE
			SYNTAX TimeTicks
			MAX-ACCESS read-only
			STATUS current
			DESCRIPTION
				"Description."
			::= { sleV2Pim4RPSetEntry 7 }

		
		sleV2Pim4Mroute OBJECT IDENTIFIER ::= { sleV2Pim4Agent 7 }

		
		sleV2Pim4MrouteXXRP OBJECT IDENTIFIER ::= { sleV2Pim4Mroute 1 }

		
		sleV2Pim4MrtXXRPTable OBJECT-TYPE
			SYNTAX SEQUENCE OF SleV2Pim4MrtXXRPEntry
			MAX-ACCESS not-accessible
			STATUS current
			DESCRIPTION
				"Description."
			::= { sleV2Pim4MrouteXXRP 1 }

		
		sleV2Pim4MrtXXRPEntry OBJECT-TYPE
			SYNTAX SleV2Pim4MrtXXRPEntry
			MAX-ACCESS not-accessible
			STATUS current
			DESCRIPTION
				"Description."
			INDEX { sleV2Pim4MrtXXRPAddress }
			::= { sleV2Pim4MrtXXRPTable 1 }

		
		SleV2Pim4MrtXXRPEntry ::=
			SEQUENCE { 
				sleV2Pim4MrtXXRPAddress
					IpAddress,
				sleV2Pim4MrtXXRPRPFNbrAddress
					IpAddress,
				sleV2Pim4MrtXXRPRPFVid
					INTEGER,
				sleV2Pim4MrtXXRPUpstreamState
					INTEGER,
				sleV2Pim4MrtXXRPJoined
					OCTET STRING,
				sleV2Pim4MrtXXRPOutgoing
					OCTET STRING
			 }

		sleV2Pim4MrtXXRPAddress OBJECT-TYPE
			SYNTAX IpAddress
			MAX-ACCESS read-only
			STATUS current
			DESCRIPTION
				"Description."
			::= { sleV2Pim4MrtXXRPEntry 1 }

		
		sleV2Pim4MrtXXRPRPFNbrAddress OBJECT-TYPE
			SYNTAX IpAddress
			MAX-ACCESS read-only
			STATUS current
			DESCRIPTION
				"Description."
			::= { sleV2Pim4MrtXXRPEntry 2 }

		
		sleV2Pim4MrtXXRPRPFVid OBJECT-TYPE
			SYNTAX INTEGER (1..4094)
			MAX-ACCESS read-only
			STATUS current
			DESCRIPTION
				"Description."
			::= { sleV2Pim4MrtXXRPEntry 3 }

		
		sleV2Pim4MrtXXRPUpstreamState OBJECT-TYPE
			SYNTAX INTEGER
				{
				nonJoined(0),
				joined(1)
				}
			MAX-ACCESS read-only
			STATUS current
			DESCRIPTION
				"Description."
			::= { sleV2Pim4MrtXXRPEntry 4 }

		
		sleV2Pim4MrtXXRPJoined OBJECT-TYPE
			SYNTAX OCTET STRING
			MAX-ACCESS read-only
			STATUS current
			DESCRIPTION
				"Description."
			::= { sleV2Pim4MrtXXRPEntry 5 }

		
		sleV2Pim4MrtXXRPOutgoing OBJECT-TYPE
			SYNTAX OCTET STRING
			MAX-ACCESS read-only
			STATUS current
			DESCRIPTION
				"Description."
			::= { sleV2Pim4MrtXXRPEntry 6 }

		
		sleV2Pim4MrouteXG OBJECT IDENTIFIER ::= { sleV2Pim4Mroute 2 }

		
		sleV2Pim4MrtXGTable OBJECT-TYPE
			SYNTAX SEQUENCE OF SleV2Pim4MrtXGEntry
			MAX-ACCESS not-accessible
			STATUS current
			DESCRIPTION
				"Description."
			::= { sleV2Pim4MrouteXG 1 }

		
		sleV2Pim4MrtXGEntry OBJECT-TYPE
			SYNTAX SleV2Pim4MrtXGEntry
			MAX-ACCESS not-accessible
			STATUS current
			DESCRIPTION
				"Description."
			INDEX { sleV2Pim4MrtXGGroupAddress }
			::= { sleV2Pim4MrtXGTable 1 }

		
		SleV2Pim4MrtXGEntry ::=
			SEQUENCE { 
				sleV2Pim4MrtXGGroupAddress
					IpAddress,
				sleV2Pim4MrtXGStatic
					INTEGER,
				sleV2Pim4MrtXGRPAddress
					IpAddress,
				sleV2Pim4MrtXGRPFNbrAddress
					IpAddress,
				sleV2Pim4MrtXGVid
					INTEGER,
				sleV2Pim4MrtXGUpstreamState
					INTEGER,
				sleV2Pim4MrtXGLocal
					OCTET STRING,
				sleV2Pim4MrtXGJoined
					OCTET STRING,
				sleV2Pim4MrtXGAssertWinner
					OCTET STRING,
				sleV2Pim4MrtXGAssertLoser
					OCTET STRING
			 }

		sleV2Pim4MrtXGGroupAddress OBJECT-TYPE
			SYNTAX IpAddress
			MAX-ACCESS read-only
			STATUS current
			DESCRIPTION
				"Description."
			::= { sleV2Pim4MrtXGEntry 1 }

		
		sleV2Pim4MrtXGStatic OBJECT-TYPE
			SYNTAX INTEGER
				{
				dynamic(0),
				static(1)
				}
			MAX-ACCESS read-only
			STATUS current
			DESCRIPTION
				"Description."
			::= { sleV2Pim4MrtXGEntry 2 }

		
		sleV2Pim4MrtXGRPAddress OBJECT-TYPE
			SYNTAX IpAddress
			MAX-ACCESS read-only
			STATUS current
			DESCRIPTION
				"Description."
			::= { sleV2Pim4MrtXGEntry 3 }

		
		sleV2Pim4MrtXGRPFNbrAddress OBJECT-TYPE
			SYNTAX IpAddress
			MAX-ACCESS read-only
			STATUS current
			DESCRIPTION
				"Description."
			::= { sleV2Pim4MrtXGEntry 4 }

		
		sleV2Pim4MrtXGVid OBJECT-TYPE
			SYNTAX INTEGER (1..4094)
			MAX-ACCESS read-only
			STATUS current
			DESCRIPTION
				"Description."
			::= { sleV2Pim4MrtXGEntry 5 }

		
		sleV2Pim4MrtXGUpstreamState OBJECT-TYPE
			SYNTAX INTEGER
				{
				notJoined(0),
				joined(1)
				}
			MAX-ACCESS read-only
			STATUS current
			DESCRIPTION
				"Description."
			::= { sleV2Pim4MrtXGEntry 6 }

		
		sleV2Pim4MrtXGLocal OBJECT-TYPE
			SYNTAX OCTET STRING
			MAX-ACCESS read-only
			STATUS current
			DESCRIPTION
				"Description."
			::= { sleV2Pim4MrtXGEntry 7 }

		
		sleV2Pim4MrtXGJoined OBJECT-TYPE
			SYNTAX OCTET STRING
			MAX-ACCESS read-only
			STATUS current
			DESCRIPTION
				"Description."
			::= { sleV2Pim4MrtXGEntry 8 }

		
		sleV2Pim4MrtXGAssertWinner OBJECT-TYPE
			SYNTAX OCTET STRING
			MAX-ACCESS read-only
			STATUS current
			DESCRIPTION
				"Description."
			::= { sleV2Pim4MrtXGEntry 9 }

		
		sleV2Pim4MrtXGAssertLoser OBJECT-TYPE
			SYNTAX OCTET STRING
			MAX-ACCESS read-only
			STATUS current
			DESCRIPTION
				"Description."
			::= { sleV2Pim4MrtXGEntry 10 }

		
		sleV2Pim4MrouteFCR OBJECT IDENTIFIER ::= { sleV2Pim4Mroute 3 }

		
		sleV2Pim4MrtFCRTable OBJECT-TYPE
			SYNTAX SEQUENCE OF SleV2Pim4MrtFCREntry
			MAX-ACCESS not-accessible
			STATUS current
			DESCRIPTION
				"Description."
			::= { sleV2Pim4MrouteFCR 1 }

		
		sleV2Pim4MrtFCREntry OBJECT-TYPE
			SYNTAX SleV2Pim4MrtFCREntry
			MAX-ACCESS not-accessible
			STATUS current
			DESCRIPTION
				"Description."
			INDEX { sleV2Pim4MrtXGGroupAddress, sleV2Pim4MrtFcrSourceAddress }
			::= { sleV2Pim4MrtFCRTable 1 }

		
		SleV2Pim4MrtFCREntry ::=
			SEQUENCE { 
				sleV2Pim4MrtFcrSourceAddress
					IpAddress,
				sleV2Pim4MrtFcrOutgoing
					OCTET STRING,
				sleV2Pim4MrtFcrKat
					TimeTicks,
				sleV2Pim4MrtFcrPktCnt
					Counter32
			 }

		sleV2Pim4MrtFcrSourceAddress OBJECT-TYPE
			SYNTAX IpAddress
			MAX-ACCESS read-only
			STATUS current
			DESCRIPTION
				"Description."
			::= { sleV2Pim4MrtFCREntry 1 }

		
		sleV2Pim4MrtFcrOutgoing OBJECT-TYPE
			SYNTAX OCTET STRING
			MAX-ACCESS read-only
			STATUS current
			DESCRIPTION
				"Description."
			::= { sleV2Pim4MrtFCREntry 2 }

		
		sleV2Pim4MrtFcrKat OBJECT-TYPE
			SYNTAX TimeTicks
			MAX-ACCESS read-only
			STATUS current
			DESCRIPTION
				"Description."
			::= { sleV2Pim4MrtFCREntry 3 }

		
		sleV2Pim4MrtFcrPktCnt OBJECT-TYPE
			SYNTAX Counter32
			MAX-ACCESS read-only
			STATUS current
			DESCRIPTION
				"Description."
			::= { sleV2Pim4MrtFCREntry 4 }

		
		sleV2Pim4MrouteSG OBJECT IDENTIFIER ::= { sleV2Pim4Mroute 4 }

		
		sleV2Pim4MrtSGTable OBJECT-TYPE
			SYNTAX SEQUENCE OF SleV2Pim4MrtSGEntry
			MAX-ACCESS not-accessible
			STATUS current
			DESCRIPTION
				"Description."
			::= { sleV2Pim4MrouteSG 1 }

		
		sleV2Pim4MrtSGEntry OBJECT-TYPE
			SYNTAX SleV2Pim4MrtSGEntry
			MAX-ACCESS not-accessible
			STATUS current
			DESCRIPTION
				"Description."
			INDEX { sleV2Pim4MrtSGSourceAddress, sleV2Pim4MrtSGGroupAddress }
			::= { sleV2Pim4MrtSGTable 1 }

		
		SleV2Pim4MrtSGEntry ::=
			SEQUENCE { 
				sleV2Pim4MrtSGSourceAddress
					IpAddress,
				sleV2Pim4MrtSGGroupAddress
					IpAddress,
				sleV2Pim4MrtSGKat
					TimeTicks,
				sleV2Pim4MrtSGRPFNbrAddress
					IpAddress,
				sleV2Pim4MrtSGRPFVid
					INTEGER,
				sleV2Pim4MrtSGSTPBit
					INTEGER,
				sleV2Pim4MrtSGUpstreamState
					INTEGER,
				sleV2Pim4MrtSGLocal
					OCTET STRING,
				sleV2Pim4MrtSGJoined
					OCTET STRING,
				sleV2Pim4MrtSGOutgoing
					OCTET STRING,
				sleV2Pim4MrtSGAssertWinner
					OCTET STRING,
				sleV2Pim4MrtSGAssertLoser
					OCTET STRING
			 }

		sleV2Pim4MrtSGSourceAddress OBJECT-TYPE
			SYNTAX IpAddress
			MAX-ACCESS read-only
			STATUS current
			DESCRIPTION
				"Description."
			::= { sleV2Pim4MrtSGEntry 1 }

		
		sleV2Pim4MrtSGGroupAddress OBJECT-TYPE
			SYNTAX IpAddress
			MAX-ACCESS read-only
			STATUS current
			DESCRIPTION
				"Description."
			::= { sleV2Pim4MrtSGEntry 2 }

		
		sleV2Pim4MrtSGKat OBJECT-TYPE
			SYNTAX TimeTicks
			MAX-ACCESS read-only
			STATUS current
			DESCRIPTION
				"Description."
			::= { sleV2Pim4MrtSGEntry 3 }

		
		sleV2Pim4MrtSGRPFNbrAddress OBJECT-TYPE
			SYNTAX IpAddress
			MAX-ACCESS read-only
			STATUS current
			DESCRIPTION
				"Description."
			::= { sleV2Pim4MrtSGEntry 4 }

		
		sleV2Pim4MrtSGRPFVid OBJECT-TYPE
			SYNTAX INTEGER (1..4094)
			MAX-ACCESS read-only
			STATUS current
			DESCRIPTION
				"Description."
			::= { sleV2Pim4MrtSGEntry 5 }

		
		sleV2Pim4MrtSGSTPBit OBJECT-TYPE
			SYNTAX INTEGER
				{
				nonSpt(0),
				spt(1)
				}
			MAX-ACCESS read-only
			STATUS current
			DESCRIPTION
				"Description."
			::= { sleV2Pim4MrtSGEntry 6 }

		
		sleV2Pim4MrtSGUpstreamState OBJECT-TYPE
			SYNTAX INTEGER
				{
				notJoined(0),
				joined(1)
				}
			MAX-ACCESS read-only
			STATUS current
			DESCRIPTION
				"Description."
			::= { sleV2Pim4MrtSGEntry 7 }

		
		sleV2Pim4MrtSGLocal OBJECT-TYPE
			SYNTAX OCTET STRING
			MAX-ACCESS read-only
			STATUS current
			DESCRIPTION
				"Description."
			::= { sleV2Pim4MrtSGEntry 8 }

		
		sleV2Pim4MrtSGJoined OBJECT-TYPE
			SYNTAX OCTET STRING
			MAX-ACCESS read-only
			STATUS current
			DESCRIPTION
				"Description."
			::= { sleV2Pim4MrtSGEntry 9 }

		
		sleV2Pim4MrtSGOutgoing OBJECT-TYPE
			SYNTAX OCTET STRING
			MAX-ACCESS read-only
			STATUS current
			DESCRIPTION
				"Description."
			::= { sleV2Pim4MrtSGEntry 10 }

		
		sleV2Pim4MrtSGAssertWinner OBJECT-TYPE
			SYNTAX OCTET STRING
			MAX-ACCESS read-only
			STATUS current
			DESCRIPTION
				"Description."
			::= { sleV2Pim4MrtSGEntry 11 }

		
		sleV2Pim4MrtSGAssertLoser OBJECT-TYPE
			SYNTAX OCTET STRING
			MAX-ACCESS read-only
			STATUS current
			DESCRIPTION
				"Description."
			::= { sleV2Pim4MrtSGEntry 12 }

		
		sleV2Pim4MrouteSGRPT OBJECT IDENTIFIER ::= { sleV2Pim4Mroute 5 }

		
		sleV2Pim4MrtSGRPTTable OBJECT-TYPE
			SYNTAX SEQUENCE OF SleV2Pim4MrtSGRPTEntry
			MAX-ACCESS not-accessible
			STATUS current
			DESCRIPTION
				"Description."
			::= { sleV2Pim4MrouteSGRPT 1 }

		
		sleV2Pim4MrtSGRPTEntry OBJECT-TYPE
			SYNTAX SleV2Pim4MrtSGRPTEntry
			MAX-ACCESS not-accessible
			STATUS current
			DESCRIPTION
				"Description."
			INDEX { sleV2Pim4MrtSGRPTSourceAddress, sleV2Pim4MrtSGRPTGroupAddress, sleV2Pim4MrtSGRPTRPAddress }
			::= { sleV2Pim4MrtSGRPTTable 1 }

		
		SleV2Pim4MrtSGRPTEntry ::=
			SEQUENCE { 
				sleV2Pim4MrtSGRPTSourceAddress
					IpAddress,
				sleV2Pim4MrtSGRPTGroupAddress
					IpAddress,
				sleV2Pim4MrtSGRPTRPAddress
					IpAddress,
				sleV2Pim4MrtSGRPTRPFNbrAddress
					IpAddress,
				sleV2Pim4MrtSGRPTRPFVid
					INTEGER,
				sleV2Pim4MrtSGRPTUpstreamState
					INTEGER,
				sleV2Pim4MrtSGRPTLocal
					OCTET STRING,
				sleV2Pim4MrtSGRPTPruned
					OCTET STRING,
				sleV2Pim4MrtSGRPTOutgoing
					OCTET STRING
			 }

		sleV2Pim4MrtSGRPTSourceAddress OBJECT-TYPE
			SYNTAX IpAddress
			MAX-ACCESS read-only
			STATUS current
			DESCRIPTION
				"Description."
			::= { sleV2Pim4MrtSGRPTEntry 1 }

		
		sleV2Pim4MrtSGRPTGroupAddress OBJECT-TYPE
			SYNTAX IpAddress
			MAX-ACCESS read-only
			STATUS current
			DESCRIPTION
				"Description."
			::= { sleV2Pim4MrtSGRPTEntry 2 }

		
		sleV2Pim4MrtSGRPTRPAddress OBJECT-TYPE
			SYNTAX IpAddress
			MAX-ACCESS read-only
			STATUS current
			DESCRIPTION
				"Description."
			::= { sleV2Pim4MrtSGRPTEntry 3 }

		
		sleV2Pim4MrtSGRPTRPFNbrAddress OBJECT-TYPE
			SYNTAX IpAddress
			MAX-ACCESS read-only
			STATUS current
			DESCRIPTION
				"Description."
			::= { sleV2Pim4MrtSGRPTEntry 4 }

		
		sleV2Pim4MrtSGRPTRPFVid OBJECT-TYPE
			SYNTAX INTEGER (1..4094)
			MAX-ACCESS read-only
			STATUS current
			DESCRIPTION
				"Description."
			::= { sleV2Pim4MrtSGRPTEntry 5 }

		
		sleV2Pim4MrtSGRPTUpstreamState OBJECT-TYPE
			SYNTAX INTEGER
				{
				rptNotJoined(0),
				pruned(1),
				notPruned(2)
				}
			MAX-ACCESS read-only
			STATUS current
			DESCRIPTION
				"Description."
			::= { sleV2Pim4MrtSGRPTEntry 6 }

		
		sleV2Pim4MrtSGRPTLocal OBJECT-TYPE
			SYNTAX OCTET STRING
			MAX-ACCESS read-only
			STATUS current
			DESCRIPTION
				"Description."
			::= { sleV2Pim4MrtSGRPTEntry 7 }

		
		sleV2Pim4MrtSGRPTPruned OBJECT-TYPE
			SYNTAX OCTET STRING
			MAX-ACCESS read-only
			STATUS current
			DESCRIPTION
				"Description."
			::= { sleV2Pim4MrtSGRPTEntry 8 }

		
		sleV2Pim4MrtSGRPTOutgoing OBJECT-TYPE
			SYNTAX OCTET STRING
			MAX-ACCESS read-only
			STATUS current
			DESCRIPTION
				"Description."
			::= { sleV2Pim4MrtSGRPTEntry 9 }

		
		sleV2Pim4StaticGroup OBJECT IDENTIFIER ::= { sleV2Pim4Agent 8 }

		
		sleV2Pim4StaticGroupTable OBJECT-TYPE
			SYNTAX SEQUENCE OF SleV2Pim4StaticGroupEntry
			MAX-ACCESS not-accessible
			STATUS current
			DESCRIPTION
				"Description."
			::= { sleV2Pim4StaticGroup 1 }

		
		sleV2Pim4StaticGroupEntry OBJECT-TYPE
			SYNTAX SleV2Pim4StaticGroupEntry
			MAX-ACCESS not-accessible
			STATUS current
			DESCRIPTION
				"Description."
			INDEX { sleV2Pim4IfVid, sleV2Pim4StaticGroupStart, sleV2Pim4StaticGroupEnd }
			::= { sleV2Pim4StaticGroupTable 1 }

		
		SleV2Pim4StaticGroupEntry ::=
			SEQUENCE { 
				sleV2Pim4StaticGroupStart
					IpAddress,
				sleV2Pim4StaticGroupEnd
					IpAddress
			 }

		sleV2Pim4StaticGroupStart OBJECT-TYPE
			SYNTAX IpAddress
			MAX-ACCESS read-only
			STATUS current
			DESCRIPTION
				"Description."
			::= { sleV2Pim4StaticGroupEntry 1 }

		
		sleV2Pim4StaticGroupEnd OBJECT-TYPE
			SYNTAX IpAddress
			MAX-ACCESS read-only
			STATUS current
			DESCRIPTION
				"Description."
			::= { sleV2Pim4StaticGroupEntry 2 }

		
		sleV2Pim4StaticGroupControl OBJECT IDENTIFIER ::= { sleV2Pim4StaticGroup 2 }

		
		sleV2Pim4StaticGroupControlRequest OBJECT-TYPE
			SYNTAX INTEGER
				{
				createPIM4StaticGroupProfile(1),
				destroyPIM4StaticGroupProfile(2)
				}
			MAX-ACCESS read-write
			STATUS current
			DESCRIPTION
				"Description."
			::= { sleV2Pim4StaticGroupControl 1 }

		
		sleV2Pim4StaticGroupControlStatus OBJECT-TYPE
			SYNTAX SleControlStatusType
			MAX-ACCESS read-write
			STATUS current
			DESCRIPTION
				"Description."
			::= { sleV2Pim4StaticGroupControl 2 }

		
		sleV2Pim4StaticGroupControlTimer OBJECT-TYPE
			SYNTAX Gauge32
			MAX-ACCESS read-write
			STATUS current
			DESCRIPTION
				"Description."
			::= { sleV2Pim4StaticGroupControl 3 }

		
		sleV2Pim4StaticGroupControlTimeStamp OBJECT-TYPE
			SYNTAX TimeTicks
			MAX-ACCESS read-write
			STATUS current
			DESCRIPTION
				"Description."
			::= { sleV2Pim4StaticGroupControl 4 }

		
		sleV2Pim4StaticGroupControlReqResult OBJECT-TYPE
			SYNTAX SleControlRequestResultType
			MAX-ACCESS read-write
			STATUS current
			DESCRIPTION
				"Description."
			::= { sleV2Pim4StaticGroupControl 5 }

		
		sleV2Pim4StaticGroupControlVid OBJECT-TYPE
			SYNTAX INTEGER (1..4094)
			MAX-ACCESS read-write
			STATUS current
			DESCRIPTION
				"Description."
			::= { sleV2Pim4StaticGroupControl 6 }

		
		sleV2Pim4StaticGroupControlStart OBJECT-TYPE
			SYNTAX IpAddress
			MAX-ACCESS read-write
			STATUS current
			DESCRIPTION
				"Description."
			::= { sleV2Pim4StaticGroupControl 7 }

		
		sleV2Pim4StaticGroupControlEnd OBJECT-TYPE
			SYNTAX IpAddress
			MAX-ACCESS read-write
			STATUS current
			DESCRIPTION
				"Description."
			::= { sleV2Pim4StaticGroupControl 8 }

		
		sleV2Pim4StaticGroupNotification OBJECT IDENTIFIER ::= { sleV2Pim4StaticGroup 3 }

		
		sleV2Pim4CreateStaticGroupProfileChanged NOTIFICATION-TYPE
			OBJECTS { sleV2Pim4IfVid, sleV2Pim4StaticGroupStart, sleV2Pim4StaticGroupEnd }
			STATUS current
			DESCRIPTION 
				"Description."
			::= { sleV2Pim4StaticGroupNotification 1 }

		
		sleV2Pim4DestroyStaticGroupProfileChanged NOTIFICATION-TYPE
			OBJECTS { sleV2Pim4StaticGroupControlVid, sleV2Pim4StaticGroupControlStart, sleV2Pim4StaticGroupControlEnd }
			STATUS current
			DESCRIPTION 
				"Description."
			::= { sleV2Pim4StaticGroupNotification 2 }

		
--  PIM Snooping
-- 1.3.6.1.4.1.6296.102.12.2.3.3
		sleV2Pim4Snooping OBJECT IDENTIFIER ::= { sleV2Pim4 3 }

		
--  PIM Snooping VLAN
-- 1.3.6.1.4.1.6296.102.12.2.3.3.1
		sleV2Pim4Vlan OBJECT IDENTIFIER ::= { sleV2Pim4Snooping 1 }

		
--  PIM Snooping VLAN Table
-- 1.3.6.1.4.1.6296.102.12.2.3.3.1.1
		sleV2Pim4VlanTable OBJECT-TYPE
			SYNTAX SEQUENCE OF SleV2Pim4VlanEntry
			MAX-ACCESS not-accessible
			STATUS current
			DESCRIPTION
				"PIM vlan table."
			::= { sleV2Pim4Vlan 1 }

		
--  PIM Snooping VLAN Entry
-- 1.3.6.1.4.1.6296.102.12.2.4.3.1.1.1
		sleV2Pim4VlanEntry OBJECT-TYPE
			SYNTAX SleV2Pim4VlanEntry
			MAX-ACCESS not-accessible
			STATUS current
			DESCRIPTION
				"key: sleV2Pim4VlanIndex"
			INDEX { sleV2Pim4VlanIndex }
			::= { sleV2Pim4VlanTable 1 }

		
		SleV2Pim4VlanEntry ::=
			SEQUENCE { 
				sleV2Pim4VlanIndex
					INTEGER,
				sleV2Pim4VlanAdminActivity
					Boolean,
				sleV2Pim4VlanOperActivity
					Boolean
			 }

--  1.3.6.1.4.1.6296.102.12.2.4.3.1.1.1.1
		sleV2Pim4VlanIndex OBJECT-TYPE
			SYNTAX INTEGER (1..4094)
			MAX-ACCESS read-only
			STATUS current
			DESCRIPTION
				"This object indicates the VLAN for PIM snooping."
			::= { sleV2Pim4VlanEntry 1 }

		
--  1.3.6.1.4.1.6296.102.12.2.4.3.1.1.1.2
		sleV2Pim4VlanAdminActivity OBJECT-TYPE
			SYNTAX Boolean
			MAX-ACCESS read-only
			STATUS current
			DESCRIPTION
				"It indicates the activity status of  the corresponding VLAN's PIM snooping, this is set by administrator."
			::= { sleV2Pim4VlanEntry 2 }

		
--  1.3.6.1.4.1.6296.102.12.2.4.3.1.1.1.3
		sleV2Pim4VlanOperActivity OBJECT-TYPE
			SYNTAX Boolean
			MAX-ACCESS read-only
			STATUS current
			DESCRIPTION
				"It indicates the operating status of  the corresponding VLAN's PIM snooping."
			::= { sleV2Pim4VlanEntry 3 }

		
--  PIM Snooping VLAN Control
-- 1.3.6.1.4.1.6296.102.12.2.3.3.1.2
		sleV2Pim4VlanControl OBJECT IDENTIFIER ::= { sleV2Pim4Vlan 2 }

		
--  1.3.6.1.4.1.6296.102.12.2.3.3.1.2.1
		sleV2Pim4VlanControlRequest OBJECT-TYPE
			SYNTAX INTEGER { setPimSnoopVlanActivity(1) }
			MAX-ACCESS read-write
			STATUS current
			DESCRIPTION
				" The request of a user command"
			::= { sleV2Pim4VlanControl 1 }

		
--  1.3.6.1.4.1.6296.102.12.2.3.3.1.2.2
		sleV2Pim4VlanControlStatus OBJECT-TYPE
			SYNTAX SleControlStatusType
			MAX-ACCESS read-only
			STATUS current
			DESCRIPTION
				" The status of user command"
			::= { sleV2Pim4VlanControl 2 }

		
--  1.3.6.1.4.1.6296.102.12.2.3.3.1.2.3
		sleV2Pim4VlanControlTimer OBJECT-TYPE
			SYNTAX Gauge32
			MAX-ACCESS read-write
			STATUS current
			DESCRIPTION
				" The maximum time for the manager for a long running user command"
			::= { sleV2Pim4VlanControl 3 }

		
--    
-- 1.3.6.1.4.1.6296.102.12.2.3.3.1.2.4
		sleV2Pim4VlanControlTimeStamp OBJECT-TYPE
			SYNTAX TimeStamp
			MAX-ACCESS read-only
			STATUS current
			DESCRIPTION
				" The time stamp of the last command(end of command)"
			::= { sleV2Pim4VlanControl 4 }

		
--  1.3.6.1.4.1.6296.102.12.2.3.3.1.2.5
		sleV2Pim4VlanControlReqResult OBJECT-TYPE
			SYNTAX SleControlRequestResultType
			MAX-ACCESS read-only
			STATUS current
			DESCRIPTION
				" The result of the last user command
				"
			::= { sleV2Pim4VlanControl 5 }

		
--  1.3.6.1.4.1.6296.102.12.2.3.3.1.2.6
		sleV2Pim4VlanControlIndex OBJECT-TYPE
			SYNTAX INTEGER (-1 | 1..4094)
			MAX-ACCESS read-write
			STATUS current
			DESCRIPTION
				"This object indicates the VLAN for PIM snooping."
			::= { sleV2Pim4VlanControl 6 }

		
--  1.3.6.1.4.1.6296.102.12.2.3.3.1.2.7
		sleV2Pim4VlanControlAdminActivity OBJECT-TYPE
			SYNTAX Boolean
			MAX-ACCESS read-write
			STATUS current
			DESCRIPTION
				"It indicates the activity status of  the corresponding VLAN's PIM snooping, this is set by administrator."
			::= { sleV2Pim4VlanControl 7 }

		
--  PIM Snooping VLAN Notification
-- 1.3.6.1.4.1.6296.102.12.2.3.3.1.3
		sleV2Pim4VlanNotification OBJECT IDENTIFIER ::= { sleV2Pim4Vlan 3 }

		
--  1.3.6.1.4.1.6296.102.12.2.3.3.1.3.1
		sleV2Pim4VlanActivityChanged NOTIFICATION-TYPE
			OBJECTS { sleV2Pim4VlanControlRequest, sleV2Pim4VlanControlReqResult, sleV2Pim4VlanControlTimeStamp, sleV2Pim4VlanAdminActivity }
			STATUS current
			DESCRIPTION 
				"setPIM4SnoopActivity"
			::= { sleV2Pim4VlanNotification 1 }

		
--  1.3.6.1.4.1.6296.102.12.2.4
		sleV2IgmpProxy OBJECT IDENTIFIER ::= { sleV2Multicast4 4 }

		
--  1.3.6.1.4.1.6296.102.12.2.4.1
		sleV2IgmpProxyBase OBJECT IDENTIFIER ::= { sleV2IgmpProxy 1 }

		
		sleV2IgmpProxyInfo OBJECT IDENTIFIER ::= { sleV2IgmpProxyBase 1 }

		
		sleV2IgmpProxyMultipath OBJECT-TYPE
			SYNTAX Boolean
			MAX-ACCESS read-only
			STATUS current
			DESCRIPTION
				"This is igmp proxy multipath activity."
			::= { sleV2IgmpProxyInfo 1 }

		
		sleV2IgmpProxyInfoControl OBJECT IDENTIFIER ::= { sleV2IgmpProxyBase 2 }

		
		sleV2IgmpProxyInfoControlRequest OBJECT-TYPE
			SYNTAX INTEGER { setIgmpProxyMultipath(1) }
			MAX-ACCESS read-write
			STATUS current
			DESCRIPTION
				"The request of a user command"
			::= { sleV2IgmpProxyInfoControl 1 }

		
		sleV2IgmpProxyInfoControlStatus OBJECT-TYPE
			SYNTAX SleControlStatusType
			MAX-ACCESS read-write
			STATUS current
			DESCRIPTION
				"The status of user command"
			::= { sleV2IgmpProxyInfoControl 2 }

		
		sleV2IgmpProxyInfoControlTimer OBJECT-TYPE
			SYNTAX Gauge32
			MAX-ACCESS read-write
			STATUS current
			DESCRIPTION
				"The maximum time for the manager for a long running user command"
			::= { sleV2IgmpProxyInfoControl 3 }

		
		sleV2IgmpProxyInfoControlTimeStamp OBJECT-TYPE
			SYNTAX TimeTicks
			MAX-ACCESS read-write
			STATUS current
			DESCRIPTION
				"The time stamp of the last command(end of command)"
			::= { sleV2IgmpProxyInfoControl 4 }

		
		sleV2IgmpProxyInfoControlReqResult OBJECT-TYPE
			SYNTAX SleControlRequestResultType
			MAX-ACCESS read-write
			STATUS current
			DESCRIPTION
				"The result of the last user command"
			::= { sleV2IgmpProxyInfoControl 5 }

		
		sleV2IgmpProxyInfoControlMultipath OBJECT-TYPE
			SYNTAX Boolean
			MAX-ACCESS read-write
			STATUS current
			DESCRIPTION
				"This is igmp proxy multipath activity."
			::= { sleV2IgmpProxyInfoControl 6 }

		
		sleV2IgmpProxyInfoNotification OBJECT IDENTIFIER ::= { sleV2IgmpProxyBase 3 }

		
		sleV2IgmpProxyMultipathChanged NOTIFICATION-TYPE
			OBJECTS { sleV2IgmpProxyInfoControlRequest, sleV2IgmpProxyInfoControlTimeStamp, sleV2IgmpProxyInfoControlReqResult, sleV2IgmpProxyInfoControlMultipath }
			STATUS current
			DESCRIPTION 
				"Description."
			::= { sleV2IgmpProxyInfoNotification 1 }

		
--  1.3.6.1.4.1.6296.102.12.2.4.2
		sleV2IgmpProxyAgent OBJECT IDENTIFIER ::= { sleV2IgmpProxy 2 }

		
--  1.3.6.1.4.1.6296.102.12.2.4.2.1
		sleV2IgmpProxyInterface OBJECT IDENTIFIER ::= { sleV2IgmpProxyAgent 1 }

		
--  1.3.6.1.4.1.6296.102.12.2.4.2.1.1
		sleV2IgmpProxyIfTable OBJECT-TYPE
			SYNTAX SEQUENCE OF SleV2IgmpProxyIfEntry
			MAX-ACCESS not-accessible
			STATUS current
			DESCRIPTION
				"IGMP proxy interface table."
			::= { sleV2IgmpProxyInterface 1 }

		
--  1.3.6.1.4.1.6296.102.12.2.4.2.1.1.1
		sleV2IgmpProxyIfEntry OBJECT-TYPE
			SYNTAX SleV2IgmpProxyIfEntry
			MAX-ACCESS not-accessible
			STATUS current
			DESCRIPTION
				"key: sleV2IgmpProxyIfIndex, sleV2IgmpProxyIfMRouteIfIndex"
			INDEX { sleV2IgmpProxyIfIndex, sleV2IgmpProxyIfMRouteIfIndex }
			::= { sleV2IgmpProxyIfTable 1 }

		
		SleV2IgmpProxyIfEntry ::=
			SEQUENCE { 
				sleV2IgmpProxyIfIndex
					INTEGER,
				sleV2IgmpProxyIfMRouteIfIndex
					INTEGER,
				sleV2IgmpProxyIfMRouteQuerySIpMode
					INTEGER,
				sleV2IgmpProxyIfMRouteQuerySIpAddr
					IpAddress,
				sleV2IgmpProxyIfService
					Boolean,
				sleV2IgmpProxyIfServiceSIpMode
					INTEGER,
				sleV2IgmpProxyIfServiceSIpAddr
					IpAddress,
				sleV2IgmpProxyIfServicePriority
					Integer32
			 }

--  1.3.6.1.4.1.6296.102.12.2.4.2.1.1.1.1
		sleV2IgmpProxyIfIndex OBJECT-TYPE
			SYNTAX INTEGER (1..4096)
			MAX-ACCESS read-only
			STATUS current
			DESCRIPTION
				"Network interface index."
			::= { sleV2IgmpProxyIfEntry 1 }

		
--  1.3.6.1.4.1.6296.102.12.2.4.2.1.1.1.2
		sleV2IgmpProxyIfMRouteIfIndex OBJECT-TYPE
			SYNTAX INTEGER (0 | 1..4096)
			MAX-ACCESS read-only
			STATUS current
			DESCRIPTION
				"This value is the igmp-proxy hostside ifindex to multicast routing"
			::= { sleV2IgmpProxyIfEntry 2 }

		
--  1.3.6.1.4.1.6296.102.12.2.4.2.1.1.1.3
		sleV2IgmpProxyIfMRouteQuerySIpMode OBJECT-TYPE
			SYNTAX INTEGER
				{
				unUsed(0),
				interfaceIpAddress(1),
				proxyService(2)
				}
			MAX-ACCESS read-only
			STATUS current
			DESCRIPTION
				"This value is the querier source IP address Mode"
			::= { sleV2IgmpProxyIfEntry 3 }

		
--  1.3.6.1.4.1.6296.102.12.2.4.2.1.1.1.4
		sleV2IgmpProxyIfMRouteQuerySIpAddr OBJECT-TYPE
			SYNTAX IpAddress
			MAX-ACCESS read-only
			STATUS current
			DESCRIPTION
				"This value is the igmp-proxy querier source IP address"
			::= { sleV2IgmpProxyIfEntry 4 }

		
--  1.3.6.1.4.1.6296.102.12.2.4.2.1.1.1.5
		sleV2IgmpProxyIfService OBJECT-TYPE
			SYNTAX Boolean
			MAX-ACCESS read-only
			STATUS current
			DESCRIPTION
				"he true is Igmp Proxy service Enabled on this interface, the false is not."
			::= { sleV2IgmpProxyIfEntry 5 }

		
--  1.3.6.1.4.1.6296.102.12.2.4.2.1.1.1.6
		sleV2IgmpProxyIfServiceSIpMode OBJECT-TYPE
			SYNTAX INTEGER
				{
				unUsed(0),
				interfaceIpAddress(1),
				manual(2),
				firstReporter(3),
				lastReporter(4)
				}
			MAX-ACCESS read-only
			STATUS current
			DESCRIPTION
				"This value is the source Ip address Mode of mroute proxy service"
			::= { sleV2IgmpProxyIfEntry 6 }

		
--  1.3.6.1.4.1.6296.102.12.2.4.2.1.1.1.7
		sleV2IgmpProxyIfServiceSIpAddr OBJECT-TYPE
			SYNTAX IpAddress
			MAX-ACCESS read-only
			STATUS current
			DESCRIPTION
				"This value is the source Ip address by user manually"
			::= { sleV2IgmpProxyIfEntry 7 }

		
		sleV2IgmpProxyIfServicePriority OBJECT-TYPE
			SYNTAX Integer32 (0..255)
			MAX-ACCESS read-only
			STATUS current
			DESCRIPTION
				"The IGMP proxy service priority"
			::= { sleV2IgmpProxyIfEntry 8 }

		
--  1.3.6.1.4.1.6296.102.12.2.4.2.1.2
		sleV2IgmpProxyIfControl OBJECT IDENTIFIER ::= { sleV2IgmpProxyInterface 2 }

		
--  1.3.6.1.4.1.6296.102.12.2.4.2.1.2.1
		sleV2IgmpProxyIfControlRequest OBJECT-TYPE
			SYNTAX INTEGER
				{
				setIgmpProxyIfMroute(1),
				setIgmpProxyIfMrouteSrcIp(2),
				setIgmpProxyIfService(3),
				setIgmpProxyIfServiceSrcIp(4),
				destroyIgmpProxyIfMroute(5)
				}
			MAX-ACCESS read-write
			STATUS current
			DESCRIPTION
				"The request of a user command"
			::= { sleV2IgmpProxyIfControl 1 }

		
--  1.3.6.1.4.1.6296.102.12.2.4.2.1.2.2
		sleV2IgmpProxyIfControlStatus OBJECT-TYPE
			SYNTAX SleControlStatusType
			MAX-ACCESS read-only
			STATUS current
			DESCRIPTION
				"The status of user command"
			::= { sleV2IgmpProxyIfControl 2 }

		
--  1.3.6.1.4.1.6296.102.12.2.4.2.1.2.3
		sleV2IgmpProxyIfControlTimer OBJECT-TYPE
			SYNTAX Gauge32
			MAX-ACCESS read-write
			STATUS current
			DESCRIPTION
				"The maximum time for the manager for a long running user command"
			::= { sleV2IgmpProxyIfControl 3 }

		
--  1.3.6.1.4.1.6296.102.12.2.4.2.1.2.4
		sleV2IgmpProxyIfControlTimeStamp OBJECT-TYPE
			SYNTAX TimeStamp
			MAX-ACCESS read-only
			STATUS current
			DESCRIPTION
				"The time stamp of the last command(end of command)"
			::= { sleV2IgmpProxyIfControl 4 }

		
--  1.3.6.1.4.1.6296.102.12.2.4.2.1.2.5
		sleV2IgmpProxyIfControlReqResult OBJECT-TYPE
			SYNTAX SleControlRequestResultType
			MAX-ACCESS read-only
			STATUS current
			DESCRIPTION
				"The result of the last user command"
			::= { sleV2IgmpProxyIfControl 5 }

		
--  1.3.6.1.4.1.6296.102.12.2.4.2.1.2.6
		sleV2IgmpProxyIfControlIndex OBJECT-TYPE
			SYNTAX INTEGER (1..4096)
			MAX-ACCESS read-write
			STATUS current
			DESCRIPTION
				"Network interface index."
			::= { sleV2IgmpProxyIfControl 6 }

		
--  1.3.6.1.4.1.6296.102.12.2.4.2.1.2.7
		sleV2IgmpProxyIfControlMrouteIfIndex OBJECT-TYPE
			SYNTAX INTEGER (-1 | 1..4096)
			MAX-ACCESS read-write
			STATUS current
			DESCRIPTION
				"This value is the igmp-proxy hostside ifindex to multicast routing"
			::= { sleV2IgmpProxyIfControl 7 }

		
--  1.3.6.1.4.1.6296.102.12.2.4.2.1.2.8
		sleV2IgmpProxyIfControlMrouteQuerySIpMode OBJECT-TYPE
			SYNTAX INTEGER
				{
				interfaceIpAddress(1),
				proxyService(2)
				}
			MAX-ACCESS read-write
			STATUS current
			DESCRIPTION
				"This value is the querier source IP address Mode"
			::= { sleV2IgmpProxyIfControl 8 }

		
--  1.3.6.1.4.1.6296.102.12.2.4.2.1.2.9
		sleV2IgmpProxyIfControlService OBJECT-TYPE
			SYNTAX Boolean
			MAX-ACCESS read-write
			STATUS current
			DESCRIPTION
				"The true is Igmp Proxy service Enabled on this interface, the false is not."
			::= { sleV2IgmpProxyIfControl 9 }

		
--  1.3.6.1.4.1.6296.102.12.2.4.2.1.2.10
		sleV2IgmpProxyIfControlServiceSIpMode OBJECT-TYPE
			SYNTAX INTEGER
				{
				interfaceIpAddress(1),
				manual(2),
				firstReporter(3),
				lastReporter(4)
				}
			MAX-ACCESS read-write
			STATUS current
			DESCRIPTION
				"This value is the source Ip address Mode of mroute proxy service"
			::= { sleV2IgmpProxyIfControl 10 }

		
--  1.3.6.1.4.1.6296.102.12.2.4.2.1.2.11
		sleV2IgmpProxyIfControlServiceSIpAddr OBJECT-TYPE
			SYNTAX IpAddress
			MAX-ACCESS read-write
			STATUS current
			DESCRIPTION
				"This value is the source Ip address by user manually"
			::= { sleV2IgmpProxyIfControl 11 }

		
--  1.3.6.1.4.1.6296.102.12.2.4.2.1.3
		sleV2IgmpProxyIfNotification OBJECT IDENTIFIER ::= { sleV2IgmpProxyInterface 3 }

		
--  1.3.6.1.4.1.6296.102.12.2.4.2.1.3.1
		sleV2IgmpProxyInterfaceMrouteChanged NOTIFICATION-TYPE
			OBJECTS { sleV2IgmpProxyIfControlRequest, sleV2IgmpProxyIfControlTimeStamp, sleV2IgmpProxyIfControlReqResult, sleV2IgmpProxyIfControlIndex, sleV2IgmpProxyIfControlMrouteIfIndex
				 }
			STATUS current
			DESCRIPTION 
				"Description."
			::= { sleV2IgmpProxyIfNotification 1 }

		
--  1.3.6.1.4.1.6296.102.12.2.4.2.1.3.2
		sleV2IgmpProxyInterfaceMrouteSourceIpChanged NOTIFICATION-TYPE
			OBJECTS { sleV2IgmpProxyIfControlRequest, sleV2IgmpProxyIfControlTimeStamp, sleV2IgmpProxyIfControlReqResult, sleV2IgmpProxyIfControlIndex, sleV2IgmpProxyIfControlMrouteQuerySIpMode
				 }
			STATUS current
			DESCRIPTION 
				"Description."
			::= { sleV2IgmpProxyIfNotification 2 }

		
--  1.3.6.1.4.1.6296.102.12.2.4.2.1.3.3
		sleV2IgmpProxyInterfaceServiceChanged NOTIFICATION-TYPE
			OBJECTS { sleV2IgmpProxyIfControlRequest, sleV2IgmpProxyIfControlTimeStamp, sleV2IgmpProxyIfControlReqResult, sleV2IgmpProxyIfControlIndex, sleV2IgmpProxyIfControlService
				 }
			STATUS current
			DESCRIPTION 
				"Description."
			::= { sleV2IgmpProxyIfNotification 3 }

		
--  1.3.6.1.4.1.6296.102.12.2.4.2.1.3.4
		sleV2IgmpProxyInterfaceServiceSourceIpChanged NOTIFICATION-TYPE
			OBJECTS { sleV2IgmpProxyIfControlRequest, sleV2IgmpProxyIfControlTimeStamp, sleV2IgmpProxyIfControlReqResult, sleV2IgmpProxyIfControlIndex, sleV2IgmpProxyIfControlServiceSIpMode, 
				sleV2IgmpProxyIfControlServiceSIpAddr }
			STATUS current
			DESCRIPTION 
				"Description."
			::= { sleV2IgmpProxyIfNotification 4 }

		
--  1.3.6.1.4.1.6296.102.12.2.4.2.1.3.1
		sleV2IgmpProxyInterfaceMrouteDeleted NOTIFICATION-TYPE
			OBJECTS { sleV2IgmpProxyIfControlRequest, sleV2IgmpProxyIfControlTimeStamp, sleV2IgmpProxyIfControlReqResult, sleV2IgmpProxyIfControlIndex, sleV2IgmpProxyIfControlMrouteIfIndex
				 }
			STATUS current
			DESCRIPTION 
				"Description."
			::= { sleV2IgmpProxyIfNotification 5 }

		
--  1.3.6.1.4.1.6296.102.12.3
		sleV2Multicast6 OBJECT IDENTIFIER ::= { sleV2Multicast 3 }

		
		sleV2Mrib6 OBJECT IDENTIFIER ::= { sleV2Multicast6 1 }

		
		sleV2M6RouteBase OBJECT IDENTIFIER ::= { sleV2Mrib6 1 }

		
		sleV2M6RouteInfo OBJECT IDENTIFIER ::= { sleV2M6RouteBase 1 }

		
		sleV2M6RouteInfoActive OBJECT-TYPE
			SYNTAX Boolean
			MAX-ACCESS read-only
			STATUS current
			DESCRIPTION
				"Description."
			::= { sleV2M6RouteInfo 1 }

		
		sleV2M6RouteInfoLimit OBJECT-TYPE
			SYNTAX INTEGER (1..2147483647)
			MAX-ACCESS read-only
			STATUS current
			DESCRIPTION
				"Description."
			::= { sleV2M6RouteInfo 2 }

		
		sleV2M6RouteInfoThreshold OBJECT-TYPE
			SYNTAX INTEGER
			MAX-ACCESS read-only
			STATUS current
			DESCRIPTION
				"Description."
			::= { sleV2M6RouteInfo 3 }

		
		sleV2M6RouteInfoUnknownFlood OBJECT-TYPE
			SYNTAX Boolean
			MAX-ACCESS read-only
			STATUS current
			DESCRIPTION
				"Description."
			::= { sleV2M6RouteInfo 4 }

		
		sleV2M6RouteInfoUnknownFloodPMap OBJECT-TYPE
			SYNTAX OCTET STRING
			MAX-ACCESS read-only
			STATUS current
			DESCRIPTION
				"Description."
			::= { sleV2M6RouteInfo 5 }

		
		sleV2M6RouteInfoNextPollTime OBJECT-TYPE
			SYNTAX TimeTicks
			MAX-ACCESS read-only
			STATUS current
			DESCRIPTION
				"Description."
			::= { sleV2M6RouteInfo 6 }

		
		sleV2M6RouteInfoNumNocacheRecv OBJECT-TYPE
			SYNTAX Counter32
			MAX-ACCESS read-only
			STATUS current
			DESCRIPTION
				"Description."
			::= { sleV2M6RouteInfo 7 }

		
		sleV2M6RouteInfoNumWrongMIFRecv OBJECT-TYPE
			SYNTAX Counter32
			MAX-ACCESS read-only
			STATUS current
			DESCRIPTION
				"Description."
			::= { sleV2M6RouteInfo 8 }

		
		sleV2M6RouteInfoNumWholePktRecv OBJECT-TYPE
			SYNTAX Counter32
			MAX-ACCESS read-only
			STATUS current
			DESCRIPTION
				"Description."
			::= { sleV2M6RouteInfo 9 }

		
		sleV2M6RouteInfoNumNocacheSent OBJECT-TYPE
			SYNTAX Counter32
			MAX-ACCESS read-only
			STATUS current
			DESCRIPTION
				"Description."
			::= { sleV2M6RouteInfo 10 }

		
		sleV2M6RouteInfoNumWrongMIFSent OBJECT-TYPE
			SYNTAX Counter32
			MAX-ACCESS read-only
			STATUS current
			DESCRIPTION
				"Description."
			::= { sleV2M6RouteInfo 11 }

		
		sleV2M6RouteInfoNumWholePktSent OBJECT-TYPE
			SYNTAX Counter32
			MAX-ACCESS read-only
			STATUS current
			DESCRIPTION
				"Description."
			::= { sleV2M6RouteInfo 12 }

		
		sleV2M6RouteInfoRegAckRecv OBJECT-TYPE
			SYNTAX Counter32
			MAX-ACCESS read-only
			STATUS current
			DESCRIPTION
				"Description."
			::= { sleV2M6RouteInfo 13 }

		
		sleV2M6RouteInfoRegNackRecv OBJECT-TYPE
			SYNTAX Counter32
			MAX-ACCESS read-only
			STATUS current
			DESCRIPTION
				"Description."
			::= { sleV2M6RouteInfo 14 }

		
		sleV2M6RouteInfoRegPktSent OBJECT-TYPE
			SYNTAX Counter32
			MAX-ACCESS read-only
			STATUS current
			DESCRIPTION
				"Description."
			::= { sleV2M6RouteInfo 15 }

		
		sleV2M6RouteInfoControl OBJECT IDENTIFIER ::= { sleV2M6RouteBase 2 }

		
		sleV2M6RouteInfoControlRequest OBJECT-TYPE
			SYNTAX INTEGER { setM6RouteInfoProfile(1) }
			MAX-ACCESS read-write
			STATUS current
			DESCRIPTION
				"Description."
			::= { sleV2M6RouteInfoControl 1 }

		
		sleV2M6RouteInfoControlStatus OBJECT-TYPE
			SYNTAX SleControlStatusType
			MAX-ACCESS read-write
			STATUS current
			DESCRIPTION
				"Description."
			::= { sleV2M6RouteInfoControl 2 }

		
		sleV2M6RouteInfoControlTimer OBJECT-TYPE
			SYNTAX Gauge32
			MAX-ACCESS read-write
			STATUS current
			DESCRIPTION
				"Description."
			::= { sleV2M6RouteInfoControl 3 }

		
		sleV2M6RouteInfoControlTimeStamp OBJECT-TYPE
			SYNTAX TimeTicks
			MAX-ACCESS read-write
			STATUS current
			DESCRIPTION
				"Description."
			::= { sleV2M6RouteInfoControl 4 }

		
		sleV2M6RouteInfoControlReqResult OBJECT-TYPE
			SYNTAX SleControlRequestResultType
			MAX-ACCESS read-write
			STATUS current
			DESCRIPTION
				"Description."
			::= { sleV2M6RouteInfoControl 5 }

		
		sleV2M6RouteInfoControlActive OBJECT-TYPE
			SYNTAX Boolean
			MAX-ACCESS read-write
			STATUS current
			DESCRIPTION
				"Description."
			::= { sleV2M6RouteInfoControl 6 }

		
		sleV2M6RouteInfoControlLimit OBJECT-TYPE
			SYNTAX INTEGER (-1 | 1..2147483647)
			MAX-ACCESS read-write
			STATUS current
			DESCRIPTION
				"Description."
			::= { sleV2M6RouteInfoControl 7 }

		
		sleV2M6RouteInfoControlThreshold OBJECT-TYPE
			SYNTAX INTEGER
			MAX-ACCESS read-write
			STATUS current
			DESCRIPTION
				"Description."
			::= { sleV2M6RouteInfoControl 8 }

		
		sleV2M6RouteInfoControlUnknownFlood OBJECT-TYPE
			SYNTAX Boolean
			MAX-ACCESS read-write
			STATUS current
			DESCRIPTION
				"Description."
			::= { sleV2M6RouteInfoControl 9 }

		
		sleV2M6RouteInfoControlUnknownFloodPMap OBJECT-TYPE
			SYNTAX OCTET STRING
			MAX-ACCESS read-write
			STATUS current
			DESCRIPTION
				"Description."
			::= { sleV2M6RouteInfoControl 10 }

		
		sleV2M6RouteInfoNotification OBJECT IDENTIFIER ::= { sleV2M6RouteBase 3 }

		
		sleV2M6RouteInfoProfileChanged NOTIFICATION-TYPE
			OBJECTS { sleV2M6RouteInfoControlRequest, sleV2M6RouteInfoControlTimeStamp, sleV2M6RouteInfoControlReqResult, sleV2M6RouteInfoActive, sleV2M6RouteInfoLimit, 
				sleV2M6RouteInfoThreshold, sleV2M6RouteInfoUnknownFlood, sleV2M6RouteInfoUnknownFloodPMap }
			STATUS current
			DESCRIPTION 
				"Description."
			::= { sleV2M6RouteInfoNotification 1 }

		
		sleV2M6Route OBJECT IDENTIFIER ::= { sleV2Mrib6 2 }

		
		sleV2M6RouteTable OBJECT-TYPE
			SYNTAX SEQUENCE OF SleV2M6RouteEntry
			MAX-ACCESS not-accessible
			STATUS current
			DESCRIPTION
				"Description."
			::= { sleV2M6Route 1 }

		
		sleV2M6RouteEntry OBJECT-TYPE
			SYNTAX SleV2M6RouteEntry
			MAX-ACCESS not-accessible
			STATUS current
			DESCRIPTION
				"Description."
			INDEX { sleV2M6RouteGroupAddress, sleV2M6RouteSourceAddress }
			::= { sleV2M6RouteTable 1 }

		
		SleV2M6RouteEntry ::=
			SEQUENCE { 
				sleV2M6RouteGroupAddress
					InetAddressIPv6,
				sleV2M6RouteSourceAddress
					InetAddressIPv6,
				sleV2M6RouteUptime
					TimeTicks,
				sleV2M6RouteExpire
					TimeTicks,
				sleV2M6RouteOwner
					INTEGER,
				sleV2M6RouteFlags
					BITS,
				sleV2M6RouteIncoming
					INTEGER,
				sleV2M6RouteOutgoing
					OCTET STRING,
				sleV2M6RouteNumWrongMIFRecv
					Counter32,
				sleV2M6RouteNumWrongMIFSent
					Counter32,
				sleV2M6RouteNumWholePktRecv
					Counter32,
				sleV2M6RouteNumWholePktSent
					Counter32,
				sleV2M6RouteNumImmStatSent
					Counter32,
				sleV2M6RouteNumTimedStatSent
					Counter32,
				sleV2M6RouteRegAckRecv
					Counter32,
				sleV2M6RouteRegNackRecv
					Counter32,
				sleV2M6RouteRegPktSent
					Counter32
			 }

		sleV2M6RouteGroupAddress OBJECT-TYPE
			SYNTAX InetAddressIPv6
			MAX-ACCESS read-only
			STATUS current
			DESCRIPTION
				"Description."
			::= { sleV2M6RouteEntry 1 }

		
		sleV2M6RouteSourceAddress OBJECT-TYPE
			SYNTAX InetAddressIPv6
			MAX-ACCESS read-only
			STATUS current
			DESCRIPTION
				"Description."
			::= { sleV2M6RouteEntry 2 }

		
		sleV2M6RouteUptime OBJECT-TYPE
			SYNTAX TimeTicks
			MAX-ACCESS read-only
			STATUS current
			DESCRIPTION
				"Description."
			::= { sleV2M6RouteEntry 3 }

		
		sleV2M6RouteExpire OBJECT-TYPE
			SYNTAX TimeTicks
			MAX-ACCESS read-only
			STATUS current
			DESCRIPTION
				"Description."
			::= { sleV2M6RouteEntry 4 }

		
		sleV2M6RouteOwner OBJECT-TYPE
			SYNTAX INTEGER
				{
				unkown(0),
				pim6(1),
				mldproxy(2)
				}
			MAX-ACCESS read-only
			STATUS current
			DESCRIPTION
				"Description."
			::= { sleV2M6RouteEntry 5 }

		
		sleV2M6RouteFlags OBJECT-TYPE
			SYNTAX BITS
				{
				statIMM(0),
				stateTIMED(1),
				fwd(2)
				}
			MAX-ACCESS read-only
			STATUS current
			DESCRIPTION
				"Description."
			::= { sleV2M6RouteEntry 6 }

		
		sleV2M6RouteIncoming OBJECT-TYPE
			SYNTAX INTEGER
			MAX-ACCESS read-only
			STATUS current
			DESCRIPTION
				"Description."
			::= { sleV2M6RouteEntry 7 }

		
		sleV2M6RouteOutgoing OBJECT-TYPE
			SYNTAX OCTET STRING
			MAX-ACCESS read-only
			STATUS current
			DESCRIPTION
				"Description."
			::= { sleV2M6RouteEntry 8 }

		
		sleV2M6RouteNumWrongMIFRecv OBJECT-TYPE
			SYNTAX Counter32
			MAX-ACCESS read-only
			STATUS current
			DESCRIPTION
				"Description."
			::= { sleV2M6RouteEntry 9 }

		
		sleV2M6RouteNumWrongMIFSent OBJECT-TYPE
			SYNTAX Counter32
			MAX-ACCESS read-only
			STATUS current
			DESCRIPTION
				"Description."
			::= { sleV2M6RouteEntry 10 }

		
		sleV2M6RouteNumWholePktRecv OBJECT-TYPE
			SYNTAX Counter32
			MAX-ACCESS read-only
			STATUS current
			DESCRIPTION
				"Description."
			::= { sleV2M6RouteEntry 11 }

		
		sleV2M6RouteNumWholePktSent OBJECT-TYPE
			SYNTAX Counter32
			MAX-ACCESS read-only
			STATUS current
			DESCRIPTION
				"Description."
			::= { sleV2M6RouteEntry 12 }

		
		sleV2M6RouteNumImmStatSent OBJECT-TYPE
			SYNTAX Counter32
			MAX-ACCESS read-only
			STATUS current
			DESCRIPTION
				"Description."
			::= { sleV2M6RouteEntry 13 }

		
		sleV2M6RouteNumTimedStatSent OBJECT-TYPE
			SYNTAX Counter32
			MAX-ACCESS read-only
			STATUS current
			DESCRIPTION
				"Description."
			::= { sleV2M6RouteEntry 14 }

		
		sleV2M6RouteRegAckRecv OBJECT-TYPE
			SYNTAX Counter32
			MAX-ACCESS read-only
			STATUS current
			DESCRIPTION
				"Description."
			::= { sleV2M6RouteEntry 15 }

		
		sleV2M6RouteRegNackRecv OBJECT-TYPE
			SYNTAX Counter32
			MAX-ACCESS read-only
			STATUS current
			DESCRIPTION
				"Description."
			::= { sleV2M6RouteEntry 16 }

		
		sleV2M6RouteRegPktSent OBJECT-TYPE
			SYNTAX Counter32
			MAX-ACCESS read-only
			STATUS current
			DESCRIPTION
				"Description."
			::= { sleV2M6RouteEntry 17 }

		
		sleV2M6RouteControl OBJECT IDENTIFIER ::= { sleV2M6Route 2 }

		
		sleV2M6RouteControlRequest OBJECT-TYPE
			SYNTAX INTEGER
				{
				clearM6RouteEntry(1),
				clearM6RouteEntryAll(2),
				clearM6RouteCounter(3),
				clearM6RouteCounterAll(4)
				}
			MAX-ACCESS read-write
			STATUS current
			DESCRIPTION
				"Description."
			::= { sleV2M6RouteControl 1 }

		
		sleV2M6RouteControlStatus OBJECT-TYPE
			SYNTAX SleControlStatusType
			MAX-ACCESS read-write
			STATUS current
			DESCRIPTION
				"Description."
			::= { sleV2M6RouteControl 2 }

		
		sleV2M6RouteControlTimer OBJECT-TYPE
			SYNTAX Gauge32
			MAX-ACCESS read-write
			STATUS current
			DESCRIPTION
				"Description."
			::= { sleV2M6RouteControl 3 }

		
		sleV2M6RouteControlTimeStamp OBJECT-TYPE
			SYNTAX TimeTicks
			MAX-ACCESS read-write
			STATUS current
			DESCRIPTION
				"Description."
			::= { sleV2M6RouteControl 4 }

		
		sleV2M6RouteControlReqResult OBJECT-TYPE
			SYNTAX SleControlRequestResultType
			MAX-ACCESS read-write
			STATUS current
			DESCRIPTION
				"Description."
			::= { sleV2M6RouteControl 5 }

		
		sleV2M6RouteControlGroupAddress OBJECT-TYPE
			SYNTAX InetAddressIPv6
			MAX-ACCESS read-write
			STATUS current
			DESCRIPTION
				"Description."
			::= { sleV2M6RouteControl 6 }

		
		sleV2M6RouteControlSourceAddress OBJECT-TYPE
			SYNTAX InetAddressIPv6
			MAX-ACCESS read-write
			STATUS current
			DESCRIPTION
				"Description."
			::= { sleV2M6RouteControl 7 }

		
		sleV2M6RouteNotification OBJECT IDENTIFIER ::= { sleV2M6Route 3 }

		
		sleV2M6RouteEntryCleared NOTIFICATION-TYPE
			OBJECTS { sleV2M6RouteControlRequest, sleV2M6RouteControlTimeStamp, sleV2M6RouteControlReqResult, sleV2M6RouteControlGroupAddress, sleV2M6RouteControlSourceAddress
				 }
			STATUS current
			DESCRIPTION 
				"Description."
			::= { sleV2M6RouteNotification 1 }

		
		sleV2M6RouteEntryClearedAll NOTIFICATION-TYPE
			OBJECTS { sleV2M6RouteControlRequest, sleV2M6RouteControlTimeStamp, sleV2M6RouteControlReqResult }
			STATUS current
			DESCRIPTION 
				"Description."
			::= { sleV2M6RouteNotification 2 }

		
		sleV2M6RouteCounterCleared NOTIFICATION-TYPE
			OBJECTS { sleV2M6RouteControlRequest, sleV2M6RouteControlTimeStamp, sleV2M6RouteControlReqResult, sleV2M6RouteControlGroupAddress, sleV2M6RouteControlSourceAddress
				 }
			STATUS current
			DESCRIPTION 
				"Description."
			::= { sleV2M6RouteNotification 3 }

		
		sleV2M6RouteCounterClearedAll NOTIFICATION-TYPE
			OBJECTS { sleV2M6RouteControlRequest, sleV2M6RouteControlTimeStamp, sleV2M6RouteControlReqResult }
			STATUS current
			DESCRIPTION 
				"Description."
			::= { sleV2M6RouteNotification 4 }

		
		sleV2Pim6 OBJECT IDENTIFIER ::= { sleV2Multicast6 2 }

		
		sleV2Pim6Base OBJECT IDENTIFIER ::= { sleV2Pim6 1 }

		
		sleV2Pim6Info OBJECT IDENTIFIER ::= { sleV2Pim6Base 1 }

		
		sleV2Pim6InfoJTTimer OBJECT-TYPE
			SYNTAX INTEGER (1..65535)
			MAX-ACCESS read-only
			STATUS current
			DESCRIPTION
				"Description."
			::= { sleV2Pim6Info 1 }

		
		sleV2Pim6InfoSPTThreshold OBJECT-TYPE
			SYNTAX Boolean
			MAX-ACCESS read-only
			STATUS current
			DESCRIPTION
				"Description."
			::= { sleV2Pim6Info 2 }

		
		sleV2Pim6InfoSPTThresholdACL OBJECT-TYPE
			SYNTAX OCTET STRING
			MAX-ACCESS read-only
			STATUS current
			DESCRIPTION
				"Description."
			::= { sleV2Pim6Info 3 }

		
		sleV2Pim6InfoSSMDefault OBJECT-TYPE
			SYNTAX Boolean
			MAX-ACCESS read-only
			STATUS current
			DESCRIPTION
				"Description."
			::= { sleV2Pim6Info 4 }

		
		sleV2Pim6InfoSSMRangeACL OBJECT-TYPE
			SYNTAX OCTET STRING
			MAX-ACCESS read-only
			STATUS current
			DESCRIPTION
				"Description."
			::= { sleV2Pim6Info 5 }

		
		sleV2Pim6InfoCRPCiscoPrefix OBJECT-TYPE
			SYNTAX Boolean
			MAX-ACCESS read-only
			STATUS current
			DESCRIPTION
				"Description."
			::= { sleV2Pim6Info 6 }

		
		sleV2Pim6InfoIgnoreRPSetPriority OBJECT-TYPE
			SYNTAX Boolean
			MAX-ACCESS read-only
			STATUS current
			DESCRIPTION
				"Description."
			::= { sleV2Pim6Info 7 }

		
		sleV2Pim6InfoBSRCandidateInterface OBJECT-TYPE
			SYNTAX INTEGER (1..65535)
			MAX-ACCESS read-only
			STATUS current
			DESCRIPTION
				"Description."
			::= { sleV2Pim6Info 8 }

		
		sleV2Pim6InfoBSRCnadidateHash OBJECT-TYPE
			SYNTAX INTEGER (0..32)
			MAX-ACCESS read-only
			STATUS current
			DESCRIPTION
				"Description."
			::= { sleV2Pim6Info 9 }

		
		sleV2Pim6InfoBSRCandidatePriority OBJECT-TYPE
			SYNTAX INTEGER (0..255)
			MAX-ACCESS read-only
			STATUS current
			DESCRIPTION
				"Description."
			::= { sleV2Pim6Info 10 }

		
		sleV2Pim6InfoBSRRole OBJECT-TYPE
			SYNTAX INTEGER
				{
				nonCandidateBSR(1),
				candidateBSR(2)
				}
			MAX-ACCESS read-write
			STATUS current
			DESCRIPTION
				"Description."
			::= { sleV2Pim6Info 11 }

		
		sleV2Pim6InfoBSRStatus OBJECT-TYPE
			SYNTAX INTEGER
				{
				noInfo(1),
				acceptAny(2),
				acceptPreferred(3),
				candidateBSR(4),
				pendingBSR(5),
				elsectedBSR(6)
				}
			MAX-ACCESS read-write
			STATUS current
			DESCRIPTION
				"Description."
			::= { sleV2Pim6Info 12 }

		
		sleV2Pim6InfoBSRUptime OBJECT-TYPE
			SYNTAX TimeTicks
			MAX-ACCESS read-write
			STATUS current
			DESCRIPTION
				"Description."
			::= { sleV2Pim6Info 13 }

		
		sleV2Pim6InfoRegisterRateLimit OBJECT-TYPE
			SYNTAX INTEGER (1..65535)
			MAX-ACCESS read-only
			STATUS current
			DESCRIPTION
				"Description."
			::= { sleV2Pim6Info 14 }

		
		sleV2Pim6InfoRegisterSourceIPAddr OBJECT-TYPE
			SYNTAX InetAddressIPv6
			MAX-ACCESS read-only
			STATUS current
			DESCRIPTION
				"Description."
			::= { sleV2Pim6Info 15 }

		
		sleV2Pim6InfoRegisterSourceInterface OBJECT-TYPE
			SYNTAX INTEGER (1..65535)
			MAX-ACCESS read-only
			STATUS current
			DESCRIPTION
				"Description."
			::= { sleV2Pim6Info 16 }

		
		sleV2Pim6InfoRegisterRPReachability OBJECT-TYPE
			SYNTAX Boolean
			MAX-ACCESS read-only
			STATUS current
			DESCRIPTION
				"Description."
			::= { sleV2Pim6Info 17 }

		
		sleV2Pim6InfoRegisterSuppression OBJECT-TYPE
			SYNTAX INTEGER (1..65535)
			MAX-ACCESS read-only
			STATUS current
			DESCRIPTION
				"Description."
			::= { sleV2Pim6Info 18 }

		
		sleV2Pim6InfoAcceptRegisterACL OBJECT-TYPE
			SYNTAX OCTET STRING
			MAX-ACCESS read-only
			STATUS current
			DESCRIPTION
				"Description."
			::= { sleV2Pim6Info 19 }

		
		sleV2Pim6InfoRPRegisterKAT OBJECT-TYPE
			SYNTAX INTEGER (1..65535)
			MAX-ACCESS read-only
			STATUS current
			DESCRIPTION
				"Description."
			::= { sleV2Pim6Info 20 }

		
		sleV2Pim6InfoCiscoRegisterChecksum OBJECT-TYPE
			SYNTAX Boolean
			MAX-ACCESS read-only
			STATUS current
			DESCRIPTION
				"Description."
			::= { sleV2Pim6Info 21 }

		
		sleV2Pim6InfoCiscoRegisterChecksumACL OBJECT-TYPE
			SYNTAX OCTET STRING
			MAX-ACCESS read-only
			STATUS current
			DESCRIPTION
				"Description."
			::= { sleV2Pim6Info 22 }

		
		sleV2Pim6InfoControl OBJECT IDENTIFIER ::= { sleV2Pim6Base 2 }

		
		sleV2Pim6InfoControlRequest OBJECT-TYPE
			SYNTAX INTEGER
				{
				setPIM6InfoProfile(1),
				setPIM6InfoRPProfile(2),
				setPIM6InfoBSRProfile(3),
				setPIM6InfoRegisterProfile(4),
				clearPIM6InfoMRT(5),
				clearPIM6InfoRPSet(6)
				}
			MAX-ACCESS read-write
			STATUS current
			DESCRIPTION
				"Description."
			::= { sleV2Pim6InfoControl 1 }

		
		sleV2Pim6InfoControlStatus OBJECT-TYPE
			SYNTAX SleControlStatusType
			MAX-ACCESS read-write
			STATUS current
			DESCRIPTION
				"Description."
			::= { sleV2Pim6InfoControl 2 }

		
		sleV2Pim6InfoControlTimer OBJECT-TYPE
			SYNTAX Gauge32
			MAX-ACCESS read-write
			STATUS current
			DESCRIPTION
				"Description."
			::= { sleV2Pim6InfoControl 3 }

		
		sleV2Pim6InfoControlTimeStamp OBJECT-TYPE
			SYNTAX TimeTicks
			MAX-ACCESS read-write
			STATUS current
			DESCRIPTION
				"Description."
			::= { sleV2Pim6InfoControl 4 }

		
		sleV2Pim6InfoControlReqResult OBJECT-TYPE
			SYNTAX SleControlRequestResultType
			MAX-ACCESS read-write
			STATUS current
			DESCRIPTION
				"Description."
			::= { sleV2Pim6InfoControl 5 }

		
		sleV2Pim6InfoControlMessageInterval OBJECT-TYPE
			SYNTAX INTEGER (-1 | 1..65535)
			MAX-ACCESS read-write
			STATUS current
			DESCRIPTION
				"Description."
			::= { sleV2Pim6InfoControl 6 }

		
		sleV2Pim6InfoControlSPTThreshold OBJECT-TYPE
			SYNTAX Boolean
			MAX-ACCESS read-write
			STATUS current
			DESCRIPTION
				"Description."
			::= { sleV2Pim6InfoControl 7 }

		
		sleV2Pim6InfoControlSPTThresholdACL OBJECT-TYPE
			SYNTAX OCTET STRING
			MAX-ACCESS read-write
			STATUS current
			DESCRIPTION
				"Description."
			::= { sleV2Pim6InfoControl 8 }

		
		sleV2Pim6InfoControlSSMDefault OBJECT-TYPE
			SYNTAX Boolean
			MAX-ACCESS read-write
			STATUS current
			DESCRIPTION
				"Description."
			::= { sleV2Pim6InfoControl 9 }

		
		sleV2Pim6InfoControlSSMRangeACL OBJECT-TYPE
			SYNTAX OCTET STRING
			MAX-ACCESS read-write
			STATUS current
			DESCRIPTION
				"Description."
			::= { sleV2Pim6InfoControl 10 }

		
		sleV2Pim6InfoControlRPCandidateInterface OBJECT-TYPE
			SYNTAX INTEGER (-1 | 1..65535)
			MAX-ACCESS read-write
			STATUS current
			DESCRIPTION
				"Description."
			::= { sleV2Pim6InfoControl 11 }

		
		sleV2Pim6InfoControlRPCandidateGroupACL OBJECT-TYPE
			SYNTAX OCTET STRING
			MAX-ACCESS read-write
			STATUS current
			DESCRIPTION
				"Description."
			::= { sleV2Pim6InfoControl 12 }

		
		sleV2Pim6InfoControlRPCandidateInterval OBJECT-TYPE
			SYNTAX INTEGER (-1 | 1..16383)
			MAX-ACCESS read-write
			STATUS current
			DESCRIPTION
				"Description."
			::= { sleV2Pim6InfoControl 13 }

		
		sleV2Pim6InfoControlRPCandidatePriority OBJECT-TYPE
			SYNTAX INTEGER (-1 | 0..255)
			MAX-ACCESS read-write
			STATUS current
			DESCRIPTION
				"Description."
			::= { sleV2Pim6InfoControl 14 }

		
		sleV2Pim6InfoControlRPAddress OBJECT-TYPE
			SYNTAX InetAddressIPv6
			MAX-ACCESS read-write
			STATUS current
			DESCRIPTION
				"Description."
			::= { sleV2Pim6InfoControl 15 }

		
		sleV2Pim6InfoControlRPAddressACL OBJECT-TYPE
			SYNTAX OCTET STRING
			MAX-ACCESS read-write
			STATUS current
			DESCRIPTION
				"Description."
			::= { sleV2Pim6InfoControl 16 }

		
		sleV2Pim6InfoControlCRPCiscoPrefix OBJECT-TYPE
			SYNTAX Boolean
			MAX-ACCESS read-write
			STATUS current
			DESCRIPTION
				"Description."
			::= { sleV2Pim6InfoControl 17 }

		
		sleV2Pim6InfoControlIgnoreRPSetPriority OBJECT-TYPE
			SYNTAX Boolean
			MAX-ACCESS read-write
			STATUS current
			DESCRIPTION
				"Description."
			::= { sleV2Pim6InfoControl 18 }

		
		sleV2Pim6InfoControlBSRCandidateInterface OBJECT-TYPE
			SYNTAX INTEGER (-1 | 1..65535)
			MAX-ACCESS read-write
			STATUS current
			DESCRIPTION
				"Description."
			::= { sleV2Pim6InfoControl 19 }

		
		sleV2Pim6InfoControlBSRCnadidateHash OBJECT-TYPE
			SYNTAX INTEGER (-1 | 0..32)
			MAX-ACCESS read-write
			STATUS current
			DESCRIPTION
				"Description."
			::= { sleV2Pim6InfoControl 20 }

		
		sleV2Pim6InfoControlBSRCandidatePriority OBJECT-TYPE
			SYNTAX INTEGER (-1 | 0..255)
			MAX-ACCESS read-write
			STATUS current
			DESCRIPTION
				"Description."
			::= { sleV2Pim6InfoControl 21 }

		
		sleV2Pim6InfoControlRegisterRateLimit OBJECT-TYPE
			SYNTAX INTEGER (-1 | 1..65535)
			MAX-ACCESS read-write
			STATUS current
			DESCRIPTION
				"Description."
			::= { sleV2Pim6InfoControl 22 }

		
		sleV2Pim6InfoControlRegisterSourceIPAddr OBJECT-TYPE
			SYNTAX InetAddressIPv6
			MAX-ACCESS read-write
			STATUS current
			DESCRIPTION
				"Description."
			::= { sleV2Pim6InfoControl 23 }

		
		sleV2Pim6InfoControlRegisterSourceInterface OBJECT-TYPE
			SYNTAX INTEGER (-1 | 1..65535)
			MAX-ACCESS read-write
			STATUS current
			DESCRIPTION
				"Description."
			::= { sleV2Pim6InfoControl 24 }

		
		sleV2Pim6InfoControlRegisterRPReachability OBJECT-TYPE
			SYNTAX Boolean
			MAX-ACCESS read-write
			STATUS current
			DESCRIPTION
				"Description."
			::= { sleV2Pim6InfoControl 25 }

		
		sleV2Pim6InfoControlRegisterSuppression OBJECT-TYPE
			SYNTAX INTEGER (-1 | 1..65535)
			MAX-ACCESS read-write
			STATUS current
			DESCRIPTION
				"Description."
			::= { sleV2Pim6InfoControl 26 }

		
		sleV2Pim6InfoControlAcceptRegisterACL OBJECT-TYPE
			SYNTAX OCTET STRING
			MAX-ACCESS read-write
			STATUS current
			DESCRIPTION
				"Description."
			::= { sleV2Pim6InfoControl 27 }

		
		sleV2Pim6InfoControlRPRegisterKAT OBJECT-TYPE
			SYNTAX INTEGER (-1 | 1..65535)
			MAX-ACCESS read-write
			STATUS current
			DESCRIPTION
				"Description."
			::= { sleV2Pim6InfoControl 28 }

		
		sleV2Pim6InfoControlCiscoRegisterChecksum OBJECT-TYPE
			SYNTAX Boolean
			MAX-ACCESS read-write
			STATUS current
			DESCRIPTION
				"Description."
			::= { sleV2Pim6InfoControl 29 }

		
		sleV2Pim6InfoControlCiscoRegisterChecksumACL OBJECT-TYPE
			SYNTAX OCTET STRING
			MAX-ACCESS read-write
			STATUS current
			DESCRIPTION
				"Description."
			::= { sleV2Pim6InfoControl 30 }

		
		sleV2Pim6InfoControlGroup OBJECT-TYPE
			SYNTAX InetAddressIPv6
			MAX-ACCESS read-write
			STATUS current
			DESCRIPTION
				"Description."
			::= { sleV2Pim6InfoControl 31 }

		
		sleV2Pim6InfoControlSource OBJECT-TYPE
			SYNTAX InetAddressIPv6
			MAX-ACCESS read-write
			STATUS current
			DESCRIPTION
				"Description."
			::= { sleV2Pim6InfoControl 32 }

		
		sleV2Pim6InfoNotification OBJECT IDENTIFIER ::= { sleV2Pim6Base 3 }

		
		sleV2Pim6InfoProfileChanged NOTIFICATION-TYPE
			OBJECTS { sleV2Pim6InfoControlRequest, sleV2Pim6InfoControlTimeStamp, sleV2Pim6InfoControlReqResult, sleV2Pim6InfoJTTimer, sleV2Pim6InfoSPTThreshold, 
				sleV2Pim6InfoSPTThresholdACL, sleV2Pim6InfoSSMDefault, sleV2Pim6InfoSSMRangeACL }
			STATUS current
			DESCRIPTION 
				"Description."
			::= { sleV2Pim6InfoNotification 1 }

		
		sleV2Pim6InfoRPProfileChanged NOTIFICATION-TYPE
			OBJECTS { sleV2Pim6InfoControlRequest, sleV2Pim6InfoControlTimeStamp, sleV2Pim6InfoControlReqResult, sleV2Pim6InfoCRPCiscoPrefix, sleV2Pim6InfoIgnoreRPSetPriority
				 }
			STATUS current
			DESCRIPTION 
				"Description."
			::= { sleV2Pim6InfoNotification 2 }

		
		sleV2Pim6InfoBSRProfileChanged NOTIFICATION-TYPE
			OBJECTS { sleV2Pim6InfoControlRequest, sleV2Pim6InfoControlTimeStamp, sleV2Pim6InfoControlReqResult, sleV2Pim6InfoBSRCandidateInterface, sleV2Pim6InfoBSRCnadidateHash, 
				sleV2Pim6InfoBSRCandidatePriority }
			STATUS current
			DESCRIPTION 
				"Description."
			::= { sleV2Pim6InfoNotification 3 }

		
		sleV2Pim6InfoRegisterProfileChanged NOTIFICATION-TYPE
			OBJECTS { sleV2Pim6InfoControlRequest, sleV2Pim6InfoControlTimeStamp, sleV2Pim6InfoControlReqResult, sleV2Pim6InfoRegisterRateLimit, sleV2Pim6InfoRegisterSourceIPAddr, 
				sleV2Pim6InfoRegisterSourceInterface, sleV2Pim6InfoRegisterRPReachability, sleV2Pim6InfoRegisterSuppression, sleV2Pim6InfoAcceptRegisterACL, sleV2Pim6InfoRPRegisterKAT, 
				sleV2Pim6InfoCiscoRegisterChecksum, sleV2Pim6InfoCiscoRegisterChecksumACL }
			STATUS current
			DESCRIPTION 
				"Description."
			::= { sleV2Pim6InfoNotification 4 }

		
		sleV2Pim6InfoMRTCleared NOTIFICATION-TYPE
			OBJECTS { sleV2Pim6InfoControlRequest, sleV2Pim6InfoControlTimeStamp, sleV2Pim6InfoControlReqResult, sleV2Pim6InfoControlGroup, sleV2Pim6InfoControlSource
				 }
			STATUS current
			DESCRIPTION 
				"Description."
			::= { sleV2Pim6InfoNotification 5 }

		
		sleV2Pim6InfoRPSetCleared NOTIFICATION-TYPE
			OBJECTS { sleV2Pim6InfoControlRequest, sleV2Pim6InfoControlTimeStamp, sleV2Pim6InfoControlReqResult }
			STATUS current
			DESCRIPTION 
				"Description."
			::= { sleV2Pim6InfoNotification 6 }

		
		sleV2Pim6Agent OBJECT IDENTIFIER ::= { sleV2Pim6 2 }

		
		sleV2Pim6Interface OBJECT IDENTIFIER ::= { sleV2Pim6Agent 1 }

		
		sleV2Pim6IfTable OBJECT-TYPE
			SYNTAX SEQUENCE OF SleV2Pim6IfEntry
			MAX-ACCESS not-accessible
			STATUS current
			DESCRIPTION
				"Description."
			::= { sleV2Pim6Interface 1 }

		
		sleV2Pim6IfEntry OBJECT-TYPE
			SYNTAX SleV2Pim6IfEntry
			MAX-ACCESS not-accessible
			STATUS current
			DESCRIPTION
				"Description."
			INDEX { sleV2Pim6IfVid }
			::= { sleV2Pim6IfTable 1 }

		
		SleV2Pim6IfEntry ::=
			SEQUENCE { 
				sleV2Pim6IfVid
					INTEGER,
				sleV2Pim6IfVifIndex
					INTEGER,
				sleV2Pim6IfLinkLocalAddress
					InetAddressIPv6,
				sleV2Pim6IfGlobalAddress
					InetAddressIPv6,
				sleV2Pim6IfDrLinkLocalAddress
					InetAddressIPv6,
				sleV2Pim6IfTriggedHelloPeriod
					INTEGER,
				sleV2Pim6IfNextHelloTime
					TimeTicks,
				sleV2Pim6IfSparseMode
					Boolean,
				sleV2Pim6IfSparseModePassive
					Boolean,
				sleV2Pim6IfHelloHoldtime
					INTEGER,
				sleV2Pim6IfHelloInterval
					INTEGER,
				sleV2Pim6IfDrPriority
					Gauge32,
				sleV2Pim6IfExcludeGenID
					Boolean,
				sleV2Pim6IfNeighborFilterACL
					OCTET STRING
			 }

		sleV2Pim6IfVid OBJECT-TYPE
			SYNTAX INTEGER (1..4094)
			MAX-ACCESS read-only
			STATUS current
			DESCRIPTION
				"Description."
			::= { sleV2Pim6IfEntry 1 }

		
		sleV2Pim6IfVifIndex OBJECT-TYPE
			SYNTAX INTEGER
			MAX-ACCESS read-only
			STATUS current
			DESCRIPTION
				"Description."
			::= { sleV2Pim6IfEntry 2 }

		
		sleV2Pim6IfLinkLocalAddress OBJECT-TYPE
			SYNTAX InetAddressIPv6
			MAX-ACCESS read-only
			STATUS current
			DESCRIPTION
				"Description."
			::= { sleV2Pim6IfEntry 3 }

		
		sleV2Pim6IfGlobalAddress OBJECT-TYPE
			SYNTAX InetAddressIPv6
			MAX-ACCESS read-only
			STATUS current
			DESCRIPTION
				"Description."
			::= { sleV2Pim6IfEntry 4 }

		
		sleV2Pim6IfDrLinkLocalAddress OBJECT-TYPE
			SYNTAX InetAddressIPv6
			MAX-ACCESS read-only
			STATUS current
			DESCRIPTION
				"Description."
			::= { sleV2Pim6IfEntry 5 }

		
		sleV2Pim6IfTriggedHelloPeriod OBJECT-TYPE
			SYNTAX INTEGER (1..18724)
			MAX-ACCESS read-only
			STATUS current
			DESCRIPTION
				"Description."
			::= { sleV2Pim6IfEntry 6 }

		
		sleV2Pim6IfNextHelloTime OBJECT-TYPE
			SYNTAX TimeTicks
			MAX-ACCESS read-only
			STATUS current
			DESCRIPTION
				"Description."
			::= { sleV2Pim6IfEntry 7 }

		
		sleV2Pim6IfSparseMode OBJECT-TYPE
			SYNTAX Boolean
			MAX-ACCESS read-only
			STATUS current
			DESCRIPTION
				"Description."
			::= { sleV2Pim6IfEntry 8 }

		
		sleV2Pim6IfSparseModePassive OBJECT-TYPE
			SYNTAX Boolean
			MAX-ACCESS read-only
			STATUS current
			DESCRIPTION
				"Description."
			::= { sleV2Pim6IfEntry 9 }

		
		sleV2Pim6IfHelloHoldtime OBJECT-TYPE
			SYNTAX INTEGER (1..65535)
			MAX-ACCESS read-only
			STATUS current
			DESCRIPTION
				"Description."
			::= { sleV2Pim6IfEntry 10 }

		
		sleV2Pim6IfHelloInterval OBJECT-TYPE
			SYNTAX INTEGER (-1 | 1..18724)
			MAX-ACCESS read-only
			STATUS current
			DESCRIPTION
				"Description."
			::= { sleV2Pim6IfEntry 11 }

		
		sleV2Pim6IfDrPriority OBJECT-TYPE
			SYNTAX Gauge32 (0..4294967294)
			MAX-ACCESS read-only
			STATUS current
			DESCRIPTION
				"Description."
			::= { sleV2Pim6IfEntry 12 }

		
		sleV2Pim6IfExcludeGenID OBJECT-TYPE
			SYNTAX Boolean
			MAX-ACCESS read-only
			STATUS current
			DESCRIPTION
				"Description."
			::= { sleV2Pim6IfEntry 13 }

		
		sleV2Pim6IfNeighborFilterACL OBJECT-TYPE
			SYNTAX OCTET STRING
			MAX-ACCESS read-only
			STATUS current
			DESCRIPTION
				"Description."
			::= { sleV2Pim6IfEntry 14 }

		
		sleV2Pim6IfControl OBJECT IDENTIFIER ::= { sleV2Pim6Interface 2 }

		
		sleV2Pim6IfControlRequest OBJECT-TYPE
			SYNTAX INTEGER { setPIM6IfInfoProfile(1) }
			MAX-ACCESS read-write
			STATUS current
			DESCRIPTION
				"Description."
			::= { sleV2Pim6IfControl 1 }

		
		sleV2Pim6IfControlStatus OBJECT-TYPE
			SYNTAX SleControlStatusType
			MAX-ACCESS read-write
			STATUS current
			DESCRIPTION
				"Description."
			::= { sleV2Pim6IfControl 2 }

		
		sleV2Pim6IfControlTimer OBJECT-TYPE
			SYNTAX Gauge32
			MAX-ACCESS read-write
			STATUS current
			DESCRIPTION
				"Description."
			::= { sleV2Pim6IfControl 3 }

		
		sleV2Pim6IfControlTimeStamp OBJECT-TYPE
			SYNTAX TimeTicks
			MAX-ACCESS read-write
			STATUS current
			DESCRIPTION
				"Description."
			::= { sleV2Pim6IfControl 4 }

		
		sleV2Pim6IfControlReqResult OBJECT-TYPE
			SYNTAX SleControlRequestResultType
			MAX-ACCESS read-write
			STATUS current
			DESCRIPTION
				"Description."
			::= { sleV2Pim6IfControl 5 }

		
		sleV2Pim6IfControlVid OBJECT-TYPE
			SYNTAX INTEGER (1..4094)
			MAX-ACCESS read-write
			STATUS current
			DESCRIPTION
				"Description."
			::= { sleV2Pim6IfControl 6 }

		
		sleV2Pim6IfControlSparseMode OBJECT-TYPE
			SYNTAX Boolean
			MAX-ACCESS read-write
			STATUS current
			DESCRIPTION
				"Description."
			::= { sleV2Pim6IfControl 7 }

		
		sleV2Pim6IfControlSparseModePassive OBJECT-TYPE
			SYNTAX Boolean
			MAX-ACCESS read-write
			STATUS current
			DESCRIPTION
				"Description."
			::= { sleV2Pim6IfControl 8 }

		
		sleV2Pim6IfControlHelloHoldtime OBJECT-TYPE
			SYNTAX INTEGER (-1 | 1..65535)
			MAX-ACCESS read-write
			STATUS current
			DESCRIPTION
				"Description."
			::= { sleV2Pim6IfControl 9 }

		
		sleV2Pim6IfControlHelloInterval OBJECT-TYPE
			SYNTAX INTEGER (-1 | 1..18724)
			MAX-ACCESS read-write
			STATUS current
			DESCRIPTION
				"Description."
			::= { sleV2Pim6IfControl 10 }

		
		sleV2Pim6IfControlDrPriority OBJECT-TYPE
			SYNTAX Gauge32 (0..4294967294)
			MAX-ACCESS read-write
			STATUS current
			DESCRIPTION
				"Description."
			::= { sleV2Pim6IfControl 11 }

		
		sleV2Pim6IfControlExcludeGenID OBJECT-TYPE
			SYNTAX Boolean
			MAX-ACCESS read-write
			STATUS current
			DESCRIPTION
				"Description."
			::= { sleV2Pim6IfControl 12 }

		
		sleV2Pim6IfControlNeighborFilterACL OBJECT-TYPE
			SYNTAX OCTET STRING
			MAX-ACCESS read-write
			STATUS current
			DESCRIPTION
				"Description."
			::= { sleV2Pim6IfControl 13 }

		
		sleV2Pim6IfNotification OBJECT IDENTIFIER ::= { sleV2Pim6Interface 3 }

		
		sleV2Pim6IfProfileChanged NOTIFICATION-TYPE
			OBJECTS { sleV2Pim6IfControlRequest, sleV2Pim6IfControlTimeStamp, sleV2Pim6IfControlReqResult, sleV2Pim6IfVid, sleV2Pim6IfSparseMode, 
				sleV2Pim6IfSparseModePassive, sleV2Pim6IfHelloHoldtime, sleV2Pim6IfHelloInterval, sleV2Pim6IfDrPriority, sleV2Pim6IfExcludeGenID, 
				sleV2Pim6IfNeighborFilterACL }
			STATUS current
			DESCRIPTION 
				"Description."
			::= { sleV2Pim6IfNotification 1 }

		
		sleV2Pim6Neighbor OBJECT IDENTIFIER ::= { sleV2Pim6Agent 2 }

		
		sleV2Pim6NeighborTable OBJECT-TYPE
			SYNTAX SEQUENCE OF SleV2Pim6NeighborEntry
			MAX-ACCESS not-accessible
			STATUS current
			DESCRIPTION
				"Description."
			::= { sleV2Pim6Neighbor 1 }

		
		sleV2Pim6NeighborEntry OBJECT-TYPE
			SYNTAX SleV2Pim6NeighborEntry
			MAX-ACCESS not-accessible
			STATUS current
			DESCRIPTION
				"Description."
			INDEX { sleV2Pim6NeighborAddress }
			::= { sleV2Pim6NeighborTable 1 }

		
		SleV2Pim6NeighborEntry ::=
			SEQUENCE { 
				sleV2Pim6NeighborAddress
					InetAddressIPv6,
				sleV2Pim6NeighborVid
					INTEGER,
				sleV2Pim6NeighborUptime
					TimeTicks,
				sleV2Pim6NeighborExpire
					TimeTicks,
				sleV2Pim6NeighborVersion
					INTEGER,
				sleV2Pim6NeighborDr
					INTEGER,
				sleV2Pim6NeighboDrPriority
					Gauge32
			 }

		sleV2Pim6NeighborAddress OBJECT-TYPE
			SYNTAX InetAddressIPv6
			MAX-ACCESS read-only
			STATUS current
			DESCRIPTION
				"Description."
			::= { sleV2Pim6NeighborEntry 1 }

		
		sleV2Pim6NeighborVid OBJECT-TYPE
			SYNTAX INTEGER (1..4094)
			MAX-ACCESS read-only
			STATUS current
			DESCRIPTION
				"Description."
			::= { sleV2Pim6NeighborEntry 2 }

		
		sleV2Pim6NeighborUptime OBJECT-TYPE
			SYNTAX TimeTicks
			MAX-ACCESS read-only
			STATUS current
			DESCRIPTION
				"Description."
			::= { sleV2Pim6NeighborEntry 3 }

		
		sleV2Pim6NeighborExpire OBJECT-TYPE
			SYNTAX TimeTicks
			MAX-ACCESS read-only
			STATUS current
			DESCRIPTION
				"Description."
			::= { sleV2Pim6NeighborEntry 4 }

		
		sleV2Pim6NeighborVersion OBJECT-TYPE
			SYNTAX INTEGER (2)
			MAX-ACCESS read-only
			STATUS current
			DESCRIPTION
				"Description."
			::= { sleV2Pim6NeighborEntry 5 }

		
		sleV2Pim6NeighborDr OBJECT-TYPE
			SYNTAX INTEGER
				{
				nonDr(0),
				dr(1)
				}
			MAX-ACCESS read-only
			STATUS current
			DESCRIPTION
				"Description."
			::= { sleV2Pim6NeighborEntry 6 }

		
		sleV2Pim6NeighboDrPriority OBJECT-TYPE
			SYNTAX Gauge32 (0..4294967294)
			MAX-ACCESS read-only
			STATUS current
			DESCRIPTION
				"Description."
			::= { sleV2Pim6NeighborEntry 7 }

		
		sleV2Pim6Nexthop OBJECT IDENTIFIER ::= { sleV2Pim6Agent 3 }

		
		sleV2Pim6NexthopTable OBJECT-TYPE
			SYNTAX SEQUENCE OF SleV2Pim6NexthopEntry
			MAX-ACCESS not-accessible
			STATUS current
			DESCRIPTION
				"Description."
			::= { sleV2Pim6Nexthop 1 }

		
		sleV2Pim6NexthopEntry OBJECT-TYPE
			SYNTAX SleV2Pim6NexthopEntry
			MAX-ACCESS not-accessible
			STATUS current
			DESCRIPTION
				"Description."
			INDEX { sleV2Pim6NexthopSourceAddress, sleV2Pim6NexthopGroupAddress }
			::= { sleV2Pim6NexthopTable 1 }

		
		SleV2Pim6NexthopEntry ::=
			SEQUENCE { 
				sleV2Pim6NexthopSourceAddress
					InetAddressIPv6,
				sleV2Pim6NexthopGroupAddress
					InetAddressIPv6,
				sleV2Pim6NexthopNum
					INTEGER,
				sleV2Pim6NexthopType
					BITS,
				sleV2Pim6NexthopAddress
					InetAddressIPv6,
				sleV2Pim6NexthopVid
					INTEGER,
				sleV2Pim6NexthopMetric
					INTEGER,
				sleV2Pim6NexthopPref
					INTEGER,
				sleV2Pim6NexthopRefcnt
					INTEGER
			 }

		sleV2Pim6NexthopSourceAddress OBJECT-TYPE
			SYNTAX InetAddressIPv6
			MAX-ACCESS read-only
			STATUS current
			DESCRIPTION
				"Description."
			::= { sleV2Pim6NexthopEntry 1 }

		
		sleV2Pim6NexthopGroupAddress OBJECT-TYPE
			SYNTAX InetAddressIPv6
			MAX-ACCESS read-only
			STATUS current
			DESCRIPTION
				"Description."
			::= { sleV2Pim6NexthopEntry 2 }

		
		sleV2Pim6NexthopNum OBJECT-TYPE
			SYNTAX INTEGER
			MAX-ACCESS read-only
			STATUS current
			DESCRIPTION
				"Description."
			::= { sleV2Pim6NexthopEntry 3 }

		
		sleV2Pim6NexthopType OBJECT-TYPE
			SYNTAX BITS
				{
				new(0),
				rp(1),
				source(2),
				unreachable(3),
				activePath(4)
				}
			MAX-ACCESS read-only
			STATUS current
			DESCRIPTION
				"Description."
			::= { sleV2Pim6NexthopEntry 4 }

		
		sleV2Pim6NexthopAddress OBJECT-TYPE
			SYNTAX InetAddressIPv6
			MAX-ACCESS read-only
			STATUS current
			DESCRIPTION
				"Description."
			::= { sleV2Pim6NexthopEntry 5 }

		
		sleV2Pim6NexthopVid OBJECT-TYPE
			SYNTAX INTEGER (1..4094)
			MAX-ACCESS read-only
			STATUS current
			DESCRIPTION
				"Description."
			::= { sleV2Pim6NexthopEntry 6 }

		
		sleV2Pim6NexthopMetric OBJECT-TYPE
			SYNTAX INTEGER
			MAX-ACCESS read-only
			STATUS current
			DESCRIPTION
				"Description."
			::= { sleV2Pim6NexthopEntry 7 }

		
		sleV2Pim6NexthopPref OBJECT-TYPE
			SYNTAX INTEGER
			MAX-ACCESS read-only
			STATUS current
			DESCRIPTION
				"Description."
			::= { sleV2Pim6NexthopEntry 8 }

		
		sleV2Pim6NexthopRefcnt OBJECT-TYPE
			SYNTAX INTEGER
			MAX-ACCESS read-only
			STATUS current
			DESCRIPTION
				"Description."
			::= { sleV2Pim6NexthopEntry 9 }

		
		sleV2Pim6CandidateRP OBJECT IDENTIFIER ::= { sleV2Pim6Agent 4 }

		
		sleV2Pim6CRPTable OBJECT-TYPE
			SYNTAX SEQUENCE OF SleV2Pim6CRPEntry
			MAX-ACCESS not-accessible
			STATUS current
			DESCRIPTION
				"Description."
			::= { sleV2Pim6CandidateRP 1 }

		
		sleV2Pim6CRPEntry OBJECT-TYPE
			SYNTAX SleV2Pim6CRPEntry
			MAX-ACCESS not-accessible
			STATUS current
			DESCRIPTION
				"Description."
			INDEX { sleV2Pim6CRPVid, sleV2Pim6CRPACL }
			::= { sleV2Pim6CRPTable 1 }

		
		SleV2Pim6CRPEntry ::=
			SEQUENCE { 
				sleV2Pim6CRPVid
					INTEGER,
				sleV2Pim6CRPACL
					OCTET STRING,
				sleV2Pim6RPActive
					Boolean,
				sleV2Pim6CRPInterval
					INTEGER,
				sleV2Pim6CRPPriority
					INTEGER,
				sleV2Pim6CRPNextAdver
					TimeTicks
			 }

		sleV2Pim6CRPVid OBJECT-TYPE
			SYNTAX INTEGER (1..4094)
			MAX-ACCESS read-only
			STATUS current
			DESCRIPTION
				"Description."
			::= { sleV2Pim6CRPEntry 1 }

		
		sleV2Pim6CRPACL OBJECT-TYPE
			SYNTAX OCTET STRING
			MAX-ACCESS read-only
			STATUS current
			DESCRIPTION
				"Description."
			::= { sleV2Pim6CRPEntry 2 }

		
		sleV2Pim6RPActive OBJECT-TYPE
			SYNTAX Boolean
			MAX-ACCESS read-only
			STATUS current
			DESCRIPTION
				"Description."
			::= { sleV2Pim6CRPEntry 3 }

		
		sleV2Pim6CRPInterval OBJECT-TYPE
			SYNTAX INTEGER (0..16383)
			MAX-ACCESS read-only
			STATUS current
			DESCRIPTION
				"Description."
			::= { sleV2Pim6CRPEntry 4 }

		
		sleV2Pim6CRPPriority OBJECT-TYPE
			SYNTAX INTEGER (0..255)
			MAX-ACCESS read-only
			STATUS current
			DESCRIPTION
				"Description."
			::= { sleV2Pim6CRPEntry 5 }

		
		sleV2Pim6CRPNextAdver OBJECT-TYPE
			SYNTAX TimeTicks
			MAX-ACCESS read-only
			STATUS current
			DESCRIPTION
				"Description."
			::= { sleV2Pim6CRPEntry 6 }

		
		sleV2Pim6CRPControl OBJECT IDENTIFIER ::= { sleV2Pim6CandidateRP 2 }

		
		sleV2Pim6CRPControlRequest OBJECT-TYPE
			SYNTAX INTEGER
				{
				createPIM6CandidateRP(1),
				destroyPIM6CandidateRP(2)
				}
			MAX-ACCESS read-write
			STATUS current
			DESCRIPTION
				"Description."
			::= { sleV2Pim6CRPControl 1 }

		
		sleV2Pim6CRPControlStatus OBJECT-TYPE
			SYNTAX SleControlStatusType
			MAX-ACCESS read-write
			STATUS current
			DESCRIPTION
				"Description."
			::= { sleV2Pim6CRPControl 2 }

		
		sleV2Pim6CRPControlTimer OBJECT-TYPE
			SYNTAX Gauge32
			MAX-ACCESS read-write
			STATUS current
			DESCRIPTION
				"Description."
			::= { sleV2Pim6CRPControl 3 }

		
		sleV2Pim6CRPControlTimeStamp OBJECT-TYPE
			SYNTAX TimeTicks
			MAX-ACCESS read-write
			STATUS current
			DESCRIPTION
				"Description."
			::= { sleV2Pim6CRPControl 4 }

		
		sleV2Pim6CRPControlReqResult OBJECT-TYPE
			SYNTAX SleControlRequestResultType
			MAX-ACCESS read-write
			STATUS current
			DESCRIPTION
				"Description."
			::= { sleV2Pim6CRPControl 5 }

		
		sleV2Pim6CRPControlVid OBJECT-TYPE
			SYNTAX INTEGER (1..4094)
			MAX-ACCESS read-write
			STATUS current
			DESCRIPTION
				"Description."
			::= { sleV2Pim6CRPControl 6 }

		
		sleV2Pim6CRPControlACL OBJECT-TYPE
			SYNTAX OCTET STRING
			MAX-ACCESS read-write
			STATUS current
			DESCRIPTION
				"Description."
			::= { sleV2Pim6CRPControl 7 }

		
		sleV2Pim6CRPControlInterval OBJECT-TYPE
			SYNTAX INTEGER (-1 | 0..16383)
			MAX-ACCESS read-write
			STATUS current
			DESCRIPTION
				"Description."
			::= { sleV2Pim6CRPControl 8 }

		
		sleV2Pim6CRPControlPriority OBJECT-TYPE
			SYNTAX INTEGER (-1 | 0..255)
			MAX-ACCESS read-write
			STATUS current
			DESCRIPTION
				"Description."
			::= { sleV2Pim6CRPControl 9 }

		
		sleV2Pim6CRPNotification OBJECT IDENTIFIER ::= { sleV2Pim6CandidateRP 3 }

		
		sleV2Pim6CreateCRPProfileChanged NOTIFICATION-TYPE
			OBJECTS { sleV2Pim6CRPVid, sleV2Pim6CRPACL, sleV2Pim6RPActive, sleV2Pim6CRPInterval, sleV2Pim6CRPPriority
				 }
			STATUS current
			DESCRIPTION 
				"Description."
			::= { sleV2Pim6CRPNotification 1 }

		
		sleV2Pim6DestroyCRPProfileChanged NOTIFICATION-TYPE
			OBJECTS { sleV2Pim6CRPControlVid, sleV2Pim6CRPControlACL }
			STATUS current
			DESCRIPTION 
				"Description."
			::= { sleV2Pim6CRPNotification 2 }

		
		sleV2Pim6StaticRP OBJECT IDENTIFIER ::= { sleV2Pim6Agent 5 }

		
		sleV2Pim6SRPTable OBJECT-TYPE
			SYNTAX SEQUENCE OF SleV2Pim6SRPEntry
			MAX-ACCESS not-accessible
			STATUS current
			DESCRIPTION
				"Description."
			::= { sleV2Pim6StaticRP 1 }

		
		sleV2Pim6SRPEntry OBJECT-TYPE
			SYNTAX SleV2Pim6SRPEntry
			MAX-ACCESS not-accessible
			STATUS current
			DESCRIPTION
				"Description."
			INDEX { sleV2Pim6SRPAddr, sleV2Pim6SRPACL }
			::= { sleV2Pim6SRPTable 1 }

		
		SleV2Pim6SRPEntry ::=
			SEQUENCE { 
				sleV2Pim6SRPAddr
					InetAddressIPv6,
				sleV2Pim6SRPACL
					OCTET STRING
			 }

		sleV2Pim6SRPAddr OBJECT-TYPE
			SYNTAX InetAddressIPv6
			MAX-ACCESS read-only
			STATUS current
			DESCRIPTION
				"Description."
			::= { sleV2Pim6SRPEntry 1 }

		
		sleV2Pim6SRPACL OBJECT-TYPE
			SYNTAX OCTET STRING
			MAX-ACCESS read-only
			STATUS current
			DESCRIPTION
				"Description."
			::= { sleV2Pim6SRPEntry 2 }

		
		sleV2Pim6SRPControl OBJECT IDENTIFIER ::= { sleV2Pim6StaticRP 2 }

		
		sleV2Pim6SRPControlRequest OBJECT-TYPE
			SYNTAX INTEGER
				{
				createPIM6StaticRP(1),
				destroyPIM6StaticRP(2)
				}
			MAX-ACCESS read-write
			STATUS current
			DESCRIPTION
				"Description."
			::= { sleV2Pim6SRPControl 1 }

		
		sleV2Pim6SRPControlStatus OBJECT-TYPE
			SYNTAX SleControlStatusType
			MAX-ACCESS read-write
			STATUS current
			DESCRIPTION
				"Description."
			::= { sleV2Pim6SRPControl 2 }

		
		sleV2Pim6SRPControlTimer OBJECT-TYPE
			SYNTAX Gauge32
			MAX-ACCESS read-write
			STATUS current
			DESCRIPTION
				"Description."
			::= { sleV2Pim6SRPControl 3 }

		
		sleV2Pim6SRPControlTimeStamp OBJECT-TYPE
			SYNTAX TimeTicks
			MAX-ACCESS read-write
			STATUS current
			DESCRIPTION
				"Description."
			::= { sleV2Pim6SRPControl 4 }

		
		sleV2Pim6SRPControlReqResult OBJECT-TYPE
			SYNTAX SleControlRequestResultType
			MAX-ACCESS read-write
			STATUS current
			DESCRIPTION
				"Description."
			::= { sleV2Pim6SRPControl 5 }

		
		sleV2Pim6SRPControlAddr OBJECT-TYPE
			SYNTAX InetAddressIPv6
			MAX-ACCESS read-write
			STATUS current
			DESCRIPTION
				"Description."
			::= { sleV2Pim6SRPControl 6 }

		
		sleV2Pim6SRPControlACL OBJECT-TYPE
			SYNTAX OCTET STRING
			MAX-ACCESS read-write
			STATUS current
			DESCRIPTION
				"Description."
			::= { sleV2Pim6SRPControl 7 }

		
		sleV2Pim6SRPNotification OBJECT IDENTIFIER ::= { sleV2Pim6StaticRP 3 }

		
		sleV2Pim6CreateSRPProfileChanged NOTIFICATION-TYPE
			OBJECTS { sleV2Pim6SRPAddr, sleV2Pim6SRPACL }
			STATUS current
			DESCRIPTION 
				"Description."
			::= { sleV2Pim6SRPNotification 1 }

		
		sleV2Pim6DestroySRPProfileChanged NOTIFICATION-TYPE
			OBJECTS { sleV2Pim6SRPControlAddr }
			STATUS current
			DESCRIPTION 
				"Description."
			::= { sleV2Pim6SRPNotification 2 }

		
		sleV2Pim6RPSet OBJECT IDENTIFIER ::= { sleV2Pim6Agent 6 }

		
		sleV2Pim6Mroute OBJECT IDENTIFIER ::= { sleV2Pim6Agent 7 }

		
		sleV2Pim6MrouteXXRP OBJECT IDENTIFIER ::= { sleV2Pim6Mroute 1 }

		
		sleV2Pim6MrtXXRPTable OBJECT-TYPE
			SYNTAX SEQUENCE OF SleV2Pim6MrtXXRPEntry
			MAX-ACCESS not-accessible
			STATUS current
			DESCRIPTION
				"Description."
			::= { sleV2Pim6MrouteXXRP 1 }

		
		sleV2Pim6MrtXXRPEntry OBJECT-TYPE
			SYNTAX SleV2Pim6MrtXXRPEntry
			MAX-ACCESS not-accessible
			STATUS current
			DESCRIPTION
				"Description."
			INDEX { sleV2Pim6MrtXXRPAddress }
			::= { sleV2Pim6MrtXXRPTable 1 }

		
		SleV2Pim6MrtXXRPEntry ::=
			SEQUENCE { 
				sleV2Pim6MrtXXRPAddress
					InetAddressIPv6,
				sleV2Pim6MrtXXRPRPFNbrAddress
					InetAddressIPv6,
				sleV2Pim6MrtXXRPRPFVid
					INTEGER,
				sleV2Pim6MrtXXRPUpstreamState
					INTEGER,
				sleV2Pim6MrtXXRPJoined
					OCTET STRING,
				sleV2Pim6MrtXXRPOutgoing
					OCTET STRING
			 }

		sleV2Pim6MrtXXRPAddress OBJECT-TYPE
			SYNTAX InetAddressIPv6
			MAX-ACCESS read-only
			STATUS current
			DESCRIPTION
				"Description."
			::= { sleV2Pim6MrtXXRPEntry 1 }

		
		sleV2Pim6MrtXXRPRPFNbrAddress OBJECT-TYPE
			SYNTAX InetAddressIPv6
			MAX-ACCESS read-only
			STATUS current
			DESCRIPTION
				"Description."
			::= { sleV2Pim6MrtXXRPEntry 2 }

		
		sleV2Pim6MrtXXRPRPFVid OBJECT-TYPE
			SYNTAX INTEGER (1..40494)
			MAX-ACCESS read-only
			STATUS current
			DESCRIPTION
				"Description."
			::= { sleV2Pim6MrtXXRPEntry 3 }

		
		sleV2Pim6MrtXXRPUpstreamState OBJECT-TYPE
			SYNTAX INTEGER
				{
				notJoined(0),
				joined(1)
				}
			MAX-ACCESS read-only
			STATUS current
			DESCRIPTION
				"Description."
			::= { sleV2Pim6MrtXXRPEntry 4 }

		
		sleV2Pim6MrtXXRPJoined OBJECT-TYPE
			SYNTAX OCTET STRING
			MAX-ACCESS read-only
			STATUS current
			DESCRIPTION
				"Description."
			::= { sleV2Pim6MrtXXRPEntry 5 }

		
		sleV2Pim6MrtXXRPOutgoing OBJECT-TYPE
			SYNTAX OCTET STRING
			MAX-ACCESS read-only
			STATUS current
			DESCRIPTION
				"Description."
			::= { sleV2Pim6MrtXXRPEntry 6 }

		
		sleV2Pim6MrouteXG OBJECT IDENTIFIER ::= { sleV2Pim6Mroute 2 }

		
		sleV2Pim6MrtXGTable OBJECT-TYPE
			SYNTAX SEQUENCE OF SleV2Pim6MrtXGEntry
			MAX-ACCESS not-accessible
			STATUS current
			DESCRIPTION
				"Description."
			::= { sleV2Pim6MrouteXG 1 }

		
		sleV2Pim6MrtXGEntry OBJECT-TYPE
			SYNTAX SleV2Pim6MrtXGEntry
			MAX-ACCESS not-accessible
			STATUS current
			DESCRIPTION
				"Description."
			INDEX { sleV2Pim6MrtXGGroupAddress, sleV2Pim6MrtXGRPAddress }
			::= { sleV2Pim6MrtXGTable 1 }

		
		SleV2Pim6MrtXGEntry ::=
			SEQUENCE { 
				sleV2Pim6MrtXGGroupAddress
					InetAddressIPv6,
				sleV2Pim6MrtXGRPAddress
					InetAddressIPv6,
				sleV2Pim6MrtXGRPFNbrAddress
					InetAddressIPv6,
				sleV2Pim6MrtXGVid
					INTEGER,
				sleV2Pim6MrtXGUpstreamState
					INTEGER,
				sleV2Pim6MrtXGLocal
					OCTET STRING,
				sleV2Pim6MrtXGJoined
					OCTET STRING,
				sleV2Pim6MrtXGAssertWinner
					OCTET STRING,
				sleV2Pim6MrtXGAssertLoser
					OCTET STRING
			 }

		sleV2Pim6MrtXGGroupAddress OBJECT-TYPE
			SYNTAX InetAddressIPv6
			MAX-ACCESS read-only
			STATUS current
			DESCRIPTION
				"Description."
			::= { sleV2Pim6MrtXGEntry 1 }

		
		sleV2Pim6MrtXGRPAddress OBJECT-TYPE
			SYNTAX InetAddressIPv6
			MAX-ACCESS read-only
			STATUS current
			DESCRIPTION
				"Description."
			::= { sleV2Pim6MrtXGEntry 2 }

		
		sleV2Pim6MrtXGRPFNbrAddress OBJECT-TYPE
			SYNTAX InetAddressIPv6
			MAX-ACCESS read-only
			STATUS current
			DESCRIPTION
				"Description."
			::= { sleV2Pim6MrtXGEntry 3 }

		
		sleV2Pim6MrtXGVid OBJECT-TYPE
			SYNTAX INTEGER (1..40494)
			MAX-ACCESS read-only
			STATUS current
			DESCRIPTION
				"Description."
			::= { sleV2Pim6MrtXGEntry 4 }

		
		sleV2Pim6MrtXGUpstreamState OBJECT-TYPE
			SYNTAX INTEGER
				{
				notJoined(0),
				joined(1)
				}
			MAX-ACCESS read-only
			STATUS current
			DESCRIPTION
				"Description."
			::= { sleV2Pim6MrtXGEntry 5 }

		
		sleV2Pim6MrtXGLocal OBJECT-TYPE
			SYNTAX OCTET STRING
			MAX-ACCESS read-only
			STATUS current
			DESCRIPTION
				"Description."
			::= { sleV2Pim6MrtXGEntry 6 }

		
		sleV2Pim6MrtXGJoined OBJECT-TYPE
			SYNTAX OCTET STRING
			MAX-ACCESS read-only
			STATUS current
			DESCRIPTION
				"Description."
			::= { sleV2Pim6MrtXGEntry 7 }

		
		sleV2Pim6MrtXGAssertWinner OBJECT-TYPE
			SYNTAX OCTET STRING
			MAX-ACCESS read-only
			STATUS current
			DESCRIPTION
				"Description."
			::= { sleV2Pim6MrtXGEntry 8 }

		
		sleV2Pim6MrtXGAssertLoser OBJECT-TYPE
			SYNTAX OCTET STRING
			MAX-ACCESS read-only
			STATUS current
			DESCRIPTION
				"Description."
			::= { sleV2Pim6MrtXGEntry 9 }

		
		sleV2Pim6MrouteFCR OBJECT IDENTIFIER ::= { sleV2Pim6Mroute 3 }

		
		sleV2Pim6MrtFcrTable OBJECT-TYPE
			SYNTAX SEQUENCE OF SleV2Pim6MrtFcrEntry
			MAX-ACCESS not-accessible
			STATUS current
			DESCRIPTION
				"Description."
			::= { sleV2Pim6MrouteFCR 1 }

		
		sleV2Pim6MrtFcrEntry OBJECT-TYPE
			SYNTAX SleV2Pim6MrtFcrEntry
			MAX-ACCESS not-accessible
			STATUS current
			DESCRIPTION
				"Description."
			INDEX { sleV2Pim6MrtXGGroupAddress, sleV2Pim6MrtFcrSourceAddress }
			::= { sleV2Pim6MrtFcrTable 1 }

		
		SleV2Pim6MrtFcrEntry ::=
			SEQUENCE { 
				sleV2Pim6MrtFcrSourceAddress
					InetAddressIPv6,
				sleV2Pim6MrtFcrOutgoing
					OCTET STRING,
				sleV2Pim6MrtFcrKat
					TimeTicks,
				sleV2Pim6MrtFcrPktCnt
					Counter32
			 }

		sleV2Pim6MrtFcrSourceAddress OBJECT-TYPE
			SYNTAX InetAddressIPv6
			MAX-ACCESS read-only
			STATUS current
			DESCRIPTION
				"Description."
			::= { sleV2Pim6MrtFcrEntry 1 }

		
		sleV2Pim6MrtFcrOutgoing OBJECT-TYPE
			SYNTAX OCTET STRING
			MAX-ACCESS read-only
			STATUS current
			DESCRIPTION
				"Description."
			::= { sleV2Pim6MrtFcrEntry 2 }

		
		sleV2Pim6MrtFcrKat OBJECT-TYPE
			SYNTAX TimeTicks
			MAX-ACCESS read-only
			STATUS current
			DESCRIPTION
				"Description."
			::= { sleV2Pim6MrtFcrEntry 3 }

		
		sleV2Pim6MrtFcrPktCnt OBJECT-TYPE
			SYNTAX Counter32
			MAX-ACCESS read-only
			STATUS current
			DESCRIPTION
				"Description."
			::= { sleV2Pim6MrtFcrEntry 4 }

		
		sleV2Pim6MrouteSG OBJECT IDENTIFIER ::= { sleV2Pim6Mroute 4 }

		
		sleV2Pim6MrtSGTable OBJECT-TYPE
			SYNTAX SEQUENCE OF SleV2Pim6MrtSGEntry
			MAX-ACCESS not-accessible
			STATUS current
			DESCRIPTION
				"Description."
			::= { sleV2Pim6MrouteSG 1 }

		
		sleV2Pim6MrtSGEntry OBJECT-TYPE
			SYNTAX SleV2Pim6MrtSGEntry
			MAX-ACCESS not-accessible
			STATUS current
			DESCRIPTION
				"Description."
			INDEX { sleV2Pim6MrtSGSourceAddress, sleV2Pim6MrtSGGroupAddress }
			::= { sleV2Pim6MrtSGTable 1 }

		
		SleV2Pim6MrtSGEntry ::=
			SEQUENCE { 
				sleV2Pim6MrtSGSourceAddress
					InetAddressIPv6,
				sleV2Pim6MrtSGGroupAddress
					InetAddressIPv6,
				sleV2Pim6MrtSGKat
					TimeTicks,
				sleV2Pim6MrtSGRPFNbrAddress
					InetAddressIPv6,
				sleV2Pim6MrtSGRPFVid
					INTEGER,
				sleV2Pim6MrtSGSTPBit
					INTEGER,
				sleV2Pim6MrtSGUpstreamState
					INTEGER,
				sleV2Pim6MrtSGLocal
					OCTET STRING,
				sleV2Pim6MrtSGJoined
					OCTET STRING,
				sleV2Pim6MrtSGOutgoing
					OCTET STRING,
				sleV2Pim6MrtSGAssertWinner
					OCTET STRING,
				sleV2Pim6MrtSGAssertLoser
					OCTET STRING
			 }

		sleV2Pim6MrtSGSourceAddress OBJECT-TYPE
			SYNTAX InetAddressIPv6
			MAX-ACCESS read-only
			STATUS current
			DESCRIPTION
				"Description."
			::= { sleV2Pim6MrtSGEntry 1 }

		
		sleV2Pim6MrtSGGroupAddress OBJECT-TYPE
			SYNTAX InetAddressIPv6
			MAX-ACCESS read-only
			STATUS current
			DESCRIPTION
				"Description."
			::= { sleV2Pim6MrtSGEntry 2 }

		
		sleV2Pim6MrtSGKat OBJECT-TYPE
			SYNTAX TimeTicks
			MAX-ACCESS read-only
			STATUS current
			DESCRIPTION
				"Description."
			::= { sleV2Pim6MrtSGEntry 3 }

		
		sleV2Pim6MrtSGRPFNbrAddress OBJECT-TYPE
			SYNTAX InetAddressIPv6
			MAX-ACCESS read-only
			STATUS current
			DESCRIPTION
				"Description."
			::= { sleV2Pim6MrtSGEntry 4 }

		
		sleV2Pim6MrtSGRPFVid OBJECT-TYPE
			SYNTAX INTEGER (1..40494)
			MAX-ACCESS read-only
			STATUS current
			DESCRIPTION
				"Description."
			::= { sleV2Pim6MrtSGEntry 5 }

		
		sleV2Pim6MrtSGSTPBit OBJECT-TYPE
			SYNTAX INTEGER
				{
				nonSpt(0),
				spt(1)
				}
			MAX-ACCESS read-only
			STATUS current
			DESCRIPTION
				"Description."
			::= { sleV2Pim6MrtSGEntry 6 }

		
		sleV2Pim6MrtSGUpstreamState OBJECT-TYPE
			SYNTAX INTEGER
				{
				notJoined(0),
				joined(1)
				}
			MAX-ACCESS read-only
			STATUS current
			DESCRIPTION
				"Description."
			::= { sleV2Pim6MrtSGEntry 7 }

		
		sleV2Pim6MrtSGLocal OBJECT-TYPE
			SYNTAX OCTET STRING
			MAX-ACCESS read-only
			STATUS current
			DESCRIPTION
				"Description."
			::= { sleV2Pim6MrtSGEntry 8 }

		
		sleV2Pim6MrtSGJoined OBJECT-TYPE
			SYNTAX OCTET STRING
			MAX-ACCESS read-only
			STATUS current
			DESCRIPTION
				"Description."
			::= { sleV2Pim6MrtSGEntry 9 }

		
		sleV2Pim6MrtSGOutgoing OBJECT-TYPE
			SYNTAX OCTET STRING
			MAX-ACCESS read-only
			STATUS current
			DESCRIPTION
				"Description."
			::= { sleV2Pim6MrtSGEntry 10 }

		
		sleV2Pim6MrtSGAssertWinner OBJECT-TYPE
			SYNTAX OCTET STRING
			MAX-ACCESS read-only
			STATUS current
			DESCRIPTION
				"Description."
			::= { sleV2Pim6MrtSGEntry 11 }

		
		sleV2Pim6MrtSGAssertLoser OBJECT-TYPE
			SYNTAX OCTET STRING
			MAX-ACCESS read-only
			STATUS current
			DESCRIPTION
				"Description."
			::= { sleV2Pim6MrtSGEntry 12 }

		
		sleV2Pim6MrouteSGRPT OBJECT IDENTIFIER ::= { sleV2Pim6Mroute 5 }

		
		sleV2Pim6MrtSGRPTTable OBJECT-TYPE
			SYNTAX SEQUENCE OF SleV2Pim6MrtSGRPTEntry
			MAX-ACCESS not-accessible
			STATUS current
			DESCRIPTION
				"Description."
			::= { sleV2Pim6MrouteSGRPT 1 }

		
		sleV2Pim6MrtSGRPTEntry OBJECT-TYPE
			SYNTAX SleV2Pim6MrtSGRPTEntry
			MAX-ACCESS not-accessible
			STATUS current
			DESCRIPTION
				"Description."
			INDEX { sleV2Pim6MrtSGRPTSourceAddress, sleV2Pim6MrtSGRPTGroupAddress, sleV2Pim6MrtSGRPTRPAddress }
			::= { sleV2Pim6MrtSGRPTTable 1 }

		
		SleV2Pim6MrtSGRPTEntry ::=
			SEQUENCE { 
				sleV2Pim6MrtSGRPTSourceAddress
					InetAddressIPv6,
				sleV2Pim6MrtSGRPTGroupAddress
					InetAddressIPv6,
				sleV2Pim6MrtSGRPTRPAddress
					InetAddressIPv6,
				sleV2Pim6MrtSGRPTRPFNbrAddress
					InetAddressIPv6,
				sleV2Pim6MrtSGRPTRPFVid
					INTEGER,
				sleV2Pim6MrtSGRPTUpstream
					INTEGER,
				sleV2Pim6MrtSGRPTLocal
					OCTET STRING,
				sleV2Pim6MrtSGRPTPruned
					OCTET STRING,
				sleV2Pim6MrtSGRPTOutgoing
					OCTET STRING
			 }

		sleV2Pim6MrtSGRPTSourceAddress OBJECT-TYPE
			SYNTAX InetAddressIPv6
			MAX-ACCESS read-only
			STATUS current
			DESCRIPTION
				"Description."
			::= { sleV2Pim6MrtSGRPTEntry 1 }

		
		sleV2Pim6MrtSGRPTGroupAddress OBJECT-TYPE
			SYNTAX InetAddressIPv6
			MAX-ACCESS read-only
			STATUS current
			DESCRIPTION
				"Description."
			::= { sleV2Pim6MrtSGRPTEntry 2 }

		
		sleV2Pim6MrtSGRPTRPAddress OBJECT-TYPE
			SYNTAX InetAddressIPv6
			MAX-ACCESS read-only
			STATUS current
			DESCRIPTION
				"Description."
			::= { sleV2Pim6MrtSGRPTEntry 3 }

		
		sleV2Pim6MrtSGRPTRPFNbrAddress OBJECT-TYPE
			SYNTAX InetAddressIPv6
			MAX-ACCESS read-only
			STATUS current
			DESCRIPTION
				"Description."
			::= { sleV2Pim6MrtSGRPTEntry 4 }

		
		sleV2Pim6MrtSGRPTRPFVid OBJECT-TYPE
			SYNTAX INTEGER (1..40494)
			MAX-ACCESS read-only
			STATUS current
			DESCRIPTION
				"Description."
			::= { sleV2Pim6MrtSGRPTEntry 5 }

		
		sleV2Pim6MrtSGRPTUpstream OBJECT-TYPE
			SYNTAX INTEGER
				{
				rptNotJoined(0),
				pruned(1),
				notPruned(2)
				}
			MAX-ACCESS read-only
			STATUS current
			DESCRIPTION
				"Description."
			::= { sleV2Pim6MrtSGRPTEntry 6 }

		
		sleV2Pim6MrtSGRPTLocal OBJECT-TYPE
			SYNTAX OCTET STRING
			MAX-ACCESS read-only
			STATUS current
			DESCRIPTION
				"Description."
			::= { sleV2Pim6MrtSGRPTEntry 7 }

		
		sleV2Pim6MrtSGRPTPruned OBJECT-TYPE
			SYNTAX OCTET STRING
			MAX-ACCESS read-only
			STATUS current
			DESCRIPTION
				"Description."
			::= { sleV2Pim6MrtSGRPTEntry 8 }

		
		sleV2Pim6MrtSGRPTOutgoing OBJECT-TYPE
			SYNTAX OCTET STRING
			MAX-ACCESS read-only
			STATUS current
			DESCRIPTION
				"Description."
			::= { sleV2Pim6MrtSGRPTEntry 9 }

		
		sleV2Pim6Snooping OBJECT IDENTIFIER ::= { sleV2Pim6 3 }

		
		sleV2Mld OBJECT IDENTIFIER ::= { sleV2Multicast6 3 }

		
		sleV2MldBase OBJECT IDENTIFIER ::= { sleV2Mld 1 }

		
		sleV2MLDInfo OBJECT IDENTIFIER ::= { sleV2MldBase 1 }

		
		sleV2MLDInfoLimitCount OBJECT-TYPE
			SYNTAX INTEGER (1..2097152)
			MAX-ACCESS read-only
			STATUS current
			DESCRIPTION
				"Description."
			::= { sleV2MLDInfo 1 }

		
		sleV2MLDInfoLimitACL OBJECT-TYPE
			SYNTAX OCTET STRING
			MAX-ACCESS read-only
			STATUS current
			DESCRIPTION
				"Description."
			::= { sleV2MLDInfo 2 }

		
		sleV2MLDInfoSSM OBJECT-TYPE
			SYNTAX Boolean
			MAX-ACCESS read-only
			STATUS current
			DESCRIPTION
				"Description."
			::= { sleV2MLDInfo 3 }

		
		sleV2MLDSnpInfoEnable OBJECT-TYPE
			SYNTAX Boolean
			MAX-ACCESS read-only
			STATUS current
			DESCRIPTION
				"Description."
			::= { sleV2MLDInfo 4 }

		
		sleV2MLDPxyMultipathGrp OBJECT-TYPE
			SYNTAX INTEGER
				{
				disable(0),
				enable(1)
				}
			MAX-ACCESS read-only
			STATUS current
			DESCRIPTION
				"Description."
			::= { sleV2MLDInfo 5 }

		
		sleV2MLDInfoControl OBJECT IDENTIFIER ::= { sleV2MldBase 2 }

		
		sleV2MLDInfoControlRequest OBJECT-TYPE
			SYNTAX INTEGER
				{
				setMLDInfoProfile(1),
				clearMLDInfoProfile(2),
				setMLDSnpInfoProfile(3),
				setMLDPxyInfoProfile(4)
				}
			MAX-ACCESS read-write
			STATUS current
			DESCRIPTION
				"Description."
			::= { sleV2MLDInfoControl 1 }

		
		sleV2MLDInfoControlStatus OBJECT-TYPE
			SYNTAX SleControlStatusType
			MAX-ACCESS read-write
			STATUS current
			DESCRIPTION
				"Description."
			::= { sleV2MLDInfoControl 2 }

		
		sleV2MLDInfoControlTimer OBJECT-TYPE
			SYNTAX Gauge32
			MAX-ACCESS read-write
			STATUS current
			DESCRIPTION
				"Description."
			::= { sleV2MLDInfoControl 3 }

		
		sleV2MLDInfoControlTimeStamp OBJECT-TYPE
			SYNTAX TimeTicks
			MAX-ACCESS read-write
			STATUS current
			DESCRIPTION
				"Description."
			::= { sleV2MLDInfoControl 4 }

		
		sleV2MLDInfoControlReqResult OBJECT-TYPE
			SYNTAX SleControlRequestResultType
			MAX-ACCESS read-write
			STATUS current
			DESCRIPTION
				"Description."
			::= { sleV2MLDInfoControl 5 }

		
		sleV2MLDInfoControlLimitCount OBJECT-TYPE
			SYNTAX INTEGER (1..2097152)
			MAX-ACCESS read-write
			STATUS current
			DESCRIPTION
				"Description."
			::= { sleV2MLDInfoControl 6 }

		
		sleV2MLDInfoControlLimitACL OBJECT-TYPE
			SYNTAX OCTET STRING
			MAX-ACCESS read-write
			STATUS current
			DESCRIPTION
				"Description."
			::= { sleV2MLDInfoControl 7 }

		
		sleV2MLDInfoControlSSM OBJECT-TYPE
			SYNTAX Boolean
			MAX-ACCESS read-write
			STATUS current
			DESCRIPTION
				"Description."
			::= { sleV2MLDInfoControl 8 }

		
		sleV2MLDInfoControlClearVid OBJECT-TYPE
			SYNTAX INTEGER (1..4094)
			MAX-ACCESS read-write
			STATUS current
			DESCRIPTION
				"Description."
			::= { sleV2MLDInfoControl 9 }

		
		sleV2MLDInfoControlClearGroup OBJECT-TYPE
			SYNTAX InetAddressIPv6
			MAX-ACCESS read-write
			STATUS current
			DESCRIPTION
				"Description."
			::= { sleV2MLDInfoControl 10 }

		
		sleV2MLDSnpInfoControlEnable OBJECT-TYPE
			SYNTAX Boolean
			MAX-ACCESS read-write
			STATUS current
			DESCRIPTION
				"Description."
			::= { sleV2MLDInfoControl 11 }

		
		sleV2MLDPxyInfoControlMultipathGrp OBJECT-TYPE
			SYNTAX INTEGER
				{
				disable(0),
				enable(1)
				}
			MAX-ACCESS read-write
			STATUS current
			DESCRIPTION
				"Description."
			::= { sleV2MLDInfoControl 12 }

		
		sleV2MLDInfoNotification OBJECT IDENTIFIER ::= { sleV2MldBase 3 }

		
		sleV2MLDInfoProfileChanged NOTIFICATION-TYPE
			OBJECTS { sleV2MLDInfoControlRequest, sleV2MLDInfoControlTimeStamp, sleV2MLDInfoControlReqResult, sleV2MLDInfoLimitCount, sleV2MLDInfoLimitACL, 
				sleV2MLDInfoSSM }
			STATUS current
			DESCRIPTION 
				"Description."
			::= { sleV2MLDInfoNotification 1 }

		
		sleV2MLDInfoProfileCleared NOTIFICATION-TYPE
			OBJECTS { sleV2MLDInfoControlRequest, sleV2MLDInfoControlTimeStamp, sleV2MLDInfoControlReqResult, sleV2MLDInfoControlClearVid, sleV2MLDInfoControlClearGroup
				 }
			STATUS current
			DESCRIPTION 
				"Description."
			::= { sleV2MLDInfoNotification 2 }

		
		sleV2MLDSnpInfoProfileChanged NOTIFICATION-TYPE
			OBJECTS { sleV2MLDInfoControlRequest, sleV2MLDInfoControlTimeStamp, sleV2MLDInfoControlReqResult, sleV2MLDSnpInfoEnable }
			STATUS current
			DESCRIPTION 
				"Description."
			::= { sleV2MLDInfoNotification 3 }

		
		sleV2MLDPxyInfoProfileChanged NOTIFICATION-TYPE
			OBJECTS { sleV2MLDInfoControlRequest, sleV2MLDInfoControlTimeStamp, sleV2MLDInfoControlReqResult, sleV2MLDPxyMultipathGrp }
			STATUS current
			DESCRIPTION 
				"Description."
			::= { sleV2MLDInfoNotification 4 }

		
		sleV2MldAgent OBJECT IDENTIFIER ::= { sleV2Mld 2 }

		
		sleV2MldInterface OBJECT IDENTIFIER ::= { sleV2MldAgent 1 }

		
		sleV2MLDIfTable OBJECT-TYPE
			SYNTAX SEQUENCE OF SleV2MLDIfEntry
			MAX-ACCESS not-accessible
			STATUS current
			DESCRIPTION
				"Description."
			::= { sleV2MldInterface 1 }

		
		sleV2MLDIfEntry OBJECT-TYPE
			SYNTAX SleV2MLDIfEntry
			MAX-ACCESS not-accessible
			STATUS current
			DESCRIPTION
				"Description."
			INDEX { sleV2MLDIfVid }
			::= { sleV2MLDIfTable 1 }

		
		SleV2MLDIfEntry ::=
			SEQUENCE { 
				sleV2MLDIfVid
					INTEGER,
				sleV2MLDIfAcl
					OCTET STRING,
				sleV2MLDIfActive
					Boolean,
				sleV2MLDIfQuerier
					INTEGER,
				sleV2MLDIfVersion
					INTEGER,
				sleV2MLDIfLinkLocalAddress
					InetAddressIPv6,
				sleV2MLDIfLimitCount
					INTEGER,
				sleV2MLDIfLimitACL
					OCTET STRING,
				sleV2MLDIfGroupNum
					INTEGER,
				sleV2MLDIfJoinNum
					INTEGER,
				sleV2MLDIfLeaveNum
					INTEGER,
				sleV2MLDIfQueryingRouter
					InetAddressIPv6,
				sleV2MLDIfQueryInterval
					INTEGER,
				sleV2MLDIfQuerierTimeout
					INTEGER,
				sleV2MLDIfQueryMaxResponseTime
					INTEGER,
				sleV2MLDIfLastMemberQueryCount
					INTEGER,
				sleV2MLDIfLastMemberQueryInterval
					INTEGER,
				sleV2MLDIfGroupMembershipInterval
					INTEGER,
				sleV2MLDIfImmLeaveACL
					OCTET STRING
			 }

		sleV2MLDIfVid OBJECT-TYPE
			SYNTAX INTEGER (1..4094)
			MAX-ACCESS read-only
			STATUS current
			DESCRIPTION
				"Description."
			::= { sleV2MLDIfEntry 1 }

		
		sleV2MLDIfAcl OBJECT-TYPE
			SYNTAX OCTET STRING
			MAX-ACCESS read-only
			STATUS current
			DESCRIPTION
				"Description."
			::= { sleV2MLDIfEntry 2 }

		
		sleV2MLDIfActive OBJECT-TYPE
			SYNTAX Boolean
			MAX-ACCESS read-only
			STATUS current
			DESCRIPTION
				"Description."
			::= { sleV2MLDIfEntry 3 }

		
		sleV2MLDIfQuerier OBJECT-TYPE
			SYNTAX INTEGER
				{
				nonQuerier(0),
				querier(1)
				}
			MAX-ACCESS read-only
			STATUS current
			DESCRIPTION
				"Description."
			::= { sleV2MLDIfEntry 4 }

		
		sleV2MLDIfVersion OBJECT-TYPE
			SYNTAX INTEGER
				{
				version1(1),
				version2(2)
				}
			MAX-ACCESS read-only
			STATUS current
			DESCRIPTION
				"Description."
			::= { sleV2MLDIfEntry 5 }

		
		sleV2MLDIfLinkLocalAddress OBJECT-TYPE
			SYNTAX InetAddressIPv6
			MAX-ACCESS read-only
			STATUS current
			DESCRIPTION
				"Description."
			::= { sleV2MLDIfEntry 6 }

		
		sleV2MLDIfLimitCount OBJECT-TYPE
			SYNTAX INTEGER (1..2097152)
			MAX-ACCESS read-only
			STATUS current
			DESCRIPTION
				"Description."
			::= { sleV2MLDIfEntry 7 }

		
		sleV2MLDIfLimitACL OBJECT-TYPE
			SYNTAX OCTET STRING
			MAX-ACCESS read-only
			STATUS current
			DESCRIPTION
				"Description."
			::= { sleV2MLDIfEntry 8 }

		
		sleV2MLDIfGroupNum OBJECT-TYPE
			SYNTAX INTEGER
			MAX-ACCESS read-only
			STATUS current
			DESCRIPTION
				"Description."
			::= { sleV2MLDIfEntry 9 }

		
		sleV2MLDIfJoinNum OBJECT-TYPE
			SYNTAX INTEGER
			MAX-ACCESS read-only
			STATUS current
			DESCRIPTION
				"Description."
			::= { sleV2MLDIfEntry 10 }

		
		sleV2MLDIfLeaveNum OBJECT-TYPE
			SYNTAX INTEGER
			MAX-ACCESS read-only
			STATUS current
			DESCRIPTION
				"Description."
			::= { sleV2MLDIfEntry 11 }

		
		sleV2MLDIfQueryingRouter OBJECT-TYPE
			SYNTAX InetAddressIPv6
			MAX-ACCESS read-only
			STATUS current
			DESCRIPTION
				"Description."
			::= { sleV2MLDIfEntry 12 }

		
		sleV2MLDIfQueryInterval OBJECT-TYPE
			SYNTAX INTEGER (1..18000)
			MAX-ACCESS read-only
			STATUS current
			DESCRIPTION
				"Description."
			::= { sleV2MLDIfEntry 13 }

		
		sleV2MLDIfQuerierTimeout OBJECT-TYPE
			SYNTAX INTEGER (60..300)
			MAX-ACCESS read-only
			STATUS current
			DESCRIPTION
				"Description."
			::= { sleV2MLDIfEntry 14 }

		
		sleV2MLDIfQueryMaxResponseTime OBJECT-TYPE
			SYNTAX INTEGER (1..240)
			MAX-ACCESS read-only
			STATUS current
			DESCRIPTION
				"Description."
			::= { sleV2MLDIfEntry 15 }

		
		sleV2MLDIfLastMemberQueryCount OBJECT-TYPE
			SYNTAX INTEGER (-1 | 2..7)
			MAX-ACCESS read-only
			STATUS current
			DESCRIPTION
				"Description."
			::= { sleV2MLDIfEntry 16 }

		
		sleV2MLDIfLastMemberQueryInterval OBJECT-TYPE
			SYNTAX INTEGER (1000..25500)
			MAX-ACCESS read-only
			STATUS current
			DESCRIPTION
				"Description."
			::= { sleV2MLDIfEntry 17 }

		
		sleV2MLDIfGroupMembershipInterval OBJECT-TYPE
			SYNTAX INTEGER
			MAX-ACCESS read-only
			STATUS current
			DESCRIPTION
				"Description."
			::= { sleV2MLDIfEntry 18 }

		
		sleV2MLDIfImmLeaveACL OBJECT-TYPE
			SYNTAX OCTET STRING
			MAX-ACCESS read-only
			STATUS current
			DESCRIPTION
				"Description."
			::= { sleV2MLDIfEntry 19 }

		
		sleV2MLDIfControl OBJECT IDENTIFIER ::= { sleV2MldInterface 2 }

		
		sleV2MLDIfControlRequest OBJECT-TYPE
			SYNTAX INTEGER { setMLDIfProfile(1) }
			MAX-ACCESS read-write
			STATUS current
			DESCRIPTION
				"Description."
			::= { sleV2MLDIfControl 1 }

		
		sleV2MLDIfControlStatus OBJECT-TYPE
			SYNTAX SleControlStatusType
			MAX-ACCESS read-write
			STATUS current
			DESCRIPTION
				"Description."
			::= { sleV2MLDIfControl 2 }

		
		sleV2MLDIfControlTimer OBJECT-TYPE
			SYNTAX Gauge32
			MAX-ACCESS read-write
			STATUS current
			DESCRIPTION
				"Description."
			::= { sleV2MLDIfControl 3 }

		
		sleV2MLDIfControlTimeStamp OBJECT-TYPE
			SYNTAX TimeTicks
			MAX-ACCESS read-write
			STATUS current
			DESCRIPTION
				"Description."
			::= { sleV2MLDIfControl 4 }

		
		sleV2MLDIfControlReqResult OBJECT-TYPE
			SYNTAX SleControlRequestResultType
			MAX-ACCESS read-write
			STATUS current
			DESCRIPTION
				"Description."
			::= { sleV2MLDIfControl 5 }

		
		sleV2MLDIfControlVid OBJECT-TYPE
			SYNTAX INTEGER (1..4094)
			MAX-ACCESS read-write
			STATUS current
			DESCRIPTION
				"Description."
			::= { sleV2MLDIfControl 6 }

		
		sleV2MLDIfControlACL OBJECT-TYPE
			SYNTAX OCTET STRING
			MAX-ACCESS read-write
			STATUS current
			DESCRIPTION
				"Description."
			::= { sleV2MLDIfControl 7 }

		
		sleV2MLDIfControlImmLeaveACL OBJECT-TYPE
			SYNTAX OCTET STRING
			MAX-ACCESS read-write
			STATUS current
			DESCRIPTION
				"Description."
			::= { sleV2MLDIfControl 8 }

		
		sleV2MLDIfControlLMQC OBJECT-TYPE
			SYNTAX INTEGER (-1 | 2..7)
			MAX-ACCESS read-write
			STATUS current
			DESCRIPTION
				"Description."
			::= { sleV2MLDIfControl 9 }

		
		sleV2MLDIfControlLMCI OBJECT-TYPE
			SYNTAX INTEGER (-1 | 1000..25500)
			MAX-ACCESS read-write
			STATUS current
			DESCRIPTION
				"Description."
			::= { sleV2MLDIfControl 10 }

		
		sleV2MLDIfControlLimitCount OBJECT-TYPE
			SYNTAX INTEGER (-1 | 1..2097152)
			MAX-ACCESS read-write
			STATUS current
			DESCRIPTION
				"Description."
			::= { sleV2MLDIfControl 11 }

		
		sleV2MLDIfControlLimitACL OBJECT-TYPE
			SYNTAX OCTET STRING
			MAX-ACCESS read-write
			STATUS current
			DESCRIPTION
				"Description."
			::= { sleV2MLDIfControl 12 }

		
		sleV2MLDIfControlQuerierTimeout OBJECT-TYPE
			SYNTAX INTEGER (-1 | 60..300)
			MAX-ACCESS read-write
			STATUS current
			DESCRIPTION
				"Description."
			::= { sleV2MLDIfControl 13 }

		
		sleV2MLDIfControlQueryInterval OBJECT-TYPE
			SYNTAX INTEGER (-1 | 1..18000)
			MAX-ACCESS read-write
			STATUS current
			DESCRIPTION
				"Description."
			::= { sleV2MLDIfControl 14 }

		
		sleV2MLDIfControlQueryMaxRespTime OBJECT-TYPE
			SYNTAX INTEGER (-1 | 1..240)
			MAX-ACCESS read-write
			STATUS current
			DESCRIPTION
				"Description."
			::= { sleV2MLDIfControl 15 }

		
		sleV2MLDIfControlRobustnessVariable OBJECT-TYPE
			SYNTAX INTEGER (-1 | 2..7)
			MAX-ACCESS read-write
			STATUS current
			DESCRIPTION
				"Description."
			::= { sleV2MLDIfControl 16 }

		
		sleV2MLDIfControlVersion OBJECT-TYPE
			SYNTAX INTEGER (-1 | 1..2)
			MAX-ACCESS read-write
			STATUS current
			DESCRIPTION
				"Description."
			::= { sleV2MLDIfControl 17 }

		
		sleV2MLDIfNotification OBJECT IDENTIFIER ::= { sleV2MldInterface 3 }

		
		sleV2MLDIfProfileChanged NOTIFICATION-TYPE
			OBJECTS { sleV2MLDIfControlRequest, sleV2MLDIfControlTimeStamp, sleV2MLDIfControlReqResult, sleV2MLDIfVid, sleV2MLDIfVersion, 
				sleV2MLDIfLinkLocalAddress, sleV2MLDIfLimitCount, sleV2MLDIfLimitACL, sleV2MLDIfQueryInterval, sleV2MLDIfQuerierTimeout, 
				sleV2MLDIfQueryMaxResponseTime, sleV2MLDIfImmLeaveACL, sleV2MLDIfLastMemberQueryCount, sleV2MLDIfLastMemberQueryInterval }
			STATUS current
			DESCRIPTION 
				"Description."
			::= { sleV2MLDIfNotification 1 }

		
		sleV2MldGroup OBJECT IDENTIFIER ::= { sleV2MldAgent 2 }

		
		sleV2MLDGroupTable OBJECT-TYPE
			SYNTAX SEQUENCE OF SleV2MLDGroupEntry
			MAX-ACCESS not-accessible
			STATUS current
			DESCRIPTION
				"Description."
			::= { sleV2MldGroup 1 }

		
		sleV2MLDGroupEntry OBJECT-TYPE
			SYNTAX SleV2MLDGroupEntry
			MAX-ACCESS not-accessible
			STATUS current
			DESCRIPTION
				"Description."
			INDEX { sleV2MLDIfVid, sleV2MLDGroupAddress }
			::= { sleV2MLDGroupTable 1 }

		
		SleV2MLDGroupEntry ::=
			SEQUENCE { 
				sleV2MLDGroupAddress
					InetAddressIPv6,
				sleV2MLDGroupUptime
					TimeTicks,
				sleV2MLDGroupMode
					INTEGER,
				sleV2MLDGroupExpire
					TimeTicks,
				sleV2MLDGroupLastReporter
					InetAddressIPv6,
				sleV2MLDGroupFirstReporter
					InetAddressIPv6
			 }

		sleV2MLDGroupAddress OBJECT-TYPE
			SYNTAX InetAddressIPv6
			MAX-ACCESS read-only
			STATUS current
			DESCRIPTION
				"Description."
			::= { sleV2MLDGroupEntry 1 }

		
		sleV2MLDGroupUptime OBJECT-TYPE
			SYNTAX TimeTicks
			MAX-ACCESS read-only
			STATUS current
			DESCRIPTION
				"Description."
			::= { sleV2MLDGroupEntry 2 }

		
		sleV2MLDGroupMode OBJECT-TYPE
			SYNTAX INTEGER
				{
				invalid(0),
				include(1),
				exclude(2)
				}
			MAX-ACCESS read-only
			STATUS current
			DESCRIPTION
				"Description."
			::= { sleV2MLDGroupEntry 3 }

		
		sleV2MLDGroupExpire OBJECT-TYPE
			SYNTAX TimeTicks
			MAX-ACCESS read-only
			STATUS current
			DESCRIPTION
				"Description."
			::= { sleV2MLDGroupEntry 4 }

		
		sleV2MLDGroupLastReporter OBJECT-TYPE
			SYNTAX InetAddressIPv6
			MAX-ACCESS read-only
			STATUS current
			DESCRIPTION
				"Description."
			::= { sleV2MLDGroupEntry 5 }

		
		sleV2MLDGroupFirstReporter OBJECT-TYPE
			SYNTAX InetAddressIPv6
			MAX-ACCESS read-only
			STATUS current
			DESCRIPTION
				"Description."
			::= { sleV2MLDGroupEntry 6 }

		
		sleV2MldSource OBJECT IDENTIFIER ::= { sleV2MldAgent 3 }

		
		sleV2MLDSourceTable OBJECT-TYPE
			SYNTAX SEQUENCE OF SleV2MLDSourceEntry
			MAX-ACCESS not-accessible
			STATUS current
			DESCRIPTION
				"Description."
			::= { sleV2MldSource 1 }

		
		sleV2MLDSourceEntry OBJECT-TYPE
			SYNTAX SleV2MLDSourceEntry
			MAX-ACCESS not-accessible
			STATUS current
			DESCRIPTION
				"Description."
			INDEX { sleV2MLDIfVid, sleV2MLDGroupAddress, sleV2MLDSourceAddress }
			::= { sleV2MLDSourceTable 1 }

		
		SleV2MLDSourceEntry ::=
			SEQUENCE { 
				sleV2MLDSourceAddress
					InetAddressIPv6,
				sleV2MLDSourceListType
					INTEGER,
				sleV2MLDSourceUptime
					TimeTicks,
				sleV2MLDSourceExpire
					TimeTicks
			 }

		sleV2MLDSourceAddress OBJECT-TYPE
			SYNTAX InetAddressIPv6
			MAX-ACCESS read-only
			STATUS current
			DESCRIPTION
				"Description."
			::= { sleV2MLDSourceEntry 1 }

		
		sleV2MLDSourceListType OBJECT-TYPE
			SYNTAX INTEGER
				{
				allow(1),
				block(2)
				}
			MAX-ACCESS read-only
			STATUS current
			DESCRIPTION
				"Description."
			::= { sleV2MLDSourceEntry 2 }

		
		sleV2MLDSourceUptime OBJECT-TYPE
			SYNTAX TimeTicks
			MAX-ACCESS read-only
			STATUS current
			DESCRIPTION
				"Description."
			::= { sleV2MLDSourceEntry 3 }

		
		sleV2MLDSourceExpire OBJECT-TYPE
			SYNTAX TimeTicks
			MAX-ACCESS read-only
			STATUS current
			DESCRIPTION
				"Description."
			::= { sleV2MLDSourceEntry 4 }

		
		sleV2MldSnooping OBJECT IDENTIFIER ::= { sleV2Mld 3 }

		
		sleV2MldSnoopingInterface OBJECT IDENTIFIER ::= { sleV2MldSnooping 1 }

		
		sleV2MLDSnpIfTable OBJECT-TYPE
			SYNTAX SEQUENCE OF SleV2MLDSnpIfEntry
			MAX-ACCESS not-accessible
			STATUS current
			DESCRIPTION
				"Description."
			::= { sleV2MldSnoopingInterface 1 }

		
		sleV2MLDSnpIfEntry OBJECT-TYPE
			SYNTAX SleV2MLDSnpIfEntry
			MAX-ACCESS not-accessible
			STATUS current
			DESCRIPTION
				"Description."
			INDEX { sleV2MLDSnpIfVid }
			::= { sleV2MLDSnpIfTable 1 }

		
		SleV2MLDSnpIfEntry ::=
			SEQUENCE { 
				sleV2MLDSnpIfVid
					INTEGER,
				sleV2MLDSnpIfAcl
					OCTET STRING,
				sleV2MLDSnpIfActive
					Boolean,
				sleV2MLDSnpIfQuerier
					INTEGER,
				sleV2MLDSnpIfVersion
					INTEGER,
				sleV2MLDSnpIfLinkLocalAddress
					InetAddressIPv6,
				sleV2MLDSnpIfLimit
					INTEGER,
				sleV2MLDSnpIfLimitACL
					OCTET STRING,
				sleV2MLDSnpIfGroupNum
					INTEGER,
				sleV2MLDSnpIfJoinNum
					INTEGER,
				sleV2MLDSnpIfLeaveNum
					INTEGER,
				sleV2MLDSnpIfQueryingRouter
					InetAddressIPv6,
				sleV2MLDSnpIfQueryInterval
					INTEGER,
				sleV2MLDSnpIfQuerierTimeout
					INTEGER,
				sleV2MLDSnpIfQueryMaxResponseTime
					INTEGER,
				sleV2MLDSnpIfLastMemberQueryCount
					INTEGER,
				sleV2MLDSnpIfLastMemberQueryInterval
					INTEGER,
				sleV2MLDSnpIfGroupMembershipInterval
					INTEGER,
				sleV2MLDSnpIfFastLeave
					Boolean,
				sleV2MLDSnpIfSuppression
					Boolean,
				sleV2MLDSnpIMroutePorts
					OCTET STRING
			 }

		sleV2MLDSnpIfVid OBJECT-TYPE
			SYNTAX INTEGER (1..4094)
			MAX-ACCESS read-only
			STATUS current
			DESCRIPTION
				"Description."
			::= { sleV2MLDSnpIfEntry 1 }

		
		sleV2MLDSnpIfAcl OBJECT-TYPE
			SYNTAX OCTET STRING
			MAX-ACCESS read-only
			STATUS current
			DESCRIPTION
				"Description."
			::= { sleV2MLDSnpIfEntry 2 }

		
		sleV2MLDSnpIfActive OBJECT-TYPE
			SYNTAX Boolean
			MAX-ACCESS read-only
			STATUS current
			DESCRIPTION
				"Description."
			::= { sleV2MLDSnpIfEntry 3 }

		
		sleV2MLDSnpIfQuerier OBJECT-TYPE
			SYNTAX INTEGER
				{
				nonQuerier(0),
				querier(1)
				}
			MAX-ACCESS read-only
			STATUS current
			DESCRIPTION
				"Description."
			::= { sleV2MLDSnpIfEntry 4 }

		
		sleV2MLDSnpIfVersion OBJECT-TYPE
			SYNTAX INTEGER
				{
				version1(1),
				version2(2)
				}
			MAX-ACCESS read-only
			STATUS current
			DESCRIPTION
				"Description."
			::= { sleV2MLDSnpIfEntry 5 }

		
		sleV2MLDSnpIfLinkLocalAddress OBJECT-TYPE
			SYNTAX InetAddressIPv6
			MAX-ACCESS read-only
			STATUS current
			DESCRIPTION
				"Description."
			::= { sleV2MLDSnpIfEntry 6 }

		
		sleV2MLDSnpIfLimit OBJECT-TYPE
			SYNTAX INTEGER (1..2097152)
			MAX-ACCESS read-only
			STATUS current
			DESCRIPTION
				"Description."
			::= { sleV2MLDSnpIfEntry 7 }

		
		sleV2MLDSnpIfLimitACL OBJECT-TYPE
			SYNTAX OCTET STRING
			MAX-ACCESS read-only
			STATUS current
			DESCRIPTION
				"Description."
			::= { sleV2MLDSnpIfEntry 8 }

		
		sleV2MLDSnpIfGroupNum OBJECT-TYPE
			SYNTAX INTEGER
			MAX-ACCESS read-only
			STATUS current
			DESCRIPTION
				"Description."
			::= { sleV2MLDSnpIfEntry 9 }

		
		sleV2MLDSnpIfJoinNum OBJECT-TYPE
			SYNTAX INTEGER
			MAX-ACCESS read-only
			STATUS current
			DESCRIPTION
				"Description."
			::= { sleV2MLDSnpIfEntry 10 }

		
		sleV2MLDSnpIfLeaveNum OBJECT-TYPE
			SYNTAX INTEGER
			MAX-ACCESS read-only
			STATUS current
			DESCRIPTION
				"Description."
			::= { sleV2MLDSnpIfEntry 11 }

		
		sleV2MLDSnpIfQueryingRouter OBJECT-TYPE
			SYNTAX InetAddressIPv6
			MAX-ACCESS read-only
			STATUS current
			DESCRIPTION
				"Description."
			::= { sleV2MLDSnpIfEntry 12 }

		
		sleV2MLDSnpIfQueryInterval OBJECT-TYPE
			SYNTAX INTEGER (1..18000)
			MAX-ACCESS read-only
			STATUS current
			DESCRIPTION
				"Description."
			::= { sleV2MLDSnpIfEntry 13 }

		
		sleV2MLDSnpIfQuerierTimeout OBJECT-TYPE
			SYNTAX INTEGER (60..300)
			MAX-ACCESS read-only
			STATUS current
			DESCRIPTION
				"Description."
			::= { sleV2MLDSnpIfEntry 14 }

		
		sleV2MLDSnpIfQueryMaxResponseTime OBJECT-TYPE
			SYNTAX INTEGER (1..240)
			MAX-ACCESS read-only
			STATUS current
			DESCRIPTION
				"Description."
			::= { sleV2MLDSnpIfEntry 15 }

		
		sleV2MLDSnpIfLastMemberQueryCount OBJECT-TYPE
			SYNTAX INTEGER (-1 | 2..7)
			MAX-ACCESS read-only
			STATUS current
			DESCRIPTION
				"Description."
			::= { sleV2MLDSnpIfEntry 16 }

		
		sleV2MLDSnpIfLastMemberQueryInterval OBJECT-TYPE
			SYNTAX INTEGER (1000..25500)
			MAX-ACCESS read-only
			STATUS current
			DESCRIPTION
				"Description."
			::= { sleV2MLDSnpIfEntry 17 }

		
		sleV2MLDSnpIfGroupMembershipInterval OBJECT-TYPE
			SYNTAX INTEGER
			MAX-ACCESS read-only
			STATUS current
			DESCRIPTION
				"Description."
			::= { sleV2MLDSnpIfEntry 18 }

		
		sleV2MLDSnpIfFastLeave OBJECT-TYPE
			SYNTAX Boolean
			MAX-ACCESS read-only
			STATUS current
			DESCRIPTION
				"Description."
			::= { sleV2MLDSnpIfEntry 19 }

		
		sleV2MLDSnpIfSuppression OBJECT-TYPE
			SYNTAX Boolean
			MAX-ACCESS read-only
			STATUS current
			DESCRIPTION
				"Description."
			::= { sleV2MLDSnpIfEntry 20 }

		
		sleV2MLDSnpIMroutePorts OBJECT-TYPE
			SYNTAX OCTET STRING
			MAX-ACCESS read-only
			STATUS current
			DESCRIPTION
				"Description."
			::= { sleV2MLDSnpIfEntry 21 }

		
		sleV2MLDSnpIfControl OBJECT IDENTIFIER ::= { sleV2MldSnoopingInterface 2 }

		
		sleV2MLDSnpIfControlRequest OBJECT-TYPE
			SYNTAX INTEGER { setMLDSnpIfProfile(1) }
			MAX-ACCESS read-write
			STATUS current
			DESCRIPTION
				"Description."
			::= { sleV2MLDSnpIfControl 1 }

		
		sleV2MLDSnpIfControlStatus OBJECT-TYPE
			SYNTAX SleControlStatusType
			MAX-ACCESS read-write
			STATUS current
			DESCRIPTION
				"Description."
			::= { sleV2MLDSnpIfControl 2 }

		
		sleV2MLDSnpIfControlTimer OBJECT-TYPE
			SYNTAX Gauge32
			MAX-ACCESS read-write
			STATUS current
			DESCRIPTION
				"Description."
			::= { sleV2MLDSnpIfControl 3 }

		
		sleV2MLDSnpIfControlTimeStamp OBJECT-TYPE
			SYNTAX TimeTicks
			MAX-ACCESS read-write
			STATUS current
			DESCRIPTION
				"Description."
			::= { sleV2MLDSnpIfControl 4 }

		
		sleV2MLDSnpIfControlReqResult OBJECT-TYPE
			SYNTAX SleControlRequestResultType
			MAX-ACCESS read-write
			STATUS current
			DESCRIPTION
				"Description."
			::= { sleV2MLDSnpIfControl 5 }

		
		sleV2MLDSnpIfControlVid OBJECT-TYPE
			SYNTAX INTEGER (1..4094)
			MAX-ACCESS read-write
			STATUS current
			DESCRIPTION
				"Description."
			::= { sleV2MLDSnpIfControl 6 }

		
		sleV2MLDSnpIfControlEnable OBJECT-TYPE
			SYNTAX Boolean
			MAX-ACCESS read-write
			STATUS current
			DESCRIPTION
				"Description."
			::= { sleV2MLDSnpIfControl 7 }

		
		sleV2MLDSnpIfControlACL OBJECT-TYPE
			SYNTAX OCTET STRING
			MAX-ACCESS read-write
			STATUS current
			DESCRIPTION
				"Description."
			::= { sleV2MLDSnpIfControl 8 }

		
		sleV2MLDSnpIfControlFastLeave OBJECT-TYPE
			SYNTAX Boolean
			MAX-ACCESS read-write
			STATUS current
			DESCRIPTION
				"Description."
			::= { sleV2MLDSnpIfControl 9 }

		
		sleV2MLDSnpIfControlLMQC OBJECT-TYPE
			SYNTAX INTEGER (-1 | 2..7)
			MAX-ACCESS read-write
			STATUS current
			DESCRIPTION
				"Description."
			::= { sleV2MLDSnpIfControl 10 }

		
		sleV2MLDSnpIfControlLMCI OBJECT-TYPE
			SYNTAX INTEGER (-1 | 1000..25500)
			MAX-ACCESS read-write
			STATUS current
			DESCRIPTION
				"Description."
			::= { sleV2MLDSnpIfControl 11 }

		
		sleV2MLDSnpIfControlLimitCount OBJECT-TYPE
			SYNTAX INTEGER (-1 | 1..2097152)
			MAX-ACCESS read-write
			STATUS current
			DESCRIPTION
				"Description."
			::= { sleV2MLDSnpIfControl 12 }

		
		sleV2MLDSnpIfControlLimitACL OBJECT-TYPE
			SYNTAX OCTET STRING
			MAX-ACCESS read-write
			STATUS current
			DESCRIPTION
				"Description."
			::= { sleV2MLDSnpIfControl 13 }

		
		sleV2MLDSnpIfControlQuerierTimeout OBJECT-TYPE
			SYNTAX INTEGER (-1 | 60..300)
			MAX-ACCESS read-write
			STATUS current
			DESCRIPTION
				"Description."
			::= { sleV2MLDSnpIfControl 14 }

		
		sleV2MLDSnpIfControlQueryInterval OBJECT-TYPE
			SYNTAX INTEGER (-1 | 1..18000)
			MAX-ACCESS read-write
			STATUS current
			DESCRIPTION
				"Description."
			::= { sleV2MLDSnpIfControl 15 }

		
		sleV2MLDSnpIfControlQueryMaxRespTime OBJECT-TYPE
			SYNTAX INTEGER (-1 | 1..240)
			MAX-ACCESS read-write
			STATUS current
			DESCRIPTION
				"Description."
			::= { sleV2MLDSnpIfControl 16 }

		
		sleV2MLDSnpIfControlRobustnessVariable OBJECT-TYPE
			SYNTAX INTEGER (-1 | 2..7)
			MAX-ACCESS read-write
			STATUS current
			DESCRIPTION
				"Description."
			::= { sleV2MLDSnpIfControl 17 }

		
		sleV2MLDSnpIfControlVersion OBJECT-TYPE
			SYNTAX INTEGER (-1 | 1..2)
			MAX-ACCESS read-write
			STATUS current
			DESCRIPTION
				"Description."
			::= { sleV2MLDSnpIfControl 18 }

		
		sleV2MLDSnpIfControlMroutePorts OBJECT-TYPE
			SYNTAX OCTET STRING
			MAX-ACCESS read-write
			STATUS current
			DESCRIPTION
				"Description."
			::= { sleV2MLDSnpIfControl 19 }

		
		sleV2MLDSnpIfControlQuerier OBJECT-TYPE
			SYNTAX Boolean
			MAX-ACCESS read-write
			STATUS current
			DESCRIPTION
				"Description."
			::= { sleV2MLDSnpIfControl 20 }

		
		sleV2MLDSnpIfControlSuppresion OBJECT-TYPE
			SYNTAX Boolean
			MAX-ACCESS read-write
			STATUS current
			DESCRIPTION
				"Description."
			::= { sleV2MLDSnpIfControl 21 }

		
		sleV2MLDSnpIfNotification OBJECT IDENTIFIER ::= { sleV2MldSnoopingInterface 3 }

		
		sleV2CreateMLDSnpIfProfile NOTIFICATION-TYPE
			OBJECTS { sleV2MLDSnpIfControlRequest, sleV2MLDSnpIfControlTimeStamp, sleV2MLDSnpIfControlReqResult, sleV2MLDSnpIfVid, sleV2MLDSnpIfActive, 
				sleV2MLDSnpIfAcl, sleV2MLDSnpIfQuerier, sleV2MLDSnpIfVersion, sleV2MLDSnpIfLinkLocalAddress, sleV2MLDSnpIfLimit, 
				sleV2MLDSnpIfLimitACL, sleV2MLDSnpIfQueryInterval, sleV2MLDSnpIfQuerierTimeout, sleV2MLDSnpIfQueryMaxResponseTime, sleV2MLDSnpIfFastLeave, 
				sleV2MLDSnpIfSuppression, sleV2MLDSnpIfLastMemberQueryCount, sleV2MLDSnpIfLastMemberQueryInterval, sleV2MLDSnpIMroutePorts }
			STATUS current
			DESCRIPTION 
				"Description."
			::= { sleV2MLDSnpIfNotification 1 }

		
		sleV2MldSnoopingGroup OBJECT IDENTIFIER ::= { sleV2MldSnooping 2 }

		
		sleV2MLDSnpGroupTable OBJECT-TYPE
			SYNTAX SEQUENCE OF SleV2MLDSnpGroupEntry
			MAX-ACCESS not-accessible
			STATUS current
			DESCRIPTION
				"Description."
			::= { sleV2MldSnoopingGroup 1 }

		
		sleV2MLDSnpGroupEntry OBJECT-TYPE
			SYNTAX SleV2MLDSnpGroupEntry
			MAX-ACCESS not-accessible
			STATUS current
			DESCRIPTION
				"Description."
			INDEX { sleV2MLDSnpIfVid, sleV2MLDSnpGroupAddress }
			::= { sleV2MLDSnpGroupTable 1 }

		
		SleV2MLDSnpGroupEntry ::=
			SEQUENCE { 
				sleV2MLDSnpGroupAddress
					InetAddressIPv6,
				sleV2MLDSnpGroupMode
					INTEGER,
				sleV2MLDSnpGroupUptime
					TimeTicks,
				sleV2MLDSnpGroupExpire
					TimeTicks,
				sleV2MLDSnpGroupLastReporter
					InetAddressIPv6,
				sleV2MLDSnpGroupFirstReporter
					InetAddressIPv6
			 }

		sleV2MLDSnpGroupAddress OBJECT-TYPE
			SYNTAX InetAddressIPv6
			MAX-ACCESS read-only
			STATUS current
			DESCRIPTION
				"Description."
			::= { sleV2MLDSnpGroupEntry 1 }

		
		sleV2MLDSnpGroupMode OBJECT-TYPE
			SYNTAX INTEGER
				{
				invalid(0),
				include(1),
				exclude(2)
				}
			MAX-ACCESS read-only
			STATUS current
			DESCRIPTION
				"Description."
			::= { sleV2MLDSnpGroupEntry 2 }

		
		sleV2MLDSnpGroupUptime OBJECT-TYPE
			SYNTAX TimeTicks
			MAX-ACCESS read-only
			STATUS current
			DESCRIPTION
				"Description."
			::= { sleV2MLDSnpGroupEntry 3 }

		
		sleV2MLDSnpGroupExpire OBJECT-TYPE
			SYNTAX TimeTicks
			MAX-ACCESS read-only
			STATUS current
			DESCRIPTION
				"Description."
			::= { sleV2MLDSnpGroupEntry 4 }

		
		sleV2MLDSnpGroupLastReporter OBJECT-TYPE
			SYNTAX InetAddressIPv6
			MAX-ACCESS read-only
			STATUS current
			DESCRIPTION
				"Description."
			::= { sleV2MLDSnpGroupEntry 5 }

		
		sleV2MLDSnpGroupFirstReporter OBJECT-TYPE
			SYNTAX InetAddressIPv6
			MAX-ACCESS read-only
			STATUS current
			DESCRIPTION
				"Description."
			::= { sleV2MLDSnpGroupEntry 6 }

		
		sleV2MldSnoopingSource OBJECT IDENTIFIER ::= { sleV2MldSnooping 3 }

		
		sleV2MLDSnpSourceTable OBJECT-TYPE
			SYNTAX SEQUENCE OF SleV2MLDSnpSourceEntry
			MAX-ACCESS not-accessible
			STATUS current
			DESCRIPTION
				"Description."
			::= { sleV2MldSnoopingSource 1 }

		
		sleV2MLDSnpSourceEntry OBJECT-TYPE
			SYNTAX SleV2MLDSnpSourceEntry
			MAX-ACCESS not-accessible
			STATUS current
			DESCRIPTION
				"Description."
			INDEX { sleV2MLDSnpIfVid, sleV2MLDSnpGroupAddress, sleV2MLDSnpSourceAddress }
			::= { sleV2MLDSnpSourceTable 1 }

		
		SleV2MLDSnpSourceEntry ::=
			SEQUENCE { 
				sleV2MLDSnpSourceAddress
					InetAddressIPv6,
				sleV2MLDSnpSourceList
					INTEGER,
				sleV2MLDSnpSourceUptime
					TimeTicks,
				sleV2MLDSnpSourceExpire
					TimeTicks
			 }

		sleV2MLDSnpSourceAddress OBJECT-TYPE
			SYNTAX InetAddressIPv6
			MAX-ACCESS read-only
			STATUS current
			DESCRIPTION
				"Description."
			::= { sleV2MLDSnpSourceEntry 1 }

		
		sleV2MLDSnpSourceList OBJECT-TYPE
			SYNTAX INTEGER
				{
				allow(1),
				block(2)
				}
			MAX-ACCESS read-only
			STATUS current
			DESCRIPTION
				"Description."
			::= { sleV2MLDSnpSourceEntry 2 }

		
		sleV2MLDSnpSourceUptime OBJECT-TYPE
			SYNTAX TimeTicks
			MAX-ACCESS read-only
			STATUS current
			DESCRIPTION
				"Description."
			::= { sleV2MLDSnpSourceEntry 3 }

		
		sleV2MLDSnpSourceExpire OBJECT-TYPE
			SYNTAX TimeTicks
			MAX-ACCESS read-only
			STATUS current
			DESCRIPTION
				"Description."
			::= { sleV2MLDSnpSourceEntry 4 }

		
		sleV2MldProxy OBJECT IDENTIFIER ::= { sleV2Mld 4 }

		
		sleV2MldProxyInterface OBJECT IDENTIFIER ::= { sleV2MldProxy 1 }

		
		sleV2MLDPxyIfTable OBJECT-TYPE
			SYNTAX SEQUENCE OF SleV2MLDPxyIfEntry
			MAX-ACCESS not-accessible
			STATUS current
			DESCRIPTION
				"Description."
			::= { sleV2MldProxyInterface 1 }

		
		sleV2MLDPxyIfEntry OBJECT-TYPE
			SYNTAX SleV2MLDPxyIfEntry
			MAX-ACCESS not-accessible
			STATUS current
			DESCRIPTION
				"Description."
			INDEX { sleV2MLDPxyIfVid }
			::= { sleV2MLDPxyIfTable 1 }

		
		SleV2MLDPxyIfEntry ::=
			SEQUENCE { 
				sleV2MLDPxyIfVid
					INTEGER,
				sleV2MLDPxyIfService
					Boolean,
				sleV2MLDPxyIfServicePriority
					INTEGER,
				sleV2MLDPxyIfMroute
					OCTET STRING
			 }

		sleV2MLDPxyIfVid OBJECT-TYPE
			SYNTAX INTEGER (1..4094)
			MAX-ACCESS read-only
			STATUS current
			DESCRIPTION
				"Description."
			::= { sleV2MLDPxyIfEntry 1 }

		
		sleV2MLDPxyIfService OBJECT-TYPE
			SYNTAX Boolean
			MAX-ACCESS read-only
			STATUS current
			DESCRIPTION
				"Description."
			::= { sleV2MLDPxyIfEntry 2 }

		
		sleV2MLDPxyIfServicePriority OBJECT-TYPE
			SYNTAX INTEGER (0..255)
			MAX-ACCESS read-only
			STATUS current
			DESCRIPTION
				"Description."
			::= { sleV2MLDPxyIfEntry 3 }

		
		sleV2MLDPxyIfMroute OBJECT-TYPE
			SYNTAX OCTET STRING
			MAX-ACCESS read-only
			STATUS current
			DESCRIPTION
				"Description."
			::= { sleV2MLDPxyIfEntry 4 }

		
		sleV2MLDPxyIfControl OBJECT IDENTIFIER ::= { sleV2MldProxyInterface 2 }

		
		sleV2MLDPxyIfControlRequest OBJECT-TYPE
			SYNTAX INTEGER { setMLDPxyIfProfile(1) }
			MAX-ACCESS read-write
			STATUS current
			DESCRIPTION
				"Description."
			::= { sleV2MLDPxyIfControl 1 }

		
		sleV2MLDPxyIfControlStatus OBJECT-TYPE
			SYNTAX SleControlStatusType
			MAX-ACCESS read-write
			STATUS current
			DESCRIPTION
				"Description."
			::= { sleV2MLDPxyIfControl 2 }

		
		sleV2MLDPxyIfControlTimer OBJECT-TYPE
			SYNTAX Gauge32
			MAX-ACCESS read-write
			STATUS current
			DESCRIPTION
				"Description."
			::= { sleV2MLDPxyIfControl 3 }

		
		sleV2MLDPxyIfControlTimeStamp OBJECT-TYPE
			SYNTAX TimeTicks
			MAX-ACCESS read-write
			STATUS current
			DESCRIPTION
				"Description."
			::= { sleV2MLDPxyIfControl 4 }

		
		sleV2MLDPxyIfControlReqResult OBJECT-TYPE
			SYNTAX SleControlRequestResultType
			MAX-ACCESS read-write
			STATUS current
			DESCRIPTION
				"Description."
			::= { sleV2MLDPxyIfControl 5 }

		
		sleV2MLDPxyIfControlVid OBJECT-TYPE
			SYNTAX INTEGER (1..4094)
			MAX-ACCESS read-write
			STATUS current
			DESCRIPTION
				"Description."
			::= { sleV2MLDPxyIfControl 6 }

		
		sleV2MLDPxyIfControlService OBJECT-TYPE
			SYNTAX Boolean
			MAX-ACCESS read-write
			STATUS current
			DESCRIPTION
				"Description."
			::= { sleV2MLDPxyIfControl 7 }

		
		sleV2MLDPxyIfControlServicePriority OBJECT-TYPE
			SYNTAX INTEGER (-1 | 0..255)
			MAX-ACCESS read-write
			STATUS current
			DESCRIPTION
				"Description."
			::= { sleV2MLDPxyIfControl 8 }

		
		sleV2MLDPxyIfControlMroute OBJECT-TYPE
			SYNTAX OCTET STRING
			MAX-ACCESS read-write
			STATUS current
			DESCRIPTION
				"Description."
			::= { sleV2MLDPxyIfControl 9 }

		
		sleV2MLDPxyIfNotification OBJECT IDENTIFIER ::= { sleV2MldProxyInterface 3 }

		
		sleV2MLDPxyIfProfileChanged NOTIFICATION-TYPE
			OBJECTS { sleV2MLDPxyIfControlRequest, sleV2MLDPxyIfControlTimeStamp, sleV2MLDPxyIfControlReqResult, sleV2MLDPxyIfVid, sleV2MLDPxyIfService, 
				sleV2MLDPxyIfServicePriority, sleV2MLDPxyIfMroute }
			STATUS current
			DESCRIPTION 
				"Description."
			::= { sleV2MLDPxyIfNotification 1 }

		
		sleV2McastIPTvMgmt OBJECT IDENTIFIER ::= { sleV2Multicast 4 }

		
		sleV2McastIPTvBase OBJECT IDENTIFIER ::= { sleV2McastIPTvMgmt 1 }

		
		sleV2McastIPTvInfo OBJECT IDENTIFIER ::= { sleV2McastIPTvBase 1 }

		
		sleV2McastIPTvInfoCacState OBJECT-TYPE
			SYNTAX INTEGER
				{
				enable(1),
				disable(2)
				}
			MAX-ACCESS read-only
			STATUS current
			DESCRIPTION
				"The system-wide cac state. default: disable(2)"
			DEFVAL { 2 }
			::= { sleV2McastIPTvInfo 1 }

		
		sleV2McastIPTvInfoPackageLimit OBJECT-TYPE
			SYNTAX INTEGER (0..65535)
			MAX-ACCESS read-only
			STATUS current
			DESCRIPTION
				"The system-wide package limitation"
			::= { sleV2McastIPTvInfo 2 }

		
		sleV2McastIPTvInfoPreviewProfileLimit OBJECT-TYPE
			SYNTAX INTEGER (0..65535)
			MAX-ACCESS read-only
			STATUS current
			DESCRIPTION
				"The system-wide preview-profile limitation"
			::= { sleV2McastIPTvInfo 3 }

		
		sleV2McastIPTvInfoChannelLimit OBJECT-TYPE
			SYNTAX INTEGER (0..65535)
			MAX-ACCESS read-only
			STATUS current
			DESCRIPTION
				"The system-wide channel limitation"
			::= { sleV2McastIPTvInfo 4 }

		
		sleV2McastIPTvInfoCacProfileLimit OBJECT-TYPE
			SYNTAX INTEGER (0..65535)
			MAX-ACCESS read-only
			STATUS current
			DESCRIPTION
				"The system-wide cac-profile limitation"
			::= { sleV2McastIPTvInfo 5 }

		
		sleV2McastIPTvInfoSubscriberLimit OBJECT-TYPE
			SYNTAX INTEGER (0..65535)
			MAX-ACCESS read-only
			STATUS current
			DESCRIPTION
				"The system-wide subscribers limitation"
			::= { sleV2McastIPTvInfo 6 }

		
		sleV2McastIPTvInfoSubscriberHistoryLimit OBJECT-TYPE
			SYNTAX INTEGER (0..65535)
			MAX-ACCESS read-only
			STATUS current
			DESCRIPTION
				"The system-wide subscriber's history limitation"
			::= { sleV2McastIPTvInfo 7 }

		
		sleV2McastIPTvInfoFullviewRecogTime OBJECT-TYPE
			SYNTAX INTEGER (0..65535)
			MAX-ACCESS read-only
			STATUS current
			DESCRIPTION
				"The system-wide full-view recognition time"
			::= { sleV2McastIPTvInfo 8 }

		
		sleV2McastIPTvControlInfo OBJECT IDENTIFIER ::= { sleV2McastIPTvBase 2 }

		
		sleV2McastIPTvInfoControlRequest OBJECT-TYPE
			SYNTAX INTEGER
				{
				setIPTvCACState(1),
				setIPTvGlobalLimit(2),
				setIPTvFullviewRecognitionTime(3)
				}
			MAX-ACCESS read-write
			STATUS current
			DESCRIPTION
				"The request of a user command"
			::= { sleV2McastIPTvControlInfo 1 }

		
		sleV2McastIPTvInfoControlStatus OBJECT-TYPE
			SYNTAX SleControlStatusType
			MAX-ACCESS read-only
			STATUS current
			DESCRIPTION
				"The status of user command"
			::= { sleV2McastIPTvControlInfo 2 }

		
		sleV2McastIPTvInfoControlTimer OBJECT-TYPE
			SYNTAX Gauge32
			MAX-ACCESS read-write
			STATUS current
			DESCRIPTION
				"The maximum time for the manager for a long running user command"
			::= { sleV2McastIPTvControlInfo 3 }

		
		sleV2McastIPTvInfoControlTimeStamp OBJECT-TYPE
			SYNTAX TimeStamp
			MAX-ACCESS read-only
			STATUS current
			DESCRIPTION
				"The time stamp of the last command(end of command)"
			::= { sleV2McastIPTvControlInfo 4 }

		
		sleV2McastIPTvInfoControlReqResult OBJECT-TYPE
			SYNTAX SleControlRequestResultType
			MAX-ACCESS read-only
			STATUS current
			DESCRIPTION
				"The result of the last user command"
			::= { sleV2McastIPTvControlInfo 5 }

		
		sleV2McastIPTvInfoControlCacState OBJECT-TYPE
			SYNTAX INTEGER
				{
				enable(1),
				disable(2)
				}
			MAX-ACCESS read-write
			STATUS current
			DESCRIPTION
				"The system-wide cac state"
			::= { sleV2McastIPTvControlInfo 6 }

		
		sleV2McastIPTvInfoControlPackageLimit OBJECT-TYPE
			SYNTAX INTEGER (0..65535)
			MAX-ACCESS read-write
			STATUS current
			DESCRIPTION
				"The system-wide package limitation"
			::= { sleV2McastIPTvControlInfo 7 }

		
		sleV2McastIPTvInfoControlPreviewProfileLimit OBJECT-TYPE
			SYNTAX INTEGER (0..65535)
			MAX-ACCESS read-write
			STATUS current
			DESCRIPTION
				"The system-wide preview-profile limitation"
			::= { sleV2McastIPTvControlInfo 8 }

		
		sleV2McastIPTvInfoControlChannelLimit OBJECT-TYPE
			SYNTAX INTEGER (0..65535)
			MAX-ACCESS read-write
			STATUS current
			DESCRIPTION
				"The system-wide channel limitation"
			::= { sleV2McastIPTvControlInfo 9 }

		
		sleV2McastIPTvInfoControlCacProfileLimit OBJECT-TYPE
			SYNTAX INTEGER (0..65535)
			MAX-ACCESS read-write
			STATUS current
			DESCRIPTION
				"The system-wide cac-profile limitation"
			::= { sleV2McastIPTvControlInfo 10 }

		
		sleV2McastIPTvInfoControlSubscriberLimit OBJECT-TYPE
			SYNTAX INTEGER (0..65535)
			MAX-ACCESS read-write
			STATUS current
			DESCRIPTION
				"The system-wide subscribers limitation"
			::= { sleV2McastIPTvControlInfo 11 }

		
		sleV2McastIPTvInfoContorlSubscriberHistoryLimit OBJECT-TYPE
			SYNTAX INTEGER (0..65535)
			MAX-ACCESS read-write
			STATUS current
			DESCRIPTION
				"The system-wide subscriber's history limitation"
			::= { sleV2McastIPTvControlInfo 12 }

		
		sleV2McastIPTvInfoControlFullviewRecogTime OBJECT-TYPE
			SYNTAX INTEGER (0..65535)
			MAX-ACCESS read-write
			STATUS current
			DESCRIPTION
				"The system-wide full-view recognition time"
			::= { sleV2McastIPTvControlInfo 13 }

		
		sleV2McastIPTvInfoNotification OBJECT IDENTIFIER ::= { sleV2McastIPTvBase 3 }

		
		sleV2McastIPTvInfoCacStateChanged NOTIFICATION-TYPE
			OBJECTS { sleV2McastIPTvInfoControlRequest, sleV2McastIPTvInfoControlTimeStamp, sleV2McastIPTvInfoControlReqResult, sleV2McastIPTvInfoControlCacState }
			STATUS current
			DESCRIPTION 
				"Description."
			::= { sleV2McastIPTvInfoNotification 1 }

		
		sleV2McastIPTvInfoLimitChanged NOTIFICATION-TYPE
			OBJECTS { sleV2McastIPTvInfoControlRequest, sleV2McastIPTvInfoControlTimeStamp, sleV2McastIPTvInfoControlReqResult, sleV2McastIPTvInfoControlPackageLimit, sleV2McastIPTvInfoControlPreviewProfileLimit, 
				sleV2McastIPTvInfoControlChannelLimit, sleV2McastIPTvInfoControlCacProfileLimit, sleV2McastIPTvInfoControlSubscriberLimit, sleV2McastIPTvInfoContorlSubscriberHistoryLimit }
			STATUS current
			DESCRIPTION 
				"Description."
			::= { sleV2McastIPTvInfoNotification 2 }

		
		sleV2McastIPTvInfoFullviewRecogTimeChanged NOTIFICATION-TYPE
			OBJECTS { sleV2McastIPTvInfoControlRequest, sleV2McastIPTvInfoControlTimeStamp, sleV2McastIPTvInfoControlReqResult, sleV2McastIPTvInfoControlFullviewRecogTime }
			STATUS current
			DESCRIPTION 
				"Description."
			::= { sleV2McastIPTvInfoNotification 3 }

		
		sleV2McastIPTvPackage OBJECT IDENTIFIER ::= { sleV2McastIPTvMgmt 2 }

		
		sleV2McastPackageTable OBJECT-TYPE
			SYNTAX SEQUENCE OF SleV2McastPackageEntry
			MAX-ACCESS not-accessible
			STATUS current
			DESCRIPTION
				"multicast package table."
			::= { sleV2McastIPTvPackage 1 }

		
		sleV2McastPackageEntry OBJECT-TYPE
			SYNTAX SleV2McastPackageEntry
			MAX-ACCESS not-accessible
			STATUS current
			DESCRIPTION
				"key: sleV2McastIPTvPackageId"
			INDEX { sleV2McastIPTvPackageId }
			::= { sleV2McastPackageTable 1 }

		
		SleV2McastPackageEntry ::=
			SEQUENCE { 
				sleV2McastIPTvPackageId
					Integer32,
				sleV2McastIPTvPackageDescription
					OCTET STRING,
				sleV2McastIPTvPackagePreviewChannelCnt
					INTEGER,
				sleV2McastIPTvPackageFullviewChannelCnt
					INTEGER
			 }

		sleV2McastIPTvPackageId OBJECT-TYPE
			SYNTAX Integer32 (1..65535)
			MAX-ACCESS read-only
			STATUS current
			DESCRIPTION
				"Package id"
			::= { sleV2McastPackageEntry 1 }

		
		sleV2McastIPTvPackageDescription OBJECT-TYPE
			SYNTAX OCTET STRING
			MAX-ACCESS read-only
			STATUS current
			DESCRIPTION
				"Package description"
			::= { sleV2McastPackageEntry 2 }

		
		sleV2McastIPTvPackagePreviewChannelCnt OBJECT-TYPE
			SYNTAX INTEGER (0..65535)
			MAX-ACCESS read-only
			STATUS current
			DESCRIPTION
				"The number of preview channel list"
			::= { sleV2McastPackageEntry 3 }

		
		sleV2McastIPTvPackageFullviewChannelCnt OBJECT-TYPE
			SYNTAX INTEGER (0..65535)
			MAX-ACCESS read-only
			STATUS current
			DESCRIPTION
				"The number of fullview channel list"
			::= { sleV2McastPackageEntry 4 }

		
		sleV2McastIPTvPackageChannelTable OBJECT-TYPE
			SYNTAX SEQUENCE OF SleV2McastIPTvPackageChannelEntry
			MAX-ACCESS not-accessible
			STATUS current
			DESCRIPTION
				"multicast IPTV package channel table."
			::= { sleV2McastIPTvPackage 2 }

		
		sleV2McastIPTvPackageChannelEntry OBJECT-TYPE
			SYNTAX SleV2McastIPTvPackageChannelEntry
			MAX-ACCESS not-accessible
			STATUS current
			DESCRIPTION
				"key: sleV2McastIPTvPackageId, sleV2McastIPTvPackageChannelId"
			INDEX { sleV2McastIPTvPackageId, sleV2McastIPTvPackageChannelId }
			::= { sleV2McastIPTvPackageChannelTable 1 }

		
		SleV2McastIPTvPackageChannelEntry ::=
			SEQUENCE { 
				sleV2McastIPTvPackageChannelId
					Integer32,
				sleV2McastIPTvPackageChannelEntitlement
					INTEGER
			 }

		sleV2McastIPTvPackageChannelId OBJECT-TYPE
			SYNTAX Integer32 (1..65535)
			MAX-ACCESS read-only
			STATUS current
			DESCRIPTION
				"Channel id"
			::= { sleV2McastIPTvPackageChannelEntry 1 }

		
		sleV2McastIPTvPackageChannelEntitlement OBJECT-TYPE
			SYNTAX INTEGER
				{
				preview(1),
				fullview(2)
				}
			MAX-ACCESS read-only
			STATUS current
			DESCRIPTION
				"The Entitlement of channel view"
			::= { sleV2McastIPTvPackageChannelEntry 2 }

		
		sleV2McastIPTvPackageControl OBJECT IDENTIFIER ::= { sleV2McastIPTvPackage 3 }

		
		sleV2McastIPTvPackageControlRequest OBJECT-TYPE
			SYNTAX INTEGER
				{
				createPackage(1),
				updatePackage(2),
				deletePackage(3),
				addPackageChannel(4),
				removePackageChannel(5)
				}
			MAX-ACCESS read-write
			STATUS current
			DESCRIPTION
				"The request of a user command"
			::= { sleV2McastIPTvPackageControl 1 }

		
		sleV2McastIPTvPackageControlStatus OBJECT-TYPE
			SYNTAX SleControlStatusType
			MAX-ACCESS read-only
			STATUS current
			DESCRIPTION
				"The status of user command"
			::= { sleV2McastIPTvPackageControl 2 }

		
		sleV2McastIPTvPackageControlTimer OBJECT-TYPE
			SYNTAX Gauge32
			MAX-ACCESS read-write
			STATUS current
			DESCRIPTION
				"The maximum time for the manager for a long running user command"
			::= { sleV2McastIPTvPackageControl 3 }

		
		sleV2McastIPTvPackageControlTimeStamp OBJECT-TYPE
			SYNTAX TimeStamp
			MAX-ACCESS read-only
			STATUS current
			DESCRIPTION
				"The time stamp of the last command(end of command)"
			::= { sleV2McastIPTvPackageControl 4 }

		
		sleV2McastIPTvPackageControlReqResult OBJECT-TYPE
			SYNTAX SleControlRequestResultType
			MAX-ACCESS read-only
			STATUS current
			DESCRIPTION
				"The result of the last user command"
			::= { sleV2McastIPTvPackageControl 5 }

		
		sleV2McastIPTvPackageControlId OBJECT-TYPE
			SYNTAX INTEGER (0..65535)
			MAX-ACCESS read-write
			STATUS current
			DESCRIPTION
				"Package id"
			::= { sleV2McastIPTvPackageControl 6 }

		
		sleV2McastIPTvPackageControlDescription OBJECT-TYPE
			SYNTAX OCTET STRING
			MAX-ACCESS read-write
			STATUS current
			DESCRIPTION
				"Package description"
			::= { sleV2McastIPTvPackageControl 7 }

		
		sleV2McastIPTvPackageControlPreviewChannelCnt OBJECT-TYPE
			SYNTAX INTEGER (0..65535)
			MAX-ACCESS read-write
			STATUS current
			DESCRIPTION
				"The number of preview channel"
			::= { sleV2McastIPTvPackageControl 8 }

		
		sleV2McastIPTvPackageControlPreviewChannelList OBJECT-TYPE
			SYNTAX OCTET STRING
			MAX-ACCESS read-write
			STATUS current
			DESCRIPTION
				"Preview channel list (each value length 4byte)"
			::= { sleV2McastIPTvPackageControl 9 }

		
		sleV2McastIPTvPackageControlFullviewChannelCnt OBJECT-TYPE
			SYNTAX INTEGER (0..65535)
			MAX-ACCESS read-write
			STATUS current
			DESCRIPTION
				"The number of fullview channel"
			::= { sleV2McastIPTvPackageControl 10 }

		
		sleV2McastIPTvPackageControlFullviewChannelList OBJECT-TYPE
			SYNTAX OCTET STRING
			MAX-ACCESS read-write
			STATUS current
			DESCRIPTION
				"Fullview channel list (each value length 4byte)"
			::= { sleV2McastIPTvPackageControl 11 }

		
		sleV2McastIPTvPackageNotification OBJECT IDENTIFIER ::= { sleV2McastIPTvPackage 4 }

		
		sleV2McastIPTvPackageCreated NOTIFICATION-TYPE
			OBJECTS { sleV2McastIPTvPackageControlRequest, sleV2McastIPTvPackageControlTimeStamp, sleV2McastIPTvPackageControlReqResult, sleV2McastIPTvPackageControlId, sleV2McastIPTvPackageControlDescription
				 }
			STATUS current
			DESCRIPTION 
				"Description."
			::= { sleV2McastIPTvPackageNotification 1 }

		
		sleV2McastIPTvPackageChanged NOTIFICATION-TYPE
			OBJECTS { sleV2McastIPTvPackageControlRequest, sleV2McastIPTvPackageControlTimeStamp, sleV2McastIPTvPackageControlReqResult, sleV2McastIPTvPackageControlId, sleV2McastIPTvPackageControlDescription
				 }
			STATUS current
			DESCRIPTION 
				"Description."
			::= { sleV2McastIPTvPackageNotification 2 }

		
		sleV2McastIPTvPackageDeleted NOTIFICATION-TYPE
			OBJECTS { sleV2McastIPTvPackageControlRequest, sleV2McastIPTvPackageControlTimeStamp, sleV2McastIPTvPackageControlReqResult, sleV2McastIPTvPackageControlId }
			STATUS current
			DESCRIPTION 
				"Description."
			::= { sleV2McastIPTvPackageNotification 3 }

		
		sleV2McastIPTvPackageAddChannel NOTIFICATION-TYPE
			OBJECTS { sleV2McastIPTvPackageControlRequest, sleV2McastIPTvPackageControlTimeStamp, sleV2McastIPTvPackageControlReqResult, sleV2McastIPTvPackageControlId, sleV2McastIPTvPackageControlPreviewChannelCnt, 
				sleV2McastIPTvPackageControlFullviewChannelCnt }
			STATUS current
			DESCRIPTION 
				"Description."
			::= { sleV2McastIPTvPackageNotification 4 }

		
		sleV2McastIPTvPackageRemoveChannel NOTIFICATION-TYPE
			OBJECTS { sleV2McastIPTvPackageControlRequest, sleV2McastIPTvPackageControlTimeStamp, sleV2McastIPTvPackageControlReqResult, sleV2McastIPTvPackageControlPreviewChannelCnt, sleV2McastIPTvPackageControlFullviewChannelCnt
				 }
			STATUS current
			DESCRIPTION 
				"Description."
			::= { sleV2McastIPTvPackageNotification 5 }

		
		sleV2McastIPTvPreviewProfile OBJECT IDENTIFIER ::= { sleV2McastIPTvMgmt 3 }

		
		sleV2McastIPTvPreviewProfileTable OBJECT-TYPE
			SYNTAX SEQUENCE OF SleV2McastIPTvPreviewProfileEntry
			MAX-ACCESS not-accessible
			STATUS current
			DESCRIPTION
				"multicast IPTV preview profile table."
			::= { sleV2McastIPTvPreviewProfile 1 }

		
		sleV2McastIPTvPreviewProfileEntry OBJECT-TYPE
			SYNTAX SleV2McastIPTvPreviewProfileEntry
			MAX-ACCESS not-accessible
			STATUS current
			DESCRIPTION
				"Description."
			INDEX { sleV2McastIPTvPreviewProfileId }
			::= { sleV2McastIPTvPreviewProfileTable 1 }
-- key: sleV2McastIPTvPreviewProfileId
		
		SleV2McastIPTvPreviewProfileEntry ::=
			SEQUENCE { 
				sleV2McastIPTvPreviewProfileId
					Integer32,
				sleV2McastIPTvPreviewProfileMaxDuration
					INTEGER,
				sleV2McastIPTvPreviewProfileMaxPreviews
					INTEGER,
				sleV2McastIPTvPreviewProfileBlackoutDuration
					INTEGER,
				sleV2McastIPTvPreviewProfileRecognitionTime
					INTEGER
			 }

		sleV2McastIPTvPreviewProfileId OBJECT-TYPE
			SYNTAX Integer32 (1..65535)
			MAX-ACCESS read-only
			STATUS current
			DESCRIPTION
				"Preview profile id"
			::= { sleV2McastIPTvPreviewProfileEntry 1 }

		
		sleV2McastIPTvPreviewProfileMaxDuration OBJECT-TYPE
			SYNTAX INTEGER (0..65535)
			MAX-ACCESS read-only
			STATUS current
			DESCRIPTION
				"Restricted time duration for Preview Channel (sec)"
			::= { sleV2McastIPTvPreviewProfileEntry 2 }

		
		sleV2McastIPTvPreviewProfileMaxPreviews OBJECT-TYPE
			SYNTAX INTEGER (0..65535)
			MAX-ACCESS read-only
			STATUS current
			DESCRIPTION
				"Restricted number of times for Preview Channel"
			::= { sleV2McastIPTvPreviewProfileEntry 3 }

		
		sleV2McastIPTvPreviewProfileBlackoutDuration OBJECT-TYPE
			SYNTAX INTEGER (0..65535)
			MAX-ACCESS read-only
			STATUS current
			DESCRIPTION
				"Time duration for blackout after seeing Preview Channel (sec)"
			::= { sleV2McastIPTvPreviewProfileEntry 4 }

		
		sleV2McastIPTvPreviewProfileRecognitionTime OBJECT-TYPE
			SYNTAX INTEGER (0..65535)
			MAX-ACCESS read-only
			STATUS current
			DESCRIPTION
				"Time duration for Recognition (sec)"
			::= { sleV2McastIPTvPreviewProfileEntry 5 }

		
		sleV2McastIPTvPreviewProfileReset OBJECT IDENTIFIER ::= { sleV2McastIPTvPreviewProfile 2 }

		
		sleV2McastIPTvPreviewProfileResetTimePeriod OBJECT-TYPE
			SYNTAX INTEGER
				{
				everyday(0),
				date1(1),
				date2(2),
				date3(3),
				date4(4),
				date5(5),
				date6(6),
				date7(7),
				date8(8),
				date9(9),
				date10(10),
				date11(11),
				date12(12),
				date13(13),
				date14(14),
				date15(15),
				date16(16),
				date17(17),
				date18(18),
				date19(19),
				date20(20),
				date21(21),
				date22(22),
				date23(23),
				date24(24),
				date25(25),
				date26(26),
				date27(27),
				date28(28),
				date29(29),
				date30(30),
				date31(31),
				sunday(32),
				monday(33),
				tuesday(34),
				wednesday(35),
				thursday(36),
				friday(37),
				saturday(38),
				none(39)
				}
			MAX-ACCESS read-only
			STATUS current
			DESCRIPTION
				"The period when Preview counters are initialized for Subscriber."
			::= { sleV2McastIPTvPreviewProfileReset 1 }

		
		sleV2McastIPTvPreviewProfileResetTime OBJECT-TYPE
			SYNTAX OCTET STRING
			MAX-ACCESS read-only
			STATUS current
			DESCRIPTION
				"The time when Preview counters are initialized for Subscriber. 
				Reset time Format : hh:mm"
			::= { sleV2McastIPTvPreviewProfileReset 2 }

		
		sleV2McastIPTvPreviewProfileControl OBJECT IDENTIFIER ::= { sleV2McastIPTvPreviewProfile 3 }

		
		sleV2McastIPTvPreviewProfileControlRequest OBJECT-TYPE
			SYNTAX INTEGER
				{
				createPreviewProfile(1),
				updatePreviewProfile(2),
				deletePreviewProfile(3),
				setPreviewReset(4),
				setPreviewInstantReset(5)
				}
			MAX-ACCESS read-write
			STATUS current
			DESCRIPTION
				"The request of a user command"
			::= { sleV2McastIPTvPreviewProfileControl 1 }

		
		sleV2McastIPTvPreviewProfileControlStatus OBJECT-TYPE
			SYNTAX SleControlStatusType
			MAX-ACCESS read-only
			STATUS current
			DESCRIPTION
				"The status of user command"
			::= { sleV2McastIPTvPreviewProfileControl 2 }

		
		sleV2McastIPTvPreviewProfileControlTimer OBJECT-TYPE
			SYNTAX Gauge32
			MAX-ACCESS read-write
			STATUS current
			DESCRIPTION
				"The maximum time for the manager for a long running user command"
			::= { sleV2McastIPTvPreviewProfileControl 3 }

		
		sleV2McastIPTvPreviewProfileControlTimeStamp OBJECT-TYPE
			SYNTAX TimeStamp
			MAX-ACCESS read-only
			STATUS current
			DESCRIPTION
				"The time stamp of the last command(end of command)"
			::= { sleV2McastIPTvPreviewProfileControl 4 }

		
		sleV2McastIPTvPreviewProfileControlReqResult OBJECT-TYPE
			SYNTAX SleControlRequestResultType
			MAX-ACCESS read-only
			STATUS current
			DESCRIPTION
				"The result of the last user command"
			::= { sleV2McastIPTvPreviewProfileControl 5 }

		
		sleV2McastIPTvPreviewProfileControlId OBJECT-TYPE
			SYNTAX INTEGER (0..65535)
			MAX-ACCESS read-write
			STATUS current
			DESCRIPTION
				"Preview profile id"
			::= { sleV2McastIPTvPreviewProfileControl 6 }

		
		sleV2McastIPTvPreviewProfileControlMaxDuration OBJECT-TYPE
			SYNTAX INTEGER (0..65535)
			MAX-ACCESS read-write
			STATUS current
			DESCRIPTION
				"Restricted time duration for Preview Channel (sec)"
			::= { sleV2McastIPTvPreviewProfileControl 7 }

		
		sleV2McastIPTvPreviewProfileControlMaxPreviews OBJECT-TYPE
			SYNTAX INTEGER (0..65535)
			MAX-ACCESS read-write
			STATUS current
			DESCRIPTION
				"Restricted number of times for Preview Channel"
			::= { sleV2McastIPTvPreviewProfileControl 8 }

		
		sleV2McastIPTvPreviewProfileControlBlackoutDuration OBJECT-TYPE
			SYNTAX INTEGER (0..65535)
			MAX-ACCESS read-write
			STATUS current
			DESCRIPTION
				"Time duration for blackout after seeing Preview Channel(sec)"
			::= { sleV2McastIPTvPreviewProfileControl 9 }

		
		sleV2McastIPTvPreviewProfileControlRecognitionTime OBJECT-TYPE
			SYNTAX INTEGER (0..65535)
			MAX-ACCESS read-write
			STATUS current
			DESCRIPTION
				"Time duration for Recognition (sec)"
			::= { sleV2McastIPTvPreviewProfileControl 10 }

		
		sleV2McastIPTvPreviewProfileControlResetTimePeriod OBJECT-TYPE
			SYNTAX INTEGER
				{
				everyday(0),
				date1(1),
				date2(2),
				date3(3),
				date4(4),
				date5(5),
				date6(6),
				date7(7),
				date8(8),
				date9(9),
				date10(10),
				date11(11),
				date12(12),
				date13(13),
				date14(14),
				date15(15),
				date16(16),
				date17(17),
				date18(18),
				date19(19),
				date20(20),
				date21(21),
				date22(22),
				date23(23),
				date24(24),
				date25(25),
				date26(26),
				date27(27),
				date28(28),
				date29(29),
				date30(30),
				date31(31),
				sunday(32),
				monday(33),
				tuesday(34),
				wednesday(35),
				thursday(36),
				friday(37),
				saturday(38),
				none(39)
				}
			MAX-ACCESS read-write
			STATUS current
			DESCRIPTION
				"The period when Preview counters are initialized for Subscriber."
			::= { sleV2McastIPTvPreviewProfileControl 11 }

		
		sleV2McastIPTvPreviewProfileControlResetTime OBJECT-TYPE
			SYNTAX OCTET STRING
			MAX-ACCESS read-write
			STATUS current
			DESCRIPTION
				"The time when Preview counters are initialized for Subscriber. 
				Reset time Format : hh:mm"
			::= { sleV2McastIPTvPreviewProfileControl 12 }

		
		sleV2McastIPTvPreviewProfileNotification OBJECT IDENTIFIER ::= { sleV2McastIPTvPreviewProfile 4 }

		
		sleV2McastIPTvPreviewProfileCreated NOTIFICATION-TYPE
			OBJECTS { sleV2McastIPTvPreviewProfileControlRequest, sleV2McastIPTvPreviewProfileControlTimeStamp, sleV2McastIPTvPreviewProfileControlReqResult, sleV2McastIPTvPreviewProfileControlId, sleV2McastIPTvPreviewProfileControlMaxDuration, 
				sleV2McastIPTvPreviewProfileControlMaxPreviews, sleV2McastIPTvPreviewProfileControlBlackoutDuration, sleV2McastIPTvPreviewProfileControlRecognitionTime }
			STATUS current
			DESCRIPTION 
				"Description."
			::= { sleV2McastIPTvPreviewProfileNotification 1 }

		
		sleV2McastIPTvPreviewProfileChanged NOTIFICATION-TYPE
			OBJECTS { sleV2McastIPTvPreviewProfileControlRequest, sleV2McastIPTvPreviewProfileControlTimeStamp, sleV2McastIPTvPreviewProfileControlReqResult, sleV2McastIPTvPreviewProfileControlId, sleV2McastIPTvPreviewProfileControlMaxDuration, 
				sleV2McastIPTvPreviewProfileControlMaxPreviews, sleV2McastIPTvPreviewProfileControlBlackoutDuration, sleV2McastIPTvPreviewProfileControlRecognitionTime }
			STATUS current
			DESCRIPTION 
				"Description."
			::= { sleV2McastIPTvPreviewProfileNotification 2 }

		
		sleV2McastIPTvPreviewProfileDeleted NOTIFICATION-TYPE
			OBJECTS { sleV2McastIPTvPreviewProfileControlRequest, sleV2McastIPTvPreviewProfileControlTimeStamp, sleV2McastIPTvPreviewProfileControlReqResult, sleV2McastIPTvPreviewProfileControlId }
			STATUS current
			DESCRIPTION 
				"Description."
			::= { sleV2McastIPTvPreviewProfileNotification 3 }

		
		sleV2McastIPTvPreviewProfileResetChanged NOTIFICATION-TYPE
			OBJECTS { sleV2McastIPTvPreviewProfileControlRequest, sleV2McastIPTvPreviewProfileControlTimeStamp, sleV2McastIPTvPreviewProfileControlReqResult, sleV2McastIPTvPreviewProfileControlResetTimePeriod, sleV2McastIPTvPreviewProfileControlResetTime
				 }
			STATUS current
			DESCRIPTION 
				"Description."
			::= { sleV2McastIPTvPreviewProfileNotification 4 }

		
		sleV2McastIPTvPreviewInstantReset NOTIFICATION-TYPE
			OBJECTS { sleV2McastIPTvPreviewProfileControlRequest, sleV2McastIPTvPreviewProfileControlTimeStamp, sleV2McastIPTvPreviewProfileControlReqResult }
			STATUS current
			DESCRIPTION 
				"Description."
			::= { sleV2McastIPTvPreviewProfileNotification 5 }

		
		sleV2McastIPTvChannel OBJECT IDENTIFIER ::= { sleV2McastIPTvMgmt 4 }

		
		sleV2McastIPTvChannelTable OBJECT-TYPE
			SYNTAX SEQUENCE OF SleV2McastIPTvChannelEntry
			MAX-ACCESS not-accessible
			STATUS current
			DESCRIPTION
				"multicast IPTV channel table."
			::= { sleV2McastIPTvChannel 1 }

		
		sleV2McastIPTvChannelEntry OBJECT-TYPE
			SYNTAX SleV2McastIPTvChannelEntry
			MAX-ACCESS not-accessible
			STATUS current
			DESCRIPTION
				"key: sleV2McastIPTvChannelId"
			INDEX { sleV2McastIPTvChannelId }
			::= { sleV2McastIPTvChannelTable 1 }

		
		SleV2McastIPTvChannelEntry ::=
			SEQUENCE { 
				sleV2McastIPTvChannelId
					Integer32,
				sleV2McastIPTvChannelSourceAddress
					IpAddress,
				sleV2McastIPTvChannelGroupAddress
					IpAddress,
				sleV2McastIPTvChannelBandwidth
					INTEGER,
				sleV2McastIPTvChannelPreviewProfileId
					INTEGER,
				sleV2McastIPTvChannelCacGroupId
					INTEGER,
				sleV2McastIPTvChannelDescription
					OCTET STRING
			 }

		sleV2McastIPTvChannelId OBJECT-TYPE
			SYNTAX Integer32 (1..65535)
			MAX-ACCESS read-only
			STATUS current
			DESCRIPTION
				"Channel id"
			::= { sleV2McastIPTvChannelEntry 1 }

		
		sleV2McastIPTvChannelSourceAddress OBJECT-TYPE
			SYNTAX IpAddress
			MAX-ACCESS read-only
			STATUS current
			DESCRIPTION
				"Multicast server address"
			::= { sleV2McastIPTvChannelEntry 2 }

		
		sleV2McastIPTvChannelGroupAddress OBJECT-TYPE
			SYNTAX IpAddress
			MAX-ACCESS read-only
			STATUS current
			DESCRIPTION
				"Multicast address (IP address of IGMP group)"
			::= { sleV2McastIPTvChannelEntry 3 }

		
		sleV2McastIPTvChannelBandwidth OBJECT-TYPE
			SYNTAX INTEGER (0..65535)
			MAX-ACCESS read-only
			STATUS current
			DESCRIPTION
				"Bandwidth of Channel (KB)"
			::= { sleV2McastIPTvChannelEntry 4 }

		
		sleV2McastIPTvChannelPreviewProfileId OBJECT-TYPE
			SYNTAX INTEGER (0..65535)
			MAX-ACCESS read-only
			STATUS current
			DESCRIPTION
				"Preview profile id"
			::= { sleV2McastIPTvChannelEntry 5 }

		
		sleV2McastIPTvChannelCacGroupId OBJECT-TYPE
			SYNTAX INTEGER (0..65535)
			MAX-ACCESS read-only
			STATUS current
			DESCRIPTION
				"The ID of CAC group"
			::= { sleV2McastIPTvChannelEntry 6 }

		
		sleV2McastIPTvChannelDescription OBJECT-TYPE
			SYNTAX OCTET STRING
			MAX-ACCESS read-only
			STATUS current
			DESCRIPTION
				"The description of Channel"
			::= { sleV2McastIPTvChannelEntry 7 }

		
		sleV2McastIPTvChannelPackageTable OBJECT-TYPE
			SYNTAX SEQUENCE OF SleV2McastIPTvChannelPackageEntry
			MAX-ACCESS not-accessible
			STATUS current
			DESCRIPTION
				"multicast IPTV channel package table."
			::= { sleV2McastIPTvChannel 2 }

		
		sleV2McastIPTvChannelPackageEntry OBJECT-TYPE
			SYNTAX SleV2McastIPTvChannelPackageEntry
			MAX-ACCESS not-accessible
			STATUS current
			DESCRIPTION
				"key: sleV2McastIPTvChannelId, sleV2McastIPTvPackageId"
			INDEX { sleV2McastIPTvChannelId, sleV2McastIPTvPackageId }
			::= { sleV2McastIPTvChannelPackageTable 1 }

		
		SleV2McastIPTvChannelPackageEntry ::=
			SEQUENCE { 
				sleV2McastIPTvChannelPackageDescription
					OCTET STRING
			 }

		sleV2McastIPTvChannelPackageDescription OBJECT-TYPE
			SYNTAX OCTET STRING
			MAX-ACCESS read-only
			STATUS current
			DESCRIPTION
				"The  description of package include this channel.
				packageId_user-description,  ex)  '1_Disney-channel'"
			::= { sleV2McastIPTvChannelPackageEntry 1 }

		
		sleV2McastIPTvChannelControl OBJECT IDENTIFIER ::= { sleV2McastIPTvChannel 3 }

		
		sleV2McastIPTvChannelControlRequest OBJECT-TYPE
			SYNTAX INTEGER
				{
				createChannel(1),
				updateChannel(2),
				deleteChannel(3)
				}
			MAX-ACCESS read-write
			STATUS current
			DESCRIPTION
				"The request of a user command"
			::= { sleV2McastIPTvChannelControl 1 }

		
		sleV2McastIPTvChannelControlStatus OBJECT-TYPE
			SYNTAX SleControlStatusType
			MAX-ACCESS read-only
			STATUS current
			DESCRIPTION
				"The status of user command"
			::= { sleV2McastIPTvChannelControl 2 }

		
		sleV2McastIPTvChannelControlTimer OBJECT-TYPE
			SYNTAX Gauge32
			MAX-ACCESS read-write
			STATUS current
			DESCRIPTION
				"The maximum time for the manager for a long running user command"
			::= { sleV2McastIPTvChannelControl 3 }

		
		sleV2McastIPTvChannelControlTimeStamp OBJECT-TYPE
			SYNTAX TimeStamp
			MAX-ACCESS read-only
			STATUS current
			DESCRIPTION
				"The time stamp of the last command(end of command)"
			::= { sleV2McastIPTvChannelControl 4 }

		
		sleV2McastIPTvChannelControlReqResult OBJECT-TYPE
			SYNTAX SleControlRequestResultType
			MAX-ACCESS read-only
			STATUS current
			DESCRIPTION
				"The result of the last user command"
			::= { sleV2McastIPTvChannelControl 5 }

		
		sleV2McastIPTvChannelControlId OBJECT-TYPE
			SYNTAX INTEGER (0..65535)
			MAX-ACCESS read-write
			STATUS current
			DESCRIPTION
				"Channel id"
			::= { sleV2McastIPTvChannelControl 6 }

		
		sleV2McastIPTvChannelControlSourceAddress OBJECT-TYPE
			SYNTAX IpAddress
			MAX-ACCESS read-write
			STATUS current
			DESCRIPTION
				"Multicast server address"
			::= { sleV2McastIPTvChannelControl 7 }

		
		sleV2McastIPTvChannelControlGroupAddress OBJECT-TYPE
			SYNTAX IpAddress
			MAX-ACCESS read-write
			STATUS current
			DESCRIPTION
				"Multicast address (IP address of IGMP group)"
			::= { sleV2McastIPTvChannelControl 8 }

		
		sleV2McastIPTvChannelControlBandwidth OBJECT-TYPE
			SYNTAX INTEGER (0..65535)
			MAX-ACCESS read-write
			STATUS current
			DESCRIPTION
				"Bandwidth of Channel"
			::= { sleV2McastIPTvChannelControl 9 }

		
		sleV2McastIPTvChannelControlPreviewProfileId OBJECT-TYPE
			SYNTAX INTEGER (0..65535)
			MAX-ACCESS read-write
			STATUS current
			DESCRIPTION
				"Preview profile id"
			::= { sleV2McastIPTvChannelControl 10 }

		
		sleV2McastIPTvChannelControlCacGroupId OBJECT-TYPE
			SYNTAX INTEGER (0..65535)
			MAX-ACCESS read-write
			STATUS current
			DESCRIPTION
				"The ID of CAC group"
			::= { sleV2McastIPTvChannelControl 11 }

		
		sleV2McastIPTvChannelControlDescription OBJECT-TYPE
			SYNTAX OCTET STRING
			MAX-ACCESS read-write
			STATUS current
			DESCRIPTION
				"The description of Channel."
			::= { sleV2McastIPTvChannelControl 12 }

		
		sleV2McastIPTvChannelNotification OBJECT IDENTIFIER ::= { sleV2McastIPTvChannel 4 }

		
		sleV2McastIPTvChannelCreated NOTIFICATION-TYPE
			OBJECTS { sleV2McastIPTvChannelControlRequest, sleV2McastIPTvChannelControlTimeStamp, sleV2McastIPTvChannelControlReqResult, sleV2McastIPTvChannelControlId, sleV2McastIPTvChannelControlSourceAddress, 
				sleV2McastIPTvChannelControlGroupAddress, sleV2McastIPTvChannelControlBandwidth, sleV2McastIPTvChannelControlPreviewProfileId, sleV2McastIPTvChannelControlCacGroupId, sleV2McastIPTvChannelControlDescription
				 }
			STATUS current
			DESCRIPTION 
				"Description."
			::= { sleV2McastIPTvChannelNotification 1 }

		
		sleV2McastIPTvChannelChanged NOTIFICATION-TYPE
			OBJECTS { sleV2McastIPTvChannelControlRequest, sleV2McastIPTvChannelControlTimeStamp, sleV2McastIPTvChannelControlReqResult, sleV2McastIPTvChannelControlId, sleV2McastIPTvChannelControlSourceAddress, 
				sleV2McastIPTvChannelControlGroupAddress, sleV2McastIPTvChannelControlBandwidth, sleV2McastIPTvChannelControlPreviewProfileId, sleV2McastIPTvChannelControlCacGroupId, sleV2McastIPTvChannelControlDescription
				 }
			STATUS current
			DESCRIPTION 
				"Description."
			::= { sleV2McastIPTvChannelNotification 2 }

		
		sleV2McastIPTvChannelDeleted NOTIFICATION-TYPE
			OBJECTS { sleV2McastIPTvChannelControlRequest, sleV2McastIPTvChannelControlTimeStamp, sleV2McastIPTvChannelControlReqResult, sleV2McastIPTvChannelControlId }
			STATUS current
			DESCRIPTION 
				"Description."
			::= { sleV2McastIPTvChannelNotification 3 }

		
		sleV2McastIPTvChannelCurrentJoined OBJECT IDENTIFIER ::= { sleV2McastIPTvChannel 5 }

		
		sleV2McastIPTvChannelCurrentVlanPortTable OBJECT-TYPE
			SYNTAX SEQUENCE OF SleV2McastIPTvChannelCurrentVlanPortEntry
			MAX-ACCESS not-accessible
			STATUS current
			DESCRIPTION
				"multicast IPTV channel current vlan port table."
			::= { sleV2McastIPTvChannelCurrentJoined 1 }

		
		sleV2McastIPTvChannelCurrentVlanPortEntry OBJECT-TYPE
			SYNTAX SleV2McastIPTvChannelCurrentVlanPortEntry
			MAX-ACCESS not-accessible
			STATUS current
			DESCRIPTION
				"key: sleV2McastIPTvChannelCurrentVlanId, sleV2McastIPTvChannelCurrentPortId, sleV2McastIPTvChannelCurrentVlanPortChannelId"
			INDEX { sleV2McastIPTvChannelCurrentVlanId, sleV2McastIPTvChannelCurrentPortId, sleV2McastIPTvChannelCurrentVlanPortChannelId }
			::= { sleV2McastIPTvChannelCurrentVlanPortTable 1 }

		
		SleV2McastIPTvChannelCurrentVlanPortEntry ::=
			SEQUENCE { 
				sleV2McastIPTvChannelCurrentVlanId
					Integer32,
				sleV2McastIPTvChannelCurrentPortId
					Integer32,
				sleV2McastIPTvChannelCurrentVlanPortChannelId
					Integer32,
				sleV2McastIPTvChannelCurrentVlanPortJoinedTime
					OCTET STRING
			 }

		sleV2McastIPTvChannelCurrentVlanId OBJECT-TYPE
			SYNTAX Integer32 (1..65535)
			MAX-ACCESS read-only
			STATUS current
			DESCRIPTION
				"The Vlan Id"
			::= { sleV2McastIPTvChannelCurrentVlanPortEntry 1 }

		
		sleV2McastIPTvChannelCurrentPortId OBJECT-TYPE
			SYNTAX Integer32 (1..65535)
			MAX-ACCESS read-only
			STATUS current
			DESCRIPTION
				"The port Id"
			::= { sleV2McastIPTvChannelCurrentVlanPortEntry 2 }

		
		sleV2McastIPTvChannelCurrentVlanPortChannelId OBJECT-TYPE
			SYNTAX Integer32 (1..65535)
			MAX-ACCESS read-only
			STATUS current
			DESCRIPTION
				"same as  sleV2McastIPTvChannelId"
			::= { sleV2McastIPTvChannelCurrentVlanPortEntry 3 }

		
		sleV2McastIPTvChannelCurrentVlanPortJoinedTime OBJECT-TYPE
			SYNTAX OCTET STRING
			MAX-ACCESS read-only
			STATUS current
			DESCRIPTION
				"The joined time of channel"
			::= { sleV2McastIPTvChannelCurrentVlanPortEntry 4 }

		
		sleV2McastIPTvChannelCurrentSubscriberTable OBJECT-TYPE
			SYNTAX SEQUENCE OF SleV2McastIPTvChannelCurrentSubscriberEntry
			MAX-ACCESS not-accessible
			STATUS current
			DESCRIPTION
				"multicast IPTV channel current subscriber table."
			::= { sleV2McastIPTvChannelCurrentJoined 2 }

		
		sleV2McastIPTvChannelCurrentSubscriberEntry OBJECT-TYPE
			SYNTAX SleV2McastIPTvChannelCurrentSubscriberEntry
			MAX-ACCESS not-accessible
			STATUS current
			DESCRIPTION
				"key: sleV2McastIPTvSubscriberId, sleV2McastIPTvChannelCurrentSubscriberChannelId"
			INDEX { sleV2McastIPTvSubscriberId, sleV2McastIPTvChannelCurrentSubscriberChannelId }
			::= { sleV2McastIPTvChannelCurrentSubscriberTable 1 }

		
		SleV2McastIPTvChannelCurrentSubscriberEntry ::=
			SEQUENCE { 
				sleV2McastIPTvChannelCurrentSubscriberChannelId
					Integer32,
				sleV2McastIPTvChannelCurrentSubscriberJoinedTime
					OCTET STRING,
				sleV2McastIPTvChannelCurrentSubscriberJoinDurationTime
					INTEGER
			 }

		sleV2McastIPTvChannelCurrentSubscriberChannelId OBJECT-TYPE
			SYNTAX Integer32 (1..65535)
			MAX-ACCESS read-only
			STATUS current
			DESCRIPTION
				"same as  sleV2McastIPTvChannelId"
			::= { sleV2McastIPTvChannelCurrentSubscriberEntry 1 }

		
		sleV2McastIPTvChannelCurrentSubscriberJoinedTime OBJECT-TYPE
			SYNTAX OCTET STRING
			MAX-ACCESS read-only
			STATUS current
			DESCRIPTION
				"indicate when subscriber joined the channel"
			::= { sleV2McastIPTvChannelCurrentSubscriberEntry 2 }

		
		sleV2McastIPTvChannelCurrentSubscriberJoinDurationTime OBJECT-TYPE
			SYNTAX INTEGER (0..65535)
			MAX-ACCESS read-only
			STATUS current
			DESCRIPTION
				"indicate how long have subscriber joined the channel"
			::= { sleV2McastIPTvChannelCurrentSubscriberEntry 3 }

		
		sleV2McastIPTvCacProfile OBJECT IDENTIFIER ::= { sleV2McastIPTvMgmt 5 }

		
		sleV2McastIPTvCacProfileTable OBJECT-TYPE
			SYNTAX SEQUENCE OF SleV2McastIPTvCacProfileEntry
			MAX-ACCESS not-accessible
			STATUS current
			DESCRIPTION
				"multicast IPTV Cac profile table."
			::= { sleV2McastIPTvCacProfile 1 }

		
		sleV2McastIPTvCacProfileEntry OBJECT-TYPE
			SYNTAX SleV2McastIPTvCacProfileEntry
			MAX-ACCESS not-accessible
			STATUS current
			DESCRIPTION
				"key: sleV2McastIPTvCacProfileId"
			INDEX { sleV2McastIPTvCacProfileId }
			::= { sleV2McastIPTvCacProfileTable 1 }

		
		SleV2McastIPTvCacProfileEntry ::=
			SEQUENCE { 
				sleV2McastIPTvCacProfileId
					Integer32,
				sleV2McastIPTvCacProfileMaxChannel
					INTEGER,
				sleV2McastIPTvCacProfileMaxBandwidth
					INTEGER,
				sleV2McastIPTvCacProfileCacGroupCnt
					INTEGER,
				sleV2McastIPTvCacProfileDescription
					OCTET STRING
			 }

		sleV2McastIPTvCacProfileId OBJECT-TYPE
			SYNTAX Integer32 (1..65535)
			MAX-ACCESS read-only
			STATUS current
			DESCRIPTION
				"CAC profile id"
			::= { sleV2McastIPTvCacProfileEntry 1 }

		
		sleV2McastIPTvCacProfileMaxChannel OBJECT-TYPE
			SYNTAX INTEGER (0..65535)
			MAX-ACCESS read-only
			STATUS current
			DESCRIPTION
				"The maximum number of channel which can be seen simultaneously"
			::= { sleV2McastIPTvCacProfileEntry 2 }

		
		sleV2McastIPTvCacProfileMaxBandwidth OBJECT-TYPE
			SYNTAX INTEGER (0..65535)
			MAX-ACCESS read-only
			STATUS current
			DESCRIPTION
				"The maximum bandwidth which CAC Profile can use"
			::= { sleV2McastIPTvCacProfileEntry 3 }

		
		sleV2McastIPTvCacProfileCacGroupCnt OBJECT-TYPE
			SYNTAX INTEGER (0..65535)
			MAX-ACCESS read-only
			STATUS current
			DESCRIPTION
				"The number of CAC group"
			::= { sleV2McastIPTvCacProfileEntry 4 }

		
		sleV2McastIPTvCacProfileDescription OBJECT-TYPE
			SYNTAX OCTET STRING
			MAX-ACCESS read-only
			STATUS current
			DESCRIPTION
				"The description of CAC profile"
			::= { sleV2McastIPTvCacProfileEntry 5 }

		
		sleV2McastIPTvCacProfileGroupTable OBJECT-TYPE
			SYNTAX SEQUENCE OF SleV2McastIPTvCacProfileGroupEntry
			MAX-ACCESS not-accessible
			STATUS current
			DESCRIPTION
				"multicast IPTV Cac profile group table."
			::= { sleV2McastIPTvCacProfile 2 }

		
		sleV2McastIPTvCacProfileGroupEntry OBJECT-TYPE
			SYNTAX SleV2McastIPTvCacProfileGroupEntry
			MAX-ACCESS not-accessible
			STATUS current
			DESCRIPTION
				"key: sleV2McastIPTvCacProfileId, sleV2McastIPTvCacProfileGroupId"
			INDEX { sleV2McastIPTvCacProfileId, sleV2McastIPTvCacProfileGroupId }
			::= { sleV2McastIPTvCacProfileGroupTable 1 }

		
		SleV2McastIPTvCacProfileGroupEntry ::=
			SEQUENCE { 
				sleV2McastIPTvCacProfileGroupId
					Integer32,
				sleV2McastIPTvCacProfileGroupMaxChanNum
					INTEGER
			 }

		sleV2McastIPTvCacProfileGroupId OBJECT-TYPE
			SYNTAX Integer32 (1..65535)
			MAX-ACCESS read-only
			STATUS current
			DESCRIPTION
				"CAC profile Group id"
			::= { sleV2McastIPTvCacProfileGroupEntry 1 }

		
		sleV2McastIPTvCacProfileGroupMaxChanNum OBJECT-TYPE
			SYNTAX INTEGER (0..65535)
			MAX-ACCESS read-only
			STATUS current
			DESCRIPTION
				"The number of channel which can be seen in CAC Group simultaneously"
			::= { sleV2McastIPTvCacProfileGroupEntry 2 }

		
		sleV2McastIPTvCacProfileControl OBJECT IDENTIFIER ::= { sleV2McastIPTvCacProfile 3 }

		
		sleV2McastIPTvCacProfileControlRequest OBJECT-TYPE
			SYNTAX INTEGER
				{
				createCACProfile(1),
				updateCACProfile(2),
				deleteCACProfile(3),
				addCACProfileGroup(4),
				removeCACProfileGroup(5)
				}
			MAX-ACCESS read-write
			STATUS current
			DESCRIPTION
				"The request of a user command"
			::= { sleV2McastIPTvCacProfileControl 1 }

		
		sleV2McastIPTvCacProfileControlStatus OBJECT-TYPE
			SYNTAX SleControlStatusType
			MAX-ACCESS read-only
			STATUS current
			DESCRIPTION
				"The status of user command"
			::= { sleV2McastIPTvCacProfileControl 2 }

		
		sleV2McastIPTvCacProfileControlTimer OBJECT-TYPE
			SYNTAX Gauge32
			MAX-ACCESS read-write
			STATUS current
			DESCRIPTION
				"The maximum time for the manager for a long running user command"
			::= { sleV2McastIPTvCacProfileControl 3 }

		
		sleV2McastIPTvCacProfileControlTimeStamp OBJECT-TYPE
			SYNTAX TimeStamp
			MAX-ACCESS read-only
			STATUS current
			DESCRIPTION
				"The time stamp of the last command(end of command)"
			::= { sleV2McastIPTvCacProfileControl 4 }

		
		sleV2McastIPTvCacProfileControlReqResult OBJECT-TYPE
			SYNTAX SleControlRequestResultType
			MAX-ACCESS read-only
			STATUS current
			DESCRIPTION
				"The result of the last user command"
			::= { sleV2McastIPTvCacProfileControl 5 }

		
		sleV2McastIPTvCacProfileControlId OBJECT-TYPE
			SYNTAX INTEGER (0..65535)
			MAX-ACCESS read-write
			STATUS current
			DESCRIPTION
				"CAC profile id"
			::= { sleV2McastIPTvCacProfileControl 6 }

		
		sleV2McastIPTvCacProfileControlMaxStream OBJECT-TYPE
			SYNTAX INTEGER (0..65535)
			MAX-ACCESS read-write
			STATUS current
			DESCRIPTION
				"The maximum number of channel which can be seen simultaneously"
			::= { sleV2McastIPTvCacProfileControl 7 }

		
		sleV2McastIPTvCacProfileControlMaxBandwidth OBJECT-TYPE
			SYNTAX INTEGER (0..65535)
			MAX-ACCESS read-write
			STATUS current
			DESCRIPTION
				"The maximum bandwidth which CAC Profile can use"
			::= { sleV2McastIPTvCacProfileControl 8 }

		
		sleV2McastIPTvCacProfileControlCacGroupCnt OBJECT-TYPE
			SYNTAX INTEGER (0..65535)
			MAX-ACCESS read-write
			STATUS current
			DESCRIPTION
				"The number of CAC group"
			::= { sleV2McastIPTvCacProfileControl 9 }

		
		sleV2McastIPTvCacProfileControlCacGroupList OBJECT-TYPE
			SYNTAX OCTET STRING
			MAX-ACCESS read-write
			STATUS current
			DESCRIPTION
				"CAC group list (each value length 4byte)"
			::= { sleV2McastIPTvCacProfileControl 10 }

		
		sleV2McastIPTvCacProfileControlCacGroupMaxChanNumList OBJECT-TYPE
			SYNTAX OCTET STRING
			MAX-ACCESS read-write
			STATUS current
			DESCRIPTION
				"The number of channel which can be seen in CAC Group simultaneously
				*The number of CAC group has to correspond with Group Max Channel
				(each value length 4byte)"
			::= { sleV2McastIPTvCacProfileControl 11 }

		
		sleV2McastIPTvCacProfileControlDescription OBJECT-TYPE
			SYNTAX OCTET STRING
			MAX-ACCESS read-write
			STATUS current
			DESCRIPTION
				"Description."
			::= { sleV2McastIPTvCacProfileControl 12 }

		
		sleV2McastIPTvCacProfileNotification OBJECT IDENTIFIER ::= { sleV2McastIPTvCacProfile 4 }

		
		sleV2McastIPTvCacProfileCreated NOTIFICATION-TYPE
			OBJECTS { sleV2McastIPTvCacProfileControlRequest, sleV2McastIPTvCacProfileControlTimeStamp, sleV2McastIPTvCacProfileControlReqResult, sleV2McastIPTvCacProfileControlId, sleV2McastIPTvCacProfileControlMaxStream, 
				sleV2McastIPTvCacProfileControlMaxBandwidth, sleV2McastIPTvCacProfileControlCacGroupCnt }
			STATUS current
			DESCRIPTION 
				"Description."
			::= { sleV2McastIPTvCacProfileNotification 1 }

		
		sleV2McastIPTvCacProfileChanged NOTIFICATION-TYPE
			OBJECTS { sleV2McastIPTvCacProfileControlRequest, sleV2McastIPTvCacProfileControlTimeStamp, sleV2McastIPTvCacProfileControlReqResult, sleV2McastIPTvCacProfileControlId, sleV2McastIPTvCacProfileControlMaxStream, 
				sleV2McastIPTvCacProfileControlMaxBandwidth }
			STATUS current
			DESCRIPTION 
				"Description."
			::= { sleV2McastIPTvCacProfileNotification 2 }

		
		sleV2McastIPTvCacProfileDeleted NOTIFICATION-TYPE
			OBJECTS { sleV2McastIPTvCacProfileControlRequest, sleV2McastIPTvCacProfileControlTimeStamp, sleV2McastIPTvCacProfileControlReqResult, sleV2McastIPTvCacProfileControlId }
			STATUS current
			DESCRIPTION 
				"Description."
			::= { sleV2McastIPTvCacProfileNotification 3 }

		
		sleV2McastIPTvCacProfileAddGroup NOTIFICATION-TYPE
			OBJECTS { sleV2McastIPTvCacProfileControlRequest, sleV2McastIPTvCacProfileControlTimeStamp, sleV2McastIPTvCacProfileControlReqResult, sleV2McastIPTvCacProfileControlId, sleV2McastIPTvCacProfileControlCacGroupCnt
				 }
			STATUS current
			DESCRIPTION 
				"Description."
			::= { sleV2McastIPTvCacProfileNotification 4 }

		
		sleV2McastIPTvCacProfileDelGroup NOTIFICATION-TYPE
			OBJECTS { sleV2McastIPTvCacProfileControlRequest, sleV2McastIPTvCacProfileControlTimeStamp, sleV2McastIPTvCacProfileControlReqResult, sleV2McastIPTvCacProfileControlId, sleV2McastIPTvCacProfileControlCacGroupCnt
				 }
			STATUS current
			DESCRIPTION 
				"Description."
			::= { sleV2McastIPTvCacProfileNotification 5 }

		
		sleV2McastIPTvSubscriber OBJECT IDENTIFIER ::= { sleV2McastIPTvMgmt 6 }

		
		sleV2McastIPTvSubscriberBase OBJECT IDENTIFIER ::= { sleV2McastIPTvSubscriber 1 }

		
		sleV2McastIPTvSubscriberMgmt OBJECT IDENTIFIER ::= { sleV2McastIPTvSubscriber 2 }

		
		sleV2McastIPTvSubscriberTable OBJECT-TYPE
			SYNTAX SEQUENCE OF SleV2McastIPTvSubscriberEntry
			MAX-ACCESS not-accessible
			STATUS current
			DESCRIPTION
				"multicast IPTV subscriber table."
			::= { sleV2McastIPTvSubscriberMgmt 1 }

		
		sleV2McastIPTvSubscriberEntry OBJECT-TYPE
			SYNTAX SleV2McastIPTvSubscriberEntry
			MAX-ACCESS not-accessible
			STATUS current
			DESCRIPTION
				"key: sleV2McastIPTvSubscriberId"
			INDEX { sleV2McastIPTvSubscriberId }
			::= { sleV2McastIPTvSubscriberTable 1 }

		
		SleV2McastIPTvSubscriberEntry ::=
			SEQUENCE { 
				sleV2McastIPTvSubscriberId
					Integer32,
				sleV2McastIPTvSubscriberPortType
					INTEGER,
				sleV2McastIPTvSubscriberSlotId
					INTEGER,
				sleV2McastIPTvSubscriberPortId
					INTEGER,
				sleV2McastIPTvSubscriberCTag
					INTEGER,
				sleV2McastIPTvSubscriberIpAddr
					IpAddress,
				sleV2McastIPTvSubscriberStatus
					INTEGER,
				sleV2McastIPTvSubscriberCacProfileId
					INTEGER,
				sleV2McastIPTvSubscriberPackageCnt
					INTEGER,
				sleV2McastIPTvSubscriberDescription
					OCTET STRING
			 }

		sleV2McastIPTvSubscriberId OBJECT-TYPE
			SYNTAX Integer32 (1..65535)
			MAX-ACCESS read-only
			STATUS current
			DESCRIPTION
				"The subscriber's ID"
			::= { sleV2McastIPTvSubscriberEntry 1 }

		
		sleV2McastIPTvSubscriberPortType OBJECT-TYPE
			SYNTAX INTEGER
				{
				physical(1),
				logical(2)
				}
			MAX-ACCESS read-only
			STATUS current
			DESCRIPTION
				"The port type. Logical(2) means trunk."
			::= { sleV2McastIPTvSubscriberEntry 2 }

		
		sleV2McastIPTvSubscriberSlotId OBJECT-TYPE
			SYNTAX INTEGER (0..65535)
			MAX-ACCESS read-only
			STATUS current
			DESCRIPTION
				"The slot number"
			::= { sleV2McastIPTvSubscriberEntry 3 }

		
		sleV2McastIPTvSubscriberPortId OBJECT-TYPE
			SYNTAX INTEGER (0..65535)
			MAX-ACCESS read-only
			STATUS current
			DESCRIPTION
				"The port number of slot (1 ~ 65535)"
			::= { sleV2McastIPTvSubscriberEntry 4 }

		
		sleV2McastIPTvSubscriberCTag OBJECT-TYPE
			SYNTAX INTEGER (0..65535)
			MAX-ACCESS read-only
			STATUS current
			DESCRIPTION
				"C-VLAN number"
			::= { sleV2McastIPTvSubscriberEntry 5 }

		
		sleV2McastIPTvSubscriberIpAddr OBJECT-TYPE
			SYNTAX IpAddress
			MAX-ACCESS read-only
			STATUS current
			DESCRIPTION
				"Subscriber IP address"
			::= { sleV2McastIPTvSubscriberEntry 6 }

		
		sleV2McastIPTvSubscriberStatus OBJECT-TYPE
			SYNTAX INTEGER
				{
				active(1),
				inactive(2)
				}
			MAX-ACCESS read-only
			STATUS current
			DESCRIPTION
				"The status of subscriber"
			::= { sleV2McastIPTvSubscriberEntry 7 }

		
		sleV2McastIPTvSubscriberCacProfileId OBJECT-TYPE
			SYNTAX INTEGER (0..65535)
			MAX-ACCESS read-only
			STATUS current
			DESCRIPTION
				"CAC profile id"
			::= { sleV2McastIPTvSubscriberEntry 8 }

		
		sleV2McastIPTvSubscriberPackageCnt OBJECT-TYPE
			SYNTAX INTEGER (0..65535)
			MAX-ACCESS read-only
			STATUS current
			DESCRIPTION
				"The number of subscriber package"
			::= { sleV2McastIPTvSubscriberEntry 9 }

		
		sleV2McastIPTvSubscriberDescription OBJECT-TYPE
			SYNTAX OCTET STRING
			MAX-ACCESS read-write
			STATUS current
			DESCRIPTION
				"The description about subscriber."
			::= { sleV2McastIPTvSubscriberEntry 10 }

		
		sleV2McastIPTvSubscriberPackageTable OBJECT-TYPE
			SYNTAX SEQUENCE OF SleV2McastIPTvSubscriberPackageEntry
			MAX-ACCESS not-accessible
			STATUS current
			DESCRIPTION
				"multicast IPTv subscriber package table."
			::= { sleV2McastIPTvSubscriberMgmt 2 }

		
		sleV2McastIPTvSubscriberPackageEntry OBJECT-TYPE
			SYNTAX SleV2McastIPTvSubscriberPackageEntry
			MAX-ACCESS not-accessible
			STATUS current
			DESCRIPTION
				"key: sleV2McastIPTvSubscriberId, sleV2McastIPTvSubscriberPackageId"
			INDEX { sleV2McastIPTvSubscriberId, sleV2McastIPTvSubscriberPackageId }
			::= { sleV2McastIPTvSubscriberPackageTable 1 }

		
		SleV2McastIPTvSubscriberPackageEntry ::=
			SEQUENCE { 
				sleV2McastIPTvSubscriberPackageId
					Integer32,
				sleV2McastIPTvSubscriberPackageStart
					OCTET STRING,
				sleV2McastIPTvSubscriberPackageEnd
					OCTET STRING
			 }

		sleV2McastIPTvSubscriberPackageId OBJECT-TYPE
			SYNTAX Integer32 (1..65535)
			MAX-ACCESS read-only
			STATUS current
			DESCRIPTION
				"The packageId of a certain subscriber"
			::= { sleV2McastIPTvSubscriberPackageEntry 1 }

		
		sleV2McastIPTvSubscriberPackageStart OBJECT-TYPE
			SYNTAX OCTET STRING
			MAX-ACCESS read-only
			STATUS current
			DESCRIPTION
				"Start time when package list becomes effective to  subscriber
				Format : hh:mm"
			::= { sleV2McastIPTvSubscriberPackageEntry 2 }

		
		sleV2McastIPTvSubscriberPackageEnd OBJECT-TYPE
			SYNTAX OCTET STRING
			MAX-ACCESS read-only
			STATUS current
			DESCRIPTION
				"End time when package list becomes invalid to subscriber
				Format : hh:mm"
			::= { sleV2McastIPTvSubscriberPackageEntry 3 }

		
		sleV2McastIPTvSubscriberControl OBJECT IDENTIFIER ::= { sleV2McastIPTvSubscriberMgmt 3 }

		
		sleV2McastIPTvSubscriberControlRequest OBJECT-TYPE
			SYNTAX INTEGER
				{
				createSubscriber(1),
				updateSubscriber(2),
				deleteSubscriber(3),
				addSubscriberPackage(4),
				removeSubscriberPackage(5),
				suspendSubscriber(6),
				resumeSubscriber(7),
				setSubscriberDescription(8)
				}
			MAX-ACCESS read-write
			STATUS current
			DESCRIPTION
				"The request of a user command"
			::= { sleV2McastIPTvSubscriberControl 1 }

		
		sleV2McastIPTvSubscriberControlStatus OBJECT-TYPE
			SYNTAX SleControlStatusType
			MAX-ACCESS read-only
			STATUS current
			DESCRIPTION
				"The status of user command"
			::= { sleV2McastIPTvSubscriberControl 2 }

		
		sleV2McastIPTvSubscriberControlTimer OBJECT-TYPE
			SYNTAX Gauge32
			MAX-ACCESS read-write
			STATUS current
			DESCRIPTION
				"The maximum time for the manager for a long running user command"
			::= { sleV2McastIPTvSubscriberControl 3 }

		
		sleV2McastIPTvSubscriberControlTimeStamp OBJECT-TYPE
			SYNTAX TimeStamp
			MAX-ACCESS read-only
			STATUS current
			DESCRIPTION
				"The time stamp of the last command(end of command)"
			::= { sleV2McastIPTvSubscriberControl 4 }

		
		sleV2McastIPTvSubscriberControlReqResult OBJECT-TYPE
			SYNTAX SleControlRequestResultType
			MAX-ACCESS read-only
			STATUS current
			DESCRIPTION
				"The result of the last user command"
			::= { sleV2McastIPTvSubscriberControl 5 }

		
		sleV2McastIPTvSubscriberControlId OBJECT-TYPE
			SYNTAX INTEGER (0..65535)
			MAX-ACCESS read-write
			STATUS current
			DESCRIPTION
				"The subscriber's ID"
			::= { sleV2McastIPTvSubscriberControl 6 }

		
		sleV2McastIPTvSubscriberControlPortType OBJECT-TYPE
			SYNTAX INTEGER
				{
				physical(1),
				logical(2)
				}
			MAX-ACCESS read-write
			STATUS current
			DESCRIPTION
				"The port type. Logical(2) means trunk."
			::= { sleV2McastIPTvSubscriberControl 7 }

		
		sleV2McastIPTvSubscriberControlSlotId OBJECT-TYPE
			SYNTAX INTEGER (0..65535)
			MAX-ACCESS read-write
			STATUS current
			DESCRIPTION
				"The slot number"
			::= { sleV2McastIPTvSubscriberControl 8 }

		
		sleV2McastIPTvSubscriberControlPortId OBJECT-TYPE
			SYNTAX INTEGER (0..65535)
			MAX-ACCESS read-write
			STATUS current
			DESCRIPTION
				"The port number of slot (1 ~ 65535)"
			::= { sleV2McastIPTvSubscriberControl 9 }

		
		sleV2McastIPTvSubscriberControlCTag OBJECT-TYPE
			SYNTAX INTEGER (0..65535)
			MAX-ACCESS read-write
			STATUS current
			DESCRIPTION
				"C-VLAN number"
			::= { sleV2McastIPTvSubscriberControl 10 }

		
		sleV2McastIPTvSubscriberControlIpAddr OBJECT-TYPE
			SYNTAX IpAddress
			MAX-ACCESS read-write
			STATUS current
			DESCRIPTION
				"Subscriber IP address"
			::= { sleV2McastIPTvSubscriberControl 11 }

		
		sleV2McastIPTvSubscriberControlCacProfileId OBJECT-TYPE
			SYNTAX INTEGER (0..65535)
			MAX-ACCESS read-write
			STATUS current
			DESCRIPTION
				"CAC profile id"
			::= { sleV2McastIPTvSubscriberControl 12 }

		
		sleV2McastIPTvSubscriberControlPackageCnt OBJECT-TYPE
			SYNTAX INTEGER (0..65535)
			MAX-ACCESS read-write
			STATUS current
			DESCRIPTION
				"The number of subscriber package"
			::= { sleV2McastIPTvSubscriberControl 13 }

		
		sleV2McastIPTvSubscriberControlPackageList OBJECT-TYPE
			SYNTAX OCTET STRING
			MAX-ACCESS read-write
			STATUS current
			DESCRIPTION
				"Package list (each value length 4byte)"
			::= { sleV2McastIPTvSubscriberControl 14 }

		
		sleV2McastIPTvSubscriberControlPackageTimeList OBJECT-TYPE
			SYNTAX OCTET STRING
			MAX-ACCESS read-write
			STATUS current
			DESCRIPTION
				"Start time when package list becomes effective to  subscriber (4byte)
				End time when package list becomes invalid to subscriber (4byte)
				(each value length 8byte)"
			::= { sleV2McastIPTvSubscriberControl 15 }

		
		sleV2McastIPTvSubscriberControlDescription OBJECT-TYPE
			SYNTAX OCTET STRING
			MAX-ACCESS read-write
			STATUS current
			DESCRIPTION
				"The description about subscriber."
			::= { sleV2McastIPTvSubscriberControl 16 }

		
		sleV2McastIPTvSubscriberNotification OBJECT IDENTIFIER ::= { sleV2McastIPTvSubscriberMgmt 4 }

		
		sleV2McastIPTvSubscriberCreated NOTIFICATION-TYPE
			OBJECTS { sleV2McastIPTvSubscriberControlRequest, sleV2McastIPTvSubscriberControlTimeStamp, sleV2McastIPTvSubscriberControlReqResult, sleV2McastIPTvSubscriberControlId, sleV2McastIPTvSubscriberControlPortType, 
				sleV2McastIPTvSubscriberControlSlotId, sleV2McastIPTvSubscriberControlPortId, sleV2McastIPTvSubscriberControlCTag, sleV2McastIPTvSubscriberControlIpAddr, sleV2McastIPTvSubscriberControlCacProfileId, 
				sleV2McastIPTvSubscriberControlDescription }
			STATUS current
			DESCRIPTION 
				"Description."
			::= { sleV2McastIPTvSubscriberNotification 1 }

		
		sleV2McastIPTvSubscriberChanged NOTIFICATION-TYPE
			OBJECTS { sleV2McastIPTvSubscriberControlRequest, sleV2McastIPTvSubscriberControlTimeStamp, sleV2McastIPTvSubscriberControlReqResult, sleV2McastIPTvSubscriberControlId, sleV2McastIPTvSubscriberControlPortType, 
				sleV2McastIPTvSubscriberControlSlotId, sleV2McastIPTvSubscriberControlPortId, sleV2McastIPTvSubscriberControlCTag, sleV2McastIPTvSubscriberControlIpAddr, sleV2McastIPTvSubscriberControlCacProfileId
				 }
			STATUS current
			DESCRIPTION 
				"Description."
			::= { sleV2McastIPTvSubscriberNotification 2 }

		
		sleV2McastIPTvSubscriberDeleted NOTIFICATION-TYPE
			OBJECTS { sleV2McastIPTvSubscriberControlRequest, sleV2McastIPTvSubscriberControlTimeStamp, sleV2McastIPTvSubscriberControlReqResult, sleV2McastIPTvSubscriberControlId }
			STATUS current
			DESCRIPTION 
				"Description."
			::= { sleV2McastIPTvSubscriberNotification 3 }

		
		sleV2McastIPTvSubscriberAddPackage NOTIFICATION-TYPE
			OBJECTS { sleV2McastIPTvSubscriberControlRequest, sleV2McastIPTvSubscriberControlTimeStamp, sleV2McastIPTvSubscriberControlPackageCnt, sleV2McastIPTvSubscriberControlReqResult, sleV2McastIPTvChannelControlId
				 }
			STATUS current
			DESCRIPTION 
				"Description."
			::= { sleV2McastIPTvSubscriberNotification 4 }

		
		sleV2McastIPTvSubscriberRemovePackage NOTIFICATION-TYPE
			OBJECTS { sleV2McastIPTvSubscriberControlRequest, sleV2McastIPTvSubscriberControlTimeStamp, sleV2McastIPTvSubscriberControlReqResult, sleV2McastIPTvSubscriberControlId, sleV2McastIPTvSubscriberControlPackageCnt
				 }
			STATUS current
			DESCRIPTION 
				"Description."
			::= { sleV2McastIPTvSubscriberNotification 5 }

		
		sleV2McastIPTvSubscriberSuspend NOTIFICATION-TYPE
			OBJECTS { sleV2McastIPTvSubscriberControlRequest, sleV2McastIPTvSubscriberControlTimeStamp, sleV2McastIPTvSubscriberControlReqResult, sleV2McastIPTvSubscriberControlId }
			STATUS current
			DESCRIPTION 
				"Description."
			::= { sleV2McastIPTvSubscriberNotification 6 }

		
		sleV2McastIPTvSubscriberResume NOTIFICATION-TYPE
			OBJECTS { sleV2McastIPTvSubscriberControlRequest, sleV2McastIPTvSubscriberControlTimeStamp, sleV2McastIPTvSubscriberControlReqResult, sleV2McastIPTvSubscriberControlId }
			STATUS current
			DESCRIPTION 
				"Description."
			::= { sleV2McastIPTvSubscriberNotification 7 }

		
		sleV2McastIPTvSubscriberDescChanged NOTIFICATION-TYPE
			OBJECTS { sleV2McastIPTvSubscriberControlRequest, sleV2McastIPTvSubscriberControlTimeStamp, sleV2McastIPTvSubscriberControlReqResult, sleV2McastIPTvSubscriberControlId, sleV2McastIPTvSubscriberControlDescription
				 }
			STATUS current
			DESCRIPTION 
				"Description."
			::= { sleV2McastIPTvSubscriberNotification 8 }

		
		sleV2McastIPTvSubscriberHistory OBJECT IDENTIFIER ::= { sleV2McastIPTvSubscriber 3 }

		
		sleV2McastIPTvSubscriberHistoryTable OBJECT-TYPE
			SYNTAX SEQUENCE OF SleV2McastIPTvSubscriberHistoryEntry
			MAX-ACCESS not-accessible
			STATUS current
			DESCRIPTION
				"multicast IPTV subscriber history table."
			::= { sleV2McastIPTvSubscriberHistory 1 }

		
		sleV2McastIPTvSubscriberHistoryEntry OBJECT-TYPE
			SYNTAX SleV2McastIPTvSubscriberHistoryEntry
			MAX-ACCESS not-accessible
			STATUS current
			DESCRIPTION
				"key: sleV2McastIPTvSubscriberId, sleV2McastIPTvSubscriberHistoryIndex"
			INDEX { sleV2McastIPTvSubscriberId, sleV2McastIPTvSubscriberHistoryIndex }
			::= { sleV2McastIPTvSubscriberHistoryTable 1 }

		
		SleV2McastIPTvSubscriberHistoryEntry ::=
			SEQUENCE { 
				sleV2McastIPTvSubscriberHistoryIndex
					Integer32,
				sleV2McastIPTvSubscriberHistoryJoinedChannelId
					INTEGER,
				sleV2McastIPTvSubscriberHistoryJoinedTime
					OCTET STRING
			 }

		sleV2McastIPTvSubscriberHistoryIndex OBJECT-TYPE
			SYNTAX Integer32 (1..65535)
			MAX-ACCESS read-only
			STATUS current
			DESCRIPTION
				"The index of subscriber's history.A25"
			::= { sleV2McastIPTvSubscriberHistoryEntry 1 }

		
		sleV2McastIPTvSubscriberHistoryJoinedChannelId OBJECT-TYPE
			SYNTAX INTEGER (0..65535)
			MAX-ACCESS read-only
			STATUS current
			DESCRIPTION
				"same as sleV2McastIPTvChannelId"
			::= { sleV2McastIPTvSubscriberHistoryEntry 2 }

		
		sleV2McastIPTvSubscriberHistoryJoinedTime OBJECT-TYPE
			SYNTAX OCTET STRING
			MAX-ACCESS read-only
			STATUS current
			DESCRIPTION
				"The Joined Time of channel."
			::= { sleV2McastIPTvSubscriberHistoryEntry 3 }

		
		sleV2McastIPTvSubscriberHistoryControl OBJECT IDENTIFIER ::= { sleV2McastIPTvSubscriberHistory 2 }

		
		sleV2McastIPTvSubscriberHistoryControlRequest OBJECT-TYPE
			SYNTAX INTEGER { clearSubscriberHistory(1) }
			MAX-ACCESS read-write
			STATUS current
			DESCRIPTION
				"The request of a user command"
			::= { sleV2McastIPTvSubscriberHistoryControl 1 }

		
		sleV2McastIPTvSubscriberHistoryControlStatus OBJECT-TYPE
			SYNTAX SleControlStatusType
			MAX-ACCESS read-only
			STATUS current
			DESCRIPTION
				"The status of user command"
			::= { sleV2McastIPTvSubscriberHistoryControl 2 }

		
		sleV2McastIPTvSubscriberHistoryControlTimer OBJECT-TYPE
			SYNTAX Gauge32
			MAX-ACCESS read-write
			STATUS current
			DESCRIPTION
				"The maximum time for the manager for a long running user command"
			::= { sleV2McastIPTvSubscriberHistoryControl 3 }

		
		sleV2McastIPTvSubscriberHistoryControlTimeStamp OBJECT-TYPE
			SYNTAX TimeStamp
			MAX-ACCESS read-only
			STATUS current
			DESCRIPTION
				"The time stamp of the last command(end of command)"
			::= { sleV2McastIPTvSubscriberHistoryControl 4 }

		
		sleV2McastIPTvSubscriberHistoryControlReqResult OBJECT-TYPE
			SYNTAX SleControlRequestResultType
			MAX-ACCESS read-only
			STATUS current
			DESCRIPTION
				"The result of the last user command"
			::= { sleV2McastIPTvSubscriberHistoryControl 5 }

		
		sleV2McastIPTvSubscriberHistoryControlId OBJECT-TYPE
			SYNTAX INTEGER (0..65535)
			MAX-ACCESS read-write
			STATUS current
			DESCRIPTION
				"The index of subscriber's history.A25"
			::= { sleV2McastIPTvSubscriberHistoryControl 6 }

		
		sleV2McastIPTvSubscriberHistoryNotification OBJECT IDENTIFIER ::= { sleV2McastIPTvSubscriberHistory 4 }

		
		sleV2McastIPTvSubscriberHistoryCleared NOTIFICATION-TYPE
			OBJECTS { sleV2McastIPTvSubscriberHistoryControlRequest, sleV2McastIPTvSubscriberHistoryControlTimeStamp, sleV2McastIPTvSubscriberHistoryControlReqResult, sleV2McastIPTvSubscriberControlId }
			STATUS current
			DESCRIPTION 
				"Description."
			::= { sleV2McastIPTvSubscriberHistoryNotification 1 }

		
		sleV2McastIPTvCDR OBJECT IDENTIFIER ::= { sleV2McastIPTvMgmt 7 }

		
		sleV2McastIPTvCDRBase OBJECT IDENTIFIER ::= { sleV2McastIPTvCDR 1 }

		
		sleV2McastIPTvCDRInfo OBJECT IDENTIFIER ::= { sleV2McastIPTvCDRBase 1 }

		
		sleV2McastIPTvCDRInfoStatus OBJECT-TYPE
			SYNTAX INTEGER
				{
				enable(1),
				disable(2)
				}
			MAX-ACCESS read-only
			STATUS current
			DESCRIPTION
				"indicate if the CDR logging is enabled or not"
			::= { sleV2McastIPTvCDRInfo 1 }

		
		sleV2McastIPTvCDRInfoKeepJoinInterval OBJECT-TYPE
			SYNTAX INTEGER (1..1440)
			UNITS "1 minute"
			MAX-ACCESS read-only
			STATUS current
			DESCRIPTION
				"keeped-join interval  <1-1440>"
			::= { sleV2McastIPTvCDRInfo 2 }

		
		sleV2McastIPTvCDRInfoLogFileName OBJECT-TYPE
			SYNTAX OCTET STRING
			MAX-ACCESS read-only
			STATUS current
			DESCRIPTION
				"CDR DB file name."
			::= { sleV2McastIPTvCDRInfo 3 }

		
		sleV2McastIPTvCDRInfoLogSize OBJECT-TYPE
			SYNTAX INTEGER (1..1000)
			UNITS "1 KB"
			MAX-ACCESS read-only
			STATUS current
			DESCRIPTION
				"CDR DB Log size <1-1000>"
			::= { sleV2McastIPTvCDRInfo 4 }

		
		sleV2McastIPTvCDRInfoExportTimeThreshold OBJECT-TYPE
			SYNTAX OCTET STRING
			MAX-ACCESS read-only
			STATUS current
			DESCRIPTION
				"The time threshold of CDR export. Format: [0-52]w[0-6]d[0-23]h"
			::= { sleV2McastIPTvCDRInfo 5 }

		
		sleV2McastIPTvCDRInfoExportTimeBegin OBJECT-TYPE
			SYNTAX OCTET STRING
			MAX-ACCESS read-only
			STATUS current
			DESCRIPTION
				"The begin time of CDR export.  Format : hh:mm"
			::= { sleV2McastIPTvCDRInfo 6 }

		
		sleV2McastIPTvCDRInfoExportAmountThreshold OBJECT-TYPE
			SYNTAX INTEGER (1..100)
			UNITS "1 %"
			MAX-ACCESS read-only
			STATUS current
			DESCRIPTION
				"The amount threshold of CDR export. <1-100>  unit : 1 %"
			::= { sleV2McastIPTvCDRInfo 7 }

		
		sleV2McastIPTvCDRInfoSyslogPriority OBJECT-TYPE
			SYNTAX INTEGER
				{
				none(0),
				emerg(1),
				alert(2),
				crit(3),
				err(4),
				warning(5),
				notice(6),
				info(7),
				debug(8)
				}
			MAX-ACCESS read-only
			STATUS current
			DESCRIPTION
				"The priority of CDR syslog.
				0 means syslog-disabled."
			::= { sleV2McastIPTvCDRInfo 8 }

		
		sleV2McastIPTvCDRInfoANInfo OBJECT-TYPE
			SYNTAX OCTET STRING
			MAX-ACCESS read-only
			STATUS current
			DESCRIPTION
				"The interface that include AN(Exporter) IP address.  Always use a primary IP address.
				It can be IP address of exporter"
			::= { sleV2McastIPTvCDRInfo 9 }

		
		sleV2McastIPTvCDRInfoControl OBJECT IDENTIFIER ::= { sleV2McastIPTvCDRBase 2 }

		
		sleV2McastIPTvCDRInfoControlRequest OBJECT-TYPE
			SYNTAX INTEGER
				{
				setCDRStatus(1),
				setCDREventProfile(2),
				setCDRLogFileProfile(3),
				setCDRExportProfile(4),
				setCDRSyslogPriority(5)
				}
			MAX-ACCESS read-write
			STATUS current
			DESCRIPTION
				"The request of a user command"
			::= { sleV2McastIPTvCDRInfoControl 1 }

		
		sleV2McastIPTvCDRInfoControlStatus OBJECT-TYPE
			SYNTAX SleControlStatusType
			MAX-ACCESS read-only
			STATUS current
			DESCRIPTION
				"The status of user command"
			::= { sleV2McastIPTvCDRInfoControl 2 }

		
		sleV2McastIPTvCDRInfoControlTimer OBJECT-TYPE
			SYNTAX Gauge32
			MAX-ACCESS read-write
			STATUS current
			DESCRIPTION
				"The maximum time for the manager for a long running user command"
			::= { sleV2McastIPTvCDRInfoControl 3 }

		
		sleV2McastIPTvCDRInfoControlTimeStamp OBJECT-TYPE
			SYNTAX TimeStamp
			MAX-ACCESS read-only
			STATUS current
			DESCRIPTION
				"The time stamp of the last command(end of command)"
			::= { sleV2McastIPTvCDRInfoControl 4 }

		
		sleV2McastIPTvCDRInfoControlReqResult OBJECT-TYPE
			SYNTAX SleControlRequestResultType
			MAX-ACCESS read-only
			STATUS current
			DESCRIPTION
				"The result of the last user command"
			::= { sleV2McastIPTvCDRInfoControl 5 }

		
		sleV2McastIPTvCDRInfoContorlStatus OBJECT-TYPE
			SYNTAX INTEGER
				{
				enable(1),
				disable(2)
				}
			MAX-ACCESS read-write
			STATUS current
			DESCRIPTION
				"indicate if the CDR logging is enabled or not"
			::= { sleV2McastIPTvCDRInfoControl 6 }

		
		sleV2McastIPTvCDRInfoContorlKeepJoinInterval OBJECT-TYPE
			SYNTAX INTEGER (1..1440)
			UNITS "1 minute"
			MAX-ACCESS read-write
			STATUS current
			DESCRIPTION
				"keeped-join interval  <1-1440>"
			::= { sleV2McastIPTvCDRInfoControl 7 }

		
		sleV2McastIPTvCDRInfoContorlLogFileName OBJECT-TYPE
			SYNTAX OCTET STRING
			MAX-ACCESS read-write
			STATUS current
			DESCRIPTION
				"CDR DB file name."
			::= { sleV2McastIPTvCDRInfoControl 8 }

		
		sleV2McastIPTvCDRInfoControlLogSize OBJECT-TYPE
			SYNTAX INTEGER (1..1000)
			UNITS "1 KB"
			MAX-ACCESS read-write
			STATUS current
			DESCRIPTION
				"CDR DB Log size <1-1000>"
			::= { sleV2McastIPTvCDRInfoControl 9 }

		
		sleV2McastIPTvCDRInfoControlExportTimeThreshold OBJECT-TYPE
			SYNTAX OCTET STRING
			MAX-ACCESS read-write
			STATUS current
			DESCRIPTION
				"The time threshold of CDR export. Format: [0-52]w[0-6]d[0-23]h"
			::= { sleV2McastIPTvCDRInfoControl 10 }

		
		sleV2McastIPTvCDRInfoControlExportTimeBegin OBJECT-TYPE
			SYNTAX OCTET STRING
			MAX-ACCESS read-write
			STATUS current
			DESCRIPTION
				"The begin time of CDR export. Format : hh:mm"
			::= { sleV2McastIPTvCDRInfoControl 11 }

		
		sleV2McastIPTvCDRInfoControlExportAmountThreshold OBJECT-TYPE
			SYNTAX INTEGER (1..100)
			UNITS "1 %"
			MAX-ACCESS read-write
			STATUS current
			DESCRIPTION
				"The amount threshold of CDR export. <1-100>  unit : 1 %"
			::= { sleV2McastIPTvCDRInfoControl 12 }

		
		sleV2McastIPTvCDRInfoControlSyslogPriority OBJECT-TYPE
			SYNTAX INTEGER
				{
				none(0),
				emerg(1),
				alert(2),
				crit(3),
				err(4),
				warning(5),
				notice(6),
				info(7),
				debug(8)
				}
			MAX-ACCESS read-write
			STATUS current
			DESCRIPTION
				"The priority of CDR syslog.
				0 means syslog-disabled."
			::= { sleV2McastIPTvCDRInfoControl 13 }

		
		sleV2McastIPTvCDRInfoControlANInfo OBJECT-TYPE
			SYNTAX OCTET STRING
			MAX-ACCESS read-write
			STATUS current
			DESCRIPTION
				"The interface that include AN(Exporter) IP address.  Always use a primary IP address.
				It can be IP address of exporter"
			::= { sleV2McastIPTvCDRInfoControl 14 }
-- The interface that include AN(Exporter) IP address. Always use a primary IP address.
-- It can be IP address of exporter
		
		sleV2McastIPTvCDRInfoNotification OBJECT IDENTIFIER ::= { sleV2McastIPTvCDRBase 3 }

		
		sleV2McastIPTvCDRInfoStatusChanged NOTIFICATION-TYPE
			OBJECTS { sleV2McastIPTvCDRInfoControlRequest, sleV2McastIPTvCDRInfoControlTimeStamp, sleV2McastIPTvCDRInfoControlReqResult, sleV2McastIPTvCDRInfoControlStatus }
			STATUS current
			DESCRIPTION 
				"Description."
			::= { sleV2McastIPTvCDRInfoNotification 1 }

		
		sleV2McastIPTvCDRInfoEventProfileChanged NOTIFICATION-TYPE
			OBJECTS { sleV2McastIPTvCDRInfoControlRequest, sleV2McastIPTvCDRInfoControlTimeStamp, sleV2McastIPTvCDRInfoControlReqResult, sleV2McastIPTvCDRInfoContorlKeepJoinInterval }
			STATUS current
			DESCRIPTION 
				"Description."
			::= { sleV2McastIPTvCDRInfoNotification 2 }

		
		sleV2McastIPTvCDRInfoLogFileProfileChanged NOTIFICATION-TYPE
			OBJECTS { sleV2McastIPTvCDRInfoControlRequest, sleV2McastIPTvCDRInfoControlTimeStamp, sleV2McastIPTvCDRInfoControlReqResult, sleV2McastIPTvCDRInfoContorlLogFileName, sleV2McastIPTvCDRInfoControlLogSize
				 }
			STATUS current
			DESCRIPTION 
				"Description."
			::= { sleV2McastIPTvCDRInfoNotification 3 }

		
		sleV2McastIPTvCDRInfoExportProfileChanged NOTIFICATION-TYPE
			OBJECTS { sleV2McastIPTvCDRInfoControlRequest, sleV2McastIPTvCDRInfoControlTimeStamp, sleV2McastIPTvCDRInfoControlReqResult, sleV2McastIPTvCDRInfoControlExportTimeThreshold, sleV2McastIPTvCDRInfoControlExportTimeBegin, 
				sleV2McastIPTvCDRInfoControlExportAmountThreshold, sleV2McastIPTvCDRInfoControlANInfo }
			STATUS current
			DESCRIPTION 
				"Description."
			::= { sleV2McastIPTvCDRInfoNotification 4 }

		
		sleV2McastIPTvCDRInfoSyslogPriorityChanged NOTIFICATION-TYPE
			OBJECTS { sleV2McastIPTvCDRInfoControlRequest, sleV2McastIPTvCDRInfoControlTimeStamp, sleV2McastIPTvCDRInfoControlReqResult, sleV2McastIPTvCDRInfoControlSyslogPriority }
			STATUS current
			DESCRIPTION 
				"Description."
			::= { sleV2McastIPTvCDRInfoNotification 5 }

		
		sleV2McastIPTvCDRLogServer OBJECT IDENTIFIER ::= { sleV2McastIPTvCDR 2 }

		
		sleV2McastIPTvCDRLogServerTable OBJECT-TYPE
			SYNTAX SEQUENCE OF SleV2McastIPTvCDRLogServerEntry
			MAX-ACCESS not-accessible
			STATUS current
			DESCRIPTION
				"multicast IPTV CDR log server table."
			::= { sleV2McastIPTvCDRLogServer 1 }

		
		sleV2McastIPTvCDRLogServerEntry OBJECT-TYPE
			SYNTAX SleV2McastIPTvCDRLogServerEntry
			MAX-ACCESS not-accessible
			STATUS current
			DESCRIPTION
				"key: sleV2McastIPTvCDRLogServerId"
			INDEX { sleV2McastIPTvCDRLogServerId }
			::= { sleV2McastIPTvCDRLogServerTable 1 }

		
		SleV2McastIPTvCDRLogServerEntry ::=
			SEQUENCE { 
				sleV2McastIPTvCDRLogServerId
					Integer32,
				sleV2McastIPTvCDRLogServerIpAddress
					IpAddress,
				sleV2McastIPTvCDRLogServerPort
					INTEGER,
				sleV2McastIPTvCDRLogServerMode
					INTEGER,
				sleV2McastIPTvCDRLogServerUserId
					OCTET STRING,
				sleV2McastIPTvCDRLogServerUserPassword
					OCTET STRING
			 }

		sleV2McastIPTvCDRLogServerId OBJECT-TYPE
			SYNTAX Integer32 (1..65535)
			MAX-ACCESS read-only
			STATUS current
			DESCRIPTION
				"LogServer Id"
			::= { sleV2McastIPTvCDRLogServerEntry 1 }

		
		sleV2McastIPTvCDRLogServerIpAddress OBJECT-TYPE
			SYNTAX IpAddress
			MAX-ACCESS read-only
			STATUS current
			DESCRIPTION
				"LogServer IP address"
			::= { sleV2McastIPTvCDRLogServerEntry 2 }

		
		sleV2McastIPTvCDRLogServerPort OBJECT-TYPE
			SYNTAX INTEGER (0..65535)
			MAX-ACCESS read-only
			STATUS current
			DESCRIPTION
				"LogServer Layer4 Port."
			::= { sleV2McastIPTvCDRLogServerEntry 3 }

		
		sleV2McastIPTvCDRLogServerMode OBJECT-TYPE
			SYNTAX INTEGER
				{
				ftp(1),
				tftp(2)
				}
			MAX-ACCESS read-only
			STATUS current
			DESCRIPTION
				"LogServer trasferring mode."
			::= { sleV2McastIPTvCDRLogServerEntry 4 }

		
		sleV2McastIPTvCDRLogServerUserId OBJECT-TYPE
			SYNTAX OCTET STRING
			MAX-ACCESS read-only
			STATUS current
			DESCRIPTION
				"LogServer User Id"
			::= { sleV2McastIPTvCDRLogServerEntry 5 }

		
		sleV2McastIPTvCDRLogServerUserPassword OBJECT-TYPE
			SYNTAX OCTET STRING
			MAX-ACCESS read-only
			STATUS current
			DESCRIPTION
				"LogServer User Password
				If user id is 'anony', user password must be 'anony'"
			::= { sleV2McastIPTvCDRLogServerEntry 6 }

		
		sleV2McastIPTvCDRLogServerControl OBJECT IDENTIFIER ::= { sleV2McastIPTvCDRLogServer 2 }

		
		sleV2McastIPTvCDRLogServerControlRequest OBJECT-TYPE
			SYNTAX INTEGER
				{
				createLogServer(1),
				deleteLogServer(2),
				uploadCDR(3),
				uploadCDRManual(4)
				}
			MAX-ACCESS read-write
			STATUS current
			DESCRIPTION
				"The request of a user command"
			::= { sleV2McastIPTvCDRLogServerControl 1 }

		
		sleV2McastIPTvCDRLogServerControlStatus OBJECT-TYPE
			SYNTAX SleControlStatusType
			MAX-ACCESS read-only
			STATUS current
			DESCRIPTION
				"The status of user command"
			::= { sleV2McastIPTvCDRLogServerControl 2 }

		
		sleV2McastIPTvCDRLogServerControlTimer OBJECT-TYPE
			SYNTAX Gauge32
			MAX-ACCESS read-write
			STATUS current
			DESCRIPTION
				"The maximum time for the manager for a long running user command"
			::= { sleV2McastIPTvCDRLogServerControl 3 }

		
		sleV2McastIPTvCDRLogServerControlTimeStamp OBJECT-TYPE
			SYNTAX TimeStamp
			MAX-ACCESS read-only
			STATUS current
			DESCRIPTION
				"The time stamp of the last command(end of command)"
			::= { sleV2McastIPTvCDRLogServerControl 4 }

		
		sleV2McastIPTvCDRLogServerControlReqResult OBJECT-TYPE
			SYNTAX SleControlRequestResultType
			MAX-ACCESS read-only
			STATUS current
			DESCRIPTION
				"The result of the last user command"
			::= { sleV2McastIPTvCDRLogServerControl 5 }

		
		sleV2McastIPTvCDRLogServerControlId OBJECT-TYPE
			SYNTAX INTEGER (0..65535)
			MAX-ACCESS read-write
			STATUS current
			DESCRIPTION
				"LogServer Id"
			::= { sleV2McastIPTvCDRLogServerControl 6 }

		
		sleV2McastIPTvCDRLogServerControlIpAddress OBJECT-TYPE
			SYNTAX IpAddress
			MAX-ACCESS read-write
			STATUS current
			DESCRIPTION
				"LogServer IP address"
			::= { sleV2McastIPTvCDRLogServerControl 7 }

		
		sleV2McastIPTvCDRLogServerControlPort OBJECT-TYPE
			SYNTAX INTEGER (0..65535)
			MAX-ACCESS read-write
			STATUS current
			DESCRIPTION
				"LogServer Layer4 Port."
			::= { sleV2McastIPTvCDRLogServerControl 8 }

		
		sleV2McastIPTvCDRLogServerControlMode OBJECT-TYPE
			SYNTAX INTEGER
				{
				ftp(1),
				tftp(2)
				}
			MAX-ACCESS read-write
			STATUS current
			DESCRIPTION
				"LogServer trasferring mode."
			::= { sleV2McastIPTvCDRLogServerControl 9 }

		
		sleV2McastIPTvCDRLogServerControlUserId OBJECT-TYPE
			SYNTAX OCTET STRING
			MAX-ACCESS read-write
			STATUS current
			DESCRIPTION
				"LogServer User Id"
			::= { sleV2McastIPTvCDRLogServerControl 10 }

		
		sleV2McastIPTvCDRLogServerControlUserPassword OBJECT-TYPE
			SYNTAX OCTET STRING
			MAX-ACCESS read-write
			STATUS current
			DESCRIPTION
				"LogServer User Password
				If user id is 'anony', user password must be 'anony'"
			::= { sleV2McastIPTvCDRLogServerControl 11 }

		
		sleV2McastIPTvCDRLogServerControlFileName OBJECT-TYPE
			SYNTAX OCTET STRING
			MAX-ACCESS read-write
			STATUS current
			DESCRIPTION
				"remote CDR DB filename (default NULL)"
			::= { sleV2McastIPTvCDRLogServerControl 12 }

		
		sleV2McastIPTvCDRLogServerNotification OBJECT IDENTIFIER ::= { sleV2McastIPTvCDRLogServer 3 }

		
		sleV2McastIPTvCDRLogServerCreated NOTIFICATION-TYPE
			OBJECTS { sleV2McastIPTvCDRLogServerControlRequest, sleV2McastIPTvCDRLogServerControlTimeStamp, sleV2McastIPTvCDRLogServerControlReqResult, sleV2McastIPTvCDRLogServerControlId, sleV2McastIPTvCDRLogServerControlIpAddress, 
				sleV2McastIPTvCDRLogServerControlPort, sleV2McastIPTvCDRLogServerControlMode, sleV2McastIPTvCDRLogServerControlUserId, sleV2McastIPTvCDRLogServerControlUserPassword }
			STATUS current
			DESCRIPTION 
				"Description."
			::= { sleV2McastIPTvCDRLogServerNotification 1 }

		
		sleV2McastIPTvCDRLogServerDeleted NOTIFICATION-TYPE
			OBJECTS { sleV2McastIPTvCDRLogServerControlRequest, sleV2McastIPTvCDRLogServerControlTimeStamp, sleV2McastIPTvCDRLogServerControlReqResult, sleV2McastIPTvCDRLogServerControlId }
			STATUS current
			DESCRIPTION 
				"Description."
			::= { sleV2McastIPTvCDRLogServerNotification 2 }

		
		sleV2McastIPTvCDRLogServerUploadCDR NOTIFICATION-TYPE
			OBJECTS { sleV2McastIPTvCDRLogServerControlRequest, sleV2McastIPTvCDRLogServerControlTimeStamp, sleV2McastIPTvCDRLogServerControlReqResult, sleV2McastIPTvCDRLogServerControlId }
			STATUS current
			DESCRIPTION 
				"Description."
			::= { sleV2McastIPTvCDRLogServerNotification 3 }

		
		sleV2McastIPTvCDRLogServerUploadCDRManual NOTIFICATION-TYPE
			OBJECTS { sleV2McastIPTvCDRLogServerControlRequest, sleV2McastIPTvCDRLogServerControlTimeStamp, sleV2McastIPTvCDRLogServerControlReqResult, sleV2McastIPTvCDRLogServerControlIpAddress, sleV2McastIPTvCDRLogServerControlPort, 
				sleV2McastIPTvCDRLogServerControlMode, sleV2McastIPTvCDRLogServerControlUserId, sleV2McastIPTvCDRLogServerControlUserPassword, sleV2McastIPTvCDRLogServerControlFileName }
			STATUS current
			DESCRIPTION 
				"Description."
			::= { sleV2McastIPTvCDRLogServerNotification 4 }

		
		sleV2McastIPTvCDRStatistics OBJECT IDENTIFIER ::= { sleV2McastIPTvCDR 3 }

		
		sleV2McastIPTvCDRLogStats OBJECT IDENTIFIER ::= { sleV2McastIPTvCDRStatistics 1 }

		
		sleV2McastIPTvCDRLogStatsTotalCount OBJECT-TYPE
			SYNTAX INTEGER (0..65535)
			MAX-ACCESS read-only
			STATUS current
			DESCRIPTION
				"The total count of CDR logging"
			::= { sleV2McastIPTvCDRLogStats 1 }

		
		sleV2McastIPTvCDRLogStatsJoinCount OBJECT-TYPE
			SYNTAX INTEGER (0..65535)
			MAX-ACCESS read-only
			STATUS current
			DESCRIPTION
				"The total count of CDR Join-logging"
			::= { sleV2McastIPTvCDRLogStats 2 }

		
		sleV2McastIPTvCDRLogStatsKeepJoinedCount OBJECT-TYPE
			SYNTAX INTEGER (0..65535)
			MAX-ACCESS read-only
			STATUS current
			DESCRIPTION
				"The total count of CDR Keep-Joined-logging"
			::= { sleV2McastIPTvCDRLogStats 3 }

		
		sleV2McastIPTvCDRLogStatsLeaveCount OBJECT-TYPE
			SYNTAX INTEGER (0..65535)
			MAX-ACCESS read-only
			STATUS current
			DESCRIPTION
				"The total count of CDR Leave-logging"
			::= { sleV2McastIPTvCDRLogStats 4 }

		
		sleV2McastIPTvCDRLogStatsLastExportDate OBJECT-TYPE
			SYNTAX OCTET STRING
			MAX-ACCESS read-only
			STATUS current
			DESCRIPTION
				"The last logging date"
			::= { sleV2McastIPTvCDRLogStats 5 }

		
		sleV2McastIPTvCDRLogStatsLastExportReason OBJECT-TYPE
			SYNTAX INTEGER
				{
				time(1),
				amount(2),
				manual(3)
				}
			MAX-ACCESS read-only
			STATUS current
			DESCRIPTION
				"The last logging reason"
			::= { sleV2McastIPTvCDRLogStats 6 }

		
		sleV2McastIPTvCDRLogStatsLastExportServerList OBJECT-TYPE
			SYNTAX OCTET STRING
			MAX-ACCESS read-only
			STATUS current
			DESCRIPTION
				"The last logging Server list.  (delimiter :  / )"
			::= { sleV2McastIPTvCDRLogStats 7 }

		
		sleV2McastIPTvCDRFormat OBJECT IDENTIFIER ::= { sleV2McastIPTvCDR 4 }

		
		sleV2McastIPTvCDRFormatTable OBJECT-TYPE
			SYNTAX SEQUENCE OF SleV2McastIPTvCDRFormatEntry
			MAX-ACCESS not-accessible
			STATUS current
			DESCRIPTION
				"multicast IPTV CDR format table."
			::= { sleV2McastIPTvCDRFormat 1 }

		
		sleV2McastIPTvCDRFormatEntry OBJECT-TYPE
			SYNTAX SleV2McastIPTvCDRFormatEntry
			MAX-ACCESS not-accessible
			STATUS current
			DESCRIPTION
				"key: sleV2McastIPTvCDRFmtName"
			INDEX { sleV2McastIPTvCDRFmtName }
			::= { sleV2McastIPTvCDRFormatTable 1 }

		
		SleV2McastIPTvCDRFormatEntry ::=
			SEQUENCE { 
				sleV2McastIPTvCDRFmtName
					OCTET STRING,
				sleV2McastIPTvCDRFmtDelimiter
					OCTET STRING,
				sleV2McastIPTvCDRFmtOrderRecordType
					OCTET STRING,
				sleV2McastIPTvCDRFmtOrderReason
					OCTET STRING,
				sleV2McastIPTvCDRFmtOrderLogTime
					OCTET STRING,
				sleV2McastIPTvCDRFmtOrderAN
					OCTET STRING,
				sleV2McastIPTvCDRFmtOrderSubscriber
					OCTET STRING,
				sleV2McastIPTvCDRFmtOrderChannel
					OCTET STRING,
				sleV2McastIPTvCDRFmtOrderChannelType
					OCTET STRING,
				sleV2McastIPTvCDRFmtOrderStartTime
					OCTET STRING,
				sleV2McastIPTvCDRFmtOrderViewingDuration
					OCTET STRING,
				sleV2McastIPTvCDRFmtJPRecId
					OCTET STRING,
				sleV2McastIPTvCDRFmtJDRecId
					OCTET STRING,
				sleV2McastIPTvCDRFmtKJRecId
					OCTET STRING,
				sleV2McastIPTvCDRFmtLPRecId
					OCTET STRING,
				sleV2McastIPTvCDRFmtLDRecId
					OCTET STRING,
				sleV2McastIPTvCDRFmtJPChTypeFullView
					OCTET STRING,
				sleV2McastIPTvCDRFmtJPChTypePreView
					OCTET STRING,
				sleV2McastIPTvCDRFmtJPChTypePayPerView
					OCTET STRING,
				sleV2McastIPTvCDRFmtJDReasonNoSubscriber
					OCTET STRING,
				sleV2McastIPTvCDRFmtJDReasonNoChannel
					OCTET STRING,
				sleV2McastIPTvCDRFmtJDReasonNotSubscribed
					OCTET STRING,
				sleV2McastIPTvCDRFmtJDReasonOverQuota
					OCTET STRING,
				sleV2McastIPTvCDRFmtJDReasonOverMaxStream
					OCTET STRING,
				sleV2McastIPTvCDRFmtJDReasonOverMaxBw
					OCTET STRING,
				sleV2McastIPTvCDRFmtKJChTypeFullView
					OCTET STRING,
				sleV2McastIPTvCDRFmtKJChTypePreView
					OCTET STRING,
				sleV2McastIPTvCDRFmtKJChTypePayPerView
					OCTET STRING,
				sleV2McastIPTvCDRFmtLPReasonLeaveChannel
					OCTET STRING,
				sleV2McastIPTvCDRFmtLPReasonTimeout
					OCTET STRING,
				sleV2McastIPTvCDRFmtLPReasonRemoveChannel
					OCTET STRING,
				sleV2McastIPTvCDRFmtLPReasonRemoveSubscriber
					OCTET STRING,
				sleV2McastIPTvCDRFmtLDReasonNoSubscriber
					OCTET STRING,
				sleV2McastIPTvCDRFmtLDReasonNoChannel
					OCTET STRING,
				sleV2McastIPTvCDRFmtLDReasonNotSubscribed
					OCTET STRING,
				sleV2McastIPTvCDRFmtLDReasonNotJoined
					OCTET STRING,
				sleV2McastIPTvCDRFmtReasonNoSubscriber
					OCTET STRING,
				sleV2McastIPTvCDRFmtReasonNoChannel
					OCTET STRING,
				sleV2McastIPTvCDRFmtReasonNotSubscribed
					OCTET STRING,
				sleV2McastIPTvCDRFmtReasonOverQuota
					OCTET STRING,
				sleV2McastIPTvCDRFmtReasonOverMaxStream
					OCTET STRING,
				sleV2McastIPTvCDRFmtReasonOverMaxBw
					OCTET STRING,
				sleV2McastIPTvCDRFmtReasonLeaveChannel
					OCTET STRING,
				sleV2McastIPTvCDRFmtReasonTimeout
					OCTET STRING,
				sleV2McastIPTvCDRFmtReasonRemoveChannel
					OCTET STRING,
				sleV2McastIPTvCDRFmtReasonRemoveSubscriber
					OCTET STRING,
				sleV2McastIPTvCDRFmtReasonNotJoined
					OCTET STRING
			 }

		sleV2McastIPTvCDRFmtName OBJECT-TYPE
			SYNTAX OCTET STRING
			MAX-ACCESS read-only
			STATUS current
			DESCRIPTION
				"The Log-format-profile name."
			::= { sleV2McastIPTvCDRFormatEntry 1 }

		
		sleV2McastIPTvCDRFmtDelimiter OBJECT-TYPE
			SYNTAX OCTET STRING
			MAX-ACCESS read-only
			STATUS current
			DESCRIPTION
				"The log delimiter. Default ','"
			::= { sleV2McastIPTvCDRFormatEntry 2 }

		
		sleV2McastIPTvCDRFmtOrderRecordType OBJECT-TYPE
			SYNTAX OCTET STRING
			MAX-ACCESS read-only
			STATUS current
			DESCRIPTION
				"<0/1-9>  0 : means omit. Default: 1"
			::= { sleV2McastIPTvCDRFormatEntry 3 }

		
		sleV2McastIPTvCDRFmtOrderReason OBJECT-TYPE
			SYNTAX OCTET STRING
			MAX-ACCESS read-only
			STATUS current
			DESCRIPTION
				"<0/1-9>  0 : means omit. Default: 2"
			::= { sleV2McastIPTvCDRFormatEntry 4 }

		
		sleV2McastIPTvCDRFmtOrderLogTime OBJECT-TYPE
			SYNTAX OCTET STRING
			MAX-ACCESS read-only
			STATUS current
			DESCRIPTION
				"<0/1-9>  0 : means omit. Default: 3"
			::= { sleV2McastIPTvCDRFormatEntry 5 }

		
		sleV2McastIPTvCDRFmtOrderAN OBJECT-TYPE
			SYNTAX OCTET STRING
			MAX-ACCESS read-only
			STATUS current
			DESCRIPTION
				"<0/1-9>  0 : means omit. Default: 4"
			::= { sleV2McastIPTvCDRFormatEntry 6 }

		
		sleV2McastIPTvCDRFmtOrderSubscriber OBJECT-TYPE
			SYNTAX OCTET STRING
			MAX-ACCESS read-only
			STATUS current
			DESCRIPTION
				"<0/1-9>  0 : means omit. Default: 5"
			::= { sleV2McastIPTvCDRFormatEntry 7 }

		
		sleV2McastIPTvCDRFmtOrderChannel OBJECT-TYPE
			SYNTAX OCTET STRING
			MAX-ACCESS read-only
			STATUS current
			DESCRIPTION
				"<0/1-9>  0 : means omit. Default: 6"
			::= { sleV2McastIPTvCDRFormatEntry 8 }

		
		sleV2McastIPTvCDRFmtOrderChannelType OBJECT-TYPE
			SYNTAX OCTET STRING
			MAX-ACCESS read-only
			STATUS current
			DESCRIPTION
				"<0/1-9>  0 : means omit. Default: 7"
			::= { sleV2McastIPTvCDRFormatEntry 9 }

		
		sleV2McastIPTvCDRFmtOrderStartTime OBJECT-TYPE
			SYNTAX OCTET STRING
			MAX-ACCESS read-only
			STATUS current
			DESCRIPTION
				"<0/1-9>  0 : means omit. Default: 8"
			::= { sleV2McastIPTvCDRFormatEntry 10 }

		
		sleV2McastIPTvCDRFmtOrderViewingDuration OBJECT-TYPE
			SYNTAX OCTET STRING
			MAX-ACCESS read-only
			STATUS current
			DESCRIPTION
				"<0/1-9>  0 : means omit. Default: 9"
			::= { sleV2McastIPTvCDRFormatEntry 11 }

		
		sleV2McastIPTvCDRFmtJPRecId OBJECT-TYPE
			SYNTAX OCTET STRING (SIZE (0..32))
			MAX-ACCESS read-only
			STATUS current
			DESCRIPTION
				"record-id : <1-255>, 0 means 'no',  max 32 string , default: string : join-permit
				The Join-Permit record ID value"
			::= { sleV2McastIPTvCDRFormatEntry 12 }

		
		sleV2McastIPTvCDRFmtJDRecId OBJECT-TYPE
			SYNTAX OCTET STRING (SIZE (0..32))
			MAX-ACCESS read-only
			STATUS current
			DESCRIPTION
				"record-id : <1-255>, 0 means 'no',  max 32 string, default: string : join-deny
				The Join-Deny record ID value"
			::= { sleV2McastIPTvCDRFormatEntry 13 }

		
		sleV2McastIPTvCDRFmtKJRecId OBJECT-TYPE
			SYNTAX OCTET STRING (SIZE (0..32))
			MAX-ACCESS read-only
			STATUS current
			DESCRIPTION
				"record-id : <1-255>, 0 means 'no',  max 32 string, default: string : keep-joined
				The Keep-Joined record ID value"
			::= { sleV2McastIPTvCDRFormatEntry 14 }

		
		sleV2McastIPTvCDRFmtLPRecId OBJECT-TYPE
			SYNTAX OCTET STRING (SIZE (0..32))
			MAX-ACCESS read-only
			STATUS current
			DESCRIPTION
				"record-id : <1-255>, 0 means 'no',  max 32 string, default: string : leave-permit
				The Leave-Permit record ID value"
			::= { sleV2McastIPTvCDRFormatEntry 15 }

		
		sleV2McastIPTvCDRFmtLDRecId OBJECT-TYPE
			SYNTAX OCTET STRING (SIZE (0..32))
			MAX-ACCESS read-only
			STATUS current
			DESCRIPTION
				"record-id : <1-255>, 0 means 'no',  max 32 string, default: string : leave-deny
				The Leave-Deny record ID value"
			::= { sleV2McastIPTvCDRFormatEntry 16 }

		
		sleV2McastIPTvCDRFmtJPChTypeFullView OBJECT-TYPE
			SYNTAX OCTET STRING (SIZE (0..32))
			MAX-ACCESS read-only
			STATUS current
			DESCRIPTION
				"record-id : <1-255>, 0 means 'no'  max 32 string   
				The Join-Permit channel-type preview record ID value
				This is prior to JoinPermitRecordId."
			::= { sleV2McastIPTvCDRFormatEntry 17 }

		
		sleV2McastIPTvCDRFmtJPChTypePreView OBJECT-TYPE
			SYNTAX OCTET STRING (SIZE (0..32))
			MAX-ACCESS read-only
			STATUS current
			DESCRIPTION
				"record-id : <1-255>, 0 means 'no'  max 32 string   
				The Join-Permit channel-type preview record ID value
				This is prior to JoinPermitRecordId."
			::= { sleV2McastIPTvCDRFormatEntry 18 }

		
		sleV2McastIPTvCDRFmtJPChTypePayPerView OBJECT-TYPE
			SYNTAX OCTET STRING (SIZE (0..32))
			MAX-ACCESS read-only
			STATUS current
			DESCRIPTION
				"record-id : <1-255>, 0 means 'no'  max 32 string   
				The Join-Permit channel-type payperview record ID value
				This is prior to JoinPermitRecordId."
			::= { sleV2McastIPTvCDRFormatEntry 19 }

		
		sleV2McastIPTvCDRFmtJDReasonNoSubscriber OBJECT-TYPE
			SYNTAX OCTET STRING (SIZE (0..32))
			MAX-ACCESS read-only
			STATUS current
			DESCRIPTION
				"record-id : <1-255>, 0 means 'no'  max 32 string   
				The Join-Deny reason-noSubscriber record ID value
				This is prior to JoinDenyRecordId"
			::= { sleV2McastIPTvCDRFormatEntry 20 }

		
		sleV2McastIPTvCDRFmtJDReasonNoChannel OBJECT-TYPE
			SYNTAX OCTET STRING (SIZE (0..32))
			MAX-ACCESS read-only
			STATUS current
			DESCRIPTION
				"record-id : <1-255>, 0 means 'no'  max 32 string   
				This is prior to JoinDenyRecordId"
			::= { sleV2McastIPTvCDRFormatEntry 21 }

		
		sleV2McastIPTvCDRFmtJDReasonNotSubscribed OBJECT-TYPE
			SYNTAX OCTET STRING (SIZE (0..32))
			MAX-ACCESS read-only
			STATUS current
			DESCRIPTION
				"record-id : <1-255>, 0 means 'no'  max 32 string   
				This is prior to JoinDenyRecordId"
			::= { sleV2McastIPTvCDRFormatEntry 22 }

		
		sleV2McastIPTvCDRFmtJDReasonOverQuota OBJECT-TYPE
			SYNTAX OCTET STRING (SIZE (0..32))
			MAX-ACCESS read-only
			STATUS current
			DESCRIPTION
				"record-id : <1-255>, 0 means 'no'  max 32 string   
				This is prior to JoinDenyRecordId"
			::= { sleV2McastIPTvCDRFormatEntry 23 }

		
		sleV2McastIPTvCDRFmtJDReasonOverMaxStream OBJECT-TYPE
			SYNTAX OCTET STRING (SIZE (0..32))
			MAX-ACCESS read-only
			STATUS current
			DESCRIPTION
				"record-id : <1-255>, 0 means 'no'  max 32 string   
				This is prior to JoinDenyRecordId"
			::= { sleV2McastIPTvCDRFormatEntry 24 }

		
		sleV2McastIPTvCDRFmtJDReasonOverMaxBw OBJECT-TYPE
			SYNTAX OCTET STRING (SIZE (0..32))
			MAX-ACCESS read-only
			STATUS current
			DESCRIPTION
				"record-id : <1-255>, 0 means 'no'  max 32 string   
				This is prior to JoinDenyRecordId"
			::= { sleV2McastIPTvCDRFormatEntry 25 }

		
		sleV2McastIPTvCDRFmtKJChTypeFullView OBJECT-TYPE
			SYNTAX OCTET STRING (SIZE (0..32))
			MAX-ACCESS read-only
			STATUS current
			DESCRIPTION
				"record-id : <1-255>, 0 means 'no'  max 32 string   
				This is prior to KeepJoinedRecordId"
			::= { sleV2McastIPTvCDRFormatEntry 26 }

		
		sleV2McastIPTvCDRFmtKJChTypePreView OBJECT-TYPE
			SYNTAX OCTET STRING (SIZE (0..32))
			MAX-ACCESS read-only
			STATUS current
			DESCRIPTION
				"record-id : <1-255>, 0 means 'no'  max 32 string   
				This  is prior to KeepJoinedRecordId"
			::= { sleV2McastIPTvCDRFormatEntry 27 }

		
		sleV2McastIPTvCDRFmtKJChTypePayPerView OBJECT-TYPE
			SYNTAX OCTET STRING (SIZE (0..32))
			MAX-ACCESS read-only
			STATUS current
			DESCRIPTION
				"record-id : <1-255>, 0 means 'no'  max 32 string   
				This is prior to KeepJoinedRecordId"
			::= { sleV2McastIPTvCDRFormatEntry 28 }

		
		sleV2McastIPTvCDRFmtLPReasonLeaveChannel OBJECT-TYPE
			SYNTAX OCTET STRING (SIZE (0..32))
			MAX-ACCESS read-only
			STATUS current
			DESCRIPTION
				"record-id : <1-255>, 0 means 'no'  max 32 string   
				This is prior to LeavePermit"
			::= { sleV2McastIPTvCDRFormatEntry 29 }

		
		sleV2McastIPTvCDRFmtLPReasonTimeout OBJECT-TYPE
			SYNTAX OCTET STRING (SIZE (0..32))
			MAX-ACCESS read-only
			STATUS current
			DESCRIPTION
				"record-id : <1-255>, 0 means 'no'  max 32 string   
				This is prior to LeavePermit"
			::= { sleV2McastIPTvCDRFormatEntry 30 }

		
		sleV2McastIPTvCDRFmtLPReasonRemoveChannel OBJECT-TYPE
			SYNTAX OCTET STRING (SIZE (0..32))
			MAX-ACCESS read-only
			STATUS current
			DESCRIPTION
				"record-id : <1-255>, 0 means 'no'  max 32 string   
				This  is prior to LeavePermit"
			::= { sleV2McastIPTvCDRFormatEntry 31 }

		
		sleV2McastIPTvCDRFmtLPReasonRemoveSubscriber OBJECT-TYPE
			SYNTAX OCTET STRING (SIZE (0..32))
			MAX-ACCESS read-only
			STATUS current
			DESCRIPTION
				"record-id : <1-255>, 0 means 'no'  max 32 string   
				This is prior to LeavePermit"
			::= { sleV2McastIPTvCDRFormatEntry 32 }

		
		sleV2McastIPTvCDRFmtLDReasonNoSubscriber OBJECT-TYPE
			SYNTAX OCTET STRING (SIZE (0..32))
			MAX-ACCESS read-only
			STATUS current
			DESCRIPTION
				"record-id : <1-255>, 0 means 'no'  max 32 string   
				This is prior to LeaveDeny"
			::= { sleV2McastIPTvCDRFormatEntry 33 }

		
		sleV2McastIPTvCDRFmtLDReasonNoChannel OBJECT-TYPE
			SYNTAX OCTET STRING (SIZE (0..32))
			MAX-ACCESS read-only
			STATUS current
			DESCRIPTION
				"record-id : <1-255>, 0 means 'no'  max 32 string   
				This is prior to LeaveDeny"
			::= { sleV2McastIPTvCDRFormatEntry 34 }

		
		sleV2McastIPTvCDRFmtLDReasonNotSubscribed OBJECT-TYPE
			SYNTAX OCTET STRING (SIZE (0..32))
			MAX-ACCESS read-only
			STATUS current
			DESCRIPTION
				"record-id : <1-255>, 0 means 'no'  max 32 string   
				This is prior to LeaveDeny"
			::= { sleV2McastIPTvCDRFormatEntry 35 }

		
		sleV2McastIPTvCDRFmtLDReasonNotJoined OBJECT-TYPE
			SYNTAX OCTET STRING (SIZE (0..32))
			MAX-ACCESS read-only
			STATUS current
			DESCRIPTION
				"record-id : <1-255>, 0 means 'no'  max 32 string   
				This is prior to LeaveDeny"
			::= { sleV2McastIPTvCDRFormatEntry 36 }

		
		sleV2McastIPTvCDRFmtReasonNoSubscriber OBJECT-TYPE
			SYNTAX OCTET STRING (SIZE (0..32))
			MAX-ACCESS read-only
			STATUS current
			DESCRIPTION
				"record-id : <1-255>, 0 means 'no'  max 32 string"
			::= { sleV2McastIPTvCDRFormatEntry 37 }

		
		sleV2McastIPTvCDRFmtReasonNoChannel OBJECT-TYPE
			SYNTAX OCTET STRING (SIZE (0..32))
			MAX-ACCESS read-only
			STATUS current
			DESCRIPTION
				"record-id : <1-255>, 0 means 'no'  max 32 string"
			::= { sleV2McastIPTvCDRFormatEntry 38 }

		
		sleV2McastIPTvCDRFmtReasonNotSubscribed OBJECT-TYPE
			SYNTAX OCTET STRING (SIZE (0..32))
			MAX-ACCESS read-only
			STATUS current
			DESCRIPTION
				"record-id : <1-255>, 0 means 'no'  max 32 string"
			::= { sleV2McastIPTvCDRFormatEntry 39 }

		
		sleV2McastIPTvCDRFmtReasonOverQuota OBJECT-TYPE
			SYNTAX OCTET STRING (SIZE (0..32))
			MAX-ACCESS read-only
			STATUS current
			DESCRIPTION
				"record-id : <1-255>, 0 means 'no'  max 32 string"
			::= { sleV2McastIPTvCDRFormatEntry 40 }

		
		sleV2McastIPTvCDRFmtReasonOverMaxStream OBJECT-TYPE
			SYNTAX OCTET STRING (SIZE (0..32))
			MAX-ACCESS read-only
			STATUS current
			DESCRIPTION
				"record-id : <1-255>, 0 means 'no'  max 32 string"
			::= { sleV2McastIPTvCDRFormatEntry 41 }

		
		sleV2McastIPTvCDRFmtReasonOverMaxBw OBJECT-TYPE
			SYNTAX OCTET STRING (SIZE (0..32))
			MAX-ACCESS read-only
			STATUS current
			DESCRIPTION
				"record-id : <1-255>, 0 means 'no'  max 32 string"
			::= { sleV2McastIPTvCDRFormatEntry 42 }

		
		sleV2McastIPTvCDRFmtReasonLeaveChannel OBJECT-TYPE
			SYNTAX OCTET STRING (SIZE (0..32))
			MAX-ACCESS read-only
			STATUS current
			DESCRIPTION
				"record-id : <1-255>, 0 means 'no'  max 32 string"
			::= { sleV2McastIPTvCDRFormatEntry 43 }

		
		sleV2McastIPTvCDRFmtReasonTimeout OBJECT-TYPE
			SYNTAX OCTET STRING (SIZE (0..32))
			MAX-ACCESS read-only
			STATUS current
			DESCRIPTION
				"record-id : <1-255>, 0 means 'no'  max 32 string"
			::= { sleV2McastIPTvCDRFormatEntry 44 }

		
		sleV2McastIPTvCDRFmtReasonRemoveChannel OBJECT-TYPE
			SYNTAX OCTET STRING (SIZE (0..32))
			MAX-ACCESS read-only
			STATUS current
			DESCRIPTION
				"record-id : <1-255>, 0 means 'no'  max 32 string"
			::= { sleV2McastIPTvCDRFormatEntry 45 }

		
		sleV2McastIPTvCDRFmtReasonRemoveSubscriber OBJECT-TYPE
			SYNTAX OCTET STRING (SIZE (0..32))
			MAX-ACCESS read-only
			STATUS current
			DESCRIPTION
				"record-id : <1-255>, 0 means 'no'  max 32 string"
			::= { sleV2McastIPTvCDRFormatEntry 46 }

		
		sleV2McastIPTvCDRFmtReasonNotJoined OBJECT-TYPE
			SYNTAX OCTET STRING (SIZE (0..32))
			MAX-ACCESS read-only
			STATUS current
			DESCRIPTION
				"record-id : <1-255>, 0 means 'no'  max 32 string"
			::= { sleV2McastIPTvCDRFormatEntry 47 }

		
		sleV2McastIPTvCDRLogFormatControl OBJECT IDENTIFIER ::= { sleV2McastIPTvCDRFormat 2 }

		
		sleV2McastIPTvCDRFmtControlRequest OBJECT-TYPE
			SYNTAX INTEGER
				{
				createCDRFormat(1),
				deleteCDRFormat(2),
				setCDROrder(3),
				setCDRRecordTypeProfile(4),
				setCDRReasonProfile(5)
				}
			MAX-ACCESS read-write
			STATUS current
			DESCRIPTION
				"The request of a user command"
			::= { sleV2McastIPTvCDRLogFormatControl 1 }

		
		sleV2McastIPTvCDRFmtControlStatus OBJECT-TYPE
			SYNTAX SleControlStatusType
			MAX-ACCESS read-only
			STATUS current
			DESCRIPTION
				"The status of user command"
			::= { sleV2McastIPTvCDRLogFormatControl 2 }

		
		sleV2McastIPTvCDRFmtControlTimer OBJECT-TYPE
			SYNTAX Gauge32
			MAX-ACCESS read-write
			STATUS current
			DESCRIPTION
				"The maximum time for the manager for a long running user command"
			::= { sleV2McastIPTvCDRLogFormatControl 3 }

		
		sleV2McastIPTvCDRFmtControlTimeStamp OBJECT-TYPE
			SYNTAX TimeStamp
			MAX-ACCESS read-only
			STATUS current
			DESCRIPTION
				"The time stamp of the last command(end of command)"
			::= { sleV2McastIPTvCDRLogFormatControl 4 }

		
		sleV2McastIPTvCDRFmtControlReqResult OBJECT-TYPE
			SYNTAX SleControlRequestResultType
			MAX-ACCESS read-only
			STATUS current
			DESCRIPTION
				"The result of the last user command"
			::= { sleV2McastIPTvCDRLogFormatControl 5 }

		
		sleV2McastIPTvCDRFmtControlName OBJECT-TYPE
			SYNTAX OCTET STRING
			MAX-ACCESS read-write
			STATUS current
			DESCRIPTION
				"The Log-format-profile name."
			::= { sleV2McastIPTvCDRLogFormatControl 6 }

		
		sleV2McastIPTvCDRFmtControlDelimiter OBJECT-TYPE
			SYNTAX OCTET STRING
			MAX-ACCESS read-write
			STATUS current
			DESCRIPTION
				"The log delimiter.  Default ','"
			::= { sleV2McastIPTvCDRLogFormatControl 7 }

		
		sleV2McastIPTvCDRFmtControlOrderRecordType OBJECT-TYPE
			SYNTAX OCTET STRING
			MAX-ACCESS read-write
			STATUS current
			DESCRIPTION
				"<0/1-9>  0 : means omit. Default: 1"
			::= { sleV2McastIPTvCDRLogFormatControl 8 }

		
		sleV2McastIPTvCDRFmtControlOrderReason OBJECT-TYPE
			SYNTAX OCTET STRING
			MAX-ACCESS read-write
			STATUS current
			DESCRIPTION
				"<0/1-9>  0 : means omit. Default: 2"
			::= { sleV2McastIPTvCDRLogFormatControl 9 }

		
		sleV2McastIPTvCDRFmtControlOrderLogTime OBJECT-TYPE
			SYNTAX OCTET STRING
			MAX-ACCESS read-write
			STATUS current
			DESCRIPTION
				"<0/1-9>  0 : means omit. Default: 3"
			::= { sleV2McastIPTvCDRLogFormatControl 10 }

		
		sleV2McastIPTvCDRFmtControlOrderAN OBJECT-TYPE
			SYNTAX OCTET STRING
			MAX-ACCESS read-write
			STATUS current
			DESCRIPTION
				"<0/1-9>  0 : means omit. Default: 4"
			::= { sleV2McastIPTvCDRLogFormatControl 11 }

		
		sleV2McastIPTvCDRFmtControlOrderSubscriber OBJECT-TYPE
			SYNTAX OCTET STRING
			MAX-ACCESS read-write
			STATUS current
			DESCRIPTION
				"<0/1-9>  0 : means omit. Default: 5"
			::= { sleV2McastIPTvCDRLogFormatControl 12 }

		
		sleV2McastIPTvCDRFmtControlOrderChannel OBJECT-TYPE
			SYNTAX OCTET STRING
			MAX-ACCESS read-write
			STATUS current
			DESCRIPTION
				"<0/1-9>  0 : means omit. Default: 6"
			::= { sleV2McastIPTvCDRLogFormatControl 13 }

		
		sleV2McastIPTvCDRFmtControlOrderChannelType OBJECT-TYPE
			SYNTAX OCTET STRING
			MAX-ACCESS read-write
			STATUS current
			DESCRIPTION
				"<0/1-9>  0 : means omit. Default: 7"
			::= { sleV2McastIPTvCDRLogFormatControl 14 }

		
		sleV2McastIPTvCDRFmtControlOrderStartTime OBJECT-TYPE
			SYNTAX OCTET STRING
			MAX-ACCESS read-write
			STATUS current
			DESCRIPTION
				"<0/1-9>  0 : means omit. Default: 8"
			::= { sleV2McastIPTvCDRLogFormatControl 15 }

		
		sleV2McastIPTvCDRFmtControlOrderViewingDuration OBJECT-TYPE
			SYNTAX OCTET STRING
			MAX-ACCESS read-write
			STATUS current
			DESCRIPTION
				"<0/1-9>  0 : means omit. Default: 9"
			::= { sleV2McastIPTvCDRLogFormatControl 16 }

		
		sleV2McastIPTvCDRFmtControlJPRecId OBJECT-TYPE
			SYNTAX OCTET STRING (SIZE (0..32))
			MAX-ACCESS read-write
			STATUS current
			DESCRIPTION
				"record-id : <1-255>, 0 means 'no',  max 32 string , default: string : join-permit
				The Join-Permit record ID value"
			::= { sleV2McastIPTvCDRLogFormatControl 17 }

		
		sleV2McastIPTvCDRFmtControlJDRecId OBJECT-TYPE
			SYNTAX OCTET STRING (SIZE (0..32))
			MAX-ACCESS read-write
			STATUS current
			DESCRIPTION
				"record-id : <1-255>, 0 means 'no',  max 32 string, default: string : join-deny
				The Join-Deny record ID value"
			::= { sleV2McastIPTvCDRLogFormatControl 18 }

		
		sleV2McastIPTvCDRFmtControlKJRecId OBJECT-TYPE
			SYNTAX OCTET STRING (SIZE (0..32))
			MAX-ACCESS read-write
			STATUS current
			DESCRIPTION
				"record-id : <1-255>, 0 means 'no',  max 32 string, default: string : keep-joined
				The Keep-Joined record ID value"
			::= { sleV2McastIPTvCDRLogFormatControl 19 }

		
		sleV2McastIPTvCDRFmtControlLPRecId OBJECT-TYPE
			SYNTAX OCTET STRING (SIZE (0..32))
			MAX-ACCESS read-write
			STATUS current
			DESCRIPTION
				"record-id : <1-255>, 0 means 'no',  max 32 string, default: string : leave-permit
				The Leave-Permit record ID value"
			::= { sleV2McastIPTvCDRLogFormatControl 20 }

		
		sleV2McastIPTvCDRFmtControlLDRecId OBJECT-TYPE
			SYNTAX OCTET STRING (SIZE (0..32))
			MAX-ACCESS read-write
			STATUS current
			DESCRIPTION
				"record-id : <1-255>, 0 means 'no',  max 32 string, default: string : leave-deny
				The Leave-Deny record ID value"
			::= { sleV2McastIPTvCDRLogFormatControl 21 }

		
		sleV2McastIPTvCDRFmtControlJPChTypeFullView OBJECT-TYPE
			SYNTAX OCTET STRING (SIZE (0..32))
			MAX-ACCESS read-write
			STATUS current
			DESCRIPTION
				"record-id : <1-255>, 0 means 'no'  max 32 string"
			::= { sleV2McastIPTvCDRLogFormatControl 22 }

		
		sleV2McastIPTvCDRFmtControlJPChTypePreView OBJECT-TYPE
			SYNTAX OCTET STRING (SIZE (0..32))
			MAX-ACCESS read-write
			STATUS current
			DESCRIPTION
				"record-id : <1-255>, 0 means 'no'  max 32 string"
			::= { sleV2McastIPTvCDRLogFormatControl 23 }

		
		sleV2McastIPTvCDRFmtControlJPChTypePayPerView OBJECT-TYPE
			SYNTAX OCTET STRING (SIZE (0..32))
			MAX-ACCESS read-write
			STATUS current
			DESCRIPTION
				"record-id : <1-255>, 0 means 'no'  max 32 string"
			::= { sleV2McastIPTvCDRLogFormatControl 24 }

		
		sleV2McastIPTvCDRFmtControlJDReasonNoSubscriber OBJECT-TYPE
			SYNTAX OCTET STRING (SIZE (0..32))
			MAX-ACCESS read-write
			STATUS current
			DESCRIPTION
				"record-id : <1-255>, 0 means 'no'  max 32 string"
			::= { sleV2McastIPTvCDRLogFormatControl 25 }

		
		sleV2McastIPTvCDRFmtControlJDReasonNoChannel OBJECT-TYPE
			SYNTAX OCTET STRING (SIZE (0..32))
			MAX-ACCESS read-write
			STATUS current
			DESCRIPTION
				"record-id : <1-255>, 0 means 'no'  max 32 string"
			::= { sleV2McastIPTvCDRLogFormatControl 26 }

		
		sleV2McastIPTvCDRFmtControlJDReasonNotSubscribed OBJECT-TYPE
			SYNTAX OCTET STRING (SIZE (0..32))
			MAX-ACCESS read-write
			STATUS current
			DESCRIPTION
				"record-id : <1-255>, 0 means 'no'  max 32 string"
			::= { sleV2McastIPTvCDRLogFormatControl 27 }

		
		sleV2McastIPTvCDRFmtControlJDReasonOverQuota OBJECT-TYPE
			SYNTAX OCTET STRING (SIZE (0..32))
			MAX-ACCESS read-write
			STATUS current
			DESCRIPTION
				"record-id : <1-255>, 0 means 'no'  max 32 string"
			::= { sleV2McastIPTvCDRLogFormatControl 28 }

		
		sleV2McastIPTvCDRFmtControlJDReasonOverMaxStream OBJECT-TYPE
			SYNTAX OCTET STRING (SIZE (0..32))
			MAX-ACCESS read-write
			STATUS current
			DESCRIPTION
				"record-id : <1-255>, 0 means 'no'  max 32 string"
			::= { sleV2McastIPTvCDRLogFormatControl 29 }

		
		sleV2McastIPTvCDRFmtControlJDReasonOverMaxBw OBJECT-TYPE
			SYNTAX OCTET STRING (SIZE (0..32))
			MAX-ACCESS read-write
			STATUS current
			DESCRIPTION
				"record-id : <1-255>, 0 means 'no'  max 32 string"
			::= { sleV2McastIPTvCDRLogFormatControl 30 }

		
		sleV2McastIPTvCDRFmtControlKJChTypeFullView OBJECT-TYPE
			SYNTAX OCTET STRING (SIZE (0..32))
			MAX-ACCESS read-write
			STATUS current
			DESCRIPTION
				"record-id : <1-255>, 0 means 'no'  max 32 string"
			::= { sleV2McastIPTvCDRLogFormatControl 31 }

		
		sleV2McastIPTvCDRFmtControlKJChTypePreview OBJECT-TYPE
			SYNTAX OCTET STRING (SIZE (0..32))
			MAX-ACCESS read-write
			STATUS current
			DESCRIPTION
				"record-id : <1-255>, 0 means 'no'  max 32 string"
			::= { sleV2McastIPTvCDRLogFormatControl 32 }

		
		sleV2McastIPTvCDRFmtControlKJChTypePayPerView OBJECT-TYPE
			SYNTAX OCTET STRING (SIZE (0..32))
			MAX-ACCESS read-write
			STATUS current
			DESCRIPTION
				"record-id : <1-255>, 0 means 'no'  max 32 string"
			::= { sleV2McastIPTvCDRLogFormatControl 33 }

		
		sleV2McastIPTvCDRFmtControlLPReasonLeaveChannel OBJECT-TYPE
			SYNTAX OCTET STRING (SIZE (0..32))
			MAX-ACCESS read-write
			STATUS current
			DESCRIPTION
				"record-id : <1-255>, 0 means 'no'  max 32 string"
			::= { sleV2McastIPTvCDRLogFormatControl 34 }

		
		sleV2McastIPTvCDRFmtControlLPReasonTimeout OBJECT-TYPE
			SYNTAX OCTET STRING (SIZE (0..32))
			MAX-ACCESS read-write
			STATUS current
			DESCRIPTION
				"record-id : <1-255>, 0 means 'no'  max 32 string"
			::= { sleV2McastIPTvCDRLogFormatControl 35 }

		
		sleV2McastIPTvCDRFmtControlLPReasonRemoveChannel OBJECT-TYPE
			SYNTAX OCTET STRING (SIZE (0..32))
			MAX-ACCESS read-write
			STATUS current
			DESCRIPTION
				"record-id : <1-255>, 0 means 'no'  max 32 string"
			::= { sleV2McastIPTvCDRLogFormatControl 36 }

		
		sleV2McastIPTvCDRFmtControlLPReasonRemoveSubscriber OBJECT-TYPE
			SYNTAX OCTET STRING (SIZE (0..32))
			MAX-ACCESS read-write
			STATUS current
			DESCRIPTION
				"record-id : <1-255>, 0 means 'no'  max 32 string"
			::= { sleV2McastIPTvCDRLogFormatControl 37 }

		
		sleV2McastIPTvCDRFmtControlLDReasonNoSubscriber OBJECT-TYPE
			SYNTAX OCTET STRING (SIZE (0..32))
			MAX-ACCESS read-write
			STATUS current
			DESCRIPTION
				"record-id : <1-255>, 0 means 'no'  max 32 string"
			::= { sleV2McastIPTvCDRLogFormatControl 38 }

		
		sleV2McastIPTvCDRFmtControlLDReasonNoChannel OBJECT-TYPE
			SYNTAX OCTET STRING (SIZE (0..32))
			MAX-ACCESS read-write
			STATUS current
			DESCRIPTION
				"record-id : <1-255>, 0 means 'no'  max 32 string"
			::= { sleV2McastIPTvCDRLogFormatControl 39 }

		
		sleV2McastIPTvCDRFmtControlLDReasonNotSubscriber OBJECT-TYPE
			SYNTAX OCTET STRING (SIZE (0..32))
			MAX-ACCESS read-write
			STATUS current
			DESCRIPTION
				"record-id : <1-255>, 0 means 'no'  max 32 string"
			::= { sleV2McastIPTvCDRLogFormatControl 40 }

		
		sleV2McastIPTvCDRFmtControlLDReasonNotJoined OBJECT-TYPE
			SYNTAX OCTET STRING (SIZE (0..32))
			MAX-ACCESS read-write
			STATUS current
			DESCRIPTION
				"record-id : <1-255>, 0 means 'no'  max 32 string"
			::= { sleV2McastIPTvCDRLogFormatControl 41 }

		
		sleV2McastIPTvCDRFmtControlReasonNoSubscriber OBJECT-TYPE
			SYNTAX OCTET STRING (SIZE (0..32))
			MAX-ACCESS read-write
			STATUS current
			DESCRIPTION
				"record-id : <1-255>, 0 means 'no'  max 32 string"
			::= { sleV2McastIPTvCDRLogFormatControl 42 }

		
		sleV2McastIPTvCDRFmtControlReasonNoChannel OBJECT-TYPE
			SYNTAX OCTET STRING (SIZE (0..32))
			MAX-ACCESS read-write
			STATUS current
			DESCRIPTION
				"record-id : <1-255>, 0 means 'no'  max 32 string"
			::= { sleV2McastIPTvCDRLogFormatControl 43 }

		
		sleV2McastIPTvCDRFmtControlReasonNotSubscribed OBJECT-TYPE
			SYNTAX OCTET STRING (SIZE (0..32))
			MAX-ACCESS read-write
			STATUS current
			DESCRIPTION
				"record-id : <1-255>, 0 means 'no'  max 32 string"
			::= { sleV2McastIPTvCDRLogFormatControl 44 }

		
		sleV2McastIPTvCDRFmtControlReasonOverQuota OBJECT-TYPE
			SYNTAX OCTET STRING (SIZE (0..32))
			MAX-ACCESS read-write
			STATUS current
			DESCRIPTION
				"record-id : <1-255>, 0 means 'no'  max 32 string"
			::= { sleV2McastIPTvCDRLogFormatControl 45 }

		
		sleV2McastIPTvCDRFmtControlReasonOverMaxStream OBJECT-TYPE
			SYNTAX OCTET STRING (SIZE (0..32))
			MAX-ACCESS read-write
			STATUS current
			DESCRIPTION
				"record-id : <1-255>, 0 means 'no'  max 32 string"
			::= { sleV2McastIPTvCDRLogFormatControl 46 }

		
		sleV2McastIPTvCDRFmtControlReasonOverMaxBx OBJECT-TYPE
			SYNTAX OCTET STRING (SIZE (0..32))
			MAX-ACCESS read-write
			STATUS current
			DESCRIPTION
				"record-id : <1-255>, 0 means 'no'  max 32 string"
			::= { sleV2McastIPTvCDRLogFormatControl 47 }

		
		sleV2McastIPTvCDRFmtControlReasonLeaveChannel OBJECT-TYPE
			SYNTAX OCTET STRING (SIZE (0..32))
			MAX-ACCESS read-write
			STATUS current
			DESCRIPTION
				"record-id : <1-255>, 0 means 'no'  max 32 string"
			::= { sleV2McastIPTvCDRLogFormatControl 48 }

		
		sleV2McastIPTvCDRFmtControlReasonTimeout OBJECT-TYPE
			SYNTAX OCTET STRING (SIZE (0..32))
			MAX-ACCESS read-write
			STATUS current
			DESCRIPTION
				"record-id : <1-255>, 0 means 'no'  max 32 string"
			::= { sleV2McastIPTvCDRLogFormatControl 49 }

		
		sleV2McastIPTvCDRFmtControlReasonRemoveChannel OBJECT-TYPE
			SYNTAX OCTET STRING (SIZE (0..32))
			MAX-ACCESS read-write
			STATUS current
			DESCRIPTION
				"record-id : <1-255>, 0 means 'no'  max 32 string"
			::= { sleV2McastIPTvCDRLogFormatControl 50 }

		
		sleV2McastIPTvCDRFmtControlReasonRemoveSubscriber OBJECT-TYPE
			SYNTAX OCTET STRING (SIZE (0..32))
			MAX-ACCESS read-write
			STATUS current
			DESCRIPTION
				"record-id : <1-255>, 0 means 'no'  max 32 string"
			::= { sleV2McastIPTvCDRLogFormatControl 51 }

		
		sleV2McastIPTvCDRFmtControlReasonNotJoined OBJECT-TYPE
			SYNTAX OCTET STRING (SIZE (0..32))
			MAX-ACCESS read-write
			STATUS current
			DESCRIPTION
				"record-id : <1-255>, 0 means 'no'  max 32 string"
			::= { sleV2McastIPTvCDRLogFormatControl 52 }

		
		sleV2McastIPTvCDRLogFormatNotification OBJECT IDENTIFIER ::= { sleV2McastIPTvCDRFormat 3 }

		
		sleV2McastIPTvCDRLogFormatCreated NOTIFICATION-TYPE
			OBJECTS { sleV2McastIPTvCDRFmtControlRequest, sleV2McastIPTvCDRFmtControlTimeStamp, sleV2McastIPTvCDRFmtControlReqResult, sleV2McastIPTvCDRFmtControlName, sleV2McastIPTvCDRFmtControlDelimiter
				 }
			STATUS current
			DESCRIPTION 
				"Description."
			::= { sleV2McastIPTvCDRLogFormatNotification 1 }

		
		sleV2McastIPTvCDRLogFormatDeleted NOTIFICATION-TYPE
			OBJECTS { sleV2McastIPTvCDRFmtControlRequest, sleV2McastIPTvCDRFmtControlTimeStamp, sleV2McastIPTvCDRFmtControlReqResult, sleV2McastIPTvCDRFmtControlName }
			STATUS current
			DESCRIPTION 
				"Description."
			::= { sleV2McastIPTvCDRLogFormatNotification 2 }

		
		sleV2McastIPTvCDRLogFormatChanged NOTIFICATION-TYPE
			OBJECTS { sleV2McastIPTvCDRFmtControlRequest, sleV2McastIPTvCDRFmtControlTimeStamp, sleV2McastIPTvCDRFmtControlReqResult, sleV2McastIPTvCDRFmtControlOrderRecordType, sleV2McastIPTvCDRFmtControlOrderReason, 
				sleV2McastIPTvCDRFmtControlOrderLogTime, sleV2McastIPTvCDRFmtControlOrderAN, sleV2McastIPTvCDRFmtControlOrderSubscriber, sleV2McastIPTvCDRFmtControlOrderChannel, sleV2McastIPTvCDRFmtControlOrderChannelType, 
				sleV2McastIPTvCDRFmtControlOrderStartTime, sleV2McastIPTvCDRFmtControlOrderViewingDuration }
			STATUS current
			DESCRIPTION 
				"Description."
			::= { sleV2McastIPTvCDRLogFormatNotification 3 }

		
		sleV2McastIPTvCDRLogFormatRecordTypeChanged NOTIFICATION-TYPE
			OBJECTS { sleV2McastIPTvCDRFmtControlRequest, sleV2McastIPTvCDRFmtControlTimer, sleV2McastIPTvCDRFmtControlTimeStamp, sleV2McastIPTvCDRFmtControlJPRecId, sleV2McastIPTvCDRFmtControlJDRecId, 
				sleV2McastIPTvCDRFmtControlKJRecId, sleV2McastIPTvCDRFmtControlLPRecId, sleV2McastIPTvCDRFmtControlLDRecId, sleV2McastIPTvCDRFmtControlJPChTypeFullView, sleV2McastIPTvCDRFmtControlJPChTypePreView, 
				sleV2McastIPTvCDRFmtControlJPChTypePayPerView, sleV2McastIPTvCDRFmtControlJDReasonNoSubscriber, sleV2McastIPTvCDRFmtControlJDReasonNoChannel, sleV2McastIPTvCDRFmtControlJDReasonNotSubscribed, sleV2McastIPTvCDRFmtControlJDReasonOverQuota, 
				sleV2McastIPTvCDRFmtControlJDReasonOverMaxStream, sleV2McastIPTvCDRFmtControlJDReasonOverMaxBw, sleV2McastIPTvCDRFmtControlKJChTypeFullView, sleV2McastIPTvCDRFmtControlKJChTypePreview, sleV2McastIPTvCDRFmtControlKJChTypePayPerView, 
				sleV2McastIPTvCDRFmtControlLPReasonLeaveChannel, sleV2McastIPTvCDRFmtControlLPReasonTimeout, sleV2McastIPTvCDRFmtControlLPReasonRemoveChannel, sleV2McastIPTvCDRFmtControlLPReasonRemoveSubscriber, sleV2McastIPTvCDRFmtControlLDReasonNoSubscriber, 
				sleV2McastIPTvCDRFmtControlLDReasonNoChannel, sleV2McastIPTvCDRFmtControlLDReasonNotSubscriber, sleV2McastIPTvCDRFmtControlLDReasonNotJoined }
			STATUS current
			DESCRIPTION 
				"Description."
			::= { sleV2McastIPTvCDRLogFormatNotification 4 }

		
		sleV2McastIPTvCDRLogFormatReasonChanged NOTIFICATION-TYPE
			OBJECTS { sleV2McastIPTvCDRFmtControlRequest, sleV2McastIPTvCDRFmtControlTimeStamp, sleV2McastIPTvCDRFmtControlReqResult, sleV2McastIPTvCDRFmtControlReasonNoSubscriber, sleV2McastIPTvCDRFmtControlReasonNoChannel, 
				sleV2McastIPTvCDRFmtControlReasonNotSubscribed, sleV2McastIPTvCDRFmtControlReasonOverQuota, sleV2McastIPTvCDRFmtControlReasonOverMaxStream, sleV2McastIPTvCDRFmtControlReasonOverMaxBx, sleV2McastIPTvCDRFmtControlReasonLeaveChannel, 
				sleV2McastIPTvCDRFmtControlReasonTimeout, sleV2McastIPTvCDRFmtControlReasonRemoveChannel, sleV2McastIPTvCDRFmtControlReasonRemoveSubscriber, sleV2McastIPTvCDRFmtControlReasonNotJoined }
			STATUS current
			DESCRIPTION 
				"Description."
			::= { sleV2McastIPTvCDRLogFormatNotification 5 }

		
--  1.3.6.1.4.1.6296.102.12.4
		sleV2McastGroup OBJECT-GROUP
			OBJECTS { sleV2M4RouteGroup, sleV2M4RouteSource, sleV2M4RouteSrcMask, sleV2M4RouteInInterface, sleV2M4RouteUpstreamNeighbor, 
				sleV2M4RouteUpTime, sleV2MRouteExpiryTime, sleV2M4RouteMcProtocol, sleV2M4RouteRtProtocol, sleV2M4RouteRtAddress, 
				sleV2M4RouteRtMask, sleV2M4RouteRtType, sleV2M4RouteOutIfCount, sleV2M4RouteOutInterface, sleV2M4RouteFlags, 
				sleV2M4RouteStsFwdPkts, sleV2M4RouteStsFwdBytes, sleV2M4RouteStsRegSentPkts, sleV2M4RouteNextHopIfIndex, sleV2M4RouteNextHopAddress, 
				sleV2M4RouteNextHopState, sleV2M4RouteNextHopUpTime, sleV2M4RouteNextHopExpiryTime, sleV2M4RouteNextHopProtocol, sleV2M4RouteNextHopClosestMemberHops, 
				sleV2M4RouteNextHopPkts, sleV2M4RouteIfIndex, sleV2M4RouteIfName, sleV2M4RouteIfTtl, sleV2M4RouteIfRateLimit, 
				sleV2M4RouteIfProtocol, sleV2M4RouteIfInMcastOctets, sleV2M4RouteIfOutMcastOctets, sleV2IgmpIfIndex, sleV2IgmpIfActivity, 
				sleV2IgmpIfVersion, sleV2IgmpIfQueryInterval, sleV2IgmpIfQuerierTimeOut, sleV2IgmpIfMaxResponseTime, sleV2IgmpIfLastMembQueryCount, 
				sleV2IgmpIfLastMembQueryIntvl, sleV2IgmpIfFastLeaveGroupList, sleV2IgmpIfQuerierUptime, sleV2IgmpIfQuerierExpireTime, sleV2IgmpIfWrongVersionQueriers, 
				sleV2IgmpIfGroupMembIntvl, sleV2IgmpIfAccessGroup, sleV2IgmpIfRobustness, sleV2IgmpIfJoins, sleV2IgmpIfGroups, 
				sleV2IgmpCacheGroup, sleV2IgmpCacheLastReporter, sleV2IgmpCacheVersion, sleV2IgmpCacheSourceFilterMode, sleV2IgmpCacheExcludeModeExpiryTimer, 
				sleV2IgmpCacheUpTime, sleV2IgmpCacheExpiryTime, sleV2IgmpCacheVersion1HostTimer, sleV2IgmpCacheVersion2HostTimer, sleV2IgmpSsmMapGroup, 
				sleV2IgmpSsmMapSource, sleV2IgmpSsmMapType, sleV2IgmpSsmMapExpire, sleV2Mvr4PortIndex, sleV2Mvr4PortType, 
				sleV2Mvr4GroupAddress, sleV2Mvr4GroupVlanIndex, sleV2Pim4VlanIndex, sleV2Pim4VlanAdminActivity, sleV2Pim4VlanOperActivity, 
				sleV2M4RouteStsWrongIfPkts, sleV2IghVlanIndex, sleV2IghVlanHelperAddress, sleV2IghVlanOperAddress, sleV2IghGroupAddress, 
				sleV2IghGroupSource, sleV2IghGroupPortIndex, sleV2IgmpIfQuerierState, sleV2IgmpIfQuerierAddress, sleV2IgsVlanIndex, 
				sleV2IgsVlanActivity, sleV2IgsVlanVersion, sleV2IgsVlanFastLeave, sleV2IgsVlanFastBlock, sleV2IgsVlanMRtLearningMode, 
				sleV2IgsVlanMRtDynamicPortMap, sleV2IgsVlanMRtStaticPortMap, sleV2IgsVlanReportSuppression, sleV2IgsVlanQuerierActivity, sleV2IgsVlanQueryInterval, 
				sleV2IgfPortIndex, sleV2IgfPortProfileIndex, sleV2IgfPortMaxGroupCount, sleV2IgfPortMaxGroupAction, sleV2IgfpRangeStartAddress, 
				sleV2IgfpRangeEndAddress, sleV2IgsGroupAddress, sleV2IgsGroupPortIndex, sleV2IgsGroupSourceFilterMode, sleV2IgsGroupExcludeModeExpiryTimer, 
				sleV2IgsGroupUpTime, sleV2IgsGroupExpiryTime, sleV2IgsReporterAddress, sleV2IgsReporterExpiryTime, sleV2IgsReporterMac, 
				sleV2IgfProfileIndex, sleV2IgfProfilePermission, sleV2IgsVlanRobustness, sleV2IgsVlanMaxResponseTime, sleV2IgsVlanQuerierTimeOut, 
				sleV2IgsVlanLastMembQueryIntvl, sleV2IgsVlanLastMembQueryCount, sleV2IgsVlanQuerierState, sleV2IgsVlanQuerierVersion, sleV2IgsVlanQuerierAddress, 
				sleV2IgsVlanQuerierPortIndex, sleV2IgsVlanQuerierUptime, sleV2IgsVlanQuerierExpireTime, sleV2IgsVlanTcnFloodActivity, sleV2IgsVlanExplicitTracking, 
				sleV2IgsVlanTxGeneralQueries, sleV2IgsVlanTxSpecialQueries, sleV2IgsVlanTxReportMessages, sleV2IgsVlanTxLeaveMessages, sleV2IgsVlanRxGeneralQueries, 
				sleV2IgsVlanRxSpecialQueries, sleV2IgsVlanRxReportMessages, sleV2IgsVlanRxLeaveMessages, sleV2IgsVlanRxValidMessages, sleV2IgsVlanRxWrongMessages, 
				sleV2IgmpSourceAddress, sleV2IgmpSourceType, sleV2IgsSourceAddress, sleV2IgsSourceType, sleV2IgsSourceUpTime, 
				sleV2IgsSourceExpiryTime, sleV2M4RouteStsRegNackRecvMsg, sleV2M4RouteStsRegAckRecvMsg, sleV2M4RouteStsImmediateSentMsg, sleV2M4RouteStsTimedSentMsg, 
				sleV2M4RouteStsWrongvifSentMsg, sleV2M4RouteStsWholepktSentMsg, sleV2M4RouteStsWrongvifRecvMsg, sleV2M4RouteStsWholepktRecvMsg, sleV2IgsVlanVersionMode, 
				sleV2IgfProfileName, sleV2IgmpIfMRouteProxyIfIndex, sleV2IgmpIfMRouteProxyStatus, sleV2IgmpIfStartupQueryInterval, sleV2IgmpIfUnsolictedReportInterval, 
				sleV2IgsPortIndex, sleV2IgsPortFastLeave, sleV2IgmpIfExceptGroup, sleV2IgmpIfLimit, sleV2IgmpIfLeaves, 
				sleV2IgsStatsRxTopoNotifications, sleV2IgsStatsv3ToIncluded, sleV2IgsStatsv3ToExcluded, sleV2IgsStatsRxFilteredPackets, sleV2IgsStatsv3Allows, 
				sleV2IgsStatsv3Blocks, sleV2IgsStatsv3IsIncluded, sleV2IgsStatsv3IsExcluded, sleV2IgsStatsRxLeaves, sleV2IgsStatsRxValidPackets, 
				sleV2IgsStatsRxInvalidPackets, sleV2IgsStatsRxOtherPackets, sleV2IgsStatsRxMacGeneralQueries, sleV2IgsStatsTxLeaves, sleV2IgsStatsRxGeneralQueries, 
				sleV2IgsStatsRxGroupSpecificQueies, sleV2IgsStatsRxReports, sleV2IgsStatsPortIndex, sleV2IgsStatsTxGeneralQueries, sleV2IgsStatsTxGroupSpecificQueies, 
				sleV2IgsStatsTxReports, sleV2IgmpSRunningState, sleV2IgmpSRunningLastLeaved, sleV2IgmpSRunningLastJoined, sleV2IgmpSRunningTotalUptime, 
				sleV2IgmpSRunningSourceAddr, sleV2IgmpSRunningGroupAddr, sleV2IgmpGRunningState, sleV2IgmpGRunningLastLeaved, sleV2IgmpGRunningLastJoined, 
				sleV2IgmpGRunningTotalUptime, sleV2IgmpGRunningGroupAddr, sleV2M4RouteInfoActivity, sleV2M4RouteInfoLimit, sleV2M4RouteInfoThreshold, 
				sleV2M4RouteInfoUnknownFlood, sleV2M4RouteInfoEntryCount, sleV2M4RouteInfoNocacheRecvMsg, sleV2M4RouteInfoWholepktRecvMsg, sleV2M4RouteInfoWrongvifRecvMsg, 
				sleV2M4RouteInfoNocacheSentMsg, sleV2M4RouteInfoWholepktSentMsg, sleV2M4RouteInfoWrongvifSentMsg, sleV2M4RouteInfoControlRequest, sleV2M4RouteInfoControlStatus, 
				sleV2M4RouteInfoControlTimer, sleV2M4RouteInfoControlTimeStamp, sleV2M4RouteInfoControlReqResult, sleV2M4RouteInfoControlActivity, sleV2M4RouteInfoControlLimit, 
				sleV2M4RouteInfoControlThreshold, sleV2M4RouteInfoControlUnknownFlood, sleV2M4RouteControlRequest, sleV2M4RouteControlStatus, sleV2M4RouteControlTimer, 
				sleV2M4RouteControlTimeStamp, sleV2M4RouteControlReqResult, sleV2M4RouteControlGroup, sleV2M4RouteControlSource, sleV2M4RouteControlSrcMask, 
				sleV2M4RouteControlMcastProtocol, sleV2M4RouteIfControlRequest, sleV2M4RouteIfControlStatus, sleV2M4RouteIfControlTimer, sleV2M4RouteIfControlTimeStamp, 
				sleV2M4RouteIfControlReqResult, sleV2M4RouteIfControlIndex, sleV2M4RouteIfControlTtl, sleV2M4RouteIfControlRateLimit, sleV2IgmpInfoSnoopActivity, 
				sleV2IgmpInfoSnoopVersion, sleV2IgmpInfoSnoopVersionMode, sleV2IgmpInfoSnoopFastLeave, sleV2IgmpInfoSnoopFastBlock, sleV2IgmpInfoSnoopReportSuppression, 
				sleV2IgmpInfoSnoopQuerierActivity, sleV2IgmpInfoSnoopQueryInterval, sleV2IgmpInfoSnoopMaxResponseTime, sleV2IgmpInfoSnoopLastMembQueryIntvl, sleV2IgmpInfoTcnFloodActivity, 
				sleV2IgmpInfoTcnQuerySolicitActivity, sleV2IgmpInfoTcnFloodQueryCount, sleV2IgmpInfoExplicitTracking, sleV2IgmpInfoMvrActivity, sleV2IgmpInfoTcnQuerySolicitAddress, 
				sleV2IgmpInfoControlRequest, sleV2IgmpInfoControlStatus, sleV2IgmpInfoControlTimer, sleV2IgmpInfoControlTimeStamp, sleV2IgmpInfoControlReqResult, 
				sleV2IgmpInfoControlSnoopActivity, sleV2IgmpInfoControlSnoopVersion, sleV2IgmpInfoControlSnoopFastLeave, sleV2IgmpInfoControlSnoopFastBlock, sleV2IgmpInfoControlSnoopReportSuppression, 
				sleV2IgmpInfoControlSnoopQuerierActivity, sleV2IgmpInfoControlSnoopQueryInterval, sleV2IgmpInfoControlSnoopMaxResponseTime, sleV2IgmpInfoControlSnoopLastMembQueryIntvl, sleV2IgmpInfoControlTcnFloodActivity, 
				sleV2IgmpInfoControlTcnQuerySolicitActivity, sleV2IgmpInfoControlTcnFloodQueryCount, sleV2IgmpInfoControlExplicitTracking, sleV2IgmpInfoControlMvrActivity, sleV2IgmpInfoControlTcnQuerySolicitAddress, 
				sleV2IghVlanControlRequest, sleV2IghVlanControlStatus, sleV2IghVlanControlTimer, sleV2IghVlanControlTimeStamp, sleV2IghVlanControlReqResult, 
				sleV2IghVlanControlIndex, sleV2IghVlanControlHelperAddress, sleV2IghGroupControlRequest, sleV2IghGroupControlStatus, sleV2IghGroupControlTimer, 
				sleV2IghGroupControlTimeStamp, sleV2IghGroupControlReqResult, sleV2IghGroupControlVlanIndex, sleV2IghGroupControlAddress, sleV2IghGroupControlSource, 
				sleV2IghGroupControlPortIndex, sleV2IgmpSsmMapControlRequest, sleV2IgmpSsmMapControlStatus, sleV2IgmpSsmMapControlTimer, sleV2IgmpSsmMapControlTimeStamp, 
				sleV2IgmpSsmMapControlReqResult, sleV2IgmpSsmMapControlGroup, sleV2IgmpSsmMapControlSource, sleV2IgmpIfControlRequest, sleV2IgmpIfControlStatus, 
				sleV2IgmpIfControlTimer, sleV2IgmpIfControlTimeStamp, sleV2IgmpIfControlReqResult, sleV2IgmpIfControlIndex, sleV2IgmpIfControlActivity, 
				sleV2IgmpIfControlVersion, sleV2IgmpIfControlQueryInterval, sleV2IgmpIfControlQuerierTimeOut, sleV2IgmpIfControlMaxResponseTime, sleV2IgmpIfControlLastMembQueryCount, 
				sleV2IgmpIfControlLastMembQueryIntvl, sleV2IgmpIfControlFastLeaveGroupList, sleV2IgmpIfControlAccessGroup, sleV2IgmpIfControlRobustness, sleV2IgmpIfControlMRouteProxyIfIndex, 
				sleV2IgmpIfControlProxyStatus, sleV2IgmpIfControlStartupQueryInterval, sleV2IgmpIfControlUnsolictedReportInterval, sleV2IgmpIfControlLimit, sleV2IgmpIfControlExceptGroup, 
				sleV2IgmpSourceControlRequest, sleV2IgmpSourceControlStatus, sleV2IgmpSourceControlTimer, sleV2IgmpSourceControlTimeStamp, sleV2IgmpSourceControlReqResult, 
				sleV2IgmpSourceControlIfIndex, sleV2IgmpSourceControlGroup, sleV2IgmpSourceControlAddress, sleV2IgmpGStateControlRequest, sleV2IgmpGStateControlStatus, 
				sleV2IgmpGStateControlTimer, sleV2IgmpGStateControlTimeStamp, sleV2IgmpGStateControlRequestResult, sleV2IgmpGStateControlGroupAddr, sleV2IgmpGStateControlSourceAddr, 
				sleV2IgsVlanControlRequest, sleV2IgsVlanControlStatus, sleV2IgsVlanControlTimer, sleV2IgsVlanControlTimeStamp, sleV2IgsVlanControlReqResult, 
				sleV2IgsVlanControlIndex, sleV2IgsVlanControlActivity, sleV2IgsVlanControlVersion, sleV2IgsVlanControlFastLeave, sleV2IgsVlanControlFastBlock, 
				sleV2IgsVlanControlMRtLearningMode, sleV2IgsVlanControlMRtStaticPortMap, sleV2IgsVlanControlReportSuppression, sleV2IgsVlanControlQuerierActivity, sleV2IgsVlanControlQueryInterval, 
				sleV2IgsVlanControlRobustness, sleV2IgsVlanControlMaxResponseTime, sleV2IgsVlanControlQuerierTimeOut, sleV2IgsVlanControlLastMembQueryIntvl, sleV2IgsVlanControlTcnFloodActivity, 
				sleV2IgsVlanControlExplicitTracking, sleV2IgsSourceControlRequest, sleV2IgsSourceControlStatus, sleV2IgsSourceControlTimer, sleV2IgsSourceControlTimeStamp, 
				sleV2IgsSourceControlReqResult, sleV2IgsSourceControlVlanIndex, sleV2IgsSourceControlGroup, sleV2IgsSourceControlPortIndex, sleV2IgsSourceControlAddress, 
				sleV2IgsPortControlRequest, sleV2IgsPortControlStatus, sleV2IgsPortControlTimer, sleV2IgsPortControlTimeStamp, sleV2IgsPortControlReqResult, 
				sleV2IgsPortControlIndex, sleV2IgsPortControlFastLeave, sleV2IgsStatsControlRequest, sleV2IgsStatsControlStatus, sleV2IgsStatsControlControlTimer, 
				sleV2IgsStatsControlTimeStamp, sleV2IgsStatsControlReqResult, sleV2IgsStatsControlIndex, sleV2IgfProfileControlRequest, sleV2IgfProfileControlStatus, 
				sleV2IgfProfileControlTimer, sleV2IgfProfileControlTimeStamp, sleV2IgfProfileControlReqResult, sleV2IgfProfileControlIndex, sleV2IgfProfileControlPermission, 
				sleV2IgfProfileControlName, sleV2IgfpRangeControlRequest, sleV2IgfpRangeControlStatus, sleV2IgfpRangeControlTimer, sleV2IgfpRangeControlTimeStamp, 
				sleV2IgfpRangeControlReqResult, sleV2IgfpRangeControlProfileIndex, sleV2IgfpRangeControlStartAddress, sleV2IgfpRangeControlEndAddress, sleV2IgfPortControlRequest, 
				sleV2IgfPortControlStatus, sleV2IgfPortControlTimer, sleV2IgfPortControlTimeStamp, sleV2IgfPortControlReqResult, sleV2IgfPortControlIndex, 
				sleV2IgfPortControlProfileIndex, sleV2IgfPortControlMaxGroupCount, sleV2IgfPortControlMaxGroupAction, sleV2Mvr4PortControlRequest, sleV2Mvr4PortControlStatus, 
				sleV2Mvr4PortControlTimer, sleV2Mvr4PortControlTimeStamp, sleV2Mvr4PortControlReqResult, sleV2Mvr4PortControlIndex, sleV2Mvr4PortControlType, 
				sleV2Mvr4GroupControlRequest, sleV2Mvr4GroupControlStatus, sleV2Mvr4GroupControlTimer, sleV2Mvr4GroupControlTimeStamp, sleV2Mvr4GroupControlReqResult, 
				sleV2Mvr4GroupControlAddress, sleV2Mvr4GroupControlVlanIndex, sleV2Pim4InfoSnoopActivity, sleV2Pim4InfoControlRequest, sleV2Pim4InfoControlStatus, 
				sleV2Pim4InfoControlTimer, sleV2Pim4InfoControlTimeStamp, sleV2Pim4InfoControlReqResult, sleV2Pim4InfoControlSnoopActivity, sleV2Pim4VlanControlRequest, 
				sleV2Pim4VlanControlStatus, sleV2Pim4VlanControlTimer, sleV2Pim4VlanControlTimeStamp, sleV2Pim4VlanControlReqResult, sleV2Pim4VlanControlIndex, 
				sleV2Pim4VlanControlAdminActivity, sleV2IgmpInfoTcnQueryInterval, sleV2IgmpInfoControlTcnQueryInterval, sleV2IgsPortControlExplicitTrackingMaxHosts, sleV2IgsPortExplicitTrackingMaxHosts, 
				sleV2IgsReporterMode, sleV2IgsReporterVersion, sleV2IgmpProxyIfIndex, sleV2IgmpProxyIfMRouteIfIndex, sleV2IgmpProxyIfControlRequest, 
				sleV2IgmpProxyIfControlStatus, sleV2IgmpProxyIfControlTimer, sleV2IgmpProxyIfControlTimeStamp, sleV2IgmpProxyIfControlReqResult, sleV2IgmpProxyIfControlIndex, 
				sleV2IgmpProxyIfControlMrouteIfIndex, sleV2IgsSourceSsmMapped, sleV2IgmpSourceUpTime, sleV2IgmpSourceExpiryTime, sleV2IgmpSourceSsmMapped, 
				sleV2IgmpProxyIfService, sleV2IgmpProxyIfMRouteQuerySIpMode, sleV2IgmpProxyIfMRouteQuerySIpAddr, sleV2IgmpProxyIfServiceSIpMode, sleV2IgmpProxyIfServiceSIpAddr, 
				sleV2IgfPortDhcpSnoopBindingPermission, sleV2IgfPortControlDhcpSnoopBindingPermission, sleV2IgmpIfVerifySrcIp, sleV2IgmpIfControlVerifySrcIp, sleV2IgmpInfoVerifyTTL, 
				sleV2IgmpInfoControlVerifyTTL, sleV2IgmpProxyIfControlService, sleV2IgmpProxyIfControlMrouteQuerySIpMode, sleV2IgmpProxyIfControlServiceSIpMode, sleV2IgfPortPacketType, 
				sleV2IgfPortControlPacketType, sleV2McastIPTvSubscriberDescription, sleV2McastIPTvSubscriberControlDescription, sleV2IgmpProxyIfServicePriority, sleV2IgmpProxyMultipath, 
				sleV2IgmpProxyInfoControlRequest, sleV2IgmpProxyInfoControlStatus, sleV2IgmpProxyInfoControlTimer, sleV2IgmpProxyInfoControlTimeStamp, sleV2IgmpProxyInfoControlReqResult, 
				sleV2IgmpProxyInfoControlMultipath, sleV2IgsSourceVId, sleV2IgsSourcenGrpAddr, sleV2IgsSourcePort, sleV2IgsVlanStatsVlanIndex, 
				sleV2IgsVlanStatsTxGeneralQueries, sleV2IgsVlanStatsTxGroupSpecificQueies, sleV2IgsVlanStatsTxReports, sleV2IgsVlanStatsTxLeaves, sleV2IgsVlanStatsRxGeneralQueries, 
				sleV2IgsVlanStatsRxGroupSpecificQueies, sleV2IgsVlanStatsRxReports, sleV2IgsVlanStatsRxLeaves, sleV2IgsVlanStatsRxValidPackets, sleV2IgsVlanStatsRxInvalidPackets, 
				sleV2IgsVlanStatsRxOtherPackets, sleV2IgsVlanStatsRxMacGeneralQueries, sleV2IgsVlanStatsRxTopoNotifications, sleV2IgsVlanStatsv3Allows, sleV2IgsVlanStatsv3Blocks, 
				sleV2IgsVlanStatsv3IsIncluded, sleV2IgsVlanStatsv3IsExcluded, sleV2IgsVlanStatsv3ToIncluded, sleV2IgsVlanStatsv3ToExcluded, sleV2IgsVlanStatsRxFilteredPackets, 
				sleV2IgsVlanStatsControlRequest, sleV2IgsVlanStatsControlStatus, sleV2IgsVlanStatsControlControlTimer, sleV2IgsVlanStatsControlTimeStamp, sleV2IgsVlanStatsControlReqResult, 
				sleV2IgsVlanStatsControlIndex, sleV2IgsPortMrouter, sleV2IgsPortControlMrouter, sleV2IgmpInfoSnoopTcnQueryGeneralStatus, sleV2IgmpInfoSnoopTcnQueryGeneralMaxResponseTime, 
				sleV2IgmpInfoControlSnoopTcnQueryGeneralStatus, sleV2IgmpInfoControlSnoopTcnQueryGeneralMaxResponseTime, sleV2IgsGroupPortInfo, sleV2IgsSourcePortInfo, sleV2IgsReporterPortInfo, 
				sleV2IgsVlanStatsTotalRxReports, sleV2IgsVlanStatsUnsuccessRxReports, sleV2IgmpinfoSnoopMrouterCpu, sleV2IgmpinfoControlSnoopMrouterCpu, sleV2IgmpInfoMaxGroupSystemCnt, 
				sleV2IgmpInfoControlMaxGroupSystemCnt, sleV2IgmpInfoSnoopMRtLearningMode, sleV2IgmpInfoControlSnoopMRtLearningMode, sleV2IgmpInfoSnoopQuerierAddress, sleV2IgmpInfoControlSnoopQuerierAddress, 
				sleV2IgsVlanControlQuerierAddress, sleV2IgsMaxBWLimitSystemMax, sleV2IgsMaxBWLimitChannelDefault, sleV2IgsMaxBWLimitPortIndex, sleV2IgsMaxBWLimitPortMax, 
				sleV2IgsMaxBWLimitChannelStart, sleV2IgsMaxBWLimitChannelEnd, sleV2IgsMaxBWLimitChannelBW, sleV2IgsMaxBWLimitControlRequest, sleV2IgsMaxBWLimitControlStatus, 
				sleV2IgsMaxBWLimitControlTimer, sleV2IgsMaxBWLimitControlTimeStamp, sleV2IgsMaxBWLimitControlReqResult, sleV2IgsMaxBWLimitControlSystemMax, sleV2IgsMaxBWLimitControlChannelDefault, 
				sleV2IgsMaxBWLimitControlPortIndex, sleV2IgsMaxBWLimitControlPortMax, sleV2IgsMaxBWLimitControlChannelStart, sleV2IgsMaxBWLimitControlChannelEnd, sleV2IgsMaxBWLimitControlChannelBW, 
				sleV2IgsMaxBWLimitPortCurrentBW, sleV2IgsMaxBWLimitSystemCurrentBw, sleV2IgmpProxyIfControlServiceSIpAddr, sleV2M4RoutInfoIpMrouteJoinedCount, sleV2IgmpInfoSnoopExplicitTrackingMacBased, 
				sleV2IgmpInfoControlSnoopExplicitTrackingMacBased, sleV2IghJoinAddress, sleV2IghJoinSource, sleV2IghJoinPortIndex, sleV2IghJoinReporter, 
				sleV2IghJoinControlRequest, sleV2IghJoinControlStatus, sleV2IghJoinControlTimer, sleV2IghJoinControlTimeStamp, sleV2IghJoinControlReqResult, 
				sleV2IghJoinControlVlanIndex, sleV2IghJoinControlAddress, sleV2IghJoinControlSource, sleV2IghJoinControlPortIndex, sleV2IghJoinControlReporter, 
				sleV2IghJoinProfilePortIndex, sleV2IghJoinProfileId, sleV2IghJoinProfileReporter, sleV2IghJoinProfileControlRequest, sleV2IghJoinProfileControlStatus, 
				sleV2IghJoinProfileControlTimer, sleV2IghJoinProfileControlTimeStamp, sleV2IghJoinProfileControlReqResult, sleV2IghJoinProfileControlVlanIndex, sleV2IghJoinProfileControlPortIndex, 
				sleV2IghJoinProfileControlId, sleV2IghJoinProfileControlReporter, sleV2IghGroupProfilePortIndex, sleV2IghGroupProfileId, sleV2IghGroupProfileControlRequest, 
				sleV2IghGroupProfileControlStatus, sleV2IghGroupProfileControlTimer, sleV2IghGroupProfileControlTimeStamp, sleV2IghGroupProfileControlReqResult, sleV2IghGroupProfileControlVlanIndex, 
				sleV2IghGroupProfileControlPortIndex, sleV2IghGroupProfileControlId, sleV2IgsPortExplicitTrackingMacBased, sleV2IgsPortDot1qSelection, sleV2IgsPortControlExplicitTrackingMacBased, 
				sleV2IgsPortControlDot1qSelection, sleV2IgmpCounterInfoGroupCount, sleV2IgmpCounterInfoSnoopingCount, sleV2McastIPTvInfoCacState, sleV2McastIPTvInfoPackageLimit, 
				sleV2McastIPTvInfoPreviewProfileLimit, sleV2McastIPTvInfoChannelLimit, sleV2McastIPTvInfoCacProfileLimit, sleV2McastIPTvInfoSubscriberLimit, sleV2McastIPTvInfoSubscriberHistoryLimit, 
				sleV2McastIPTvInfoFullviewRecogTime, sleV2McastIPTvInfoControlRequest, sleV2McastIPTvInfoControlStatus, sleV2McastIPTvInfoControlTimer, sleV2McastIPTvInfoControlTimeStamp, 
				sleV2McastIPTvInfoControlReqResult, sleV2McastIPTvInfoControlCacState, sleV2McastIPTvInfoControlPackageLimit, sleV2McastIPTvInfoControlPreviewProfileLimit, sleV2McastIPTvInfoControlChannelLimit, 
				sleV2McastIPTvInfoControlCacProfileLimit, sleV2McastIPTvInfoControlSubscriberLimit, sleV2McastIPTvInfoContorlSubscriberHistoryLimit, sleV2McastIPTvInfoControlFullviewRecogTime, sleV2McastIPTvPackageId, 
				sleV2McastIPTvPackageDescription, sleV2McastIPTvPackagePreviewChannelCnt, sleV2McastIPTvPackageFullviewChannelCnt, sleV2McastIPTvPackageChannelId, sleV2McastIPTvPackageChannelEntitlement, 
				sleV2McastIPTvPackageControlRequest, sleV2McastIPTvPackageControlStatus, sleV2McastIPTvPackageControlTimer, sleV2McastIPTvPackageControlTimeStamp, sleV2McastIPTvPackageControlReqResult, 
				sleV2McastIPTvPackageControlId, sleV2McastIPTvPackageControlDescription, sleV2McastIPTvPackageControlPreviewChannelCnt, sleV2McastIPTvPackageControlPreviewChannelList, sleV2McastIPTvPackageControlFullviewChannelCnt, 
				sleV2McastIPTvPackageControlFullviewChannelList, sleV2McastIPTvPreviewProfileId, sleV2McastIPTvPreviewProfileMaxDuration, sleV2McastIPTvPreviewProfileMaxPreviews, sleV2McastIPTvPreviewProfileBlackoutDuration, 
				sleV2McastIPTvPreviewProfileRecognitionTime, sleV2McastIPTvPreviewProfileResetTimePeriod, sleV2McastIPTvPreviewProfileResetTime, sleV2McastIPTvPreviewProfileControlRequest, sleV2McastIPTvPreviewProfileControlStatus, 
				sleV2McastIPTvPreviewProfileControlTimer, sleV2McastIPTvPreviewProfileControlTimeStamp, sleV2McastIPTvPreviewProfileControlReqResult, sleV2McastIPTvPreviewProfileControlId, sleV2McastIPTvPreviewProfileControlMaxDuration, 
				sleV2McastIPTvPreviewProfileControlMaxPreviews, sleV2McastIPTvPreviewProfileControlBlackoutDuration, sleV2McastIPTvPreviewProfileControlRecognitionTime, sleV2McastIPTvPreviewProfileControlResetTimePeriod, sleV2McastIPTvPreviewProfileControlResetTime, 
				sleV2McastIPTvChannelId, sleV2McastIPTvChannelSourceAddress, sleV2McastIPTvChannelGroupAddress, sleV2McastIPTvChannelBandwidth, sleV2McastIPTvChannelPreviewProfileId, 
				sleV2McastIPTvChannelCacGroupId, sleV2McastIPTvChannelDescription, sleV2McastIPTvChannelPackageDescription, sleV2McastIPTvChannelControlRequest, sleV2McastIPTvChannelControlStatus, 
				sleV2McastIPTvChannelControlTimer, sleV2McastIPTvChannelControlTimeStamp, sleV2McastIPTvChannelControlReqResult, sleV2McastIPTvChannelControlId, sleV2McastIPTvChannelControlSourceAddress, 
				sleV2McastIPTvChannelControlGroupAddress, sleV2McastIPTvChannelControlBandwidth, sleV2McastIPTvChannelControlPreviewProfileId, sleV2McastIPTvChannelControlCacGroupId, sleV2McastIPTvChannelControlDescription, 
				sleV2McastIPTvChannelCurrentVlanId, sleV2McastIPTvChannelCurrentPortId, sleV2McastIPTvChannelCurrentVlanPortChannelId, sleV2McastIPTvChannelCurrentVlanPortJoinedTime, sleV2McastIPTvChannelCurrentSubscriberChannelId, 
				sleV2McastIPTvChannelCurrentSubscriberJoinedTime, sleV2McastIPTvChannelCurrentSubscriberJoinDurationTime, sleV2McastIPTvCacProfileId, sleV2McastIPTvCacProfileMaxChannel, sleV2McastIPTvCacProfileMaxBandwidth, 
				sleV2McastIPTvCacProfileCacGroupCnt, sleV2McastIPTvCacProfileDescription, sleV2McastIPTvCacProfileGroupId, sleV2McastIPTvCacProfileGroupMaxChanNum, sleV2McastIPTvCacProfileControlRequest, 
				sleV2McastIPTvCacProfileControlStatus, sleV2McastIPTvCacProfileControlTimer, sleV2McastIPTvCacProfileControlTimeStamp, sleV2McastIPTvCacProfileControlReqResult, sleV2McastIPTvCacProfileControlId, 
				sleV2McastIPTvCacProfileControlMaxStream, sleV2McastIPTvCacProfileControlMaxBandwidth, sleV2McastIPTvCacProfileControlCacGroupCnt, sleV2McastIPTvCacProfileControlCacGroupList, sleV2McastIPTvCacProfileControlCacGroupMaxChanNumList, 
				sleV2McastIPTvCacProfileControlDescription, sleV2McastIPTvSubscriberId, sleV2McastIPTvSubscriberPortType, sleV2McastIPTvSubscriberSlotId, sleV2McastIPTvSubscriberPortId, 
				sleV2McastIPTvSubscriberCTag, sleV2McastIPTvSubscriberIpAddr, sleV2McastIPTvSubscriberStatus, sleV2McastIPTvSubscriberCacProfileId, sleV2McastIPTvSubscriberPackageCnt, 
				sleV2McastIPTvSubscriberPackageId, sleV2McastIPTvSubscriberPackageStart, sleV2McastIPTvSubscriberPackageEnd, sleV2McastIPTvSubscriberControlRequest, sleV2McastIPTvSubscriberControlStatus, 
				sleV2McastIPTvSubscriberControlTimer, sleV2McastIPTvSubscriberControlTimeStamp, sleV2McastIPTvSubscriberControlReqResult, sleV2McastIPTvSubscriberControlId, sleV2McastIPTvSubscriberControlPortType, 
				sleV2McastIPTvSubscriberControlSlotId, sleV2McastIPTvSubscriberControlPortId, sleV2McastIPTvSubscriberControlCTag, sleV2McastIPTvSubscriberControlIpAddr, sleV2McastIPTvSubscriberControlCacProfileId, 
				sleV2McastIPTvSubscriberControlPackageCnt, sleV2McastIPTvSubscriberControlPackageList, sleV2McastIPTvSubscriberControlPackageTimeList, sleV2McastIPTvSubscriberHistoryIndex, sleV2McastIPTvSubscriberHistoryJoinedChannelId, 
				sleV2McastIPTvSubscriberHistoryJoinedTime, sleV2McastIPTvSubscriberHistoryControlRequest, sleV2McastIPTvSubscriberHistoryControlStatus, sleV2McastIPTvSubscriberHistoryControlTimer, sleV2McastIPTvSubscriberHistoryControlTimeStamp, 
				sleV2McastIPTvSubscriberHistoryControlReqResult, sleV2McastIPTvSubscriberHistoryControlId, sleV2McastIPTvCDRInfoStatus, sleV2McastIPTvCDRInfoKeepJoinInterval, sleV2McastIPTvCDRInfoLogFileName, 
				sleV2McastIPTvCDRInfoLogSize, sleV2McastIPTvCDRInfoExportTimeThreshold, sleV2McastIPTvCDRInfoExportTimeBegin, sleV2McastIPTvCDRInfoExportAmountThreshold, sleV2McastIPTvCDRInfoSyslogPriority, 
				sleV2McastIPTvCDRInfoANInfo, sleV2McastIPTvCDRInfoControlRequest, sleV2McastIPTvCDRInfoControlStatus, sleV2McastIPTvCDRInfoControlTimer, sleV2McastIPTvCDRInfoControlTimeStamp, 
				sleV2McastIPTvCDRInfoControlReqResult, sleV2McastIPTvCDRInfoContorlStatus, sleV2McastIPTvCDRInfoContorlKeepJoinInterval, sleV2McastIPTvCDRInfoContorlLogFileName, sleV2McastIPTvCDRInfoControlLogSize, 
				sleV2McastIPTvCDRInfoControlExportTimeThreshold, sleV2McastIPTvCDRInfoControlExportTimeBegin, sleV2McastIPTvCDRInfoControlExportAmountThreshold, sleV2McastIPTvCDRInfoControlSyslogPriority, sleV2McastIPTvCDRInfoControlANInfo, 
				sleV2McastIPTvCDRLogServerId, sleV2McastIPTvCDRLogServerIpAddress, sleV2McastIPTvCDRLogServerPort, sleV2McastIPTvCDRLogServerMode, sleV2McastIPTvCDRLogServerUserId, 
				sleV2McastIPTvCDRLogServerUserPassword, sleV2McastIPTvCDRLogServerControlRequest, sleV2McastIPTvCDRLogServerControlStatus, sleV2McastIPTvCDRLogServerControlTimer, sleV2McastIPTvCDRLogServerControlTimeStamp, 
				sleV2McastIPTvCDRLogServerControlReqResult, sleV2McastIPTvCDRLogServerControlId, sleV2McastIPTvCDRLogServerControlIpAddress, sleV2McastIPTvCDRLogServerControlPort, sleV2McastIPTvCDRLogServerControlMode, 
				sleV2McastIPTvCDRLogServerControlUserId, sleV2McastIPTvCDRLogServerControlUserPassword, sleV2McastIPTvCDRLogServerControlFileName, sleV2McastIPTvCDRLogStatsTotalCount, sleV2McastIPTvCDRLogStatsJoinCount, 
				sleV2McastIPTvCDRLogStatsKeepJoinedCount, sleV2McastIPTvCDRLogStatsLeaveCount, sleV2McastIPTvCDRLogStatsLastExportDate, sleV2McastIPTvCDRLogStatsLastExportReason, sleV2McastIPTvCDRLogStatsLastExportServerList, 
				sleV2McastIPTvCDRFmtName, sleV2McastIPTvCDRFmtDelimiter, sleV2McastIPTvCDRFmtOrderRecordType, sleV2McastIPTvCDRFmtOrderReason, sleV2McastIPTvCDRFmtOrderLogTime, 
				sleV2McastIPTvCDRFmtOrderAN, sleV2McastIPTvCDRFmtOrderSubscriber, sleV2McastIPTvCDRFmtOrderChannel, sleV2McastIPTvCDRFmtOrderChannelType, sleV2McastIPTvCDRFmtOrderStartTime, 
				sleV2McastIPTvCDRFmtOrderViewingDuration, sleV2McastIPTvCDRFmtJPRecId, sleV2McastIPTvCDRFmtJDRecId, sleV2McastIPTvCDRFmtKJRecId, sleV2McastIPTvCDRFmtLPRecId, 
				sleV2McastIPTvCDRFmtLDRecId, sleV2McastIPTvCDRFmtJPChTypeFullView, sleV2McastIPTvCDRFmtJPChTypePreView, sleV2McastIPTvCDRFmtJPChTypePayPerView, sleV2McastIPTvCDRFmtJDReasonNoSubscriber, 
				sleV2McastIPTvCDRFmtJDReasonNoChannel, sleV2McastIPTvCDRFmtJDReasonNotSubscribed, sleV2McastIPTvCDRFmtJDReasonOverQuota, sleV2McastIPTvCDRFmtJDReasonOverMaxStream, sleV2McastIPTvCDRFmtJDReasonOverMaxBw, 
				sleV2McastIPTvCDRFmtKJChTypeFullView, sleV2McastIPTvCDRFmtKJChTypePreView, sleV2McastIPTvCDRFmtKJChTypePayPerView, sleV2McastIPTvCDRFmtLPReasonLeaveChannel, sleV2McastIPTvCDRFmtLPReasonTimeout, 
				sleV2McastIPTvCDRFmtLPReasonRemoveChannel, sleV2McastIPTvCDRFmtLPReasonRemoveSubscriber, sleV2McastIPTvCDRFmtLDReasonNoSubscriber, sleV2McastIPTvCDRFmtLDReasonNoChannel, sleV2McastIPTvCDRFmtLDReasonNotSubscribed, 
				sleV2McastIPTvCDRFmtLDReasonNotJoined, sleV2McastIPTvCDRFmtReasonNoSubscriber, sleV2McastIPTvCDRFmtReasonNoChannel, sleV2McastIPTvCDRFmtReasonNotSubscribed, sleV2McastIPTvCDRFmtReasonOverQuota, 
				sleV2McastIPTvCDRFmtReasonOverMaxStream, sleV2McastIPTvCDRFmtReasonOverMaxBw, sleV2McastIPTvCDRFmtReasonLeaveChannel, sleV2McastIPTvCDRFmtReasonTimeout, sleV2McastIPTvCDRFmtReasonRemoveChannel, 
				sleV2McastIPTvCDRFmtReasonRemoveSubscriber, sleV2McastIPTvCDRFmtReasonNotJoined, sleV2McastIPTvCDRFmtControlRequest, sleV2McastIPTvCDRFmtControlStatus, sleV2McastIPTvCDRFmtControlTimer, 
				sleV2McastIPTvCDRFmtControlTimeStamp, sleV2McastIPTvCDRFmtControlReqResult, sleV2McastIPTvCDRFmtControlName, sleV2McastIPTvCDRFmtControlDelimiter, sleV2McastIPTvCDRFmtControlOrderRecordType, 
				sleV2McastIPTvCDRFmtControlOrderReason, sleV2McastIPTvCDRFmtControlOrderLogTime, sleV2McastIPTvCDRFmtControlOrderAN, sleV2McastIPTvCDRFmtControlOrderSubscriber, sleV2McastIPTvCDRFmtControlOrderChannel, 
				sleV2McastIPTvCDRFmtControlOrderChannelType, sleV2McastIPTvCDRFmtControlOrderStartTime, sleV2McastIPTvCDRFmtControlOrderViewingDuration, sleV2McastIPTvCDRFmtControlJPRecId, sleV2McastIPTvCDRFmtControlJDRecId, 
				sleV2McastIPTvCDRFmtControlKJRecId, sleV2McastIPTvCDRFmtControlLPRecId, sleV2McastIPTvCDRFmtControlLDRecId, sleV2McastIPTvCDRFmtControlJPChTypeFullView, sleV2McastIPTvCDRFmtControlJPChTypePreView, 
				sleV2McastIPTvCDRFmtControlJPChTypePayPerView, sleV2McastIPTvCDRFmtControlJDReasonNoSubscriber, sleV2McastIPTvCDRFmtControlJDReasonNoChannel, sleV2McastIPTvCDRFmtControlJDReasonNotSubscribed, sleV2McastIPTvCDRFmtControlJDReasonOverQuota, 
				sleV2McastIPTvCDRFmtControlJDReasonOverMaxStream, sleV2McastIPTvCDRFmtControlJDReasonOverMaxBw, sleV2McastIPTvCDRFmtControlKJChTypeFullView, sleV2McastIPTvCDRFmtControlKJChTypePreview, sleV2McastIPTvCDRFmtControlKJChTypePayPerView, 
				sleV2McastIPTvCDRFmtControlLPReasonLeaveChannel, sleV2McastIPTvCDRFmtControlLPReasonTimeout, sleV2McastIPTvCDRFmtControlLPReasonRemoveChannel, sleV2McastIPTvCDRFmtControlLPReasonRemoveSubscriber, sleV2McastIPTvCDRFmtControlLDReasonNoSubscriber, 
				sleV2McastIPTvCDRFmtControlLDReasonNoChannel, sleV2McastIPTvCDRFmtControlLDReasonNotSubscriber, sleV2McastIPTvCDRFmtControlLDReasonNotJoined, sleV2McastIPTvCDRFmtControlReasonNoSubscriber, sleV2McastIPTvCDRFmtControlReasonNoChannel, 
				sleV2McastIPTvCDRFmtControlReasonNotSubscribed, sleV2McastIPTvCDRFmtControlReasonOverQuota, sleV2McastIPTvCDRFmtControlReasonOverMaxStream, sleV2McastIPTvCDRFmtControlReasonOverMaxBx, sleV2McastIPTvCDRFmtControlReasonLeaveChannel, 
				sleV2McastIPTvCDRFmtControlReasonTimeout, sleV2McastIPTvCDRFmtControlReasonRemoveChannel, sleV2McastIPTvCDRFmtControlReasonRemoveSubscriber, sleV2Pim4NeighborAddress, sleV2Pim4NeighborUptime, 
				sleV2Pim4NeighborExpireTime, sleV2Pim4NeighborVersion, sleV2Pim4NeighborDr, sleV2Pim4NeighborDrPriority, sleV2IgmpIfRaOption, 
				sleV2IgmpIfStartupQueryCnt, sleV2IgmpIfControlRaOption, sleV2IgmpIfControlStartupQueryCnt, sleV2Pim4IfVid, sleV2Pim4IfVifIndex, 
				sleV2Pim4IfAddress, sleV2Pim4IfDrAddress, sleV2Pim4IfTriggedHelloPeriod, sleV2Pim4IfFlapCredit, sleV2Pim4IfFlapTotalTimes, 
				sleV2Pim4IfFlapFirstTime, sleV2Pim4IfFlapLastTime, sleV2Pim4IfNextHelloTime, sleV2Pim4IfSparseMode, sleV2Pim4IfSparseModePassive, 
				sleV2Pim4IfQueryHoldtime, sleV2Pim4IfQueryInterval, sleV2Pim4IfDrPriority, sleV2Pim4IfExcludeGenID, sleV2Pim4IfNeighborFilterACL, 
				sleV2Pim4IfGroupFilterACL, sleV2Pim4IfGroupFilterRangeACL, sleV2Pim4IfPropagationDelay, sleV2Pim4IfBsrBorder, sleV2Pim4IfUnicastBsm, 
				sleV2Pim4IfControlRequest, sleV2Pim4IfControlStatus, sleV2Pim4IfControlTimer, sleV2Pim4IfControlTimeStamp, sleV2Pim4IfControlReqResult, 
				sleV2Pim4IfControlVid, sleV2Pim4IfControlSparseMode, sleV2Pim4IfControlSparseModePassive, sleV2Pim4IfControlQueryHoldtime, sleV2Pim4IfControlQueryInterval, 
				sleV2Pim4IfControlDrPriority, sleV2Pim4IfControlExcludeGenID, sleV2Pim4IfControlNeighborFilterACL, sleV2Pim4IfControlGroupFilterACL, sleV2Pim4IfControlGroupFilterRangeACL, 
				sleV2Pim4IfControlPropagationDelay, sleV2Pim4IfControlBsrBorder, sleV2Pim4IfControlUnicastBsm, sleV2Pim4NexthopSourceAddress, sleV2Pim4NexthopGroupAddress, 
				sleV2Pim4NexthopNum, sleV2Pim4NexthopType, sleV2Pim4NexthopAddress, sleV2Pim4NexthopVid, sleV2Pim4NexthopMetric, 
				sleV2Pim4NexthopPref, sleV2Pim4NexthopRefcnt, sleV2Pim4CRPVid, sleV2Pim4CRPACL, sleV2Pim4RPActive, 
				sleV2Pim4CRPInterval, sleV2Pim4CRPPriority, sleV2Pim4CRPNextAdver, sleV2Pim4CRPControlRequest, sleV2Pim4CRPControlStatus, 
				sleV2Pim4CRPControlTimer, sleV2Pim4CRPControlTimeStamp, sleV2Pim4CRPControlReqResult, sleV2Pim4CRPControlVid, sleV2Pim4CRPControlACL, 
				sleV2Pim4CRPControlInterval, sleV2Pim4CRPControlPriority, sleV2Pim4SRPAddr, sleV2Pim4SRPACL, sleV2Pim4SRPOverride, 
				sleV2Pim4SRPControlRequest, sleV2Pim4SRPControlStatus, sleV2Pim4SRPControlTimer, sleV2Pim4SRPControlTimeStamp, sleV2Pim4SRPControlReqResult, 
				sleV2Pim4SRPControlAddr, sleV2Pim4SRPControlACL, sleV2Pim4SRPControlOverride, sleV2Pim4RPSetGroupAddress, sleV2Pim4RPSetGroupMask, 
				sleV2Pim4RPSetRPAddress, sleV2Pim4RPSetSourceAddress, sleV2Pim4RPSetPriority, sleV2Pim4RPSetUptime, sleV2Pim4RPSetExpire, 
				sleV2Pim4MrtXXRPAddress, sleV2Pim4MrtXXRPRPFNbrAddress, sleV2Pim4MrtXXRPRPFVid, sleV2Pim4MrtXXRPUpstreamState, sleV2Pim4MrtXXRPJoined, 
				sleV2Pim4MrtXXRPOutgoing, sleV2Pim4MrtXGGroupAddress, sleV2Pim4MrtXGStatic, sleV2Pim4MrtXGRPAddress, sleV2Pim4MrtXGRPFNbrAddress, 
				sleV2Pim4MrtXGVid, sleV2Pim4MrtXGUpstreamState, sleV2Pim4MrtXGLocal, sleV2Pim4MrtXGJoined, sleV2Pim4MrtXGAssertWinner, 
				sleV2Pim4MrtXGAssertLoser, sleV2Pim4MrtFcrSourceAddress, sleV2Pim4MrtFcrOutgoing, sleV2Pim4MrtFcrKat, sleV2Pim4MrtFcrPktCnt, 
				sleV2Pim4MrtSGSourceAddress, sleV2Pim4MrtSGGroupAddress, sleV2Pim4MrtSGKat, sleV2Pim4MrtSGRPFNbrAddress, sleV2Pim4MrtSGRPFVid, 
				sleV2Pim4MrtSGSTPBit, sleV2Pim4MrtSGUpstreamState, sleV2Pim4MrtSGLocal, sleV2Pim4MrtSGJoined, sleV2Pim4MrtSGOutgoing, 
				sleV2Pim4MrtSGAssertWinner, sleV2Pim4MrtSGAssertLoser, sleV2Pim4MrtSGRPTSourceAddress, sleV2Pim4MrtSGRPTGroupAddress, sleV2Pim4MrtSGRPTRPAddress, 
				sleV2Pim4MrtSGRPTRPFNbrAddress, sleV2Pim4MrtSGRPTRPFVid, sleV2Pim4MrtSGRPTUpstreamState, sleV2Pim4MrtSGRPTLocal, sleV2Pim4MrtSGRPTPruned, 
				sleV2Pim4MrtSGRPTOutgoing, sleV2Pim4StaticGroupStart, sleV2Pim4StaticGroupEnd, sleV2Pim4StaticGroupControlRequest, sleV2Pim4StaticGroupControlStatus, 
				sleV2Pim4StaticGroupControlTimer, sleV2Pim4StaticGroupControlTimeStamp, sleV2Pim4StaticGroupControlReqResult, sleV2Pim4StaticGroupControlVid, sleV2Pim4StaticGroupControlStart, 
				sleV2Pim4StaticGroupControlEnd, sleV2IgmpInfoSsmMapActive, sleV2IgmpInfoLimit, sleV2IgmpInfoLimitExcept, sleV2IgmpInfoControlSsmMapActive, 
				sleV2IgmpInfoControlLimit, sleV2IgmpInfoControlLimitExcept, sleV2IgmpIfOfflink, sleV2IgmpIfControlOfflink, sleV2IgmpStaticGrpGroup, 
				sleV2IgmpStaticGrpSource, sleV2IgmpStaticGrpSsm, sleV2IgmpStaticGrpControlRequest, sleV2IgmpStaticGrpControlStatus, sleV2IgmpStaticGrpControlTimer, 
				sleV2IgmpIStaticGrpControlTimeStamp, sleV2IgmpStaticGrpControlReqResult, sleV2IgmpStaticGrpControlIndex, sleV2IgmpStaticGrpControlGroup, sleV2IgmpStaticGrpControlSource, 
				sleV2IgmpStaticGrpControlSsm, sleV2IgmpSsmMapStaticAcl, sleV2IgmpSsmMapStaticSource, sleV2IgmpSsmMapStaticControlRequest, sleV2IgmpSsmMapStaticControlStatus, 
				sleV2IgmpSsmMapStaticControlTimer, sleV2IgmpSsmMapStaticControlTimeStamp, sleV2IgmpSsmMapStaticControlReqResult, sleV2IgmpSsmMapStaticControlAcl, sleV2IgmpSsmMapStaticControlSource, 
				sleV2McastIPTvCDRFmtControlReasonNotJoined, sleV2IgsMaxBWLimitControlPortEnd, sleV2Pim4InfoMultiPath, sleV2Pim4InfoMessageInterval, sleV2Pim4InfoSPTThreshold, 
				sleV2Pim4InfoSPTThresholdACL, sleV2Pim4InfoSSMDefault, sleV2Pim4InfoSSMRangeACL, sleV2Pim4InfoCRPCiscoPrefix, sleV2Pim4InfoIgnoreRPSetPriority, 
				sleV2Pim4InfoBSRCandidateInterface, sleV2Pim4InfoBSRCandidateHash, sleV2Pim4InfoBSRCandidatePriority, sleV2Pim4InfoBSRRole, sleV2Pim4InfoBSRStatus, 
				sleV2Pim4InfoBSRUptime, sleV2Pim4InfoRegisterRateLimit, sleV2Pim4InfoRegisterSourceIPAddr, sleV2Pim4InfoRegisterSourceInterface, sleV2Pim4InfoRegisterRPReachability, 
				sleV2Pim4InfoRegisterSuppression, sleV2Pim4InfoAcceptRegisterACL, sleV2Pim4InfoRPRegisterKAT, sleV2Pim4InfoCiscoRegisterChecksum, sleV2Pim4InfoCiscoRegisterChecksumACL, 
				sleV2Pim4InfoVIFFlapDiscredit, sleV2Pim4InfoVIFFlapDiscreditUnit, sleV2Pim4InfoVIFFlapDiscreditHalfTime, sleV2Pim4InfoControlMultipath, sleV2Pim4InfoControlMessageInterval, 
				sleV2Pim4InfoControlSPTThreshold, sleV2Pim4InfoControlSPTThresholdACL, sleV2Pim4InfoControlSSMDefault, sleV2Pim4InfoControlSSMRangeACL, sleV2Pim4InfoControlCRPCiscoPrefix, 
				sleV2Pim4InfoControlIgnoreRPSetPriority, sleV2Pim4InfoControlBSRCandidateInterface, sleV2Pim4InfoControlBSRCnadidateHash, sleV2Pim4InfoControlBSRCandidatePriority, sleV2Pim4InfoControlRegisterRateLimit, 
				sleV2Pim4InfoControlRegisterSourceIPAddr, sleV2Pim4InfoControlRegisterSourceInterface, sleV2Pim4InfoControlRegisterRPReachability, sleV2Pim4InfoControlRegisterSuppression, sleV2Pim4InfoControlAcceptRegisterACL, 
				sleV2Pim4InfoControlRPRegisterKAT, sleV2Pim4InfoControlCiscoRegisterChecksum, sleV2Pim4InfoControlCiscoRegisterChecksumACL, sleV2Pim4InfoControlVIFFlapDiscredit, sleV2Pim4InfoControlVIFFlapDiscreditUnit, 
				sleV2Pim4InfoControlVIFFlapDiscreditHalfTime, sleV2Pim4InfoControlGroup, sleV2Pim4InfoControlSource, sleV2Pim4InfoControlClearVIF, sleV2M6RouteInfoActive, 
				sleV2M6RouteInfoLimit, sleV2M6RouteInfoThreshold, sleV2M6RouteInfoUnknownFlood, sleV2M6RouteInfoUnknownFloodPMap, sleV2M6RouteInfoNextPollTime, 
				sleV2M6RouteInfoNumNocacheRecv, sleV2M6RouteInfoNumWrongMIFRecv, sleV2M6RouteInfoNumWholePktRecv, sleV2M6RouteInfoNumNocacheSent, sleV2M6RouteInfoNumWrongMIFSent, 
				sleV2M6RouteInfoNumWholePktSent, sleV2M6RouteInfoRegAckRecv, sleV2M6RouteInfoRegNackRecv, sleV2M6RouteInfoRegPktSent, sleV2M6RouteInfoControlRequest, 
				sleV2M6RouteInfoControlStatus, sleV2M6RouteInfoControlTimer, sleV2M6RouteInfoControlTimeStamp, sleV2M6RouteInfoControlReqResult, sleV2M6RouteInfoControlActive, 
				sleV2M6RouteInfoControlLimit, sleV2M6RouteInfoControlThreshold, sleV2M6RouteInfoControlUnknownFlood, sleV2M6RouteInfoControlUnknownFloodPMap, sleV2M6RouteGroupAddress, 
				sleV2M6RouteSourceAddress, sleV2M6RouteUptime, sleV2M6RouteExpire, sleV2M6RouteOwner, sleV2M6RouteFlags, 
				sleV2M6RouteIncoming, sleV2M6RouteOutgoing, sleV2M6RouteNumWrongMIFRecv, sleV2M6RouteNumWrongMIFSent, sleV2M6RouteNumWholePktRecv, 
				sleV2M6RouteNumWholePktSent, sleV2M6RouteNumImmStatSent, sleV2M6RouteNumTimedStatSent, sleV2M6RouteRegAckRecv, sleV2M6RouteRegNackRecv, 
				sleV2M6RouteRegPktSent, sleV2M6RouteControlRequest, sleV2M6RouteControlStatus, sleV2M6RouteControlTimer, sleV2M6RouteControlTimeStamp, 
				sleV2M6RouteControlReqResult, sleV2M6RouteControlGroupAddress, sleV2M6RouteControlSourceAddress, sleV2Pim6InfoJTTimer, sleV2Pim6InfoSPTThreshold, 
				sleV2Pim6InfoSPTThresholdACL, sleV2Pim6InfoSSMDefault, sleV2Pim6InfoSSMRangeACL, sleV2Pim6InfoCRPCiscoPrefix, sleV2Pim6InfoIgnoreRPSetPriority, 
				sleV2Pim6InfoBSRCandidateInterface, sleV2Pim6InfoBSRCnadidateHash, sleV2Pim6InfoBSRCandidatePriority, sleV2Pim6InfoBSRRole, sleV2Pim6InfoBSRStatus, 
				sleV2Pim6InfoBSRUptime, sleV2Pim6InfoRegisterRateLimit, sleV2Pim6InfoRegisterSourceIPAddr, sleV2Pim6InfoRegisterSourceInterface, sleV2Pim6InfoRegisterRPReachability, 
				sleV2Pim6InfoRegisterSuppression, sleV2Pim6InfoAcceptRegisterACL, sleV2Pim6InfoRPRegisterKAT, sleV2Pim6InfoCiscoRegisterChecksum, sleV2Pim6InfoCiscoRegisterChecksumACL, 
				sleV2Pim6InfoControlRequest, sleV2Pim6InfoControlStatus, sleV2Pim6InfoControlTimer, sleV2Pim6InfoControlTimeStamp, sleV2Pim6InfoControlReqResult, 
				sleV2Pim6InfoControlMessageInterval, sleV2Pim6InfoControlSPTThreshold, sleV2Pim6InfoControlSPTThresholdACL, sleV2Pim6InfoControlSSMDefault, sleV2Pim6InfoControlSSMRangeACL, 
				sleV2Pim6InfoControlRPCandidateInterface, sleV2Pim6InfoControlRPCandidateGroupACL, sleV2Pim6InfoControlRPCandidateInterval, sleV2Pim6InfoControlRPCandidatePriority, sleV2Pim6InfoControlRPAddress, 
				sleV2Pim6InfoControlRPAddressACL, sleV2Pim6InfoControlCRPCiscoPrefix, sleV2Pim6InfoControlIgnoreRPSetPriority, sleV2Pim6InfoControlBSRCandidateInterface, sleV2Pim6InfoControlBSRCnadidateHash, 
				sleV2Pim6InfoControlBSRCandidatePriority, sleV2Pim6InfoControlRegisterRateLimit, sleV2Pim6InfoControlRegisterSourceIPAddr, sleV2Pim6InfoControlRegisterSourceInterface, sleV2Pim6InfoControlRegisterRPReachability, 
				sleV2Pim6InfoControlRegisterSuppression, sleV2Pim6InfoControlAcceptRegisterACL, sleV2Pim6InfoControlRPRegisterKAT, sleV2Pim6InfoControlCiscoRegisterChecksum, sleV2Pim6InfoControlCiscoRegisterChecksumACL, 
				sleV2Pim6InfoControlGroup, sleV2Pim6InfoControlSource, sleV2Pim6IfVid, sleV2Pim6IfVifIndex, sleV2Pim6IfLinkLocalAddress, 
				sleV2Pim6IfGlobalAddress, sleV2Pim6IfDrLinkLocalAddress, sleV2Pim6IfTriggedHelloPeriod, sleV2Pim6IfNextHelloTime, sleV2Pim6IfSparseMode, 
				sleV2Pim6IfSparseModePassive, sleV2Pim6IfHelloHoldtime, sleV2Pim6IfHelloInterval, sleV2Pim6IfDrPriority, sleV2Pim6IfExcludeGenID, 
				sleV2Pim6IfNeighborFilterACL, sleV2Pim6IfControlRequest, sleV2Pim6IfControlStatus, sleV2Pim6IfControlTimer, sleV2Pim6IfControlTimeStamp, 
				sleV2Pim6IfControlReqResult, sleV2Pim6IfControlVid, sleV2Pim6IfControlSparseMode, sleV2Pim6IfControlSparseModePassive, sleV2Pim6IfControlHelloHoldtime, 
				sleV2Pim6IfControlHelloInterval, sleV2Pim6IfControlDrPriority, sleV2Pim6IfControlExcludeGenID, sleV2Pim6IfControlNeighborFilterACL, sleV2Pim6NeighborAddress, 
				sleV2Pim6NeighborVid, sleV2Pim6NeighborUptime, sleV2Pim6NeighborExpire, sleV2Pim6NeighborVersion, sleV2Pim6NeighborDr, 
				sleV2Pim6NeighboDrPriority, sleV2Pim6NexthopSourceAddress, sleV2Pim6NexthopGroupAddress, sleV2Pim6NexthopNum, sleV2Pim6NexthopType, 
				sleV2Pim6NexthopAddress, sleV2Pim6NexthopVid, sleV2Pim6NexthopMetric, sleV2Pim6NexthopPref, sleV2Pim6NexthopRefcnt, 
				sleV2Pim6CRPVid, sleV2Pim6CRPACL, sleV2Pim6RPActive, sleV2Pim6CRPInterval, sleV2Pim6CRPPriority, 
				sleV2Pim6CRPNextAdver, sleV2Pim6CRPControlRequest, sleV2Pim6CRPControlStatus, sleV2Pim6CRPControlTimer, sleV2Pim6CRPControlTimeStamp, 
				sleV2Pim6CRPControlReqResult, sleV2Pim6CRPControlVid, sleV2Pim6CRPControlACL, sleV2Pim6CRPControlInterval, sleV2Pim6CRPControlPriority, 
				sleV2Pim6SRPAddr, sleV2Pim6SRPACL, sleV2Pim6SRPControlRequest, sleV2Pim6SRPControlStatus, sleV2Pim6SRPControlTimer, 
				sleV2Pim6SRPControlTimeStamp, sleV2Pim6SRPControlReqResult, sleV2Pim6SRPControlAddr, sleV2Pim6SRPControlACL, sleV2Pim6MrtXXRPAddress, 
				sleV2Pim6MrtXXRPRPFNbrAddress, sleV2Pim6MrtXXRPRPFVid, sleV2Pim6MrtXXRPUpstreamState, sleV2Pim6MrtXXRPJoined, sleV2Pim6MrtXXRPOutgoing, 
				sleV2Pim6MrtXGGroupAddress, sleV2Pim6MrtXGRPAddress, sleV2Pim6MrtXGRPFNbrAddress, sleV2Pim6MrtXGVid, sleV2Pim6MrtXGUpstreamState, 
				sleV2Pim6MrtXGLocal, sleV2Pim6MrtXGJoined, sleV2Pim6MrtXGAssertWinner, sleV2Pim6MrtXGAssertLoser, sleV2Pim6MrtFcrSourceAddress, 
				sleV2Pim6MrtFcrOutgoing, sleV2Pim6MrtFcrKat, sleV2Pim6MrtFcrPktCnt, sleV2Pim6MrtSGSourceAddress, sleV2Pim6MrtSGGroupAddress, 
				sleV2Pim6MrtSGKat, sleV2Pim6MrtSGRPFNbrAddress, sleV2Pim6MrtSGRPFVid, sleV2Pim6MrtSGSTPBit, sleV2Pim6MrtSGUpstreamState, 
				sleV2Pim6MrtSGLocal, sleV2Pim6MrtSGJoined, sleV2Pim6MrtSGOutgoing, sleV2Pim6MrtSGAssertWinner, sleV2Pim6MrtSGAssertLoser, 
				sleV2Pim6MrtSGRPTSourceAddress, sleV2Pim6MrtSGRPTGroupAddress, sleV2Pim6MrtSGRPTRPAddress, sleV2Pim6MrtSGRPTRPFNbrAddress, sleV2Pim6MrtSGRPTRPFVid, 
				sleV2Pim6MrtSGRPTUpstream, sleV2Pim6MrtSGRPTLocal, sleV2Pim6MrtSGRPTPruned, sleV2Pim6MrtSGRPTOutgoing, sleV2MLDInfoLimitCount, 
				sleV2MLDInfoLimitACL, sleV2MLDInfoSSM, sleV2MLDSnpInfoEnable, sleV2MLDPxyMultipathGrp, sleV2MLDInfoControlRequest, 
				sleV2MLDInfoControlStatus, sleV2MLDInfoControlTimer, sleV2MLDInfoControlTimeStamp, sleV2MLDInfoControlReqResult, sleV2MLDInfoControlLimitCount, 
				sleV2MLDInfoControlLimitACL, sleV2MLDInfoControlSSM, sleV2MLDInfoControlClearVid, sleV2MLDInfoControlClearGroup, sleV2MLDSnpInfoControlEnable, 
				sleV2MLDPxyInfoControlMultipathGrp, sleV2MLDIfVid, sleV2MLDIfAcl, sleV2MLDIfActive, sleV2MLDIfQuerier, 
				sleV2MLDIfVersion, sleV2MLDIfLinkLocalAddress, sleV2MLDIfLimitCount, sleV2MLDIfLimitACL, sleV2MLDIfGroupNum, 
				sleV2MLDIfJoinNum, sleV2MLDIfLeaveNum, sleV2MLDIfQueryingRouter, sleV2MLDIfQueryInterval, sleV2MLDIfQuerierTimeout, 
				sleV2MLDIfQueryMaxResponseTime, sleV2MLDIfLastMemberQueryCount, sleV2MLDIfLastMemberQueryInterval, sleV2MLDIfGroupMembershipInterval, sleV2MLDIfImmLeaveACL, 
				sleV2MLDIfControlRequest, sleV2MLDIfControlStatus, sleV2MLDIfControlTimer, sleV2MLDIfControlTimeStamp, sleV2MLDIfControlReqResult, 
				sleV2MLDIfControlVid, sleV2MLDIfControlACL, sleV2MLDIfControlImmLeaveACL, sleV2MLDIfControlLMQC, sleV2MLDIfControlLMCI, 
				sleV2MLDIfControlLimitCount, sleV2MLDIfControlLimitACL, sleV2MLDIfControlQuerierTimeout, sleV2MLDIfControlQueryInterval, sleV2MLDIfControlQueryMaxRespTime, 
				sleV2MLDIfControlRobustnessVariable, sleV2MLDIfControlVersion, sleV2MLDGroupAddress, sleV2MLDGroupUptime, sleV2MLDGroupMode, 
				sleV2MLDGroupExpire, sleV2MLDGroupLastReporter, sleV2MLDGroupFirstReporter, sleV2MLDSourceAddress, sleV2MLDSourceListType, 
				sleV2MLDSourceUptime, sleV2MLDSourceExpire, sleV2MLDSnpIfVid, sleV2MLDSnpIfAcl, sleV2MLDSnpIfActive, 
				sleV2MLDSnpIfQuerier, sleV2MLDSnpIfVersion, sleV2MLDSnpIfLinkLocalAddress, sleV2MLDSnpIfLimit, sleV2MLDSnpIfLimitACL, 
				sleV2MLDSnpIfGroupNum, sleV2MLDSnpIfJoinNum, sleV2MLDSnpIfLeaveNum, sleV2MLDSnpIfQueryingRouter, sleV2MLDSnpIfQueryInterval, 
				sleV2MLDSnpIfQuerierTimeout, sleV2MLDSnpIfQueryMaxResponseTime, sleV2MLDSnpIfLastMemberQueryCount, sleV2MLDSnpIfLastMemberQueryInterval, sleV2MLDSnpIfGroupMembershipInterval, 
				sleV2MLDSnpIfFastLeave, sleV2MLDSnpIfSuppression, sleV2MLDSnpIMroutePorts, sleV2MLDSnpIfControlRequest, sleV2MLDSnpIfControlStatus, 
				sleV2MLDSnpIfControlTimer, sleV2MLDSnpIfControlTimeStamp, sleV2MLDSnpIfControlReqResult, sleV2MLDSnpIfControlVid, sleV2MLDSnpIfControlEnable, 
				sleV2MLDSnpIfControlACL, sleV2MLDSnpIfControlFastLeave, sleV2MLDSnpIfControlLMQC, sleV2MLDSnpIfControlLMCI, sleV2MLDSnpIfControlLimitCount, 
				sleV2MLDSnpIfControlLimitACL, sleV2MLDSnpIfControlQuerierTimeout, sleV2MLDSnpIfControlQueryInterval, sleV2MLDSnpIfControlQueryMaxRespTime, sleV2MLDSnpIfControlRobustnessVariable, 
				sleV2MLDSnpIfControlVersion, sleV2MLDSnpIfControlMroutePorts, sleV2MLDSnpIfControlQuerier, sleV2MLDSnpIfControlSuppresion, sleV2MLDSnpGroupAddress, 
				sleV2MLDSnpGroupMode, sleV2MLDSnpGroupUptime, sleV2MLDSnpGroupExpire, sleV2MLDSnpGroupLastReporter, sleV2MLDSnpGroupFirstReporter, 
				sleV2MLDSnpSourceAddress, sleV2MLDSnpSourceList, sleV2MLDSnpSourceUptime, sleV2MLDSnpSourceExpire, sleV2MLDPxyIfVid, 
				sleV2MLDPxyIfService, sleV2MLDPxyIfServicePriority, sleV2MLDPxyIfMroute, sleV2MLDPxyIfControlRequest, sleV2MLDPxyIfControlStatus, 
				sleV2MLDPxyIfControlTimer, sleV2MLDPxyIfControlTimeStamp, sleV2MLDPxyIfControlReqResult, sleV2MLDPxyIfControlVid, sleV2MLDPxyIfControlService, 
				sleV2MLDPxyIfControlServicePriority, sleV2MLDPxyIfControlMroute }
			STATUS current
			DESCRIPTION 
				"Description."
			::= { sleV2Multicast 5 }

		
--  1.3.6.1.4.1.6296.102.12.5
		sleV2McastNotificationGroup NOTIFICATION-GROUP
			NOTIFICATIONS { sleV2IghVlanProfileChanged, sleV2IghGroupCreated, sleV2IghGroupDestroyed, sleV2IgmpInterfaceActivityChanged, sleV2IgmpInterfaceProfileChanged, 
				sleV2IgsVlanCreated, sleV2IgsVlanDestroyed, sleV2IgsVlanProfileChanged, sleV2IgsVlanMRouteProfileChanged, sleV2IgsVlanQuerierProfileChanced, 
				sleV2IgsVlanTcnProfileChanced, sleV2IgsVlanStatisticsCleared, sleV2IgfPortProfileChanged, sleV2IgfPortMaxGroupChanged, sleV2M4RouteInfoActivityChanged, 
				sleV2M4RouteInfoLimitChanged, sleV2M4RouteInfoUnkwonFloodChanged, sleV2IgmpInfoSnoopActivityChanged, sleV2IgmpInfoTcnProfileChanged, sleV2IgmpInfoMvrActivityChanged, 
				sleV2IgmpSsmMapCreated, sleV2IgmpSsmMapDestroyed, sleV2Pim4InfoSnoopingActivityChanged, sleV2Pim4VlanActivityChanged, sleV2Mvr4GroupCreated, 
				sleV2Mvr4GroupDestroyed, sleV2M4RouteEntryDestroyed, sleV2M4RouteInterfaceProfileChanged, sleV2IgmpInfoQuerierProfileChanged, sleV2Mvr4PortProfileChanged, 
				sleV2IgmpSourceCreated, sleV2IgmpSourceDestroyed, sleV2IgsSourceCreated, sleV2IgsSourceDestroyed, sleV2IghGroupCleared, 
				sleV2IgfpRangeAdded, sleV2IgfpRangeDeleted, sleV2M4RoutAllStatisticsCleared, sleV2IgmpInterfaceMrouteChanged, sleV2IgmpInterfaceProxyServiceChanged, 
				sleV2IgsPortrofileChanged, sleV2IgmpInterfaceStatsCleared, sleV2IgsStatsCleared, sleV2IgmpGStateAllCleared, sleV2IgmpGStateSessionCleared, 
				sleV2IgmpGStateGroupCleared, sleV2IgmpInfoTcnProfileSolicitAddressChanged, sleV2IgmpInfoTcnProfileQueryIntervalChanged, sleV2IgsPortExplicitTrackingMaxHostsChanged, sleV2IgmpProxyInterfaceMrouteChanged, 
				sleV2IgmpProxyInterfaceServiceChanged, sleV2IgfPortDhcpSnoopBindingPermissionChanged, sleV2IgmpInterfaceVerifySrcIpChanged, sleV2IgmpInfoVerifyTTLChanged, sleV2IgmpInfoSnoopExplicitTrackingMacBasedChanged, 
				sleV2IghJoinCreated, sleV2IghJoinDestroyed, sleV2IghJoinCleared, sleV2IghJoinProfileCreated, sleV2IghJoinProfileDestroyed, 
				sleV2IghGroupProfileCreated, sleV2IghGroupProfileDestroyed, sleV2IgsPortExplicitTrackingMacBasedChanged, sleV2IgsPortDot1qChanged, sleV2McastIPTvInfoCacStateChanged, 
				sleV2McastIPTvInfoLimitChanged, sleV2McastIPTvInfoFullviewRecogTimeChanged, sleV2McastIPTvPackageCreated, sleV2McastIPTvPackageChanged, sleV2McastIPTvPackageDeleted, 
				sleV2McastIPTvPackageAddChannel, sleV2McastIPTvPackageRemoveChannel, sleV2McastIPTvPreviewProfileCreated, sleV2McastIPTvPreviewProfileChanged, sleV2McastIPTvPreviewProfileDeleted, 
				sleV2McastIPTvPreviewProfileResetChanged, sleV2McastIPTvPreviewInstantReset, sleV2McastIPTvChannelCreated, sleV2McastIPTvChannelChanged, sleV2McastIPTvChannelDeleted, 
				sleV2McastIPTvCacProfileCreated, sleV2McastIPTvCacProfileChanged, sleV2McastIPTvCacProfileDeleted, sleV2McastIPTvCacProfileAddGroup, sleV2McastIPTvCacProfileDelGroup, 
				sleV2McastIPTvSubscriberCreated, sleV2McastIPTvSubscriberChanged, sleV2McastIPTvSubscriberDeleted, sleV2McastIPTvSubscriberAddPackage, sleV2McastIPTvSubscriberRemovePackage, 
				sleV2McastIPTvSubscriberSuspend, sleV2McastIPTvSubscriberResume, sleV2McastIPTvSubscriberHistoryCleared, sleV2McastIPTvCDRInfoStatusChanged, sleV2McastIPTvCDRInfoEventProfileChanged, 
				sleV2McastIPTvCDRInfoLogFileProfileChanged, sleV2McastIPTvCDRInfoExportProfileChanged, sleV2McastIPTvCDRInfoSyslogPriorityChanged, sleV2McastIPTvCDRLogServerCreated, sleV2McastIPTvCDRLogServerDeleted, 
				sleV2McastIPTvCDRLogServerUploadCDR, sleV2McastIPTvCDRLogServerUploadCDRManual, sleV2McastIPTvCDRLogFormatCreated, sleV2McastIPTvCDRLogFormatDeleted, sleV2McastIPTvCDRLogFormatChanged, 
				sleV2McastIPTvCDRLogFormatRecordTypeChanged, sleV2McastIPTvCDRLogFormatReasonChanged, sleV2IgfPortPacketTypeChanged, sleV2McastIPTvSubscriberDescChanged, sleV2IgmpProxyMultipathChanged, 
				sleV2IgmpProxyInterfaceMrouteDeleted, sleV2IgsVlanStatsCleared, sleV2IgsPortMrouterchanged, sleV2IgmpInfoSnoopTcnQueryGeneralChanged, sleV2IgmpinfoSnoopMrouterCpuChanged, 
				sleV2IgmpInfoMaxGroupSystemCntChanged, sleV2IgmpInfoMaxGroupSystemCntDeleted, sleV2IgmpInfoSnoopMRouteProfileChanged, sleV2IgsMaxBWLimitSystemMaxChanged, sleV2IgsMaxBWLimitChannelDefaultChanged, 
				sleV2IgsMaxBWLimitPortMaxChanged, sleV2IgsMaxBWLimitChannelAdded, sleV2IgsMaxBWLimitChannelDeleted, sleV2IgsMaxBWLimitCurrentBWCleared, sleV2IgsMaxBWLimitPortCurrentBWCleared, 
				sleV2Pim4InfoProfileChanged, sleV2Pim4InfoRPProfileChanged, sleV2Pim4InfoBSRProfileChanged, sleV2Pim4InfoRegisterProfileChanged, sleV2Pim4InfoVIFFlapDiscreditProfileChanged, 
				sleV2Pim4InfoMRTCleared, sleV2Pim4InfoRPSetCleared, sleV2Pim4InfoFlapVIFCleared, sleV2M6RouteInfoProfileChanged, sleV2M6RouteEntryCleared, 
				sleV2M6RouteEntryClearedAll, sleV2M6RouteCounterCleared, sleV2M6RouteCounterClearedAll, sleV2Pim6InfoProfileChanged, sleV2Pim6InfoRPProfileChanged, 
				sleV2Pim6InfoBSRProfileChanged, sleV2Pim6InfoRegisterProfileChanged, sleV2Pim6InfoMRTCleared, sleV2Pim6InfoRPSetCleared, sleV2Pim6IfProfileChanged, 
				sleV2Pim6CreateCRPProfileChanged, sleV2Pim6DestroyCRPProfileChanged, sleV2Pim6CreateSRPProfileChanged, sleV2Pim6DestroySRPProfileChanged, sleV2MLDInfoProfileChanged, 
				sleV2MLDInfoProfileCleared, sleV2MLDSnpInfoProfileChanged, sleV2MLDPxyInfoProfileChanged, sleV2MLDIfProfileChanged, sleV2CreateMLDSnpIfProfile, 
				sleV2MLDPxyIfProfileChanged, sleV2Pim4IfProfileChanged, sleV2Pim4CreateCRPProfileChanged, sleV2Pim4DestroyCRPProfileChanged, sleV2Pim4CreateSRPProfileChanged, 
				sleV2Pim4DestroySRPProfileChanged, sleV2Pim4CreateStaticGroupProfileChanged, sleV2Pim4DestroyStaticGroupProfileChanged, sleV2M4RoutStatisticsCleared, sleV2M4RoutAllEntriesCleared, 
				sleV2IgfProfileCreated, sleV2IgfProfileDestroyed, sleV2IgfProfileChanged, sleV2IgfProfileByNameCreated, sleV2IgmpProxyInterfaceMrouteSourceIpChanged, 
				sleV2IgmpProxyInterfaceServiceSourceIpChanged }
			STATUS current
			DESCRIPTION 
				"Description."
			::= { sleV2Multicast 6 }

		
	
	END

--
-- slev2-multicast-mib.mib
--
