-- file automatically created


TELDAT-TRAP-BFD-MIB DEFINITIONS ::= BEGIN


IMPORTS
	MODULE-IDENTITY,OBJECT-TYPE,OBJECT-IDENTITY,NOTIFICATION-TYPE,Integer32,IpAddress
		FROM SNMPv2-SMI
	DisplayString
		FROM SNMPv2-TC
	telEventTraps
		FROM TELDAT-MIB;


bfdTrapsMIB MODULE-IDENTITY
    LAST-UPDATED "201401200930Z"
    ORGANIZATION "Teldat, S.A."
    CONTACT-INFO 
        "Teldat, S.A.
        Customer Service

        Postal: Parque Tecnologico de Madrid
                Tres Cantos 28760
                Madrid, SPAIN

        Tel.: +34 918 076 565

        http://www.teldat.com"
    DESCRIPTION
        "This Module Information Base file is defined for managing received
        SNMP notifications generated by the BFD event subsystem."
    REVISION "201401200930Z"
    DESCRIPTION "Initial implementation"
        ::= { telEventTraps 203 }


bfdEventsGroup	OBJECT IDENTIFIER	::= { bfdTrapsMIB 1 }

bfdNotifications	OBJECT IDENTIFIER	::= { bfdTrapsMIB 2 }
bfdNotificationsPrefix	OBJECT IDENTIFIER	::= { bfdNotifications 0 }

bfdEventObjects2 OBJECT-IDENTITY
    STATUS current
    DESCRIPTION
        "Event BFD.2
        A BFD packet with invalid TTL value has been received."
    ::= { bfdEventsGroup 2 }

bfd2-ttl-received OBJECT-TYPE
    SYNTAX Integer32
    MAX-ACCESS accessible-for-notify
    STATUS current
    DESCRIPTION
        "Parameter 'ttl-received' in event BFD.2"
    ::= { bfdEventObjects2 1 }

bfd2-peer-address OBJECT-TYPE
    SYNTAX DisplayString
    MAX-ACCESS accessible-for-notify
    STATUS current
    DESCRIPTION
        "Parameter 'peer-address' in event BFD.2"
    ::= { bfdEventObjects2 2 }

bfdEventObjects3 OBJECT-IDENTITY
    STATUS current
    DESCRIPTION
        "Event BFD.3
        A BFD packet with invalid size has been received."
    ::= { bfdEventsGroup 3 }

bfd3-peer-address OBJECT-TYPE
    SYNTAX DisplayString
    MAX-ACCESS accessible-for-notify
    STATUS current
    DESCRIPTION
        "Parameter 'peer-address' in event BFD.3"
    ::= { bfdEventObjects3 1 }

bfdEventObjects4 OBJECT-IDENTITY
    STATUS current
    DESCRIPTION
        "Event BFD.4
        A BFD packet with invalid BFD version has been received."
    ::= { bfdEventsGroup 4 }

bfd4-protocol-version OBJECT-TYPE
    SYNTAX Integer32
    MAX-ACCESS accessible-for-notify
    STATUS current
    DESCRIPTION
        "Parameter 'protocol-version' in event BFD.4"
    ::= { bfdEventObjects4 1 }

bfd4-peer-address OBJECT-TYPE
    SYNTAX DisplayString
    MAX-ACCESS accessible-for-notify
    STATUS current
    DESCRIPTION
        "Parameter 'peer-address' in event BFD.4"
    ::= { bfdEventObjects4 2 }

bfdEventObjects5 OBJECT-IDENTITY
    STATUS current
    DESCRIPTION
        "Event BFD.5
        A BFD packet with invalid length has been received."
    ::= { bfdEventsGroup 5 }

bfd5-packet-legth OBJECT-TYPE
    SYNTAX Integer32
    MAX-ACCESS accessible-for-notify
    STATUS current
    DESCRIPTION
        "Parameter 'packet-legth' in event BFD.5"
    ::= { bfdEventObjects5 1 }

bfd5-peer-address OBJECT-TYPE
    SYNTAX DisplayString
    MAX-ACCESS accessible-for-notify
    STATUS current
    DESCRIPTION
        "Parameter 'peer-address' in event BFD.5"
    ::= { bfdEventObjects5 2 }

bfdEventObjects6 OBJECT-IDENTITY
    STATUS current
    DESCRIPTION
        "Event BFD.6
        A BFD packet with zero detect time multiplier has been received."
    ::= { bfdEventsGroup 6 }

bfd6-peer-address OBJECT-TYPE
    SYNTAX DisplayString
    MAX-ACCESS accessible-for-notify
    STATUS current
    DESCRIPTION
        "Parameter 'peer-address' in event BFD.6"
    ::= { bfdEventObjects6 1 }

bfdEventObjects7 OBJECT-IDENTITY
    STATUS current
    DESCRIPTION
        "Event BFD.7
        A BFD packet with zero in the My Discriminator field has been received."
    ::= { bfdEventsGroup 7 }

bfd7-peer-address OBJECT-TYPE
    SYNTAX DisplayString
    MAX-ACCESS accessible-for-notify
    STATUS current
    DESCRIPTION
        "Parameter 'peer-address' in event BFD.7"
    ::= { bfdEventObjects7 1 }

bfdEventObjects8 OBJECT-IDENTITY
    STATUS current
    DESCRIPTION
        "Event BFD.8
        A BFD packet with zero in the Your Duscriminator field and non-zero
        in the I Hear You flag has been received."
    ::= { bfdEventsGroup 8 }

bfd8-peer-address OBJECT-TYPE
    SYNTAX DisplayString
    MAX-ACCESS accessible-for-notify
    STATUS current
    DESCRIPTION
        "Parameter 'peer-address' in event BFD.8"
    ::= { bfdEventObjects8 1 }

bfdEventObjects9 OBJECT-IDENTITY
    STATUS current
    DESCRIPTION
        "Event BFD.9
        The system could not find a valid session for the BFD packet received."
    ::= { bfdEventsGroup 9 }

bfd9-peer-address OBJECT-TYPE
    SYNTAX DisplayString
    MAX-ACCESS accessible-for-notify
    STATUS current
    DESCRIPTION
        "Parameter 'peer-address' in event BFD.9"
    ::= { bfdEventObjects9 1 }

bfdEventObjects10 OBJECT-IDENTITY
    STATUS current
    DESCRIPTION
        "Event BFD.10
        Some of the BFD definition parameters has changed and timers must be
        renegotiated."
    ::= { bfdEventsGroup 10 }

bfd10-session-disc OBJECT-TYPE
    SYNTAX Integer32
    MAX-ACCESS accessible-for-notify
    STATUS current
    DESCRIPTION
        "Parameter 'session-disc' in event BFD.10"
    ::= { bfdEventObjects10 1 }

bfd10-peer-address OBJECT-TYPE
    SYNTAX DisplayString
    MAX-ACCESS accessible-for-notify
    STATUS current
    DESCRIPTION
        "Parameter 'peer-address' in event BFD.10"
    ::= { bfdEventObjects10 2 }

bfdEventObjects11 OBJECT-IDENTITY
    STATUS current
    DESCRIPTION
        "Event BFD.11
        A BFD poll sequence has been finished."
    ::= { bfdEventsGroup 11 }

bfd11-session-disc OBJECT-TYPE
    SYNTAX Integer32
    MAX-ACCESS accessible-for-notify
    STATUS current
    DESCRIPTION
        "Parameter 'session-disc' in event BFD.11"
    ::= { bfdEventObjects11 1 }

bfd11-peer-address OBJECT-TYPE
    SYNTAX DisplayString
    MAX-ACCESS accessible-for-notify
    STATUS current
    DESCRIPTION
        "Parameter 'peer-address' in event BFD.11"
    ::= { bfdEventObjects11 2 }

bfdEventObjects12 OBJECT-IDENTITY
    STATUS current
    DESCRIPTION
        "Event BFD.12
        A BFD session is coming to DOWN state because remote peer is 
        administratively down."
    ::= { bfdEventsGroup 12 }

bfd12-session-disc OBJECT-TYPE
    SYNTAX Integer32
    MAX-ACCESS accessible-for-notify
    STATUS current
    DESCRIPTION
        "Parameter 'session-disc' in event BFD.12"
    ::= { bfdEventObjects12 1 }

bfd12-peer-address OBJECT-TYPE
    SYNTAX DisplayString
    MAX-ACCESS accessible-for-notify
    STATUS current
    DESCRIPTION
        "Parameter 'peer-address' in event BFD.12"
    ::= { bfdEventObjects12 2 }

bfdEventObjects13 OBJECT-IDENTITY
    STATUS current
    DESCRIPTION
        "Event BFD.13
        The detection period has been finished without receiving packets from
        the remote peer. Session will come down."
    ::= { bfdEventsGroup 13 }

bfd13-session-disc OBJECT-TYPE
    SYNTAX Integer32
    MAX-ACCESS accessible-for-notify
    STATUS current
    DESCRIPTION
        "Parameter 'session-disc' in event BFD.13"
    ::= { bfdEventObjects13 1 }

bfd13-peer-address OBJECT-TYPE
    SYNTAX DisplayString
    MAX-ACCESS accessible-for-notify
    STATUS current
    DESCRIPTION
        "Parameter 'peer-address' in event BFD.13"
    ::= { bfdEventObjects13 2 }

bfd13-bfd-state OBJECT-TYPE
    SYNTAX DisplayString
    MAX-ACCESS accessible-for-notify
    STATUS current
    DESCRIPTION
        "Parameter 'bfd-state' in event BFD.13"
    ::= { bfdEventObjects13 3 }

bfdEventObjects14 OBJECT-IDENTITY
    STATUS current
    DESCRIPTION
        "Event BFD.14
        A BFD session is coming to DOWN state."
    ::= { bfdEventsGroup 14 }

bfd14-session-disc OBJECT-TYPE
    SYNTAX Integer32
    MAX-ACCESS accessible-for-notify
    STATUS current
    DESCRIPTION
        "Parameter 'session-disc' in event BFD.14"
    ::= { bfdEventObjects14 1 }

bfd14-peer-address OBJECT-TYPE
    SYNTAX DisplayString
    MAX-ACCESS accessible-for-notify
    STATUS current
    DESCRIPTION
        "Parameter 'peer-address' in event BFD.14"
    ::= { bfdEventObjects14 2 }

bfdEventObjects15 OBJECT-IDENTITY
    STATUS current
    DESCRIPTION
        "Event BFD.15
        A BFD session is coming to UP state."
    ::= { bfdEventsGroup 15 }

bfd15-session-disc OBJECT-TYPE
    SYNTAX Integer32
    MAX-ACCESS accessible-for-notify
    STATUS current
    DESCRIPTION
        "Parameter 'session-disc' in event BFD.15"
    ::= { bfdEventObjects15 1 }

bfd15-peer-address OBJECT-TYPE
    SYNTAX DisplayString
    MAX-ACCESS accessible-for-notify
    STATUS current
    DESCRIPTION
        "Parameter 'peer-address' in event BFD.15"
    ::= { bfdEventObjects15 2 }

bfdEventObjects16 OBJECT-IDENTITY
    STATUS current
    DESCRIPTION
        "Event BFD.16
        A BFD session with this value of Your Discriminator does not exist in
        the system."
    ::= { bfdEventsGroup 16 }

bfd16-session-disc OBJECT-TYPE
    SYNTAX Integer32
    MAX-ACCESS accessible-for-notify
    STATUS current
    DESCRIPTION
        "Parameter 'session-disc' in event BFD.16"
    ::= { bfdEventObjects16 1 }

bfd16-peer-address OBJECT-TYPE
    SYNTAX DisplayString
    MAX-ACCESS accessible-for-notify
    STATUS current
    DESCRIPTION
        "Parameter 'peer-address' in event BFD.16"
    ::= { bfdEventObjects16 2 }

bfdEventObjects17 OBJECT-IDENTITY
    STATUS current
    DESCRIPTION
        "Event BFD.17
        A BFD session with this peer does not exist in the system."
    ::= { bfdEventsGroup 17 }

bfd17-peer-address OBJECT-TYPE
    SYNTAX DisplayString
    MAX-ACCESS accessible-for-notify
    STATUS current
    DESCRIPTION
        "Parameter 'peer-address' in event BFD.17"
    ::= { bfdEventObjects17 1 }

bfdEventObjects18 OBJECT-IDENTITY
    STATUS current
    DESCRIPTION
        "Event BFD.18
        The BFD protocol sending function has failed."
    ::= { bfdEventsGroup 18 }

bfd18-peer-address OBJECT-TYPE
    SYNTAX DisplayString
    MAX-ACCESS accessible-for-notify
    STATUS current
    DESCRIPTION
        "Parameter 'peer-address' in event BFD.18"
    ::= { bfdEventObjects18 1 }

bfdEventObjects19 OBJECT-IDENTITY
    STATUS current
    DESCRIPTION
        "Event BFD.19
        The system has not enough memory to allocate a new BFD session."
    ::= { bfdEventsGroup 19 }

bfd19-peer-address OBJECT-TYPE
    SYNTAX DisplayString
    MAX-ACCESS accessible-for-notify
    STATUS current
    DESCRIPTION
        "Parameter 'peer-address' in event BFD.19"
    ::= { bfdEventObjects19 1 }

bfdEventObjects20 OBJECT-IDENTITY
    STATUS current
    DESCRIPTION
        "Event BFD.20
        The system can not get a free socket for a new BFD session."
    ::= { bfdEventsGroup 20 }

bfd20-peer-address OBJECT-TYPE
    SYNTAX DisplayString
    MAX-ACCESS accessible-for-notify
    STATUS current
    DESCRIPTION
        "Parameter 'peer-address' in event BFD.20"
    ::= { bfdEventObjects20 1 }

bfdEventObjects21 OBJECT-IDENTITY
    STATUS current
    DESCRIPTION
        "Event BFD.21
        The system can not set TTL value for a new BFD session."
    ::= { bfdEventsGroup 21 }

bfd21-peer-address OBJECT-TYPE
    SYNTAX DisplayString
    MAX-ACCESS accessible-for-notify
    STATUS current
    DESCRIPTION
        "Parameter 'peer-address' in event BFD.21"
    ::= { bfdEventObjects21 1 }

bfdEventObjects22 OBJECT-IDENTITY
    STATUS current
    DESCRIPTION
        "Event BFD.22
        The system can not find a free source port for a new BFD session."
    ::= { bfdEventsGroup 22 }

bfd22-peer-address OBJECT-TYPE
    SYNTAX DisplayString
    MAX-ACCESS accessible-for-notify
    STATUS current
    DESCRIPTION
        "Parameter 'peer-address' in event BFD.22"
    ::= { bfdEventObjects22 1 }

bfdEventObjects23 OBJECT-IDENTITY
    STATUS current
    DESCRIPTION
        "Event BFD.23
        A new BFD session has been successfully created."
    ::= { bfdEventsGroup 23 }

bfd23-session-disc OBJECT-TYPE
    SYNTAX Integer32
    MAX-ACCESS accessible-for-notify
    STATUS current
    DESCRIPTION
        "Parameter 'session-disc' in event BFD.23"
    ::= { bfdEventObjects23 1 }

bfd23-local-address OBJECT-TYPE
    SYNTAX DisplayString
    MAX-ACCESS accessible-for-notify
    STATUS current
    DESCRIPTION
        "Parameter 'local-address' in event BFD.23"
    ::= { bfdEventObjects23 2 }

bfd23-peer-address OBJECT-TYPE
    SYNTAX DisplayString
    MAX-ACCESS accessible-for-notify
    STATUS current
    DESCRIPTION
        "Parameter 'peer-address' in event BFD.23"
    ::= { bfdEventObjects23 3 }

bfdEventObjects24 OBJECT-IDENTITY
    STATUS current
    DESCRIPTION
        "Event BFD.24
        The session that is been deleted does not exsist in the session hash."
    ::= { bfdEventsGroup 24 }

bfd24-session-disc OBJECT-TYPE
    SYNTAX Integer32
    MAX-ACCESS accessible-for-notify
    STATUS current
    DESCRIPTION
        "Parameter 'session-disc' in event BFD.24"
    ::= { bfdEventObjects24 1 }

bfdEventObjects25 OBJECT-IDENTITY
    STATUS current
    DESCRIPTION
        "Event BFD.25
        The session that is been deleted does not exsist in the peer hash."
    ::= { bfdEventsGroup 25 }

bfd25-session-disc OBJECT-TYPE
    SYNTAX Integer32
    MAX-ACCESS accessible-for-notify
    STATUS current
    DESCRIPTION
        "Parameter 'session-disc' in event BFD.25"
    ::= { bfdEventObjects25 1 }

bfdEventObjects26 OBJECT-IDENTITY
    STATUS current
    DESCRIPTION
        "Event BFD.26
        The session that is been deleted does not exsist in the session list."
    ::= { bfdEventsGroup 26 }

bfd26-session-disc OBJECT-TYPE
    SYNTAX Integer32
    MAX-ACCESS accessible-for-notify
    STATUS current
    DESCRIPTION
        "Parameter 'session-disc' in event BFD.26"
    ::= { bfdEventObjects26 1 }

bfdEventObjects27 OBJECT-IDENTITY
    STATUS current
    DESCRIPTION
        "Event BFD.27
        A BFD poll sequence has been started."
    ::= { bfdEventsGroup 27 }

bfd27-session-disc OBJECT-TYPE
    SYNTAX Integer32
    MAX-ACCESS accessible-for-notify
    STATUS current
    DESCRIPTION
        "Parameter 'session-disc' in event BFD.27"
    ::= { bfdEventObjects27 1 }

bfd27-peer-address OBJECT-TYPE
    SYNTAX DisplayString
    MAX-ACCESS accessible-for-notify
    STATUS current
    DESCRIPTION
        "Parameter 'peer-address' in event BFD.27"
    ::= { bfdEventObjects27 2 }

bfd27-detect-timer OBJECT-TYPE
    SYNTAX Integer32
    MAX-ACCESS accessible-for-notify
    STATUS current
    DESCRIPTION
        "Parameter 'detect-timer' in event BFD.27"
    ::= { bfdEventObjects27 3 }

bfdEventObjects28 OBJECT-IDENTITY
    STATUS current
    DESCRIPTION
        "Event BFD.28
        The session is administratively enabled."
    ::= { bfdEventsGroup 28 }

bfd28-session-disc OBJECT-TYPE
    SYNTAX Integer32
    MAX-ACCESS accessible-for-notify
    STATUS current
    DESCRIPTION
        "Parameter 'session-disc' in event BFD.28"
    ::= { bfdEventObjects28 1 }

bfd28-peer-address OBJECT-TYPE
    SYNTAX DisplayString
    MAX-ACCESS accessible-for-notify
    STATUS current
    DESCRIPTION
        "Parameter 'peer-address' in event BFD.28"
    ::= { bfdEventObjects28 2 }

bfdEventObjects29 OBJECT-IDENTITY
    STATUS current
    DESCRIPTION
        "Event BFD.29
        The session is administratively disabled."
    ::= { bfdEventsGroup 29 }

bfd29-session-disc OBJECT-TYPE
    SYNTAX Integer32
    MAX-ACCESS accessible-for-notify
    STATUS current
    DESCRIPTION
        "Parameter 'session-disc' in event BFD.29"
    ::= { bfdEventObjects29 1 }

bfd29-peer-address OBJECT-TYPE
    SYNTAX DisplayString
    MAX-ACCESS accessible-for-notify
    STATUS current
    DESCRIPTION
        "Parameter 'peer-address' in event BFD.29"
    ::= { bfdEventObjects29 2 }

bfdEventObjects33 OBJECT-IDENTITY
    STATUS current
    DESCRIPTION
        "Event BFD.33
        The system can not bind a socket to the BFD destination port."
    ::= { bfdEventsGroup 33 }

bfd33-port-number OBJECT-TYPE
    SYNTAX Integer32
    MAX-ACCESS accessible-for-notify
    STATUS current
    DESCRIPTION
        "Parameter 'port-number' in event BFD.33"
    ::= { bfdEventObjects33 1 }

bfdEventObjects34 OBJECT-IDENTITY
    STATUS current
    DESCRIPTION
        "Event BFD.34
        A routing protocol has been succesfully registered in a BFD session."
    ::= { bfdEventsGroup 34 }

bfd34-protocol-name OBJECT-TYPE
    SYNTAX DisplayString
    MAX-ACCESS accessible-for-notify
    STATUS current
    DESCRIPTION
        "Parameter 'protocol-name' in event BFD.34"
    ::= { bfdEventObjects34 1 }

bfd34-session-disc OBJECT-TYPE
    SYNTAX Integer32
    MAX-ACCESS accessible-for-notify
    STATUS current
    DESCRIPTION
        "Parameter 'session-disc' in event BFD.34"
    ::= { bfdEventObjects34 2 }

bfd34-local-address OBJECT-TYPE
    SYNTAX DisplayString
    MAX-ACCESS accessible-for-notify
    STATUS current
    DESCRIPTION
        "Parameter 'local-address' in event BFD.34"
    ::= { bfdEventObjects34 3 }

bfd34-peer-address OBJECT-TYPE
    SYNTAX DisplayString
    MAX-ACCESS accessible-for-notify
    STATUS current
    DESCRIPTION
        "Parameter 'peer-address' in event BFD.34"
    ::= { bfdEventObjects34 4 }

bfdEventObjects35 OBJECT-IDENTITY
    STATUS current
    DESCRIPTION
        "Event BFD.35
        The session can not be created."
    ::= { bfdEventsGroup 35 }

bfd35-local-address OBJECT-TYPE
    SYNTAX DisplayString
    MAX-ACCESS accessible-for-notify
    STATUS current
    DESCRIPTION
        "Parameter 'local-address' in event BFD.35"
    ::= { bfdEventObjects35 1 }

bfd35-peer-address OBJECT-TYPE
    SYNTAX DisplayString
    MAX-ACCESS accessible-for-notify
    STATUS current
    DESCRIPTION
        "Parameter 'peer-address' in event BFD.35"
    ::= { bfdEventObjects35 2 }

bfdEventObjects36 OBJECT-IDENTITY
    STATUS current
    DESCRIPTION
        "Event BFD.36
        There is no need to create a new BFD session with the peer, a session
        already exists."
    ::= { bfdEventsGroup 36 }

bfd36-peer-address OBJECT-TYPE
    SYNTAX DisplayString
    MAX-ACCESS accessible-for-notify
    STATUS current
    DESCRIPTION
        "Parameter 'peer-address' in event BFD.36"
    ::= { bfdEventObjects36 1 }

bfd36-session-disc OBJECT-TYPE
    SYNTAX Integer32
    MAX-ACCESS accessible-for-notify
    STATUS current
    DESCRIPTION
        "Parameter 'session-disc' in event BFD.36"
    ::= { bfdEventObjects36 2 }

bfd36-bfd-state OBJECT-TYPE
    SYNTAX DisplayString
    MAX-ACCESS accessible-for-notify
    STATUS current
    DESCRIPTION
        "Parameter 'bfd-state' in event BFD.36"
    ::= { bfdEventObjects36 3 }

bfdEventObjects37 OBJECT-IDENTITY
    STATUS current
    DESCRIPTION
        "Event BFD.37
        A change in the BFD state machine has happened."
    ::= { bfdEventsGroup 37 }

bfd37-session-disc OBJECT-TYPE
    SYNTAX Integer32
    MAX-ACCESS accessible-for-notify
    STATUS current
    DESCRIPTION
        "Parameter 'session-disc' in event BFD.37"
    ::= { bfdEventObjects37 1 }

bfd37-bfd-prev-state OBJECT-TYPE
    SYNTAX DisplayString
    MAX-ACCESS accessible-for-notify
    STATUS current
    DESCRIPTION
        "Parameter 'bfd-prev-state' in event BFD.37"
    ::= { bfdEventObjects37 2 }

bfd37-bfd-new-state OBJECT-TYPE
    SYNTAX DisplayString
    MAX-ACCESS accessible-for-notify
    STATUS current
    DESCRIPTION
        "Parameter 'bfd-new-state' in event BFD.37"
    ::= { bfdEventObjects37 3 }

bfdEventObjects38 OBJECT-IDENTITY
    STATUS current
    DESCRIPTION
        "Event BFD.38
        A packet has been sent to a neighbour."
    ::= { bfdEventsGroup 38 }

bfd38-local-address OBJECT-TYPE
    SYNTAX DisplayString
    MAX-ACCESS accessible-for-notify
    STATUS current
    DESCRIPTION
        "Parameter 'local-address' in event BFD.38"
    ::= { bfdEventObjects38 1 }

bfd38-peer-address OBJECT-TYPE
    SYNTAX DisplayString
    MAX-ACCESS accessible-for-notify
    STATUS current
    DESCRIPTION
        "Parameter 'peer-address' in event BFD.38"
    ::= { bfdEventObjects38 2 }

bfd38-bfdversion OBJECT-TYPE
    SYNTAX Integer32
    MAX-ACCESS accessible-for-notify
    STATUS current
    DESCRIPTION
        "Parameter 'bfdversion' in event BFD.38"
    ::= { bfdEventObjects38 3 }

bfd38-diag-code OBJECT-TYPE
    SYNTAX Integer32
    MAX-ACCESS accessible-for-notify
    STATUS current
    DESCRIPTION
        "Parameter 'diag-code' in event BFD.38"
    ::= { bfdEventObjects38 4 }

bfd38-flags OBJECT-TYPE
    SYNTAX DisplayString
    MAX-ACCESS accessible-for-notify
    STATUS current
    DESCRIPTION
        "Parameter 'flags' in event BFD.38"
    ::= { bfdEventObjects38 5 }

bfd38-detetct-mult OBJECT-TYPE
    SYNTAX Integer32
    MAX-ACCESS accessible-for-notify
    STATUS current
    DESCRIPTION
        "Parameter 'detetct-mult' in event BFD.38"
    ::= { bfdEventObjects38 6 }

bfd38-pkt-len OBJECT-TYPE
    SYNTAX Integer32
    MAX-ACCESS accessible-for-notify
    STATUS current
    DESCRIPTION
        "Parameter 'pkt-len' in event BFD.38"
    ::= { bfdEventObjects38 7 }

bfdEventObjects39 OBJECT-IDENTITY
    STATUS current
    DESCRIPTION
        "Event BFD.39
        A packet has been received from a neighbour."
    ::= { bfdEventsGroup 39 }

bfd39-peer-address OBJECT-TYPE
    SYNTAX DisplayString
    MAX-ACCESS accessible-for-notify
    STATUS current
    DESCRIPTION
        "Parameter 'peer-address' in event BFD.39"
    ::= { bfdEventObjects39 1 }

bfd39-local-address OBJECT-TYPE
    SYNTAX DisplayString
    MAX-ACCESS accessible-for-notify
    STATUS current
    DESCRIPTION
        "Parameter 'local-address' in event BFD.39"
    ::= { bfdEventObjects39 2 }

bfd39-bfdversion OBJECT-TYPE
    SYNTAX Integer32
    MAX-ACCESS accessible-for-notify
    STATUS current
    DESCRIPTION
        "Parameter 'bfdversion' in event BFD.39"
    ::= { bfdEventObjects39 3 }

bfd39-diag-code OBJECT-TYPE
    SYNTAX Integer32
    MAX-ACCESS accessible-for-notify
    STATUS current
    DESCRIPTION
        "Parameter 'diag-code' in event BFD.39"
    ::= { bfdEventObjects39 4 }

bfd39-flags OBJECT-TYPE
    SYNTAX DisplayString
    MAX-ACCESS accessible-for-notify
    STATUS current
    DESCRIPTION
        "Parameter 'flags' in event BFD.39"
    ::= { bfdEventObjects39 5 }

bfd39-detetct-mult OBJECT-TYPE
    SYNTAX Integer32
    MAX-ACCESS accessible-for-notify
    STATUS current
    DESCRIPTION
        "Parameter 'detetct-mult' in event BFD.39"
    ::= { bfdEventObjects39 6 }

bfd39-pkt-len OBJECT-TYPE
    SYNTAX Integer32
    MAX-ACCESS accessible-for-notify
    STATUS current
    DESCRIPTION
        "Parameter 'pkt-len' in event BFD.39"
    ::= { bfdEventObjects39 7 }

bfdEventObjects40 OBJECT-IDENTITY
    STATUS current
    DESCRIPTION
        "Event BFD.40
        This event shows the BFD packet body contents."
    ::= { bfdEventsGroup 40 }

bfd40-mydisc OBJECT-TYPE
    SYNTAX Integer32
    MAX-ACCESS accessible-for-notify
    STATUS current
    DESCRIPTION
        "Parameter 'mydisc' in event BFD.40"
    ::= { bfdEventObjects40 1 }

bfd40-yourdisc OBJECT-TYPE
    SYNTAX Integer32
    MAX-ACCESS accessible-for-notify
    STATUS current
    DESCRIPTION
        "Parameter 'yourdisc' in event BFD.40"
    ::= { bfdEventObjects40 2 }

bfd40-des-mintx OBJECT-TYPE
    SYNTAX Integer32
    MAX-ACCESS accessible-for-notify
    STATUS current
    DESCRIPTION
        "Parameter 'des-mintx' in event BFD.40"
    ::= { bfdEventObjects40 3 }

bfd40-req-minrx OBJECT-TYPE
    SYNTAX Integer32
    MAX-ACCESS accessible-for-notify
    STATUS current
    DESCRIPTION
        "Parameter 'req-minrx' in event BFD.40"
    ::= { bfdEventObjects40 4 }

bfd40-req-minechorx OBJECT-TYPE
    SYNTAX Integer32
    MAX-ACCESS accessible-for-notify
    STATUS current
    DESCRIPTION
        "Parameter 'req-minechorx' in event BFD.40"
    ::= { bfdEventObjects40 5 }

bfdEventObjects42 OBJECT-IDENTITY
    STATUS current
    DESCRIPTION
        "Event BFD.42
        The BFD parameter configuration does not exist or an interface with
        this IP address does not exist. Protocol can not be registered. "
    ::= { bfdEventsGroup 42 }

bfd42-intfc-addr OBJECT-TYPE
    SYNTAX DisplayString
    MAX-ACCESS accessible-for-notify
    STATUS current
    DESCRIPTION
        "Parameter 'intfc-addr' in event BFD.42"
    ::= { bfdEventObjects42 1 }

bfd42-protocol OBJECT-TYPE
    SYNTAX DisplayString
    MAX-ACCESS accessible-for-notify
    STATUS current
    DESCRIPTION
        "Parameter 'protocol' in event BFD.42"
    ::= { bfdEventObjects42 2 }

bfdEventObjects43 OBJECT-IDENTITY
    STATUS current
    DESCRIPTION
        "Event BFD.43
        A BFD packet with zero in the Your Duscriminator field and with not Down
        or Admindown in the state field has been received."
    ::= { bfdEventsGroup 43 }

bfd43-peer-address OBJECT-TYPE
    SYNTAX DisplayString
    MAX-ACCESS accessible-for-notify
    STATUS current
    DESCRIPTION
        "Parameter 'peer-address' in event BFD.43"
    ::= { bfdEventObjects43 1 }

bfdEventObjects44 OBJECT-IDENTITY
    STATUS current
    DESCRIPTION
        "Event BFD.44
        A routing protocol registered in a BFD session is being deleted."
    ::= { bfdEventsGroup 44 }

bfd44-protocol-name OBJECT-TYPE
    SYNTAX DisplayString
    MAX-ACCESS accessible-for-notify
    STATUS current
    DESCRIPTION
        "Parameter 'protocol-name' in event BFD.44"
    ::= { bfdEventObjects44 1 }

bfd44-session-disc OBJECT-TYPE
    SYNTAX Integer32
    MAX-ACCESS accessible-for-notify
    STATUS current
    DESCRIPTION
        "Parameter 'session-disc' in event BFD.44"
    ::= { bfdEventObjects44 2 }

bfd44-local-address OBJECT-TYPE
    SYNTAX DisplayString
    MAX-ACCESS accessible-for-notify
    STATUS current
    DESCRIPTION
        "Parameter 'local-address' in event BFD.44"
    ::= { bfdEventObjects44 3 }

bfd44-peer-address OBJECT-TYPE
    SYNTAX DisplayString
    MAX-ACCESS accessible-for-notify
    STATUS current
    DESCRIPTION
        "Parameter 'peer-address' in event BFD.44"
    ::= { bfdEventObjects44 4 }

bfdEventObjects45 OBJECT-IDENTITY
    STATUS current
    DESCRIPTION
        "Event BFD.45
        The Key Chain is probably not configured, so the protocol is not able to
        find it."
    ::= { bfdEventsGroup 45 }

bfd45-keychain-name OBJECT-TYPE
    SYNTAX DisplayString
    MAX-ACCESS accessible-for-notify
    STATUS current
    DESCRIPTION
        "Parameter 'keychain-name' in event BFD.45"
    ::= { bfdEventObjects45 1 }

bfdEventObjects46 OBJECT-IDENTITY
    STATUS current
    DESCRIPTION
        "Event BFD.46
        The protocol is not able to find a valid Key inside the Key Chain, maybe
        it is not configured."
    ::= { bfdEventsGroup 46 }

bfd46-keychain-name OBJECT-TYPE
    SYNTAX DisplayString
    MAX-ACCESS accessible-for-notify
    STATUS current
    DESCRIPTION
        "Parameter 'keychain-name' in event BFD.46"
    ::= { bfdEventObjects46 1 }

bfdEventObjects47 OBJECT-IDENTITY
    STATUS current
    DESCRIPTION
        "Event BFD.47
        A packet without authentication has been received but session requires
        authentication. The packet will be discarded and ignored."
    ::= { bfdEventsGroup 47 }

bfd47-peer-address OBJECT-TYPE
    SYNTAX DisplayString
    MAX-ACCESS accessible-for-notify
    STATUS current
    DESCRIPTION
        "Parameter 'peer-address' in event BFD.47"
    ::= { bfdEventObjects47 1 }

bfd47-authentication-type OBJECT-TYPE
    SYNTAX DisplayString
    MAX-ACCESS accessible-for-notify
    STATUS current
    DESCRIPTION
        "Parameter 'authentication-type' in event BFD.47"
    ::= { bfdEventObjects47 2 }

bfdEventObjects48 OBJECT-IDENTITY
    STATUS current
    DESCRIPTION
        "Event BFD.48
        A packet with authentication has been received but authentication type
        is not correct for the configured session. The packet will be discarded
        and ignored."
    ::= { bfdEventsGroup 48 }

bfd48-authentication-type OBJECT-TYPE
    SYNTAX DisplayString
    MAX-ACCESS accessible-for-notify
    STATUS current
    DESCRIPTION
        "Parameter 'authentication-type' in event BFD.48"
    ::= { bfdEventObjects48 1 }

bfd48-peer-address OBJECT-TYPE
    SYNTAX DisplayString
    MAX-ACCESS accessible-for-notify
    STATUS current
    DESCRIPTION
        "Parameter 'peer-address' in event BFD.48"
    ::= { bfdEventObjects48 2 }

bfdEventObjects49 OBJECT-IDENTITY
    STATUS current
    DESCRIPTION
        "Event BFD.49
        A packet with authentication has been received but the Key ID is invalid
        for the configured session. Check both remote and local configurations."
    ::= { bfdEventsGroup 49 }

bfd49-key-identifier OBJECT-TYPE
    SYNTAX Integer32
    MAX-ACCESS accessible-for-notify
    STATUS current
    DESCRIPTION
        "Parameter 'key-identifier' in event BFD.49"
    ::= { bfdEventObjects49 1 }

bfd49-peer-address OBJECT-TYPE
    SYNTAX DisplayString
    MAX-ACCESS accessible-for-notify
    STATUS current
    DESCRIPTION
        "Parameter 'peer-address' in event BFD.49"
    ::= { bfdEventObjects49 2 }

bfdEventObjects50 OBJECT-IDENTITY
    STATUS current
    DESCRIPTION
        "Event BFD.50
        A packet with authentication has been received but authentication
        length is invalid for Authentication Type."
    ::= { bfdEventsGroup 50 }

bfd50-authentication-length OBJECT-TYPE
    SYNTAX Integer32
    MAX-ACCESS accessible-for-notify
    STATUS current
    DESCRIPTION
        "Parameter 'authentication-length' in event BFD.50"
    ::= { bfdEventObjects50 1 }

bfd50-peer-address OBJECT-TYPE
    SYNTAX DisplayString
    MAX-ACCESS accessible-for-notify
    STATUS current
    DESCRIPTION
        "Parameter 'peer-address' in event BFD.50"
    ::= { bfdEventObjects50 2 }

bfdEventObjects51 OBJECT-IDENTITY
    STATUS current
    DESCRIPTION
        "Event BFD.51
        The protocol is not able to find received Key ID inside Key Chain, maybe
        it is not configured."
    ::= { bfdEventsGroup 51 }

bfd51-key-identifier OBJECT-TYPE
    SYNTAX Integer32
    MAX-ACCESS accessible-for-notify
    STATUS current
    DESCRIPTION
        "Parameter 'key-identifier' in event BFD.51"
    ::= { bfdEventObjects51 1 }

bfd51-keychain-name OBJECT-TYPE
    SYNTAX DisplayString
    MAX-ACCESS accessible-for-notify
    STATUS current
    DESCRIPTION
        "Parameter 'keychain-name' in event BFD.51"
    ::= { bfdEventObjects51 2 }

bfd51-peer-address OBJECT-TYPE
    SYNTAX DisplayString
    MAX-ACCESS accessible-for-notify
    STATUS current
    DESCRIPTION
        "Parameter 'peer-address' in event BFD.51"
    ::= { bfdEventObjects51 3 }

bfdEventObjects52 OBJECT-IDENTITY
    STATUS current
    DESCRIPTION
        "Event BFD.52
        A packet with authentication has been received but authentication
        sequence number is invalid."
    ::= { bfdEventsGroup 52 }

bfd52-authentication-seqnum OBJECT-TYPE
    SYNTAX Integer32
    MAX-ACCESS accessible-for-notify
    STATUS current
    DESCRIPTION
        "Parameter 'authentication-seqnum' in event BFD.52"
    ::= { bfdEventObjects52 1 }

bfd52-peer-address OBJECT-TYPE
    SYNTAX DisplayString
    MAX-ACCESS accessible-for-notify
    STATUS current
    DESCRIPTION
        "Parameter 'peer-address' in event BFD.52"
    ::= { bfdEventObjects52 2 }

bfd52-last-authentication-seqnum OBJECT-TYPE
    SYNTAX Integer32
    MAX-ACCESS accessible-for-notify
    STATUS current
    DESCRIPTION
        "Parameter 'last-authentication-seqnum' in event BFD.52"
    ::= { bfdEventObjects52 3 }

bfdEventObjects53 OBJECT-IDENTITY
    STATUS current
    DESCRIPTION
        "Event BFD.53
        A packet with authentication has been received but authentication
        digest is invalid."
    ::= { bfdEventsGroup 53 }

bfd53-peer-address OBJECT-TYPE
    SYNTAX DisplayString
    MAX-ACCESS accessible-for-notify
    STATUS current
    DESCRIPTION
        "Parameter 'peer-address' in event BFD.53"
    ::= { bfdEventObjects53 1 }


bfdNotification1 NOTIFICATION-TYPE
    STATUS current
    DESCRIPTION
        "Notification of Event BFD.1

        Message: 'Error receiving from BFD socket'

        The BFD protocol receive function has failed."
    ::= { bfdNotificationsPrefix 1 }

bfdNotification2 NOTIFICATION-TYPE
    OBJECTS { 
              bfd2-ttl-received, 
              bfd2-peer-address 
            }
    STATUS current
    DESCRIPTION
        "Notification of Event BFD.2

        Message: 'Received pkt with invalid TTL $1 from $2'

        Parameters list:
              $1: bfd2-ttl-received
              $2: bfd2-peer-address

        A BFD packet with invalid TTL value has been received."
    ::= { bfdNotificationsPrefix 2 }

bfdNotification3 NOTIFICATION-TYPE
    OBJECTS { 
              bfd3-peer-address 
            }
    STATUS current
    DESCRIPTION
        "Notification of Event BFD.3

        Message: 'Received short packet from $1'

        Parameters list:
              $1: bfd3-peer-address

        A BFD packet with invalid size has been received."
    ::= { bfdNotificationsPrefix 3 }

bfdNotification4 NOTIFICATION-TYPE
    OBJECTS { 
              bfd4-protocol-version, 
              bfd4-peer-address 
            }
    STATUS current
    DESCRIPTION
        "Notification of Event BFD.4

        Message: 'Received bad version $1 from $2'

        Parameters list:
              $1: bfd4-protocol-version
              $2: bfd4-peer-address

        A BFD packet with invalid BFD version has been received."
    ::= { bfdNotificationsPrefix 4 }

bfdNotification5 NOTIFICATION-TYPE
    OBJECTS { 
              bfd5-packet-legth, 
              bfd5-peer-address 
            }
    STATUS current
    DESCRIPTION
        "Notification of Event BFD.5

        Message: 'Invalid length $1 in control pkt from $2'

        Parameters list:
              $1: bfd5-packet-legth
              $2: bfd5-peer-address

        A BFD packet with invalid length has been received."
    ::= { bfdNotificationsPrefix 5 }

bfdNotification6 NOTIFICATION-TYPE
    OBJECTS { 
              bfd6-peer-address 
            }
    STATUS current
    DESCRIPTION
        "Notification of Event BFD.6

        Message: 'Detect Mult is zero in pkt from $1'

        Parameters list:
              $1: bfd6-peer-address

        A BFD packet with zero detect time multiplier has been received."
    ::= { bfdNotificationsPrefix 6 }

bfdNotification7 NOTIFICATION-TYPE
    OBJECTS { 
              bfd7-peer-address 
            }
    STATUS current
    DESCRIPTION
        "Notification of Event BFD.7

        Message: 'My discriminator is zero in pkt from $1'

        Parameters list:
              $1: bfd7-peer-address

        A BFD packet with zero in the My Discriminator field has been received."
    ::= { bfdNotificationsPrefix 7 }

bfdNotification8 NOTIFICATION-TYPE
    OBJECTS { 
              bfd8-peer-address 
            }
    STATUS current
    DESCRIPTION
        "Notification of Event BFD.8

        Message: 'Zero Your Discriminator and non-zero I Hear You in pkt from $1'

        Parameters list:
              $1: bfd8-peer-address

        A BFD packet with zero in the Your Duscriminator field and non-zero
        in the I Hear You flag has been received."
    ::= { bfdNotificationsPrefix 8 }

bfdNotification9 NOTIFICATION-TYPE
    OBJECTS { 
              bfd9-peer-address 
            }
    STATUS current
    DESCRIPTION
        "Notification of Event BFD.9

        Message: 'Can not find session for ctl pkt from $1'

        Parameters list:
              $1: bfd9-peer-address

        The system could not find a valid session for the BFD packet received."
    ::= { bfdNotificationsPrefix 9 }

bfdNotification10 NOTIFICATION-TYPE
    OBJECTS { 
              bfd10-session-disc, 
              bfd10-peer-address 
            }
    STATUS current
    DESCRIPTION
        "Notification of Event BFD.10

        Message: 'Timer renegotiation started for session 0x$1 to peer $2'

        Parameters list:
              $1: bfd10-session-disc
              $2: bfd10-peer-address

        Some of the BFD definition parameters has changed and timers must be
        renegotiated."
    ::= { bfdNotificationsPrefix 10 }

bfdNotification11 NOTIFICATION-TYPE
    OBJECTS { 
              bfd11-session-disc, 
              bfd11-peer-address 
            }
    STATUS current
    DESCRIPTION
        "Notification of Event BFD.11

        Message: 'Poll sequence concluded for session 0x$1 to peer $2'

        Parameters list:
              $1: bfd11-session-disc
              $2: bfd11-peer-address

        A BFD poll sequence has been finished."
    ::= { bfdNotificationsPrefix 11 }

bfdNotification12 NOTIFICATION-TYPE
    OBJECTS { 
              bfd12-session-disc, 
              bfd12-peer-address 
            }
    STATUS current
    DESCRIPTION
        "Notification of Event BFD.12

        Message: 'Neigbor down on session 0x$1 with peer $2'

        Parameters list:
              $1: bfd12-session-disc
              $2: bfd12-peer-address

        A BFD session is coming to DOWN state because remote peer is 
        administratively down."
    ::= { bfdNotificationsPrefix 12 }

bfdNotification13 NOTIFICATION-TYPE
    OBJECTS { 
              bfd13-session-disc, 
              bfd13-peer-address,
              bfd13-bfd-state 
            }
    STATUS current
    DESCRIPTION
        "Notification of Event BFD.13

        Message: 'Detect timeout on session 0x$1 with peer $2, in state $3'

        Parameters list:
              $1: bfd13-session-disc
              $2: bfd13-peer-address
              $3: bfd13-bfd-state

        The detection period has been finished without receiving packets from
        the remote peer. Session will come down."
    ::= { bfdNotificationsPrefix 13 }

bfdNotification14 NOTIFICATION-TYPE
    OBJECTS { 
              bfd14-session-disc, 
              bfd14-peer-address 
            }
    STATUS current
    DESCRIPTION
        "Notification of Event BFD.14

        Message: 'Session 0x$1 down to peer $2'

        Parameters list:
              $1: bfd14-session-disc
              $2: bfd14-peer-address

        A BFD session is coming to DOWN state."
    ::= { bfdNotificationsPrefix 14 }

bfdNotification15 NOTIFICATION-TYPE
    OBJECTS { 
              bfd15-session-disc, 
              bfd15-peer-address 
            }
    STATUS current
    DESCRIPTION
        "Notification of Event BFD.15

        Message: 'Session 0x$1 up to peer $2'

        Parameters list:
              $1: bfd15-session-disc
              $2: bfd15-peer-address

        A BFD session is coming to UP state."
    ::= { bfdNotificationsPrefix 15 }

bfdNotification16 NOTIFICATION-TYPE
    OBJECTS { 
              bfd16-session-disc, 
              bfd16-peer-address 
            }
    STATUS current
    DESCRIPTION
        "Notification of Event BFD.16

        Message: 'Can not find session for yourDisc 0x$1 from $2'

        Parameters list:
              $1: bfd16-session-disc
              $2: bfd16-peer-address

        A BFD session with this value of Your Discriminator does not exist in
        the system."
    ::= { bfdNotificationsPrefix 16 }

bfdNotification17 NOTIFICATION-TYPE
    OBJECTS { 
              bfd17-peer-address 
            }
    STATUS current
    DESCRIPTION
        "Notification of Event BFD.17

        Message: 'Can not find session for peer $1'

        Parameters list:
              $1: bfd17-peer-address

        A BFD session with this peer does not exist in the system."
    ::= { bfdNotificationsPrefix 17 }

bfdNotification18 NOTIFICATION-TYPE
    OBJECTS { 
              bfd18-peer-address 
            }
    STATUS current
    DESCRIPTION
        "Notification of Event BFD.18

        Message: 'Error sending control pkt to peer $1'

        Parameters list:
              $1: bfd18-peer-address

        The BFD protocol sending function has failed."
    ::= { bfdNotificationsPrefix 18 }

bfdNotification19 NOTIFICATION-TYPE
    OBJECTS { 
              bfd19-peer-address 
            }
    STATUS current
    DESCRIPTION
        "Notification of Event BFD.19

        Message: 'Can not malloc memory for new session for peer $1'

        Parameters list:
              $1: bfd19-peer-address

        The system has not enough memory to allocate a new BFD session."
    ::= { bfdNotificationsPrefix 19 }

bfdNotification20 NOTIFICATION-TYPE
    OBJECTS { 
              bfd20-peer-address 
            }
    STATUS current
    DESCRIPTION
        "Notification of Event BFD.20

        Message: 'Can not get socket for new session for peer $1'

        Parameters list:
              $1: bfd20-peer-address

        The system can not get a free socket for a new BFD session."
    ::= { bfdNotificationsPrefix 20 }

bfdNotification21 NOTIFICATION-TYPE
    OBJECTS { 
              bfd21-peer-address 
            }
    STATUS current
    DESCRIPTION
        "Notification of Event BFD.21

        Message: 'Can not set TTL for new session for peer $1'

        Parameters list:
              $1: bfd21-peer-address

        The system can not set TTL value for a new BFD session."
    ::= { bfdNotificationsPrefix 21 }

bfdNotification22 NOTIFICATION-TYPE
    OBJECTS { 
              bfd22-peer-address 
            }
    STATUS current
    DESCRIPTION
        "Notification of Event BFD.22

        Message: 'Can not find source port for new session for peer $1'

        Parameters list:
              $1: bfd22-peer-address

        The system can not find a free source port for a new BFD session."
    ::= { bfdNotificationsPrefix 22 }

bfdNotification23 NOTIFICATION-TYPE
    OBJECTS { 
              bfd23-session-disc, 
              bfd23-local-address,
              bfd23-peer-address 
            }
    STATUS current
    DESCRIPTION
        "Notification of Event BFD.23

        Message: 'Created new session 0x$1 from $2 to peer $3'

        Parameters list:
              $1: bfd23-session-disc
              $2: bfd23-local-address
              $3: bfd23-peer-address

        A new BFD session has been successfully created."
    ::= { bfdNotificationsPrefix 23 }

bfdNotification24 NOTIFICATION-TYPE
    OBJECTS { 
              bfd24-session-disc 
            }
    STATUS current
    DESCRIPTION
        "Notification of Event BFD.24

        Message: 'Can not find session 0x$1 in session hash'

        Parameters list:
              $1: bfd24-session-disc

        The session that is been deleted does not exsist in the session hash."
    ::= { bfdNotificationsPrefix 24 }

bfdNotification25 NOTIFICATION-TYPE
    OBJECTS { 
              bfd25-session-disc 
            }
    STATUS current
    DESCRIPTION
        "Notification of Event BFD.25

        Message: 'Can not find session 0x$1 in peer hash'

        Parameters list:
              $1: bfd25-session-disc

        The session that is been deleted does not exsist in the peer hash."
    ::= { bfdNotificationsPrefix 25 }

bfdNotification26 NOTIFICATION-TYPE
    OBJECTS { 
              bfd26-session-disc 
            }
    STATUS current
    DESCRIPTION
        "Notification of Event BFD.26

        Message: 'Can not find session 0x$1 in session list'

        Parameters list:
              $1: bfd26-session-disc

        The session that is been deleted does not exsist in the session list."
    ::= { bfdNotificationsPrefix 26 }

bfdNotification27 NOTIFICATION-TYPE
    OBJECTS { 
              bfd27-session-disc, 
              bfd27-peer-address,
              bfd27-detect-timer 
            }
    STATUS current
    DESCRIPTION
        "Notification of Event BFD.27

        Message: 'Poll sequence started for session 0x$1 to peer $2, timer $3'

        Parameters list:
              $1: bfd27-session-disc
              $2: bfd27-peer-address
              $3: bfd27-detect-timer

        A BFD poll sequence has been started."
    ::= { bfdNotificationsPrefix 27 }

bfdNotification28 NOTIFICATION-TYPE
    OBJECTS { 
              bfd28-session-disc, 
              bfd28-peer-address 
            }
    STATUS current
    DESCRIPTION
        "Notification of Event BFD.28

        Message: 'Session 0x$1 to peer $2 enabled'

        Parameters list:
              $1: bfd28-session-disc
              $2: bfd28-peer-address

        The session is administratively enabled."
    ::= { bfdNotificationsPrefix 28 }

bfdNotification29 NOTIFICATION-TYPE
    OBJECTS { 
              bfd29-session-disc, 
              bfd29-peer-address 
            }
    STATUS current
    DESCRIPTION
        "Notification of Event BFD.29

        Message: 'Session 0x$1 to peer $2 disabled'

        Parameters list:
              $1: bfd29-session-disc
              $2: bfd29-peer-address

        The session is administratively disabled."
    ::= { bfdNotificationsPrefix 29 }

bfdNotification30 NOTIFICATION-TYPE
    STATUS current
    DESCRIPTION
        "Notification of Event BFD.30

        Message: 'Can not get receive socket'

        The system can not get a free socket for the BFD packet reception."
    ::= { bfdNotificationsPrefix 30 }

bfdNotification31 NOTIFICATION-TYPE
    STATUS current
    DESCRIPTION
        "Notification of Event BFD.31

        Message: 'Can not set TTL for outgoing packets'

        The system can not set TTL value for outgoing BFD packets."
    ::= { bfdNotificationsPrefix 31 }

bfdNotification32 NOTIFICATION-TYPE
    STATUS current
    DESCRIPTION
        "Notification of Event BFD.32

        Message: 'Can not set receive TTL for incoming packets'

        The system can not set TTL value for incoming BFD packets."
    ::= { bfdNotificationsPrefix 32 }

bfdNotification33 NOTIFICATION-TYPE
    OBJECTS { 
              bfd33-port-number 
            }
    STATUS current
    DESCRIPTION
        "Notification of Event BFD.33

        Message: 'Can not bind socket to default port $1'

        Parameters list:
              $1: bfd33-port-number

        The system can not bind a socket to the BFD destination port."
    ::= { bfdNotificationsPrefix 33 }

bfdNotification34 NOTIFICATION-TYPE
    OBJECTS { 
              bfd34-protocol-name, 
              bfd34-session-disc,
              bfd34-local-address,
              bfd34-peer-address 
            }
    STATUS current
    DESCRIPTION
        "Notification of Event BFD.34

        Message: 'Routing protocol $1 registered in session 0x$2 from $3 to peer $4'

        Parameters list:
              $1: bfd34-protocol-name
              $2: bfd34-session-disc
              $3: bfd34-local-address
              $4: bfd34-peer-address

        A routing protocol has been succesfully registered in a BFD session."
    ::= { bfdNotificationsPrefix 34 }

bfdNotification35 NOTIFICATION-TYPE
    OBJECTS { 
              bfd35-local-address, 
              bfd35-peer-address 
            }
    STATUS current
    DESCRIPTION
        "Notification of Event BFD.35

        Message: 'Can not create session from $1 to peer $2'

        Parameters list:
              $1: bfd35-local-address
              $2: bfd35-peer-address

        The session can not be created."
    ::= { bfdNotificationsPrefix 35 }

bfdNotification36 NOTIFICATION-TYPE
    OBJECTS { 
              bfd36-peer-address, 
              bfd36-session-disc,
              bfd36-bfd-state 
            }
    STATUS current
    DESCRIPTION
        "Notification of Event BFD.36

        Message: 'A session already exists with peer $1, session: 0x$2, state: $3'

        Parameters list:
              $1: bfd36-peer-address
              $2: bfd36-session-disc
              $3: bfd36-bfd-state

        There is no need to create a new BFD session with the peer, a session
        already exists."
    ::= { bfdNotificationsPrefix 36 }

bfdNotification37 NOTIFICATION-TYPE
    OBJECTS { 
              bfd37-session-disc, 
              bfd37-bfd-prev-state,
              bfd37-bfd-new-state 
            }
    STATUS current
    DESCRIPTION
        "Notification of Event BFD.37

        Message: 'BFD session 0x$1 state change $2 -> $3'

        Parameters list:
              $1: bfd37-session-disc
              $2: bfd37-bfd-prev-state
              $3: bfd37-bfd-new-state

        A change in the BFD state machine has happened."
    ::= { bfdNotificationsPrefix 37 }

bfdNotification38 NOTIFICATION-TYPE
    OBJECTS { 
              bfd38-local-address, 
              bfd38-peer-address,
              bfd38-bfdversion,
              bfd38-diag-code,
              bfd38-flags,
              bfd38-detetct-mult,
              bfd38-pkt-len 
            }
    STATUS current
    DESCRIPTION
        "Notification of Event BFD.38

        Message: 'TxPkt src:$1 dst:$2 ver:$3 diag:$4 $5 mult:$6 len:$7'

        Parameters list:
              $1: bfd38-local-address
              $2: bfd38-peer-address
              $3: bfd38-bfdversion
              $4: bfd38-diag-code
              $5: bfd38-flags
              $6: bfd38-detetct-mult
              $7: bfd38-pkt-len

        A packet has been sent to a neighbour."
    ::= { bfdNotificationsPrefix 38 }

bfdNotification39 NOTIFICATION-TYPE
    OBJECTS { 
              bfd39-peer-address, 
              bfd39-local-address,
              bfd39-bfdversion,
              bfd39-diag-code,
              bfd39-flags,
              bfd39-detetct-mult,
              bfd39-pkt-len 
            }
    STATUS current
    DESCRIPTION
        "Notification of Event BFD.39

        Message: 'RxPkt src:$1 dst:$2 ver:$3 diag:$4 $5 mult:$6 len:$7'

        Parameters list:
              $1: bfd39-peer-address
              $2: bfd39-local-address
              $3: bfd39-bfdversion
              $4: bfd39-diag-code
              $5: bfd39-flags
              $6: bfd39-detetct-mult
              $7: bfd39-pkt-len

        A packet has been received from a neighbour."
    ::= { bfdNotificationsPrefix 39 }

bfdNotification40 NOTIFICATION-TYPE
    OBJECTS { 
              bfd40-mydisc, 
              bfd40-yourdisc,
              bfd40-des-mintx,
              bfd40-req-minrx,
              bfd40-req-minechorx 
            }
    STATUS current
    DESCRIPTION
        "Notification of Event BFD.40

        Message: 'mydisc:0x$1 ydisc:0x$2 Dmtx:$3 Rmtx:$4 Rmerx:$5'

        Parameters list:
              $1: bfd40-mydisc
              $2: bfd40-yourdisc
              $3: bfd40-des-mintx
              $4: bfd40-req-minrx
              $5: bfd40-req-minechorx

        This event shows the BFD packet body contents."
    ::= { bfdNotificationsPrefix 40 }

bfdNotification41 NOTIFICATION-TYPE
    STATUS current
    DESCRIPTION
        "Notification of Event BFD.41

        Message: 'Disable this event to disable event packet sampling'

        By disabling this event all received and sent packets will display
        an event. "
    ::= { bfdNotificationsPrefix 41 }

bfdNotification42 NOTIFICATION-TYPE
    OBJECTS { 
              bfd42-intfc-addr, 
              bfd42-protocol 
            }
    STATUS current
    DESCRIPTION
        "Notification of Event BFD.42

        Message: 'Could not find BFD configuration for interface with addr: $1, protocol $2 registration failed'

        Parameters list:
              $1: bfd42-intfc-addr
              $2: bfd42-protocol

        The BFD parameter configuration does not exist or an interface with
        this IP address does not exist. Protocol can not be registered. "
    ::= { bfdNotificationsPrefix 42 }

bfdNotification43 NOTIFICATION-TYPE
    OBJECTS { 
              bfd43-peer-address 
            }
    STATUS current
    DESCRIPTION
        "Notification of Event BFD.43

        Message: 'Zero Your Discriminator and peer state not DOWN in pkt from $1'

        Parameters list:
              $1: bfd43-peer-address

        A BFD packet with zero in the Your Duscriminator field and with not Down
        or Admindown in the state field has been received."
    ::= { bfdNotificationsPrefix 43 }

bfdNotification44 NOTIFICATION-TYPE
    OBJECTS { 
              bfd44-protocol-name, 
              bfd44-session-disc,
              bfd44-local-address,
              bfd44-peer-address 
            }
    STATUS current
    DESCRIPTION
        "Notification of Event BFD.44

        Message: 'Routing protocol $1 registered in session 0x$2 from $3 to peer $4 is being deleted'

        Parameters list:
              $1: bfd44-protocol-name
              $2: bfd44-session-disc
              $3: bfd44-local-address
              $4: bfd44-peer-address

        A routing protocol registered in a BFD session is being deleted."
    ::= { bfdNotificationsPrefix 44 }

bfdNotification45 NOTIFICATION-TYPE
    OBJECTS { 
              bfd45-keychain-name 
            }
    STATUS current
    DESCRIPTION
        "Notification of Event BFD.45

        Message: 'Can not find Key Chain $1, check configuration to resolve the problem'

        Parameters list:
              $1: bfd45-keychain-name

        The Key Chain is probably not configured, so the protocol is not able to
        find it."
    ::= { bfdNotificationsPrefix 45 }

bfdNotification46 NOTIFICATION-TYPE
    OBJECTS { 
              bfd46-keychain-name 
            }
    STATUS current
    DESCRIPTION
        "Notification of Event BFD.46

        Message: 'Can not find a valid Key inside Key Chain $1, check configuration to resolve the problem'

        Parameters list:
              $1: bfd46-keychain-name

        The protocol is not able to find a valid Key inside the Key Chain, maybe
        it is not configured."
    ::= { bfdNotificationsPrefix 46 }

bfdNotification47 NOTIFICATION-TYPE
    OBJECTS { 
              bfd47-peer-address, 
              bfd47-authentication-type 
            }
    STATUS current
    DESCRIPTION
        "Notification of Event BFD.47

        Message: 'Received packet from peer $1 without authentication, $2 authentication required for this session'

        Parameters list:
              $1: bfd47-peer-address
              $2: bfd47-authentication-type

        A packet without authentication has been received but session requires
        authentication. The packet will be discarded and ignored."
    ::= { bfdNotificationsPrefix 47 }

bfdNotification48 NOTIFICATION-TYPE
    OBJECTS { 
              bfd48-authentication-type, 
              bfd48-peer-address 
            }
    STATUS current
    DESCRIPTION
        "Notification of Event BFD.48

        Message: 'Received wrong $1 authentication type from peer $2'

        Parameters list:
              $1: bfd48-authentication-type
              $2: bfd48-peer-address

        A packet with authentication has been received but authentication type
        is not correct for the configured session. The packet will be discarded
        and ignored."
    ::= { bfdNotificationsPrefix 48 }

bfdNotification49 NOTIFICATION-TYPE
    OBJECTS { 
              bfd49-key-identifier, 
              bfd49-peer-address 
            }
    STATUS current
    DESCRIPTION
        "Notification of Event BFD.49

        Message: 'Invalid Key ID $1 received from peer $2'

        Parameters list:
              $1: bfd49-key-identifier
              $2: bfd49-peer-address

        A packet with authentication has been received but the Key ID is invalid
        for the configured session. Check both remote and local configurations."
    ::= { bfdNotificationsPrefix 49 }

bfdNotification50 NOTIFICATION-TYPE
    OBJECTS { 
              bfd50-authentication-length, 
              bfd50-peer-address 
            }
    STATUS current
    DESCRIPTION
        "Notification of Event BFD.50

        Message: 'Received invalid authentication length $1 from peer $2'

        Parameters list:
              $1: bfd50-authentication-length
              $2: bfd50-peer-address

        A packet with authentication has been received but authentication
        length is invalid for Authentication Type."
    ::= { bfdNotificationsPrefix 50 }

bfdNotification51 NOTIFICATION-TYPE
    OBJECTS { 
              bfd51-key-identifier, 
              bfd51-keychain-name,
              bfd51-peer-address 
            }
    STATUS current
    DESCRIPTION
        "Notification of Event BFD.51

        Message: 'Can not find Key ID $1 inside Key Chain $2, for peer $3'

        Parameters list:
              $1: bfd51-key-identifier
              $2: bfd51-keychain-name
              $3: bfd51-peer-address

        The protocol is not able to find received Key ID inside Key Chain, maybe
        it is not configured."
    ::= { bfdNotificationsPrefix 51 }

bfdNotification52 NOTIFICATION-TYPE
    OBJECTS { 
              bfd52-authentication-seqnum, 
              bfd52-peer-address,
              bfd52-last-authentication-seqnum 
            }
    STATUS current
    DESCRIPTION
        "Notification of Event BFD.52

        Message: 'Received invalid authentication sequence number $1 from peer $2, last was $3'

        Parameters list:
              $1: bfd52-authentication-seqnum
              $2: bfd52-peer-address
              $3: bfd52-last-authentication-seqnum

        A packet with authentication has been received but authentication
        sequence number is invalid."
    ::= { bfdNotificationsPrefix 52 }

bfdNotification53 NOTIFICATION-TYPE
    OBJECTS { 
              bfd53-peer-address 
            }
    STATUS current
    DESCRIPTION
        "Notification of Event BFD.53

        Message: 'Authentication fail in packet received from peer $1'

        Parameters list:
              $1: bfd53-peer-address

        A packet with authentication has been received but authentication
        digest is invalid."
    ::= { bfdNotificationsPrefix 53 }


END
