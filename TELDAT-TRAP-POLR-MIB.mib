-- file automatically created


TELDAT-TRAP-POLR-MIB DEFINITIONS ::= BEGIN


IMPORTS
	MODULE-IDENTITY,OBJECT-TYPE,OBJECT-IDENTITY,NOTIFICATION-TYPE,Integer32,IpAddress
		FROM SNMPv2-SMI
	DisplayString
		FROM SNMPv2-TC
	telEventTraps
		FROM TELDAT-MIB;


polrTrapsMIB MODULE-IDENTITY
    LAST-UPDATED "201401200930Z"
    ORGANIZATION "Teldat, S.A."
    CONTACT-INFO 
        "Teldat, S.A.
        Customer Service

        Postal: Parque Tecnologico de Madrid
                Tres Cantos 28760
                Madrid, SPAIN

        Tel.: +34 918 076 565

        http://www.teldat.com"
    DESCRIPTION
        "This Module Information Base file is defined for managing received
        SNMP notifications generated by the POLR event subsystem."
    REVISION "201401200930Z"
    DESCRIPTION "Initial implementation"
        ::= { telEventTraps 162 }


polrEventsGroup	OBJECT IDENTIFIER	::= { polrTrapsMIB 1 }

polrNotifications	OBJECT IDENTIFIER	::= { polrTrapsMIB 2 }
polrNotificationsPrefix	OBJECT IDENTIFIER	::= { polrNotifications 0 }

polrEventObjects1 OBJECT-IDENTITY
    STATUS current
    DESCRIPTION
        "Event POLR.1
        A packet was generated from specified address for specified address.
        Packet length and protocol are also shown. This packet will be tested
        for policy routing."
    ::= { polrEventsGroup 1 }

polr1-srcaddr OBJECT-TYPE
    SYNTAX IpAddress
    MAX-ACCESS accessible-for-notify
    STATUS current
    DESCRIPTION
        "Parameter 'srcaddr' in event POLR.1"
    ::= { polrEventObjects1 1 }

polr1-dstaddr OBJECT-TYPE
    SYNTAX IpAddress
    MAX-ACCESS accessible-for-notify
    STATUS current
    DESCRIPTION
        "Parameter 'dstaddr' in event POLR.1"
    ::= { polrEventObjects1 2 }

polr1-length OBJECT-TYPE
    SYNTAX Integer32
    MAX-ACCESS accessible-for-notify
    STATUS current
    DESCRIPTION
        "Parameter 'length' in event POLR.1"
    ::= { polrEventObjects1 3 }

polr1-protocol OBJECT-TYPE
    SYNTAX Integer32
    MAX-ACCESS accessible-for-notify
    STATUS current
    DESCRIPTION
        "Parameter 'protocol' in event POLR.1"
    ::= { polrEventObjects1 4 }

polrEventObjects2 OBJECT-IDENTITY
    STATUS current
    DESCRIPTION
        "Event POLR.2
        A packet was received from specified address for specified address, on
        specified interface. Packet length and protocol are also shown. This
        packet will be tested for policy routing."
    ::= { polrEventsGroup 2 }

polr2-srcaddr OBJECT-TYPE
    SYNTAX IpAddress
    MAX-ACCESS accessible-for-notify
    STATUS current
    DESCRIPTION
        "Parameter 'srcaddr' in event POLR.2"
    ::= { polrEventObjects2 1 }

polr2-dstaddr OBJECT-TYPE
    SYNTAX IpAddress
    MAX-ACCESS accessible-for-notify
    STATUS current
    DESCRIPTION
        "Parameter 'dstaddr' in event POLR.2"
    ::= { polrEventObjects2 2 }

polr2-length OBJECT-TYPE
    SYNTAX Integer32
    MAX-ACCESS accessible-for-notify
    STATUS current
    DESCRIPTION
        "Parameter 'length' in event POLR.2"
    ::= { polrEventObjects2 3 }

polr2-protocol OBJECT-TYPE
    SYNTAX Integer32
    MAX-ACCESS accessible-for-notify
    STATUS current
    DESCRIPTION
        "Parameter 'protocol' in event POLR.2"
    ::= { polrEventObjects2 4 }

polr2-interface OBJECT-TYPE
    SYNTAX DisplayString
    MAX-ACCESS accessible-for-notify
    STATUS current
    DESCRIPTION
        "Parameter 'interface' in event POLR.2"
    ::= { polrEventObjects2 5 }

polrEventObjects4 OBJECT-IDENTITY
    STATUS current
    DESCRIPTION
        "Event POLR.4
        No route map associated to specified interface."
    ::= { polrEventsGroup 4 }

polr4-interface OBJECT-TYPE
    SYNTAX DisplayString
    MAX-ACCESS accessible-for-notify
    STATUS current
    DESCRIPTION
        "Parameter 'interface' in event POLR.4"
    ::= { polrEventObjects4 1 }

polrEventObjects5 OBJECT-IDENTITY
    STATUS current
    DESCRIPTION
        "Event POLR.5
        A packet was generated from specified address for specified address.
        Packet length and protocol are also shown. This packet did not match the
        specified route map."
    ::= { polrEventsGroup 5 }

polr5-srcaddr OBJECT-TYPE
    SYNTAX IpAddress
    MAX-ACCESS accessible-for-notify
    STATUS current
    DESCRIPTION
        "Parameter 'srcaddr' in event POLR.5"
    ::= { polrEventObjects5 1 }

polr5-dstaddr OBJECT-TYPE
    SYNTAX IpAddress
    MAX-ACCESS accessible-for-notify
    STATUS current
    DESCRIPTION
        "Parameter 'dstaddr' in event POLR.5"
    ::= { polrEventObjects5 2 }

polr5-length OBJECT-TYPE
    SYNTAX Integer32
    MAX-ACCESS accessible-for-notify
    STATUS current
    DESCRIPTION
        "Parameter 'length' in event POLR.5"
    ::= { polrEventObjects5 3 }

polr5-protocol OBJECT-TYPE
    SYNTAX Integer32
    MAX-ACCESS accessible-for-notify
    STATUS current
    DESCRIPTION
        "Parameter 'protocol' in event POLR.5"
    ::= { polrEventObjects5 4 }

polr5-routemap OBJECT-TYPE
    SYNTAX DisplayString
    MAX-ACCESS accessible-for-notify
    STATUS current
    DESCRIPTION
        "Parameter 'routemap' in event POLR.5"
    ::= { polrEventObjects5 5 }

polrEventObjects6 OBJECT-IDENTITY
    STATUS current
    DESCRIPTION
        "Event POLR.6
        A packet was received from specified address for specified address, on
        specified interface. Packet length and protocol are also shown. This
        packet did not match the specified route map."
    ::= { polrEventsGroup 6 }

polr6-srcaddr OBJECT-TYPE
    SYNTAX IpAddress
    MAX-ACCESS accessible-for-notify
    STATUS current
    DESCRIPTION
        "Parameter 'srcaddr' in event POLR.6"
    ::= { polrEventObjects6 1 }

polr6-dstaddr OBJECT-TYPE
    SYNTAX IpAddress
    MAX-ACCESS accessible-for-notify
    STATUS current
    DESCRIPTION
        "Parameter 'dstaddr' in event POLR.6"
    ::= { polrEventObjects6 2 }

polr6-length OBJECT-TYPE
    SYNTAX Integer32
    MAX-ACCESS accessible-for-notify
    STATUS current
    DESCRIPTION
        "Parameter 'length' in event POLR.6"
    ::= { polrEventObjects6 3 }

polr6-protocol OBJECT-TYPE
    SYNTAX Integer32
    MAX-ACCESS accessible-for-notify
    STATUS current
    DESCRIPTION
        "Parameter 'protocol' in event POLR.6"
    ::= { polrEventObjects6 4 }

polr6-interface OBJECT-TYPE
    SYNTAX DisplayString
    MAX-ACCESS accessible-for-notify
    STATUS current
    DESCRIPTION
        "Parameter 'interface' in event POLR.6"
    ::= { polrEventObjects6 5 }

polr6-routemap OBJECT-TYPE
    SYNTAX DisplayString
    MAX-ACCESS accessible-for-notify
    STATUS current
    DESCRIPTION
        "Parameter 'routemap' in event POLR.6"
    ::= { polrEventObjects6 6 }

polrEventObjects7 OBJECT-IDENTITY
    STATUS current
    DESCRIPTION
        "Event POLR.7
        A packet was generated from specified address for specified address.
        Packet length and protocol are also shown. This packet did match the
        specified entry of the specified route map."
    ::= { polrEventsGroup 7 }

polr7-srcaddr OBJECT-TYPE
    SYNTAX IpAddress
    MAX-ACCESS accessible-for-notify
    STATUS current
    DESCRIPTION
        "Parameter 'srcaddr' in event POLR.7"
    ::= { polrEventObjects7 1 }

polr7-dstaddr OBJECT-TYPE
    SYNTAX IpAddress
    MAX-ACCESS accessible-for-notify
    STATUS current
    DESCRIPTION
        "Parameter 'dstaddr' in event POLR.7"
    ::= { polrEventObjects7 2 }

polr7-length OBJECT-TYPE
    SYNTAX Integer32
    MAX-ACCESS accessible-for-notify
    STATUS current
    DESCRIPTION
        "Parameter 'length' in event POLR.7"
    ::= { polrEventObjects7 3 }

polr7-protocol OBJECT-TYPE
    SYNTAX Integer32
    MAX-ACCESS accessible-for-notify
    STATUS current
    DESCRIPTION
        "Parameter 'protocol' in event POLR.7"
    ::= { polrEventObjects7 4 }

polr7-routemap OBJECT-TYPE
    SYNTAX DisplayString
    MAX-ACCESS accessible-for-notify
    STATUS current
    DESCRIPTION
        "Parameter 'routemap' in event POLR.7"
    ::= { polrEventObjects7 5 }

polr7-entrynumber OBJECT-TYPE
    SYNTAX Integer32
    MAX-ACCESS accessible-for-notify
    STATUS current
    DESCRIPTION
        "Parameter 'entrynumber' in event POLR.7"
    ::= { polrEventObjects7 6 }

polrEventObjects8 OBJECT-IDENTITY
    STATUS current
    DESCRIPTION
        "Event POLR.8
        A packet was received from specified address for specified address, on
        specified interface. Packet length and protocol are also shown. This
        packet did match the specified entry of the specified route map."
    ::= { polrEventsGroup 8 }

polr8-srcaddr OBJECT-TYPE
    SYNTAX IpAddress
    MAX-ACCESS accessible-for-notify
    STATUS current
    DESCRIPTION
        "Parameter 'srcaddr' in event POLR.8"
    ::= { polrEventObjects8 1 }

polr8-dstaddr OBJECT-TYPE
    SYNTAX IpAddress
    MAX-ACCESS accessible-for-notify
    STATUS current
    DESCRIPTION
        "Parameter 'dstaddr' in event POLR.8"
    ::= { polrEventObjects8 2 }

polr8-length OBJECT-TYPE
    SYNTAX Integer32
    MAX-ACCESS accessible-for-notify
    STATUS current
    DESCRIPTION
        "Parameter 'length' in event POLR.8"
    ::= { polrEventObjects8 3 }

polr8-protocol OBJECT-TYPE
    SYNTAX Integer32
    MAX-ACCESS accessible-for-notify
    STATUS current
    DESCRIPTION
        "Parameter 'protocol' in event POLR.8"
    ::= { polrEventObjects8 4 }

polr8-interface OBJECT-TYPE
    SYNTAX DisplayString
    MAX-ACCESS accessible-for-notify
    STATUS current
    DESCRIPTION
        "Parameter 'interface' in event POLR.8"
    ::= { polrEventObjects8 5 }

polr8-routemap OBJECT-TYPE
    SYNTAX DisplayString
    MAX-ACCESS accessible-for-notify
    STATUS current
    DESCRIPTION
        "Parameter 'routemap' in event POLR.8"
    ::= { polrEventObjects8 6 }

polr8-entrynumber OBJECT-TYPE
    SYNTAX Integer32
    MAX-ACCESS accessible-for-notify
    STATUS current
    DESCRIPTION
        "Parameter 'entrynumber' in event POLR.8"
    ::= { polrEventObjects8 7 }

polrEventObjects9 OBJECT-IDENTITY
    STATUS current
    DESCRIPTION
        "Event POLR.9
        A packet was received from specified address for specified address. The
        tos field was changed from oldtos to newtos."
    ::= { polrEventsGroup 9 }

polr9-srcaddr OBJECT-TYPE
    SYNTAX IpAddress
    MAX-ACCESS accessible-for-notify
    STATUS current
    DESCRIPTION
        "Parameter 'srcaddr' in event POLR.9"
    ::= { polrEventObjects9 1 }

polr9-dstaddr OBJECT-TYPE
    SYNTAX IpAddress
    MAX-ACCESS accessible-for-notify
    STATUS current
    DESCRIPTION
        "Parameter 'dstaddr' in event POLR.9"
    ::= { polrEventObjects9 2 }

polr9-oldtos OBJECT-TYPE
    SYNTAX Integer32
    MAX-ACCESS accessible-for-notify
    STATUS current
    DESCRIPTION
        "Parameter 'oldtos' in event POLR.9"
    ::= { polrEventObjects9 3 }

polr9-newtos OBJECT-TYPE
    SYNTAX Integer32
    MAX-ACCESS accessible-for-notify
    STATUS current
    DESCRIPTION
        "Parameter 'newtos' in event POLR.9"
    ::= { polrEventObjects9 4 }

polrEventObjects10 OBJECT-IDENTITY
    STATUS current
    DESCRIPTION
        "Event POLR.10
        A packet was received from specified address for specified address. The
        next hop is set to the specified interface."
    ::= { polrEventsGroup 10 }

polr10-srcaddr OBJECT-TYPE
    SYNTAX IpAddress
    MAX-ACCESS accessible-for-notify
    STATUS current
    DESCRIPTION
        "Parameter 'srcaddr' in event POLR.10"
    ::= { polrEventObjects10 1 }

polr10-dstaddr OBJECT-TYPE
    SYNTAX IpAddress
    MAX-ACCESS accessible-for-notify
    STATUS current
    DESCRIPTION
        "Parameter 'dstaddr' in event POLR.10"
    ::= { polrEventObjects10 2 }

polr10-interface OBJECT-TYPE
    SYNTAX DisplayString
    MAX-ACCESS accessible-for-notify
    STATUS current
    DESCRIPTION
        "Parameter 'interface' in event POLR.10"
    ::= { polrEventObjects10 3 }

polrEventObjects11 OBJECT-IDENTITY
    STATUS current
    DESCRIPTION
        "Event POLR.11
        A packet was received from specified address for specified address. The
        next hop is set to the specified address."
    ::= { polrEventsGroup 11 }

polr11-srcaddr OBJECT-TYPE
    SYNTAX IpAddress
    MAX-ACCESS accessible-for-notify
    STATUS current
    DESCRIPTION
        "Parameter 'srcaddr' in event POLR.11"
    ::= { polrEventObjects11 1 }

polr11-dstaddr OBJECT-TYPE
    SYNTAX IpAddress
    MAX-ACCESS accessible-for-notify
    STATUS current
    DESCRIPTION
        "Parameter 'dstaddr' in event POLR.11"
    ::= { polrEventObjects11 2 }

polr11-nexthop OBJECT-TYPE
    SYNTAX IpAddress
    MAX-ACCESS accessible-for-notify
    STATUS current
    DESCRIPTION
        "Parameter 'nexthop' in event POLR.11"
    ::= { polrEventObjects11 3 }

polrEventObjects12 OBJECT-IDENTITY
    STATUS current
    DESCRIPTION
        "Event POLR.12
        A packet was received from specified address for specified address. The
        packet is forwarded based on routing table rather than policy routing."
    ::= { polrEventsGroup 12 }

polr12-srcaddr OBJECT-TYPE
    SYNTAX IpAddress
    MAX-ACCESS accessible-for-notify
    STATUS current
    DESCRIPTION
        "Parameter 'srcaddr' in event POLR.12"
    ::= { polrEventObjects12 1 }

polr12-dstaddr OBJECT-TYPE
    SYNTAX IpAddress
    MAX-ACCESS accessible-for-notify
    STATUS current
    DESCRIPTION
        "Parameter 'dstaddr' in event POLR.12"
    ::= { polrEventObjects12 2 }

polrEventObjects13 OBJECT-IDENTITY
    STATUS current
    DESCRIPTION
        "Event POLR.13
        A packet was received from specified address for specified address. The
        default next hop is set to the specified interface."
    ::= { polrEventsGroup 13 }

polr13-srcaddr OBJECT-TYPE
    SYNTAX IpAddress
    MAX-ACCESS accessible-for-notify
    STATUS current
    DESCRIPTION
        "Parameter 'srcaddr' in event POLR.13"
    ::= { polrEventObjects13 1 }

polr13-dstaddr OBJECT-TYPE
    SYNTAX IpAddress
    MAX-ACCESS accessible-for-notify
    STATUS current
    DESCRIPTION
        "Parameter 'dstaddr' in event POLR.13"
    ::= { polrEventObjects13 2 }

polr13-interface OBJECT-TYPE
    SYNTAX DisplayString
    MAX-ACCESS accessible-for-notify
    STATUS current
    DESCRIPTION
        "Parameter 'interface' in event POLR.13"
    ::= { polrEventObjects13 3 }

polrEventObjects14 OBJECT-IDENTITY
    STATUS current
    DESCRIPTION
        "Event POLR.14
        A packet was received from specified address for specified address. The
        default next hop is set to the specified address."
    ::= { polrEventsGroup 14 }

polr14-srcaddr OBJECT-TYPE
    SYNTAX IpAddress
    MAX-ACCESS accessible-for-notify
    STATUS current
    DESCRIPTION
        "Parameter 'srcaddr' in event POLR.14"
    ::= { polrEventObjects14 1 }

polr14-dstaddr OBJECT-TYPE
    SYNTAX IpAddress
    MAX-ACCESS accessible-for-notify
    STATUS current
    DESCRIPTION
        "Parameter 'dstaddr' in event POLR.14"
    ::= { polrEventObjects14 2 }

polr14-nexthop OBJECT-TYPE
    SYNTAX IpAddress
    MAX-ACCESS accessible-for-notify
    STATUS current
    DESCRIPTION
        "Parameter 'nexthop' in event POLR.14"
    ::= { polrEventObjects14 3 }

polrEventObjects15 OBJECT-IDENTITY
    STATUS current
    DESCRIPTION
        "Event POLR.15
        A packet was received from specified address for specified address. No
        specific route was found for this packet, therefore default routing is
        performed."
    ::= { polrEventsGroup 15 }

polr15-srcaddr OBJECT-TYPE
    SYNTAX IpAddress
    MAX-ACCESS accessible-for-notify
    STATUS current
    DESCRIPTION
        "Parameter 'srcaddr' in event POLR.15"
    ::= { polrEventObjects15 1 }

polr15-dstaddr OBJECT-TYPE
    SYNTAX IpAddress
    MAX-ACCESS accessible-for-notify
    STATUS current
    DESCRIPTION
        "Parameter 'dstaddr' in event POLR.15"
    ::= { polrEventObjects15 2 }

polrEventObjects16 OBJECT-IDENTITY
    STATUS current
    DESCRIPTION
        "Event POLR.16
        A packet was received from specified address for specified address. The
        DF bit was changed from oldDF to newDF."
    ::= { polrEventsGroup 16 }

polr16-srcaddr OBJECT-TYPE
    SYNTAX IpAddress
    MAX-ACCESS accessible-for-notify
    STATUS current
    DESCRIPTION
        "Parameter 'srcaddr' in event POLR.16"
    ::= { polrEventObjects16 1 }

polr16-dstaddr OBJECT-TYPE
    SYNTAX IpAddress
    MAX-ACCESS accessible-for-notify
    STATUS current
    DESCRIPTION
        "Parameter 'dstaddr' in event POLR.16"
    ::= { polrEventObjects16 2 }

polr16-oldDF OBJECT-TYPE
    SYNTAX Integer32
    MAX-ACCESS accessible-for-notify
    STATUS current
    DESCRIPTION
        "Parameter 'oldDF' in event POLR.16"
    ::= { polrEventObjects16 3 }

polr16-newDF OBJECT-TYPE
    SYNTAX Integer32
    MAX-ACCESS accessible-for-notify
    STATUS current
    DESCRIPTION
        "Parameter 'newDF' in event POLR.16"
    ::= { polrEventObjects16 4 }

polrEventObjects17 OBJECT-IDENTITY
    STATUS current
    DESCRIPTION
        "Event POLR.17
        A packet was received from specified address for specified address. The
        packet will be processed locally."
    ::= { polrEventsGroup 17 }

polr17-srcaddr OBJECT-TYPE
    SYNTAX IpAddress
    MAX-ACCESS accessible-for-notify
    STATUS current
    DESCRIPTION
        "Parameter 'srcaddr' in event POLR.17"
    ::= { polrEventObjects17 1 }

polr17-dstaddr OBJECT-TYPE
    SYNTAX IpAddress
    MAX-ACCESS accessible-for-notify
    STATUS current
    DESCRIPTION
        "Parameter 'dstaddr' in event POLR.17"
    ::= { polrEventObjects17 2 }

polrEventObjects18 OBJECT-IDENTITY
    STATUS current
    DESCRIPTION
        "Event POLR.18
        A packet was received from specified address for specified address. The
        packet will be processed locally by default."
    ::= { polrEventsGroup 18 }

polr18-srcaddr OBJECT-TYPE
    SYNTAX IpAddress
    MAX-ACCESS accessible-for-notify
    STATUS current
    DESCRIPTION
        "Parameter 'srcaddr' in event POLR.18"
    ::= { polrEventObjects18 1 }

polr18-dstaddr OBJECT-TYPE
    SYNTAX IpAddress
    MAX-ACCESS accessible-for-notify
    STATUS current
    DESCRIPTION
        "Parameter 'dstaddr' in event POLR.18"
    ::= { polrEventObjects18 2 }

polrEventObjects19 OBJECT-IDENTITY
    STATUS current
    DESCRIPTION
        "Event POLR.19
        A packet was received from specified address for specified address. Its
        label value was changed from oldvalue to newvalue."
    ::= { polrEventsGroup 19 }

polr19-srcaddr OBJECT-TYPE
    SYNTAX IpAddress
    MAX-ACCESS accessible-for-notify
    STATUS current
    DESCRIPTION
        "Parameter 'srcaddr' in event POLR.19"
    ::= { polrEventObjects19 1 }

polr19-dstaddr OBJECT-TYPE
    SYNTAX IpAddress
    MAX-ACCESS accessible-for-notify
    STATUS current
    DESCRIPTION
        "Parameter 'dstaddr' in event POLR.19"
    ::= { polrEventObjects19 2 }

polr19-oldlabel OBJECT-TYPE
    SYNTAX Integer32
    MAX-ACCESS accessible-for-notify
    STATUS current
    DESCRIPTION
        "Parameter 'oldlabel' in event POLR.19"
    ::= { polrEventObjects19 3 }

polr19-newlabel OBJECT-TYPE
    SYNTAX Integer32
    MAX-ACCESS accessible-for-notify
    STATUS current
    DESCRIPTION
        "Parameter 'newlabel' in event POLR.19"
    ::= { polrEventObjects19 4 }

polrEventObjects20 OBJECT-IDENTITY
    STATUS current
    DESCRIPTION
        "Event POLR.20
        A packet was received from specified address for specified address. The
        AFS session mark was changed from oldmark to newmark."
    ::= { polrEventsGroup 20 }

polr20-srcaddr OBJECT-TYPE
    SYNTAX IpAddress
    MAX-ACCESS accessible-for-notify
    STATUS current
    DESCRIPTION
        "Parameter 'srcaddr' in event POLR.20"
    ::= { polrEventObjects20 1 }

polr20-dstaddr OBJECT-TYPE
    SYNTAX IpAddress
    MAX-ACCESS accessible-for-notify
    STATUS current
    DESCRIPTION
        "Parameter 'dstaddr' in event POLR.20"
    ::= { polrEventObjects20 2 }

polr20-oldmark OBJECT-TYPE
    SYNTAX Integer32
    MAX-ACCESS accessible-for-notify
    STATUS current
    DESCRIPTION
        "Parameter 'oldmark' in event POLR.20"
    ::= { polrEventObjects20 3 }

polr20-newmark OBJECT-TYPE
    SYNTAX Integer32
    MAX-ACCESS accessible-for-notify
    STATUS current
    DESCRIPTION
        "Parameter 'newmark' in event POLR.20"
    ::= { polrEventObjects20 4 }


polrNotification1 NOTIFICATION-TYPE
    OBJECTS { 
              polr1-srcaddr, 
              polr1-dstaddr,
              polr1-length,
              polr1-protocol 
            }
    STATUS current
    DESCRIPTION
        "Notification of Event POLR.1

        Message: 'test local packet from $1 for $2 of length $3 protocol $4'

        Parameters list:
              $1: polr1-srcaddr
              $2: polr1-dstaddr
              $3: polr1-length
              $4: polr1-protocol

        A packet was generated from specified address for specified address.
        Packet length and protocol are also shown. This packet will be tested
        for policy routing."
    ::= { polrNotificationsPrefix 1 }

polrNotification2 NOTIFICATION-TYPE
    OBJECTS { 
              polr2-srcaddr, 
              polr2-dstaddr,
              polr2-length,
              polr2-protocol,
              polr2-interface 
            }
    STATUS current
    DESCRIPTION
        "Notification of Event POLR.2

        Message: 'test packet from $1 for $2 of length $3 protocol $4 from interface $5'

        Parameters list:
              $1: polr2-srcaddr
              $2: polr2-dstaddr
              $3: polr2-length
              $4: polr2-protocol
              $5: polr2-interface

        A packet was received from specified address for specified address, on
        specified interface. Packet length and protocol are also shown. This
        packet will be tested for policy routing."
    ::= { polrNotificationsPrefix 2 }

polrNotification3 NOTIFICATION-TYPE
    STATUS current
    DESCRIPTION
        "Notification of Event POLR.3

        Message: 'local policy routing disabled'

        No route map associated to locally generated packets."
    ::= { polrNotificationsPrefix 3 }

polrNotification4 NOTIFICATION-TYPE
    OBJECTS { 
              polr4-interface 
            }
    STATUS current
    DESCRIPTION
        "Notification of Event POLR.4

        Message: 'policy routing disabled on interface $1'

        Parameters list:
              $1: polr4-interface

        No route map associated to specified interface."
    ::= { polrNotificationsPrefix 4 }

polrNotification5 NOTIFICATION-TYPE
    OBJECTS { 
              polr5-srcaddr, 
              polr5-dstaddr,
              polr5-length,
              polr5-protocol,
              polr5-routemap 
            }
    STATUS current
    DESCRIPTION
        "Notification of Event POLR.5

        Message: 'missed local packet from $1 for $2 of length $3 protocol $4 with route map $5'

        Parameters list:
              $1: polr5-srcaddr
              $2: polr5-dstaddr
              $3: polr5-length
              $4: polr5-protocol
              $5: polr5-routemap

        A packet was generated from specified address for specified address.
        Packet length and protocol are also shown. This packet did not match the
        specified route map."
    ::= { polrNotificationsPrefix 5 }

polrNotification6 NOTIFICATION-TYPE
    OBJECTS { 
              polr6-srcaddr, 
              polr6-dstaddr,
              polr6-length,
              polr6-protocol,
              polr6-interface,
              polr6-routemap 
            }
    STATUS current
    DESCRIPTION
        "Notification of Event POLR.6

        Message: 'missed packet from $1 for $2 of length $3 protocol $4 interface $5 with route map $6'

        Parameters list:
              $1: polr6-srcaddr
              $2: polr6-dstaddr
              $3: polr6-length
              $4: polr6-protocol
              $5: polr6-interface
              $6: polr6-routemap

        A packet was received from specified address for specified address, on
        specified interface. Packet length and protocol are also shown. This
        packet did not match the specified route map."
    ::= { polrNotificationsPrefix 6 }

polrNotification7 NOTIFICATION-TYPE
    OBJECTS { 
              polr7-srcaddr, 
              polr7-dstaddr,
              polr7-length,
              polr7-protocol,
              polr7-routemap,
              polr7-entrynumber 
            }
    STATUS current
    DESCRIPTION
        "Notification of Event POLR.7

        Message: 'match of local packet from $1 for $2 of length $3 protocol $4 with route map $5 entry $6'

        Parameters list:
              $1: polr7-srcaddr
              $2: polr7-dstaddr
              $3: polr7-length
              $4: polr7-protocol
              $5: polr7-routemap
              $6: polr7-entrynumber

        A packet was generated from specified address for specified address.
        Packet length and protocol are also shown. This packet did match the
        specified entry of the specified route map."
    ::= { polrNotificationsPrefix 7 }

polrNotification8 NOTIFICATION-TYPE
    OBJECTS { 
              polr8-srcaddr, 
              polr8-dstaddr,
              polr8-length,
              polr8-protocol,
              polr8-interface,
              polr8-routemap,
              polr8-entrynumber 
            }
    STATUS current
    DESCRIPTION
        "Notification of Event POLR.8

        Message: 'match of packet from $1 for $2 of length $3 protocol $4 interface $5 with route map $6 entry $7'

        Parameters list:
              $1: polr8-srcaddr
              $2: polr8-dstaddr
              $3: polr8-length
              $4: polr8-protocol
              $5: polr8-interface
              $6: polr8-routemap
              $7: polr8-entrynumber

        A packet was received from specified address for specified address, on
        specified interface. Packet length and protocol are also shown. This
        packet did match the specified entry of the specified route map."
    ::= { polrNotificationsPrefix 8 }

polrNotification9 NOTIFICATION-TYPE
    OBJECTS { 
              polr9-srcaddr, 
              polr9-dstaddr,
              polr9-oldtos,
              polr9-newtos 
            }
    STATUS current
    DESCRIPTION
        "Notification of Event POLR.9

        Message: 'set packet from $1 for $2 field tos changed from 0x$3 to 0x$4'

        Parameters list:
              $1: polr9-srcaddr
              $2: polr9-dstaddr
              $3: polr9-oldtos
              $4: polr9-newtos

        A packet was received from specified address for specified address. The
        tos field was changed from oldtos to newtos."
    ::= { polrNotificationsPrefix 9 }

polrNotification10 NOTIFICATION-TYPE
    OBJECTS { 
              polr10-srcaddr, 
              polr10-dstaddr,
              polr10-interface 
            }
    STATUS current
    DESCRIPTION
        "Notification of Event POLR.10

        Message: 'set packet from $1 for $2 next hop interface $3'

        Parameters list:
              $1: polr10-srcaddr
              $2: polr10-dstaddr
              $3: polr10-interface

        A packet was received from specified address for specified address. The
        next hop is set to the specified interface."
    ::= { polrNotificationsPrefix 10 }

polrNotification11 NOTIFICATION-TYPE
    OBJECTS { 
              polr11-srcaddr, 
              polr11-dstaddr,
              polr11-nexthop 
            }
    STATUS current
    DESCRIPTION
        "Notification of Event POLR.11

        Message: 'set packet from $1 for $2 next hop $3'

        Parameters list:
              $1: polr11-srcaddr
              $2: polr11-dstaddr
              $3: polr11-nexthop

        A packet was received from specified address for specified address. The
        next hop is set to the specified address."
    ::= { polrNotificationsPrefix 11 }

polrNotification12 NOTIFICATION-TYPE
    OBJECTS { 
              polr12-srcaddr, 
              polr12-dstaddr 
            }
    STATUS current
    DESCRIPTION
        "Notification of Event POLR.12

        Message: 'forward packet from $1 for $2 with routing table'

        Parameters list:
              $1: polr12-srcaddr
              $2: polr12-dstaddr

        A packet was received from specified address for specified address. The
        packet is forwarded based on routing table rather than policy routing."
    ::= { polrNotificationsPrefix 12 }

polrNotification13 NOTIFICATION-TYPE
    OBJECTS { 
              polr13-srcaddr, 
              polr13-dstaddr,
              polr13-interface 
            }
    STATUS current
    DESCRIPTION
        "Notification of Event POLR.13

        Message: 'set packet from $1 for $2 default next hop interface $3'

        Parameters list:
              $1: polr13-srcaddr
              $2: polr13-dstaddr
              $3: polr13-interface

        A packet was received from specified address for specified address. The
        default next hop is set to the specified interface."
    ::= { polrNotificationsPrefix 13 }

polrNotification14 NOTIFICATION-TYPE
    OBJECTS { 
              polr14-srcaddr, 
              polr14-dstaddr,
              polr14-nexthop 
            }
    STATUS current
    DESCRIPTION
        "Notification of Event POLR.14

        Message: 'set packet from $1 for $2 default next hop $3'

        Parameters list:
              $1: polr14-srcaddr
              $2: polr14-dstaddr
              $3: polr14-nexthop

        A packet was received from specified address for specified address. The
        default next hop is set to the specified address."
    ::= { polrNotificationsPrefix 14 }

polrNotification15 NOTIFICATION-TYPE
    OBJECTS { 
              polr15-srcaddr, 
              polr15-dstaddr 
            }
    STATUS current
    DESCRIPTION
        "Notification of Event POLR.15

        Message: 'default routing for packet from $1 for $2'

        Parameters list:
              $1: polr15-srcaddr
              $2: polr15-dstaddr

        A packet was received from specified address for specified address. No
        specific route was found for this packet, therefore default routing is
        performed."
    ::= { polrNotificationsPrefix 15 }

polrNotification16 NOTIFICATION-TYPE
    OBJECTS { 
              polr16-srcaddr, 
              polr16-dstaddr,
              polr16-oldDF,
              polr16-newDF 
            }
    STATUS current
    DESCRIPTION
        "Notification of Event POLR.16

        Message: 'set packet from $1 for $2 DF bit changed from $3 to $4'

        Parameters list:
              $1: polr16-srcaddr
              $2: polr16-dstaddr
              $3: polr16-oldDF
              $4: polr16-newDF

        A packet was received from specified address for specified address. The
        DF bit was changed from oldDF to newDF."
    ::= { polrNotificationsPrefix 16 }

polrNotification17 NOTIFICATION-TYPE
    OBJECTS { 
              polr17-srcaddr, 
              polr17-dstaddr 
            }
    STATUS current
    DESCRIPTION
        "Notification of Event POLR.17

        Message: 'packet from $1 for $2 will be processed locally'

        Parameters list:
              $1: polr17-srcaddr
              $2: polr17-dstaddr

        A packet was received from specified address for specified address. The
        packet will be processed locally."
    ::= { polrNotificationsPrefix 17 }

polrNotification18 NOTIFICATION-TYPE
    OBJECTS { 
              polr18-srcaddr, 
              polr18-dstaddr 
            }
    STATUS current
    DESCRIPTION
        "Notification of Event POLR.18

        Message: 'packet from $1 for $2 will be processed locally by default'

        Parameters list:
              $1: polr18-srcaddr
              $2: polr18-dstaddr

        A packet was received from specified address for specified address. The
        packet will be processed locally by default."
    ::= { polrNotificationsPrefix 18 }

polrNotification19 NOTIFICATION-TYPE
    OBJECTS { 
              polr19-srcaddr, 
              polr19-dstaddr,
              polr19-oldlabel,
              polr19-newlabel 
            }
    STATUS current
    DESCRIPTION
        "Notification of Event POLR.19

        Message: 'set packet from $1 for $2 field label changed from $3 to $4'

        Parameters list:
              $1: polr19-srcaddr
              $2: polr19-dstaddr
              $3: polr19-oldlabel
              $4: polr19-newlabel

        A packet was received from specified address for specified address. Its
        label value was changed from oldvalue to newvalue."
    ::= { polrNotificationsPrefix 19 }

polrNotification20 NOTIFICATION-TYPE
    OBJECTS { 
              polr20-srcaddr, 
              polr20-dstaddr,
              polr20-oldmark,
              polr20-newmark 
            }
    STATUS current
    DESCRIPTION
        "Notification of Event POLR.20

        Message: 'set packet from $1 for $2 AFS session mark changed from $3 to $4'

        Parameters list:
              $1: polr20-srcaddr
              $2: polr20-dstaddr
              $3: polr20-oldmark
              $4: polr20-newmark

        A packet was received from specified address for specified address. The
        AFS session mark was changed from oldmark to newmark."
    ::= { polrNotificationsPrefix 20 }


END
