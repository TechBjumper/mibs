-- 
-- $Copyright$
-- Copyright (C) Fujitsu Siemens Computers GmbH 2001
-- All rights reserved
-- Copyright (C) 1996 by Acer Incorporated. All rights reserved. No Part
-- of this publication may be reproduced, transmitted, transcribed, stored
-- in a retrieval system, or translated into any language or computer
-- language, in any form or by any means, electronic, mechanical,
-- magnetic, optical, chemical, manual or otherwise, without the prior
-- written permission of Acer Incorporated.
--

ASM-PRIVATE-COMMIB DEFINITIONS ::= BEGIN
--
-- ASM MIB Common Objects
--
IMPORTS
        Counter, Gauge, enterprises, IpAddress FROM RFC1155-SMI
        DisplayString FROM RFC1213-MIB
        OBJECT-TYPE FROM RFC-1212;


-- Private-MIB

acer            OBJECT IDENTIFIER::= { enterprises 1050 }
asm             OBJECT IDENTIFIER ::={ acer 25 }

-- textual conventions

-- DisplayString ::=
--      OCTET STRING (SIZE(0..48))

-- Groups in ASM

storage 	OBJECT IDENTIFIER ::= { asm 1 }
nic		OBJECT IDENTIFIER ::= { asm 2 }
systemBoard	OBJECT IDENTIFIER ::= { asm 3 }
serverEnvrm	OBJECT IDENTIFIER ::= { asm 4 }
asmsystem	OBJECT IDENTIFIER ::= { asm 5 }
asmalarm	OBJECT IDENTIFIER ::= { asm 7 }

nwNic	OBJECT IDENTIFIER ::= { nic 3 }
scoNic	OBJECT IDENTIFIER ::= { nic 4 }
ntNic	OBJECT IDENTIFIER ::= { nic 5 }

-- The Storage group
-- Diskette Drive

disketteDriveTable OBJECT-TYPE
        SYNTAX SEQUENCE OF DisketteDriveEntry
        ACCESS not-accessible
        STATUS mandatory
        DESCRIPTION
                "This entry is a table containing information about all
                diskette drives."
        ::= { storage 1 }

disketteDriveEntry OBJECT-TYPE
        SYNTAX DisketteDriveEntry
        ACCESS not-accessible
        STATUS mandatory
        DESCRIPTION
                "This entry contains information about each diskette drive."
        INDEX  { disketteDrvIndex }
        ::= { disketteDriveTable 1 }

DisketteDrvIndex ::= INTEGER
        {
          a(1),
          b(2)
        }

DisketteDriveEntry ::= SEQUENCE {
        disketteDrvIndex DisketteDrvIndex,
        disketteDrvType INTEGER(0..5)
}

disketteDrvIndex OBJECT-TYPE
        SYNTAX DisketteDrvIndex
        ACCESS read-only
        STATUS mandatory
        DESCRIPTION
                "This entry displays the diskette drive table index."
        ::= { disketteDriveEntry 1 }

disketteDrvType OBJECT-TYPE
        SYNTAX INTEGER(0..5)
        ACCESS read-only
        STATUS mandatory
        DESCRIPTION
                "This entry displays the diskette drive type:
                0 = Not present
                1 = 360K 5.25inch
                2 = 1.2M 5.25inch
                3 = 720K 3.5inch
                4 = 1.44M 3.5inch
                5 = 2.88M 3.5inch"
        ::= { disketteDriveEntry 2 }

-- Hard Disk Controller

totalHdCntrlNum OBJECT-TYPE
        SYNTAX INTEGER
        ACCESS read-only
        STATUS mandatory
        DESCRIPTION
                "This entry displays the total number of hard disk
                controllers (HDC)."
        ::= { storage 2 }

hdControllerTable OBJECT-TYPE
        SYNTAX SEQUENCE OF HdControllerEntry
        ACCESS not-accessible
        STATUS mandatory
        DESCRIPTION
                "This entry is a table containing information about all HDCs."
        ::= { storage 3 }

--totalDiskNum OBJECT-TYPE
--        SYNTAX INTEGER
--        ACCESS read-only
--        STATUS mandatory
--        DESCRIPTION
--                "This entry displays the number of hard disks installed."
--        ::= { storage 4 }

--diskTable OBJECT-TYPE
--        SYNTAX SEQUENCE OF DiskEntry
--        ACCESS not-accessible
--        STATUS mandatory
--        DESCRIPTION
--                "This entry is a table containing information about all hard
--                disks installed."
--        ::= { storage 5 }

--totalLDiskNum OBJECT-TYPE
--      SYNTAX INTEGER
--      ACCESS read-only
--      STATUS mandatory
--      DESCRIPTION
--              "The number of logical disks in the system"
--      ::= { storage 6 }

-- logicalDiskTable OBJECT-TYPE
--      SYNTAX SEQUENCE OF LogicalDiskEntry
--      ACCESS not-accessible
--      STATUS mandatory
--      DESCRIPTION
--              "A list of logical disk drive information in the system"
--      ::= { storage 7 }

hdControllerEntry OBJECT-TYPE
        SYNTAX HdControllerEntry
        ACCESS not-accessible
        STATUS mandatory
        DESCRIPTION
                "This entry contains information about each HDC."
        INDEX { hdCntrlNum }
        ::= { hdControllerTable 1 }

HdControllerEntry ::= SEQUENCE {
        hdCntrlNum      INTEGER,
        hdCntrlSlotNum  INTEGER(1..12),
--      hdCntrlChannel  INTEGER(1..3),
        hdCntrlType     INTEGER,
--      hdCntrlVendor           DisplayString,
        hdCntrlIoPort           INTEGER,
        hdCntrlIntr             INTEGER(0..15),
--      hdCntrlBIOSAddr         INTEGER,
        hdCntrlDMA              INTEGER(0..7),
--      hdCntrlFirmware         DisplayString,
        hdCntrlModel            DisplayString
--      hdCntrlCacheSize        INTEGER,
--      hdCntrlId               INTEGER(0..7)
}

hdCntrlNum OBJECT-TYPE
        SYNTAX INTEGER
        ACCESS read-only
        STATUS mandatory
        DESCRIPTION
            "This entry is an index to the HDC table starting at zero (0). "
        ::= { hdControllerEntry 1 }

hdCntrlSlotNum OBJECT-TYPE
        SYNTAX INTEGER(1..12)
        ACCESS read-only
        STATUS mandatory
        DESCRIPTION
                "This entry shows the slot number occupied by the controller."
        ::= { hdControllerEntry 2 }

-- hdCntrlChannel OBJECT-TYPE
--      SYNTAX INTEGER(1..3)
--      ACCESS read-only
--      STATUS mandatory
--      DESCRIPTION
--              "This entry displays the number of channels of the HDC."
--      ::= { hdControllerEntry 3 }

hdCntrlType OBJECT-TYPE
        SYNTAX INTEGER
        ACCESS read-only
        STATUS mandatory
        DESCRIPTION
                "This entry shows the HDC type:
                 0 = Unknown
                 1 = SCSI
                 2 = IDE"
        ::= { hdControllerEntry 4 }

-- hdCntrlVendor OBJECT-TYPE
--      SYNTAX DisplayString
--      ACCESS read-only
--      STATUS mandatory
--      DESCRIPTION
--              "This entry shows a description of the HDC vendor."
--      ::= { hdControllerEntry 5 }

hdCntrlIoPort OBJECT-TYPE
        SYNTAX INTEGER
        ACCESS read-only
        STATUS mandatory
        DESCRIPTION
                "This entry shows the I/O port address occupied by the HDC."
        ::= { hdControllerEntry 6 }

hdCntrlIntr OBJECT-TYPE
        SYNTAX INTEGER(0..15)
        ACCESS read-only
        STATUS mandatory
        DESCRIPTION
                "This entry shows the interrupt number occupied by the HDC."
        ::= { hdControllerEntry 7 }

-- hdCntrlBIOSAddr OBJECT-TYPE
--      SYNTAX INTEGER
--      ACCESS read-only
--      STATUS mandatory
--      DESCRIPTION
--              "This entry shows the HDC's BIOS address between 0xC0000-0xEFFFF."
--      ::= { hdControllerEntry 8 }

hdCntrlDMA OBJECT-TYPE
        SYNTAX INTEGER(0..7)
        ACCESS read-only
        STATUS mandatory
        DESCRIPTION
                "This entry shows the DMA channel occupied by the HDC."
        ::= { hdControllerEntry 9 }

-- hdCntrlFirmware OBJECT-TYPE
--      SYNTAX DisplayString
--      ACCESS read-only
--      STATUS mandatory
--      DESCRIPTION
--              "This entry shows the HDC's firmware version."
--      ::= { hdControllerEntry 10 }

hdCntrlModel OBJECT-TYPE
        SYNTAX DisplayString
        ACCESS read-only
        STATUS mandatory
        DESCRIPTION
                "This entry shows the HDC model name."
        ::= { hdControllerEntry 11 }

-- hdCntrlCacheSize OBJECT-TYPE
--      SYNTAX INTEGER
--      ACCESS read-only
--      STATUS mandatory
--      DESCRIPTION
--              "For HDCs with proprietary cache, this entry will show
--              the cache size in KB."
--      ::= { hdControllerEntry 12 }
--
-- hdCntrlId OBJECT-TYPE
--      SYNTAX INTEGER(0..7)
--      ACCESS read-only
--      STATUS mandatory
--      DESCRIPTION
--              "This entry shows the SCSI ID occupied by a SCSI controller card."
--      ::= { hdControllerEntry 13 }

totalDiskNum OBJECT-TYPE
        SYNTAX INTEGER
        ACCESS read-only
        STATUS mandatory
        DESCRIPTION
                "This entry displays the number of hard disks installed."
        ::= { storage 4 }

diskTable OBJECT-TYPE
        SYNTAX SEQUENCE OF DiskEntry
        ACCESS not-accessible
        STATUS mandatory
        DESCRIPTION
                "This entry is a table containing information about all hard
                disks installed."
        ::= { storage 5 }

diskEntry OBJECT-TYPE
        SYNTAX DiskEntry
        ACCESS not-accessible
        STATUS mandatory
        DESCRIPTION
                "This entry contains information about each disk drive installed."
        INDEX  { diskNum }
        ::= { diskTable 1 }

DiskEntry ::= SEQUENCE {
        diskNum                 INTEGER,
        diskHdCntrlNum          INTEGER,
        diskHdCntrlSlotNum      INTEGER(1..12),
--      diskHdCntrlChannel      INTEGER(1..3),
        diskId                  INTEGER(0..7),
--      diskVendor              DisplayString,
        diskSize                INTEGER,
        diskModel               DisplayString,
--      diskSerialNum           DisplayString,
        diskType                OCTET STRING (SIZE(4)),
--      diskLoc                 DisplayString,

--- Disk performance
        diskBusyRatio                   INTEGER,
        averageDiskReadWriteTime        INTEGER,
        numberOfDiskTransfer            INTEGER,
        byteOfDiskTransfer              INTEGER
}

diskNum OBJECT-TYPE
        SYNTAX INTEGER
        ACCESS read-only
        STATUS mandatory
        DESCRIPTION
            "This entry is an index to the disk table starting at zero (0). "
        ::= { diskEntry 1 }

diskHdCntrlNum OBJECT-TYPE
        SYNTAX INTEGER
        ACCESS read-only
        STATUS mandatory
        DESCRIPTION
                "This entry shows the HDC number (refer to hdCntrlNum) to which the
disk is connected."
        ::= { diskEntry 2 }

diskHdCntrlSlotNum OBJECT-TYPE
        SYNTAX  INTEGER(1..12)
        ACCESS read-only
        STATUS mandatory
        DESCRIPTION
                "This entry shows the slot number of the HDC (refer to hdCntrlSlotNum) to which
the disk is connected. "
        ::= { diskEntry 3 }

-- diskHdCntrlChannel OBJECT-TYPE
--      SYNTAX  INTEGER(1..3)
--      ACCESS read-only
--      STATUS mandatory
--      DESCRIPTION
--              "This entry shows the HDC channel number to which the disk is connected. "
--      ::= { diskEntry 4 }

diskId OBJECT-TYPE
        SYNTAX INTEGER(0..7)
        ACCESS read-only
        STATUS mandatory
        DESCRIPTION
                "This entry displays disk IDs depending on each disk type.  For example, with a SCSI
disk installed, the value for this entry will represent a SCSI ID.  IDE disks have two
values:  0 refers to a master drive while 1 refers to a slave drive."
        ::= { diskEntry 5 }

-- diskVendor OBJECT-TYPE
--      SYNTAX DisplayString
--      ACCESS read-only
--      STATUS mandatory
--      DESCRIPTION
--              "This entry shows disk vendor information."
--      ::= { diskEntry 6 }

diskSize OBJECT-TYPE
        SYNTAX INTEGER
        ACCESS read-only
        STATUS mandatory
        DESCRIPTION
                "This entry shows the physical disk size in KB."
        ::= { diskEntry 7 }

diskModel OBJECT-TYPE
        SYNTAX DisplayString
        ACCESS read-only
        STATUS mandatory
        DESCRIPTION
                "This entry shows the disk model."
        ::= { diskEntry 8 }

-- diskSerialNum OBJECT-TYPE
--      SYNTAX DisplayString
--      ACCESS read-only
--      STATUS mandatory
--      DESCRIPTION
--              "This entry shows the disk serial number."
--      ::= { diskEntry 9 }

diskType OBJECT-TYPE
        SYNTAX OCTET STRING (SIZE(4))
        ACCESS read-only
        STATUS mandatory
        DESCRIPTION
                "This entry shows the disk type, i.e. SCSI, IDE or N/A."
        ::= { diskEntry 10 }

-- diskLoc OBJECT-TYPE
--      SYNTAX DisplayString
--      ACCESS read-write
--      STATUS mandatory
--      DESCRIPTION
--              "This entry shows the disk's physical location."
--      ::= { diskEntry 11 }

--- Disk performance
diskBusyRatio   OBJECT-TYPE
        SYNTAX INTEGER
        ACCESS read-only
        STATUS mandatory
        DESCRIPTION
                "This entry shows the Disk Busy ratio (%)."
        ::= { diskEntry 12 }

averageDiskReadWriteTime        OBJECT-TYPE
        SYNTAX INTEGER
        ACCESS read-only
        STATUS mandatory
        DESCRIPTION
                "This entry shows the disk's average read/write time."
        ::= { diskEntry 13 }

numberOfDiskTransfer    OBJECT-TYPE
        SYNTAX INTEGER
        ACCESS read-only
        STATUS mandatory
        DESCRIPTION
                "This entry shows the number of disk transfers."
        ::= { diskEntry 14 }

byteOfDiskTransfer      OBJECT-TYPE
        SYNTAX INTEGER
        ACCESS read-only
        STATUS mandatory
        DESCRIPTION
                "This entry shows the total size of all disk transfers in bytes."
        ::= { diskEntry 15 }

deviceType OBJECT-TYPE
        SYNTAX INTEGER
        ACCESS read-only
        STATUS mandatory
        DESCRIPTION
                "This entry shows the device type.
                0 : Unknown device
                1 : Hard disk
                2 : CD-ROM drive
                3 : Tape drive"
        ::= { diskEntry 16 }

-- LogicalDiskEntry ::= SEQUENCE {
--      ldiskHdCntrlNum INTEGER(1..12),
--      ldiskHdCntrlSlotNum     INTEGER(1..12),
--      ldiskHdCntrlChannel     INTEGER(1..3),
--      logicalDiskId   INTEGER(0..31),
--      logicalDiskSize INTEGER,
--      logicalDiskLoc  DisplayString,
--      logicalDiskRaidType INTEGER(0..5)
-- }
--
-- logicalDiskEntry OBJECT-TYPE
--      SYNTAX LogicalDiskEntry
--      ACCESS not-accessible
--      STATUS mandatory
--      DESCRIPTION
--              "A collection of logical disk drive information on
--              the controller"
--      INDEX  { ldiskHdCntrlSlotNum, ldiskHdCntrlChannel}
--      ::= { logicalDiskTable 1 }
--
-- ldiskHdCntrlNum OBJECT-TYPE
--      SYNTAX INTEGER(1..12)
--      ACCESS read-only
--      STATUS mandatory
--      DESCRIPTION
--              "***The controller number of the logical hard disk located."
--      ::= { logicalDiskEntry 1 }
--
-- ldiskHdCntrlSlotNum OBJECT-TYPE
--      SYNTAX INTEGER(1..12)
--      ACCESS read-only
--      STATUS mandatory
--      DESCRIPTION
--              "The logical disk on the hard disk controller"
--      ::= { logicalDiskEntry 2 }
--
-- ldiskHdCntrlChannel OBJECT-TYPE
--      SYNTAX  INTEGER(1..3)
--      ACCESS read-only
--      STATUS mandatory
--      DESCRIPTION
--              "***The logical disk on which hd controller channel is"
--      ::= { logicalDiskEntry 3 }
--
-- logicalDiskId OBJECT-TYPE
--      SYNTAX INTEGER(0..31)
--      ACCESS read-only
--      STATUS mandatory
--      DESCRIPTION
--              "The ID assigned to the logical disk drive"
--      ::= { logicalDiskEntry 4 }
--
-- logicalDiskSize OBJECT-TYPE
--      SYNTAX INTEGER
--      ACCESS read-only
--      STATUS mandatory
--      DESCRIPTION
--              "The logical disk drive size"
--      ::= { logicalDiskEntry 5 }
--
-- logicalDiskLoc OBJECT-TYPE
--      SYNTAX DisplayString
--      ACCESS read-write
--      STATUS mandatory
--      DESCRIPTION
--              "***The location of logical disk drive connected to
--              the managed server"
--      ::= { logicalDiskEntry 6 }
--
-- logicalDiskRaidType OBJECT-TYPE
--      SYNTAX INTEGER(0..5)
--      ACCESS read-only
--      STATUS mandatory
--      DESCRIPTION
--              "The RAID(0,1,2,3,4,5) type of the logical disk drive"
--      ::= { logicalDiskEntry 7 }


-- The NIC group

totalNicCntrlNum OBJECT-TYPE
        SYNTAX INTEGER(0..7)
        ACCESS read-only
        STATUS mandatory
        DESCRIPTION
                "This entry displays the number of network interface controllers (NIC) installed."
        ::= { nic 1 }

nicControllerTable OBJECT-TYPE
        SYNTAX SEQUENCE OF NicControllerEntry
        ACCESS not-accessible
        STATUS mandatory
        DESCRIPTION
                "This entry is a table containing information about all NICs installed."
        ::= { nic 2 }




nicControllerEntry OBJECT-TYPE
        SYNTAX NicControllerEntry
        ACCESS not-accessible
        STATUS mandatory
        DESCRIPTION
                "This entry contains generic information about each NIC."
        INDEX  { nicCntrlNum }
        ::= { nicControllerTable 1 }

NicControllerEntry ::= SEQUENCE {
        nicCntrlNum             INTEGER,
        nicCntrlSlotNum         INTEGER,
        nicCntrlIoPort          INTEGER,
        nicCntrlDMA             INTEGER(0..7),
        nicCntrlIntr            INTEGER(0..15),
        nicCntrlSharedMem       INTEGER,
--      nicCntrlVendor          DisplayString,
        nicCntrlModel           DisplayString,
--      nicCntrlFirmware        DisplayString,
        nicCntrlType            DisplayString,
        nicMACAddress           DisplayString,
        nicMediaType            INTEGER,
        nicInterfaceSpeed       INTEGER
}

nicCntrlNum OBJECT-TYPE
        SYNTAX INTEGER
        ACCESS read-only
        STATUS mandatory
        DESCRIPTION
          "This entry is an index of the NIC table starting at 0."
        ::= { nicControllerEntry 1 }

nicCntrlSlotNum OBJECT-TYPE
        SYNTAX INTEGER
        ACCESS read-only
        STATUS mandatory
        DESCRIPTION
                "This entry shows the slot number occupied by the NIC."
        ::= { nicControllerEntry 2 }

nicCntrlIoPort OBJECT-TYPE
        SYNTAX INTEGER
        ACCESS read-only
        STATUS mandatory
        DESCRIPTION
                "This entry shows the IO port occupied by the NIC."
        ::= { nicControllerEntry 3 }

nicCntrlDMA OBJECT-TYPE
        SYNTAX INTEGER(0..7)
        ACCESS read-only
        STATUS mandatory
        DESCRIPTION
                "This entry shows the DMA channel occupied by the NIC."
        ::= { nicControllerEntry 4 }

nicCntrlIntr OBJECT-TYPE
        SYNTAX INTEGER(0..15)
        ACCESS read-only
        STATUS mandatory
        DESCRIPTION
                "This entry shows the interrupt number occupied by the NIC."
        ::= { nicControllerEntry 5 }

nicCntrlSharedMem OBJECT-TYPE
        SYNTAX INTEGER
        ACCESS read-only
        STATUS mandatory
        DESCRIPTION
                "This entry shows the shared memory address used by the NIC."
        ::= { nicControllerEntry 6 }

-- nicCntrlVendor OBJECT-TYPE
--      SYNTAX DisplayString
--      ACCESS read-only
--      STATUS mandatory
--      DESCRIPTION
--              "This entry shows the NIC vendor information."
--      ::= { nicControllerEntry 7 }

nicCntrlModel OBJECT-TYPE
        SYNTAX DisplayString
        ACCESS read-only
        STATUS mandatory
        DESCRIPTION
                "This entry shows the NIC model. "
        ::= { nicControllerEntry 8 }

-- nicCntrlFirmware OBJECT-TYPE
--      SYNTAX DisplayString
--      ACCESS read-only
--      STATUS mandatory
--      DESCRIPTION
--              "This entry shows NIC firmware information."
--      ::= { nicControllerEntry 9 }

nicCntrlType OBJECT-TYPE
        SYNTAX DisplayString
        ACCESS read-only
        STATUS mandatory
        DESCRIPTION
                "This entry shows the NIC type information such as Ethernet or Token Ring."
        ::= { nicControllerEntry 10 }

nicMACAddress OBJECT-TYPE
        SYNTAX DisplayString
        ACCESS read-only
        STATUS mandatory
        DESCRIPTION
                "This entry shows the NIC hardware's six-byte address."
        ::= { nicControllerEntry 11 }

nicMediaType OBJECT-TYPE
        SYNTAX INTEGER
        ACCESS read-only
        STATUS mandatory
        DESCRIPTION
                "This entry shows the NIC media type information: 1=Ethernet 2=Token-Ring"
        ::= { nicControllerEntry 12 }

nicInterfaceSpeed OBJECT-TYPE
        SYNTAX INTEGER
        ACCESS read-only
        STATUS mandatory
        DESCRIPTION
                "This entry shows the NIC interface speed information in
                 byte/sec"
      ::= { nicControllerEntry 13 }

--nwNic   OBJECT IDENTIFIER ::= { nic 3 }
--scoNic  OBJECT IDENTIFIER ::= { nic 4 }
--ntNic   OBJECT IDENTIFIER ::= { nic 5 }

glbThldNicByte  OBJECT-TYPE
        SYNTAX INTEGER
        ACCESS read-write
        STATUS mandatory
        DESCRIPTION
                "This entry is the global threshold setting for NIC received/transmitted bytes.
                 Default is 100Mbps/8 = 12500000."
        ::= { nic 6 }

glbThldNicPacket        OBJECT-TYPE
        SYNTAX INTEGER
        ACCESS read-write
        STATUS mandatory
        DESCRIPTION
                "This entry is the global threshold setting for NIC received/transmitted packets.
                 Default is 100Mbps/8/50 = 250000."
        ::= { nic 7 }

glbThldNicFault OBJECT-TYPE
        SYNTAX INTEGER
        ACCESS read-write
        STATUS mandatory
        DESCRIPTION
                "This entry is the global threshold setting for NIC fault counters.
                 Default is 0xFFFFFFFF, therefore, no SNMP traps will be sent."
        ::= { nic 8 }

-- NetWare NIC specific Information

nwNicGenericCounterTable OBJECT-TYPE
	SYNTAX SEQUENCE OF NWNicGenericCounter
	ACCESS not-accessible
	STATUS mandatory
	DESCRIPTION
		"This entry is a table containing information about all
                groups of NetWare NIC generic counters."
	::= { nwNic 1 }

nwNicGenericCounter OBJECT-TYPE
	SYNTAX NWNicGenericCounter
	ACCESS not-accessible
	STATUS mandatory
	DESCRIPTION
		"This entry contains information about each group
		of NetWare NIC generic counters."
--	INDEX  { INTEGER }
	::= { nwNicGenericCounterTable 1 }

NWNicGenericCounter	::= SEQUENCE {
	nwNicNumRcvPkts 	Gauge,
	nwNicNumRcvBytes	Gauge,
	nwNicNumSndPkts 	Gauge,
	nwNicNumSndBytes	Gauge,
	nwNicNoEcbCount 	Counter,
	nwNicSndTooBigCnt	Counter,
	nwNicRcvPktOvlCnt	Counter,
	nwNicRcvPktTooBigCnt	Counter,
	nwNicRcvPktTooSmallCnt	Counter,
	nwNicRcvPktMiscErr	Counter,
	nwNicSndPktMiscErr	Counter,
	nwNicSndPktRetryCnt	Counter,
	nwNicChkSumErr		Counter,
	nwNicRcvMismatchCnt	Counter,
	nwNicAdapterRstCnt	Counter
}

-- NetWare NIC generic counters

nwNicNumRcvPkts OBJECT-TYPE
	SYNTAX Gauge
	ACCESS read-only
	STATUS mandatory
	DESCRIPTION
		"This entry shows the number of received packets
                by the LAN card."
	::= { nwNicGenericCounter 1 }

nwNicNumRcvBytes OBJECT-TYPE
	SYNTAX Gauge
	ACCESS read-only
	STATUS mandatory
	DESCRIPTION
		"This entry shows the number of received bytes
                by the LAN card."
	::= { nwNicGenericCounter 2 }

nwNicNumSndPkts OBJECT-TYPE
	SYNTAX Gauge
	ACCESS read-only
	STATUS mandatory
	DESCRIPTION
		"This entry shows the number of sent packets
                from the LAN card."
	::= { nwNicGenericCounter 3 }

nwNicNumSndBytes OBJECT-TYPE
	SYNTAX Gauge
	ACCESS read-only
	STATUS mandatory
	DESCRIPTION
		"This entry shows the number of sent bytes
                from the LAN card."
	::= { nwNicGenericCounter 4 }

nwNicNoEcbCount OBJECT-TYPE
	SYNTAX Counter
	ACCESS read-only
	STATUS mandatory
	DESCRIPTION
		"This entry shows the No ECB Available Count."
	::= { nwNicGenericCounter 5 }

nwNicSndTooBigCnt OBJECT-TYPE
	SYNTAX Counter
	ACCESS read-only
	STATUS mandatory
	DESCRIPTION
		"This entry shows the Send Packet Too Big Count."
	::= { nwNicGenericCounter 6 }

nwNicRcvPktOvlCnt OBJECT-TYPE
	SYNTAX Counter
	ACCESS read-only
	STATUS mandatory
	DESCRIPTION
		"This entry shows the Receive Packet Overflow Count."
	::= { nwNicGenericCounter 7 }

nwNicRcvPktTooBigCnt OBJECT-TYPE
	SYNTAX Counter
	ACCESS read-only
	STATUS mandatory
	DESCRIPTION
		"This entry shows the Receive Packet Too Big Count."
	::= { nwNicGenericCounter 8 }

nwNicRcvPktTooSmallCnt OBJECT-TYPE
	SYNTAX Counter
	ACCESS read-only
	STATUS mandatory
	DESCRIPTION
		"This entry shows the Receive Packet Too Small Count."
	::= { nwNicGenericCounter 9 }

nwNicRcvPktMiscErr OBJECT-TYPE
	SYNTAX Counter
	ACCESS read-only
	STATUS mandatory
	DESCRIPTION
		"This entry shows the Receive Packet Miscellaneous Errors."
	::= { nwNicGenericCounter 10 }

nwNicSndPktMiscErr OBJECT-TYPE
	SYNTAX Counter
	ACCESS read-only
	STATUS mandatory
	DESCRIPTION
		"This entry shows the Send Packet Miscellaneous Errors."
	::= { nwNicGenericCounter 11 }

nwNicSndPktRetryCnt OBJECT-TYPE
	SYNTAX Counter
	ACCESS read-only
	STATUS mandatory
	DESCRIPTION
		"This entry shows the Send Packet Retry Count."
	::= { nwNicGenericCounter 12 }

nwNicChkSumErr OBJECT-TYPE
	SYNTAX Counter
	ACCESS read-only
	STATUS mandatory
	DESCRIPTION
		"This entry shows the Checksum Errors."
	::= { nwNicGenericCounter 13 }

nwNicRcvMismatchCnt OBJECT-TYPE
	SYNTAX Counter
	ACCESS read-only
	STATUS mandatory
	DESCRIPTION
		"This entry shows the Hardware Receive Mismatch Count."
	::= { nwNicGenericCounter 14 }

nwNicAdapterRstCnt OBJECT-TYPE
	SYNTAX Counter
	ACCESS read-only
	STATUS mandatory
	DESCRIPTION
		"This entry shows the Adapter Reset Count."
	::= { nwNicGenericCounter 15 }

nwNicGenericThresholdTable OBJECT-TYPE
	SYNTAX SEQUENCE OF NWNicGenericThreshold
	ACCESS not-accessible
	STATUS mandatory
	DESCRIPTION
		"This entry is a table containing information about all
                groups of thresholds for NetWare NIC generic counters."
	::= { nwNic 2 }

nwNicGenericThreshold OBJECT-TYPE
	SYNTAX NWNicGenericThreshold
	ACCESS not-accessible
	STATUS mandatory
	DESCRIPTION
		"This entry contains information about each group
                of thresholds for NetWare NIC generic counters."
--	INDEX  { INTEGER }
	::= { nwNicGenericThresholdTable 1 }

NWNicGenericThreshold	::= SEQUENCE {
	nwNicNumRcvPktsThreshold	INTEGER,
	nwNicNumRcvBytesThreshold	INTEGER,
	nwNicNumSndPktsThreshold	INTEGER,
	nwNicNumSndBytesThreshold	INTEGER,
	nwNicNoEcbCountThreshold	INTEGER,
	nwNicSndTooBigCntThreshold	INTEGER,
	nwNicRcvPktOvlCntThreshold	INTEGER,
	nwNicRcvPktTooBigCntThreshold	INTEGER,
	nwNicRcvPktTooSmallCntThreshold INTEGER,
	nwNicRcvPktMiscErrThreshold	INTEGER,
	nwNicSndPktMiscErrThreshold	INTEGER,
	nwNicSndPktRetryCntThreshold	INTEGER,
	nwNicChkSumErrThreshold 	INTEGER,
	nwNicRcvMismatchCntThreshold	INTEGER,
	nwNicAdapterRstCntThreshold	INTEGER
}

-- NetWare NIC generic thresholds

nwNicNumRcvPktsThreshold OBJECT-TYPE
	SYNTAX INTEGER
	ACCESS read-write
	STATUS mandatory
	DESCRIPTION
		"This entry shows the threshold setting of received packets
                by the LAN card."
	::= { nwNicGenericThreshold 1 }

nwNicNumRcvBytesThreshold OBJECT-TYPE
	SYNTAX INTEGER
	ACCESS read-write
	STATUS mandatory
	DESCRIPTION
		"This entry shows the threshold setting of received bytes
                by the LAN card."
	::= { nwNicGenericThreshold 2 }

nwNicNumSndPktsThreshold OBJECT-TYPE
	SYNTAX INTEGER
	ACCESS read-write
	STATUS mandatory
	DESCRIPTION
		"This entry shows the threshold setting of sent packets
                from the LAN card."
	::= { nwNicGenericThreshold 3 }

nwNicNumSndBytesThreshold OBJECT-TYPE
	SYNTAX INTEGER
	ACCESS read-write
	STATUS mandatory
	DESCRIPTION
		"This entry shows the threshold setting of sent bytes
                from the LAN card."
	::= { nwNicGenericThreshold 4 }

nwNicNoEcbCountThreshold OBJECT-TYPE
	SYNTAX INTEGER
	ACCESS read-write
	STATUS mandatory
	DESCRIPTION
		"This entry shows the threshold setting of
                No ECB Available Count."
	::= { nwNicGenericThreshold 5 }

nwNicSndTooBigCntThreshold OBJECT-TYPE
	SYNTAX INTEGER
	ACCESS read-write
	STATUS mandatory
	DESCRIPTION
		"This entry shows the threshold setting of
		Send Packet Too Big Count."
	::= { nwNicGenericThreshold 6 }

nwNicRcvPktOvlCntThreshold OBJECT-TYPE
	SYNTAX INTEGER
	ACCESS read-write
	STATUS mandatory
	DESCRIPTION
		"This entry shows the threshold setting of
                Receive Packet Overflow Count."
	::= { nwNicGenericThreshold 7 }

nwNicRcvPktTooBigCntThreshold OBJECT-TYPE
	SYNTAX INTEGER
	ACCESS read-write
	STATUS mandatory
	DESCRIPTION
		"This entry shows the threshold setting of
		Receive Packet Too Big Count."
	::= { nwNicGenericThreshold 8 }

nwNicRcvPktTooSmallCntThreshold OBJECT-TYPE
	SYNTAX INTEGER
	ACCESS read-write
	STATUS mandatory
	DESCRIPTION
		"This entry shows the threshold setting of
		Receive Packet Too Small Count."
	::= { nwNicGenericThreshold 9 }

nwNicRcvPktMiscErrThreshold OBJECT-TYPE
	SYNTAX INTEGER
	ACCESS read-write
	STATUS mandatory
	DESCRIPTION
		"This entry shows the threshold setting of
		Receive Packet Miscellaneous Errors."
	::= { nwNicGenericThreshold 10 }

nwNicSndPktMiscErrThreshold OBJECT-TYPE
	SYNTAX INTEGER
	ACCESS read-write
	STATUS mandatory
	DESCRIPTION
		"This entry shows the threshold setting of
		Send Packet Miscellaneous Errors."
	::= { nwNicGenericThreshold 11 }

nwNicSndPktRetryCntThreshold OBJECT-TYPE
	SYNTAX INTEGER
	ACCESS read-write
	STATUS mandatory
	DESCRIPTION
		"This entry shows the threshold setting of
		Send Packet Retry Count."
	::= { nwNicGenericThreshold 12 }

nwNicChkSumErrThreshold OBJECT-TYPE
	SYNTAX INTEGER
	ACCESS read-write
	STATUS mandatory
	DESCRIPTION
		"This entry shows the threshold setting of
		Checksum Errors."
	::= { nwNicGenericThreshold 13 }

nwNicRcvMismatchCntThreshold OBJECT-TYPE
	SYNTAX INTEGER
	ACCESS read-write
	STATUS mandatory
	DESCRIPTION
		"This entry shows the threshold setting of
		Hardware Receive Mismatch Count."
	::= { nwNicGenericThreshold 14 }

nwNicAdapterRstCntThreshold OBJECT-TYPE
	SYNTAX INTEGER
	ACCESS read-write
	STATUS mandatory
	DESCRIPTION
		"This entry shows the threshold setting of
		Adapter Reset Count."
	::= { nwNicGenericThreshold 15 }

nwNicEthernetCounterTable OBJECT-TYPE
	SYNTAX SEQUENCE OF NWNicEthernetCounter
	ACCESS not-accessible
	STATUS mandatory
	DESCRIPTION
		"This entry is a table containing information about all
                groups of NetWare NIC Ethernet counters."
	::= { nwNic 3 }

nwNicEthernetCounter OBJECT-TYPE
	SYNTAX NWNicEthernetCounter
	ACCESS not-accessible
	STATUS mandatory
	DESCRIPTION
		"This entry contains information about each group
		of NetWare NIC Ethernet counters."
--	INDEX  { INTEGER }
	::= { nwNicEthernetCounterTable 1 }

NWNicEthernetCounter	::= SEQUENCE {
	nwNicSndOkSingleColliCnt	Counter,
	nwNicSndOkMultipleColliCnt	Counter,
	nwNicSndOkButDeferred		Counter,
	nwNicSndAbortLateColli		Counter,
	nwNicSndAbortExcessColli	Counter,
	nwNicSndAbortCarrierSense	Counter,
	nwNicSndAbortExcessDefer	Counter,
	nwNicRcvAbortFrameAlignment	Counter
}

-- NetWare NIC Ethernet counters

nwNicSndOkSingleColliCnt OBJECT-TYPE
	SYNTAX Counter
	ACCESS read-only
	STATUS mandatory
	DESCRIPTION
		"This entry shows the Send OK Single Collision Count."
	::= { nwNicEthernetCounter 1 }

nwNicSndOkMultipleColliCnt OBJECT-TYPE
	SYNTAX Counter
	ACCESS read-only
	STATUS mandatory
	DESCRIPTION
		"This entry shows the Send OK Multiple Collision Count."
	::= { nwNicEthernetCounter 2 }

nwNicSndOkButDeferred OBJECT-TYPE
	SYNTAX Counter
	ACCESS read-only
	STATUS mandatory
	DESCRIPTION
		"This entry shows the Send OK But Deferred."
	::= { nwNicEthernetCounter 3 }

nwNicSndAbortLateColli OBJECT-TYPE
	SYNTAX Counter
	ACCESS read-only
	STATUS mandatory
	DESCRIPTION
		"This entry shows the Send Abort From Late Collision."
	::= { nwNicEthernetCounter 4 }

nwNicSndAbortExcessColli OBJECT-TYPE
	SYNTAX Counter
	ACCESS read-only
	STATUS mandatory
	DESCRIPTION
		"This entry shows the Send Abort From Excess Collisions."
	::= { nwNicEthernetCounter 5 }

nwNicSndAbortCarrierSense OBJECT-TYPE
	SYNTAX Counter
	ACCESS read-only
	STATUS mandatory
	DESCRIPTION
		"This entry shows the Send Abort From Carrier Sense."
	::= { nwNicEthernetCounter 6 }

nwNicSndAbortExcessDefer OBJECT-TYPE
	SYNTAX Counter
	ACCESS read-only
	STATUS mandatory
	DESCRIPTION
		"This entry shows the Send Abort From Excessive Deferral."
	::= { nwNicEthernetCounter 7 }

nwNicRcvAbortFrameAlignment OBJECT-TYPE
	SYNTAX Counter
	ACCESS read-only
	STATUS mandatory
	DESCRIPTION
		"This entry shows the Receive Abort From Bad Frame Alignment."
	::= { nwNicEthernetCounter 8 }


nwNicEthernetThresholdTable OBJECT-TYPE
	SYNTAX SEQUENCE OF NWNicEthernetThreshold
	ACCESS not-accessible
	STATUS mandatory
	DESCRIPTION
		"This entry is a table containing information about all
                groups of thresholds for NetWare NIC Ethernet counters."
	::= { nwNic 4 }

nwNicEthernetThreshold OBJECT-TYPE
	SYNTAX NWNicEthernetThreshold
	ACCESS not-accessible
	STATUS mandatory
	DESCRIPTION
		"This entry contains information about each group
                of thresholds for NetWare NIC Ethernet counters."
--	INDEX  { INTEGER }
	::= { nwNicEthernetThresholdTable 1 }

NWNicEthernetThreshold	::= SEQUENCE {
	nwNicSndOkSingleColliCntThreshold	INTEGER,
	nwNicSndOkMultipleColliCntThreshold	INTEGER,
	nwNicSndOkButDeferredThreshold		INTEGER,
	nwNicSndAbortLateColliThreshold 	INTEGER,
	nwNicSndAbortExcessColliThreshold	INTEGER,
	nwNicSndAbortCarrierSenseThreshold	INTEGER,
	nwNicSndAbortExcessDeferThreshold	INTEGER,
	nwNicRcvAbortFrameAlignmentThreshold	INTEGER
}

-- NetWare NIC Ethernet thresholds

nwNicSndOkSingleColliCntThreshold OBJECT-TYPE
	SYNTAX INTEGER
	ACCESS read-write
	STATUS mandatory
	DESCRIPTION
		"This entry shows the threshold setting of
                Send OK Single Collision Count."
	::= { nwNicEthernetThreshold 1 }

nwNicSndOkMultipleColliCntThreshold OBJECT-TYPE
	SYNTAX INTEGER
	ACCESS read-write
	STATUS mandatory
	DESCRIPTION
		"This entry shows the threshold setting of
		Send OK Multiple Collision Count."
	::= { nwNicEthernetThreshold 2 }

nwNicSndOkButDeferredThreshold OBJECT-TYPE
	SYNTAX INTEGER
	ACCESS read-write
	STATUS mandatory
	DESCRIPTION
		"This entry shows the threshold setting of
		Send OK But Deferred."
	::= { nwNicEthernetThreshold 3 }

nwNicSndAbortLateColliThreshold OBJECT-TYPE
	SYNTAX INTEGER
	ACCESS read-write
	STATUS mandatory
	DESCRIPTION
		"This entry shows the threshold setting of
		Send Abort From Late Collision."
	::= { nwNicEthernetThreshold 4 }

nwNicSndAbortExcessColliThreshold OBJECT-TYPE
	SYNTAX INTEGER
	ACCESS read-write
	STATUS mandatory
	DESCRIPTION
		"This entry shows the threshold setting of
                Send Abort From Excess Collisions."
	::= { nwNicEthernetThreshold 5 }

nwNicSndAbortCarrierSenseThreshold OBJECT-TYPE
	SYNTAX INTEGER
	ACCESS read-write
	STATUS mandatory
	DESCRIPTION
		"This entry shows the threshold setting of
		Send Abort From Carrier Sense."
	::= { nwNicEthernetThreshold 6 }

nwNicSndAbortExcessDeferThreshold OBJECT-TYPE
	SYNTAX INTEGER
	ACCESS read-write
	STATUS mandatory
	DESCRIPTION
		"This entry shows the threshold setting of
		Send Abort From Excessive Deferral."
	::= { nwNicEthernetThreshold 7 }

nwNicRcvAbortFrameAlignmentThreshold OBJECT-TYPE
	SYNTAX INTEGER
	ACCESS read-write
	STATUS mandatory
	DESCRIPTION
		"This entry shows the threshold setting of
		Receive Abort From Bad Frame Alignment."
	::= { nwNicEthernetThreshold 8 }


nwNicTokenRingCounterTable OBJECT-TYPE
	SYNTAX SEQUENCE OF NWNicTokenRingCounter
	ACCESS not-accessible
	STATUS mandatory
	DESCRIPTION
		"This entry is a table containing information about all
                groups of NetWare NIC Token Ring counters."
	::= { nwNic 5 }

nwNicTokenRingCounter OBJECT-TYPE
	SYNTAX NWNicTokenRingCounter
	ACCESS not-accessible
	STATUS mandatory
	DESCRIPTION
		"This entry contains information about each group
		of NetWare NIC Token Ring counters."
	--INDEX  { INTEGER }
	::= { nwNicTokenRingCounterTable 1 }

NWNicTokenRingCounter	::= SEQUENCE {
	nwNicACErrorCounter		Counter,
	nwNicAbortDelimiterCounter	Counter,
	nwNicBurstErrorCounter		Counter,
	nwNicFrameCopiedErrorCounter	Counter,
	nwNicFrequencyErrorCounter	Counter,
	nwNicInternalErrorCounter	Counter,
	nwNicLastRingStatus		Counter,
	nwNicLineErrorCounter		Counter,
	nwNicLostFrameCounter		Counter,
	nwNicTokenErrorCounter		Counter
}

-- NetWare NIC Token-Ring counters

nwNicACErrorCounter OBJECT-TYPE
	SYNTAX Counter
	ACCESS read-only
	STATUS mandatory
	DESCRIPTION
		"This entry shows the ACErrorCounter."
	::= { nwNicTokenRingCounter 1 }

nwNicAbortDelimiterCounter OBJECT-TYPE
	SYNTAX Counter
	ACCESS read-only
	STATUS mandatory
	DESCRIPTION
		"This entry shows the AbortDelimiterCounter."
	::= { nwNicTokenRingCounter 2 }

nwNicBurstErrorCounter OBJECT-TYPE
	SYNTAX Counter
	ACCESS read-only
	STATUS mandatory
	DESCRIPTION
		"This entry shows the BurstErrorCounter."
	::= { nwNicTokenRingCounter 3 }

nwNicFrameCopiedErrorCounter OBJECT-TYPE
	SYNTAX Counter
	ACCESS read-only
	STATUS mandatory
	DESCRIPTION
		"This entry shows the FrameCopiedErrorCounter."
	::= { nwNicTokenRingCounter 4 }

nwNicFrequencyErrorCounter OBJECT-TYPE
	SYNTAX Counter
	ACCESS read-only
	STATUS mandatory
	DESCRIPTION
		"This entry shows the FrequencyErrorCounter."
	::= { nwNicTokenRingCounter 5 }

nwNicInternalErrorCounter OBJECT-TYPE
	SYNTAX Counter
	ACCESS read-only
	STATUS mandatory
	DESCRIPTION
		"This entry shows the InternalErrorCounter."
	::= { nwNicTokenRingCounter 6 }

nwNicLastRingStatus OBJECT-TYPE
	SYNTAX Counter
	ACCESS read-only
	STATUS mandatory
	DESCRIPTION
		"This entry shows the LastRingStatus."
	::= { nwNicTokenRingCounter 7 }

nwNicLineErrorCounter OBJECT-TYPE
	SYNTAX Counter
	ACCESS read-only
	STATUS mandatory
	DESCRIPTION
		"This entry shows the LineErrorCounter."
	::= { nwNicTokenRingCounter 8 }

nwNicLostFrameCounter OBJECT-TYPE
	SYNTAX Counter
	ACCESS read-only
	STATUS mandatory
	DESCRIPTION
		"This entry shows the LostFrameCounter."
	::= { nwNicTokenRingCounter 9 }

nwNicTokenErrorCounter OBJECT-TYPE
	SYNTAX Counter
	ACCESS read-only
	STATUS mandatory
	DESCRIPTION
		"This entry shows the TokenErrorCounter."
	::= { nwNicTokenRingCounter 10 }



nwNicTokenRingThresholdTable OBJECT-TYPE
	SYNTAX SEQUENCE OF NWNicTokenRingThreshold
	ACCESS not-accessible
	STATUS mandatory
	DESCRIPTION
		"This entry is a table containing information about all
                groups of thresholds for NetWare NIC Token Ring counters."
	::= { nwNic 6 }

nwNicTokenRingThreshold OBJECT-TYPE
	SYNTAX NWNicTokenRingThreshold
	ACCESS not-accessible
	STATUS mandatory
	DESCRIPTION
		"This entry contains information about each group
                of thresholds for NetWare NIC Token Ring counters."
	--INDEX  { INTEGER }
	::= { nwNicTokenRingThresholdTable 1 }

NWNicTokenRingThreshold ::= SEQUENCE {
	nwNicACErrorCounterThreshold		INTEGER,
	nwNicAbortDelimiterCounterThreshold	INTEGER,
	nwNicBurstErrorCounterThreshold 	INTEGER,
	nwNicFrameCopiedErrorCounterThreshold	INTEGER,
	nwNicFrequencyErrorCounterThreshold	INTEGER,
	nwNicInternalErrorCounterThreshold	INTEGER,
	nwNicLastRingStatusThreshold		INTEGER,
	nwNicLineErrorCounterThreshold		INTEGER,
	nwNicLostFrameCounterThreshold		INTEGER,
	nwNicTokenErrorCounterThreshold 	INTEGER
}

-- NetWare NIC Token-Ring thresholds

nwNicACErrorCounterThreshold OBJECT-TYPE
	SYNTAX INTEGER
	ACCESS read-write
	STATUS mandatory
	DESCRIPTION
		"This entry shows the threshold setting of
		ACErrorCounter." 
	::= { nwNicTokenRingThreshold 1 }

nwNicAbortDelimiterCounterThreshold OBJECT-TYPE
	SYNTAX INTEGER
	ACCESS read-write
	STATUS mandatory
	DESCRIPTION
		"This entry shows the threshold setting of
		AbortDelimiterCounter."
	::= { nwNicTokenRingThreshold 2 }

nwNicBurstErrorCounterThreshold OBJECT-TYPE
	SYNTAX INTEGER
	ACCESS read-write
	STATUS mandatory
	DESCRIPTION
		"This entry shows the threshold setting of
		BurstErrorCounter."
	::= { nwNicTokenRingThreshold 3 }

nwNicFrameCopiedErrorCounterThreshold OBJECT-TYPE
	SYNTAX INTEGER
	ACCESS read-write
	STATUS mandatory
	DESCRIPTION
		"This entry shows the threshold setting of
		FrameCopiedErrorCounter."
	::= { nwNicTokenRingThreshold 4 }

nwNicFrequencyErrorCounterThreshold OBJECT-TYPE
	SYNTAX INTEGER
	ACCESS read-write
	STATUS mandatory
	DESCRIPTION
		"This entry shows the threshold setting of
		FrequencyErrorCounter."
	::= { nwNicTokenRingThreshold 5 }

nwNicInternalErrorCounterThreshold OBJECT-TYPE
	SYNTAX INTEGER
	ACCESS read-write
	STATUS mandatory
	DESCRIPTION
		"This entry shows the threshold setting of
		InternalErrorCounter."
	::= { nwNicTokenRingThreshold 6 }

nwNicLastRingStatusThreshold OBJECT-TYPE
	SYNTAX INTEGER
	ACCESS read-write
	STATUS mandatory
	DESCRIPTION
		"This entry shows the threshold setting of
		LastRingStatus."
	::= { nwNicTokenRingThreshold 7 }

nwNicLineErrorCounterThreshold OBJECT-TYPE
	SYNTAX INTEGER
	ACCESS read-write
	STATUS mandatory
	DESCRIPTION
		"This entry shows the threshold setting of
		LineErrorCounter."
	::= { nwNicTokenRingThreshold 8 }

nwNicLostFrameCounterThreshold OBJECT-TYPE
	SYNTAX INTEGER
	ACCESS read-write
	STATUS mandatory
	DESCRIPTION
		"This entry shows the threshold setting of
		LostFrameCounter."
	::= { nwNicTokenRingThreshold 9 }

nwNicTokenErrorCounterThreshold OBJECT-TYPE
	SYNTAX INTEGER
	ACCESS read-write
	STATUS mandatory
	DESCRIPTION
		"This entry shows the threshold setting of
		TokenErrorCounter."
	::= { nwNicTokenRingThreshold 10 }

ntNicGenericCounterTable OBJECT-TYPE
	SYNTAX SEQUENCE OF NTNicGenericCounter
	ACCESS not-accessible
	STATUS mandatory
	DESCRIPTION
		"This entry is a table of Windows NT NIC generic counters."
	::= { ntNic 1 }

ntNicGenericCounter OBJECT-TYPE
	SYNTAX NTNicGenericCounter
	ACCESS not-accessible
	STATUS mandatory
	DESCRIPTION
		"This entry contains information about each Windows NT NIC generic counter."
	--INDEX  { INTEGER }
	::= { ntNicGenericCounterTable 1 }

NTNicGenericCounter	::= SEQUENCE {
	ntNicCntFrameXmitOk		Counter,
	ntNicCntFrameRcvOk		Counter,
	ntNicCntFrameXmitErr		Counter,
	ntNicCntFrameRcvErr		Counter,
	ntNicCntRcvFailNoBuf		Counter,
	ntNicCntDirByteXmit		Counter,
	ntNicCntDirPktXmit		Counter,
	ntNicCntMulCastByteXmit 	Counter,
	ntNicCntMulCastPktXmit		Counter,
	ntNicCntBrdCastByteXmit 	Counter,
	ntNicCntBrdCastPktXmit		Counter,
	ntNicCntDirByteRcv		Counter,
	ntNicCntDirPktRcv		Counter,
	ntNicCntMulCastByteRcv		Counter,
	ntNicCntMulCastPktRcv		Counter,
	ntNicCntBrdCastByteRcv		Counter,
	ntNicCntBrdCastPktRcv		Counter,
	ntNicCntFrameRcvCRCErr		Counter,
	ntNicXmitQueueLength		INTEGER
}

-- Windows NT NIC generic counters

ntNicCntFrameXmitOk		OBJECT-TYPE
	SYNTAX Counter
	ACCESS read-only
	STATUS mandatory
	DESCRIPTION
		"This entry is the number of frames transmitted without errors."
	::= { ntNicGenericCounter 1 }

ntNicCntFrameRcvOk		OBJECT-TYPE
	SYNTAX Counter
	ACCESS read-only
	STATUS mandatory
	DESCRIPTION
		"This entry is the number of frames the NIC received with no errors."
	::= { ntNicGenericCounter 2 }

ntNicCntFrameXmitErr		OBJECT-TYPE
	SYNTAX Counter
	ACCESS read-only
	STATUS mandatory
	DESCRIPTION
		"This entry is the number of frames the NIC fails to transmit."
	::= { ntNicGenericCounter 3 }

ntNicCntFrameRcvErr		OBJECT-TYPE
	SYNTAX Counter
	ACCESS read-only
	STATUS mandatory
	DESCRIPTION
		"This entry is the number of frames the NIC receives but is abandoned due to errors."
	::= { ntNicGenericCounter 4 }

ntNicCntRcvFailNoBuf		OBJECT-TYPE
	SYNTAX Counter
	ACCESS read-only
	STATUS mandatory
	DESCRIPTION
		"This entry is the number of frames the NIC cannot receive due to lack of buffer space."
	::= { ntNicGenericCounter 5 }

ntNicCntDirByteXmit		OBJECT-TYPE
	SYNTAX Counter
	ACCESS read-only
	STATUS mandatory
	DESCRIPTION
		"This entry is the number of bytes in directed packets transmitted without errors."
	::= { ntNicGenericCounter 6 }

ntNicCntDirPktXmit	      OBJECT-TYPE
	SYNTAX Counter
	ACCESS read-only
	STATUS mandatory
	DESCRIPTION
		"This entry is the number of directed packets transmitted without errors."
	::= { ntNicGenericCounter 7 }

ntNicCntMulCastByteXmit 	OBJECT-TYPE
	SYNTAX Counter
	ACCESS read-only
	STATUS mandatory
	DESCRIPTION
		"This entry is the number of bytes in multicast packets transmitted without errors."
	::= { ntNicGenericCounter 8 }

ntNicCntMulCastPktXmit	      OBJECT-TYPE
	SYNTAX Counter
	ACCESS read-only
	STATUS mandatory
	DESCRIPTION
		"This entry is the number of multicast packets transmitted without errors."
	::= { ntNicGenericCounter 9 }

ntNicCntBrdCastByteXmit 	OBJECT-TYPE
	SYNTAX Counter
	ACCESS read-only
	STATUS mandatory
	DESCRIPTION
		"This entry is the number of bytes in broadcast packets transmitted without errors."
	::= { ntNicGenericCounter 10 }

ntNicCntBrdCastPktXmit	      OBJECT-TYPE
	SYNTAX Counter
	ACCESS read-only
	STATUS mandatory
	DESCRIPTION
		"This entry is the number of broadcast packets transmitted without errors."
	::= { ntNicGenericCounter 11 }

ntNicCntDirByteRcv	       OBJECT-TYPE
	SYNTAX Counter
	ACCESS read-only
	STATUS mandatory
	DESCRIPTION
		"This entry is the number of bytes in directed packets received without errors."
	::= { ntNicGenericCounter 12 }

ntNicCntDirPktRcv	     OBJECT-TYPE
	SYNTAX Counter
	ACCESS read-only
	STATUS mandatory
	DESCRIPTION
		"This entry is the number of directed packets received without errors."
	::= { ntNicGenericCounter 13 }

ntNicCntMulCastByteRcv	       OBJECT-TYPE
	SYNTAX Counter
	ACCESS read-only
	STATUS mandatory
	DESCRIPTION
		"This entry is the number of bytes in multicast packets received 
without errors."
	::= { ntNicGenericCounter 14 }

ntNicCntMulCastPktRcv	     OBJECT-TYPE
	SYNTAX Counter
	ACCESS read-only
	STATUS mandatory
	DESCRIPTION
		"This entry is the number of multicast packets received without errors."
	::= { ntNicGenericCounter 15 }

ntNicCntBrdCastByteRcv	       OBJECT-TYPE
	SYNTAX Counter
	ACCESS read-only
	STATUS mandatory
	DESCRIPTION
		"This entry is the number of bytes in broadcast packets received without errors."
	::= { ntNicGenericCounter 16 }

ntNicCntBrdCastPktRcv	     OBJECT-TYPE
	SYNTAX Counter
	ACCESS read-only
	STATUS mandatory
	DESCRIPTION
		"This entry is the number of broadcast packets received without errors."
	::= { ntNicGenericCounter 17 }

ntNicCntFrameRcvCRCErr		OBJECT-TYPE
	SYNTAX Counter
	ACCESS read-only
	STATUS mandatory
	DESCRIPTION
		"This entry is the number of frames received with checksum errors."
	::= { ntNicGenericCounter 18 }

ntNicXmitQueueLength		OBJECT-TYPE
	SYNTAX INTEGER
	ACCESS read-only
	STATUS mandatory
	DESCRIPTION
		"This entry is the number of packets the NIC driver queues for transmission."
	::= { ntNicGenericCounter 19 }

ntNicGenericThresholdTable OBJECT-TYPE
	SYNTAX SEQUENCE OF NTNicGenericThreshold
	ACCESS not-accessible
	STATUS mandatory
	DESCRIPTION
		"This entry is a table of threshold values for Windows NT NIC generic counters."
	::= { ntNic 2 }

ntNicGenericThreshold OBJECT-TYPE
	SYNTAX NTNicGenericThreshold
	ACCESS not-accessible
	STATUS mandatory
	DESCRIPTION
		"This entry contains the threshold value for each Windows NT NIC generic counter."
	--INDEX  { INTEGER }
	::= { ntNicGenericThresholdTable 1 }

NTNicGenericThreshold	::= SEQUENCE {
	ntNicTldFrameXmitOk		INTEGER,
	ntNicTldFrameRcvOk		INTEGER,
	ntNicTldFrameXmitErr		INTEGER,
	ntNicTldFrameRcvErr		INTEGER,
	ntNicTldRcvFailNoBuf		INTEGER,
	ntNicTldDirByteXmit		INTEGER,
	ntNicTldDirPktXmit		INTEGER,
	ntNicTldMulCastByteXmit 	INTEGER,
	ntNicTldMulCastPktXmit		INTEGER,
	ntNicTldBrdCastByteXmit 	INTEGER,
	ntNicTldBrdCastPktXmit		INTEGER,
	ntNicTldDirByteRcv		INTEGER,
	ntNicTldDirPktRcv		INTEGER,
	ntNicTldMulCastByteRcv		INTEGER,
	ntNicTldMulCastPktRcv		INTEGER,
	ntNicTldBrdCastByteRcv		INTEGER,
	ntNicTldBrdCastPktRcv		INTEGER,
	ntNicTldFrameRcvCRCErr		INTEGER,
	ntNicTldXmitQueueLength 	INTEGER
}

-- Windows NT NIC generic thresholds

ntNicTldFrameXmitOk		OBJECT-TYPE
	SYNTAX INTEGER
	ACCESS read-write
	STATUS mandatory
	DESCRIPTION
		"This entry is the threshold value of frames transmitted without errors."
	::= { ntNicGenericThreshold 1 }

ntNicTldFrameRcvOk		OBJECT-TYPE
	SYNTAX INTEGER
	ACCESS read-write
	STATUS mandatory
	DESCRIPTION
		"This entry is the threshold value of frames the NIC receives with no errors."
	::= { ntNicGenericThreshold 2 }

ntNicTldFrameXmitErr		OBJECT-TYPE
	SYNTAX INTEGER
	ACCESS read-write
	STATUS mandatory
	DESCRIPTION
		"This entry is the threshold value of frames the NIC fails to transmit."
	::= { ntNicGenericThreshold 3 }

ntNicTldFrameRcvErr		OBJECT-TYPE
	SYNTAX INTEGER
	ACCESS read-write
	STATUS mandatory
	DESCRIPTION
		"This entry is the threshold value of frames the NIC receives but are abandoned due to errors."
	::= { ntNicGenericThreshold 4 }

ntNicTldRcvFailNoBuf		OBJECT-TYPE
	SYNTAX INTEGER
	ACCESS read-write
	STATUS mandatory
	DESCRIPTION
		"This entry is the threshold value of frames the NIC cannot receive due to 
		lack of buffer space."
	::= { ntNicGenericThreshold 5 }

ntNicTldDirByteXmit		OBJECT-TYPE
	SYNTAX INTEGER
	ACCESS read-write
	STATUS mandatory
	DESCRIPTION
		"This entry is the threshold value of bytes in directed packets transmitted without errors."
	::= { ntNicGenericThreshold 6 }

ntNicTldDirPktXmit	      OBJECT-TYPE
	SYNTAX INTEGER
	ACCESS read-write
	STATUS mandatory
	DESCRIPTION
		"This entry is the threshold value of directed packets transmitted without errors."
	::= { ntNicGenericThreshold 7 }

ntNicTldMulCastByteXmit 	OBJECT-TYPE
	SYNTAX INTEGER
	ACCESS read-write
	STATUS mandatory
	DESCRIPTION
		"This entry is the threshold value of bytes in multicast packets transmitted 
		without errors."
	::= { ntNicGenericThreshold 8 }

ntNicTldMulCastPktXmit	      OBJECT-TYPE
	SYNTAX INTEGER
	ACCESS read-write
	STATUS mandatory
	DESCRIPTION
		"This entry is the threshold value of multicast packets transmitted without errors."
	::= { ntNicGenericThreshold 9 }

ntNicTldBrdCastByteXmit 	OBJECT-TYPE
	SYNTAX INTEGER
	ACCESS read-write
	STATUS mandatory
	DESCRIPTION
		"This entry is the threshold value of bytes in broadcast packets transmitted 
		without errors."
	::= { ntNicGenericThreshold 10 }

ntNicTldBrdCastPktXmit	      OBJECT-TYPE
	SYNTAX INTEGER
	ACCESS read-write
	STATUS mandatory
	DESCRIPTION
		"This entry is the threshold value of broadcast packets transmitted without errors."
	::= { ntNicGenericThreshold 11 }

ntNicTldDirByteRcv	       OBJECT-TYPE
	SYNTAX INTEGER
	ACCESS read-write
	STATUS mandatory
	DESCRIPTION
		"This entry is the threshold value of bytes in directed packets received without errors."
	::= { ntNicGenericThreshold 12 }

ntNicTldDirPktRcv	     OBJECT-TYPE
	SYNTAX INTEGER
	ACCESS read-write
	STATUS mandatory
	DESCRIPTION
		"This entry is the threshold value of directed packets received without errors."
	::= { ntNicGenericThreshold 13 }

ntNicTldMulCastByteRcv	       OBJECT-TYPE
	SYNTAX INTEGER
	ACCESS read-write
	STATUS mandatory
	DESCRIPTION
		"This entry is the threshold value of bytes in multicast packets received 
		without errors."
	::= { ntNicGenericThreshold 14 }

ntNicTldMulCastPktRcv	     OBJECT-TYPE
	SYNTAX INTEGER
	ACCESS read-write
	STATUS mandatory
	DESCRIPTION
		"This entry is the threshold value of multicast packets received without errors."
	::= { ntNicGenericThreshold 15 }

ntNicTldBrdCastByteRcv	       OBJECT-TYPE
	SYNTAX INTEGER
	ACCESS read-write
	STATUS mandatory
	DESCRIPTION
		"This entry is the threshold value of bytes in broadcast packets received without errors."
	::= { ntNicGenericThreshold 16 }

ntNicTldBrdCastPktRcv	     OBJECT-TYPE
	SYNTAX INTEGER
	ACCESS read-write
	STATUS mandatory
	DESCRIPTION
		"This entry is the threshold value of broadcast packets received without errors."
	::= { ntNicGenericThreshold 17 }

ntNicTldFrameRcvCRCErr		OBJECT-TYPE
	SYNTAX INTEGER
	ACCESS read-write
	STATUS mandatory
	DESCRIPTION
		"This entry is the threshold value of frames received with checksum errors."
	::= { ntNicGenericThreshold 18 }

ntNicTldXmitQueueLength 	   OBJECT-TYPE
	SYNTAX INTEGER
	ACCESS read-write
	STATUS mandatory
	DESCRIPTION
		"This entry is the threshold value of packets the NIC driver queues for transmission."
	::= { ntNicGenericThreshold 19 }

-- GenericThresholdTable End


ntNicEthernetCounterTable OBJECT-TYPE
	SYNTAX SEQUENCE OF NTNicEthernetCounter
	ACCESS not-accessible
	STATUS mandatory
	DESCRIPTION
		"This entry is a table of Windows NT NIC Ethernet counters."
	::= { ntNic 3 }

-- EthernetCounterTable Begin

ntNicEthernetCounter OBJECT-TYPE
	SYNTAX NTNicEthernetCounter
	ACCESS not-accessible
	STATUS mandatory
	DESCRIPTION
		"This entry contains information about each Windows NT NIC Ethernet counter."
	--INDEX  { INTEGER }
	::= { ntNicEthernetCounterTable 1 }

NTNicEthernetCounter	::= SEQUENCE {
	ntNicCntRcvFrameAlignErr	  Counter,
	ntNicCntXmitOkOneCollision	  Counter,
	ntNicCntXmitOkMoreCollision	  Counter,
	ntNicCntXmitOkDeffered		  Counter,
	ntNicCntXmitFailMaxCollision	  Counter,
	ntNicCntRcvErrOverrun		  Counter,
	ntNicCntXmitErrUnderrun 	  Counter,
	ntNicCntXmitHeartbeat		  Counter,
	ntNicCntTimesCRSLost		  Counter,
	ntNicCntXmitLateCollision	  Counter
}

-- Windows NT NIC Ethernet counters

ntNicCntRcvFrameAlignErr	  OBJECT-TYPE
	SYNTAX Counter
	ACCESS read-only
	STATUS mandatory
	DESCRIPTION
		"This entry is the number of frames received with alignment errors."
	::= { ntNicEthernetCounter 1 }

ntNicCntXmitOkOneCollision	  OBJECT-TYPE
	SYNTAX Counter
	ACCESS read-only
	STATUS mandatory
	DESCRIPTION
		"This entry is the number of frames successfully transmitted after exactly one collision."
	::= { ntNicEthernetCounter 2 }

ntNicCntXmitOkMoreCollision	  OBJECT-TYPE
	SYNTAX Counter
	ACCESS read-only
	STATUS mandatory
	DESCRIPTION
		"This entry is the number of frames successfully transmitted after more than 
		one collision."
	::= { ntNicEthernetCounter 3 }

ntNicCntXmitOkDeffered		  OBJECT-TYPE
	SYNTAX Counter
	ACCESS read-only
	STATUS mandatory
	DESCRIPTION
		"This entry is the number of frames successfully transmitted after the NIC 
		defers transmission at least once."
	::= { ntNicEthernetCounter 4 }

ntNicCntXmitFailMaxCollision	  OBJECT-TYPE
	SYNTAX Counter
	ACCESS read-only
	STATUS mandatory
	DESCRIPTION
		"This entry is the number of frames not transmitted due to excessive collisions."
	::= { ntNicEthernetCounter 5 }

ntNicCntRcvErrOverrun		  OBJECT-TYPE
	SYNTAX Counter
	ACCESS read-only
	STATUS mandatory
	DESCRIPTION
		"This entry is the number of frames not received due to over-run errors."
	::= { ntNicEthernetCounter 6 }

ntNicCntXmitErrUnderrun 	  OBJECT-TYPE
	SYNTAX Counter
	ACCESS read-only
	STATUS mandatory
	DESCRIPTION
		"This entry is the number of frames not transmitted due to under-run errors."
	::= { ntNicEthernetCounter 7 }

ntNicCntXmitHeartbeat		  OBJECT-TYPE
	SYNTAX Counter
	ACCESS read-only
	STATUS mandatory
	DESCRIPTION
		"This entry is the number of frames successfully transmitted without detection 
		of the collision-detect heartbeat."
	::= { ntNicEthernetCounter 8 }

ntNicCntTimesCRSLost		  OBJECT-TYPE
	SYNTAX Counter
	ACCESS read-only
	STATUS mandatory
	DESCRIPTION
		"This entry is the number of times the CRS signal has been lost during 
		packet transmission."
	::= { ntNicEthernetCounter 9 }

ntNicCntXmitLateCollision	  OBJECT-TYPE
	SYNTAX Counter
	ACCESS read-only
	STATUS mandatory
	DESCRIPTION
		"This entry is the number of collisions detected after the normal window."
	::= { ntNicEthernetCounter 10 }

-- Ethernet Count Table end


ntNicEthernetThresholdTable OBJECT-TYPE
	SYNTAX SEQUENCE OF NTNicEthernetThreshold
	ACCESS not-accessible
	STATUS mandatory
	DESCRIPTION
		"This entry is a table of threshold values for Windows NT NIC Ethernet counters."
	::= { ntNic 4 }

-- Ethernet Threshold Begin


ntNicEthernetThreshold OBJECT-TYPE
	SYNTAX NTNicEthernetThreshold
	ACCESS not-accessible
	STATUS mandatory
	DESCRIPTION
		"This entry contains the threshold value for each Windows NT NIC Ethernet counter."
	--INDEX  { INTEGER }
	::= { ntNicEthernetThresholdTable 1 }

NTNicEthernetThreshold	::= SEQUENCE {
	ntNicTldRcvFrameAlignErr	  INTEGER,
	ntNicTldXmitOkOneCollision	  INTEGER,
	ntNicTldXmitOkMoreCollision	  INTEGER,
	ntNicTldXmitOkDeffered		  INTEGER,
	ntNicTldXmitFailMaxCollision	  INTEGER,
	ntNicTldRcvErrOverrun		  INTEGER,
	ntNicTldXmitErrUnderrun 	  INTEGER,
	ntNicTldXmitHeartbeat		  INTEGER,
	ntNicTldTimesCRSLost		  INTEGER,
	ntNicTldXmitLateCollision	  INTEGER
}

-- Windows NT NIC Ethernet thresholds

ntNicTldRcvFrameAlignErr	  OBJECT-TYPE
	SYNTAX INTEGER
	ACCESS read-write
	STATUS mandatory
	DESCRIPTION
		"This entry is the threshold value of frames received with alignment errors."
	::= { ntNicEthernetThreshold 1 }

ntNicTldXmitOkOneCollision	  OBJECT-TYPE
	SYNTAX INTEGER
	ACCESS read-write
	STATUS mandatory
	DESCRIPTION
		"This entry is the threshold value of frames successfully transmitted after 
		exactly one collision."
	::= { ntNicEthernetThreshold 2 }

ntNicTldXmitOkMoreCollision	  OBJECT-TYPE
	SYNTAX INTEGER
	ACCESS read-write
	STATUS mandatory
	DESCRIPTION
		"This entry is the threshold value of frames successfully transmitted after more 
		than one collision."
	::= { ntNicEthernetThreshold 3 }

ntNicTldXmitOkDeffered		  OBJECT-TYPE
	SYNTAX INTEGER
	ACCESS read-write
	STATUS mandatory
	DESCRIPTION
		"This entry is the threshold value of frames successfully transmitted after the 
		NIC defers transmission at least once."
	::= { ntNicEthernetThreshold 4 }

ntNicTldXmitFailMaxCollision	  OBJECT-TYPE
	SYNTAX INTEGER
	ACCESS read-write
	STATUS mandatory
	DESCRIPTION
		"This entry is the threshold value of frames not transmitted due to excessive collisions."
	::= { ntNicEthernetThreshold 5 }

ntNicTldRcvErrOverrun		  OBJECT-TYPE
	SYNTAX INTEGER
	ACCESS read-write
	STATUS mandatory
	DESCRIPTION
		"This entry is the threshold value of frames not received due to over-run errors."
	::= { ntNicEthernetThreshold 6 }

ntNicTldXmitErrUnderrun 	  OBJECT-TYPE
	SYNTAX INTEGER
	ACCESS read-write
	STATUS mandatory
	DESCRIPTION
		"This entry is the threshold value of frames not transmitted due to under-run errors."
	::= { ntNicEthernetThreshold 7 }

ntNicTldXmitHeartbeat		  OBJECT-TYPE
	SYNTAX INTEGER
	ACCESS read-write
	STATUS mandatory
	DESCRIPTION
		"This entry is the threshold value of frames successfully transmitted without detection 
		of the collision-detect heartbeat."
	::= { ntNicEthernetThreshold 8 }

ntNicTldTimesCRSLost		  OBJECT-TYPE
	SYNTAX INTEGER
	ACCESS read-write
	STATUS mandatory
	DESCRIPTION
		"This entry is the threshold value for the number of times the CRS signal has been 
		lost during packet transmission."
	::= { ntNicEthernetThreshold 9 }

ntNicTldXmitLateCollision	  OBJECT-TYPE
	SYNTAX INTEGER
	ACCESS read-write
	STATUS mandatory
	DESCRIPTION
		"This entry is the threshold value of collisions detected after the normal window."
	::= { ntNicEthernetThreshold 10 }

-- EthernetThreshold Table End


ntNicTokenRingCounterTable OBJECT-TYPE
	SYNTAX SEQUENCE OF NTNicTokenRingCounter
	ACCESS not-accessible
	STATUS mandatory
	DESCRIPTION
		"This entry is a table of Windows NT NIC Token Ring counters."
	::= { ntNic 5 }

-- TokenRing Counter Table Begin

ntNicTokenRingCounter OBJECT-TYPE
	SYNTAX NTNicTokenRingCounter
	ACCESS not-accessible
	STATUS mandatory
	DESCRIPTION
		"This entry contains information about each Windows NT NIC Token Ring counter."
	--INDEX  { INTEGER }
	::= { ntNicTokenRingCounterTable 1 }

NTNicTokenRingCounter	::= SEQUENCE {
	ntNicCntACError 	    Counter,
	ntNicCntAbortDelimiter	    Counter,
	ntNicCntBurstError	    Counter,
	ntNicCntFrameCopiedError    Counter,
	ntNicCntFrequencyError	    Counter,
	ntNicCntInternalError	    Counter,
	ntNicCntLastRingStatus	    INTEGER,
	ntNicCntLineError	    Counter,
	ntNicCntLostFrame	    Counter,
	ntNicCntTokenError	    Counter
}

-- Windows NT NIC Token-Ring counters

ntNicCntACError OBJECT-TYPE
	SYNTAX Counter
	ACCESS read-only
	STATUS mandatory
	DESCRIPTION
		"This entry is the number of frames with A/C errors."
	::= { ntNicTokenRingCounter 1 }

ntNicCntAbortDelimiter OBJECT-TYPE
	SYNTAX Counter
	ACCESS read-only
	STATUS mandatory
	DESCRIPTION
		"This entry is the number of abort delimiters transmitted."
	::= { ntNicTokenRingCounter 2 }

ntNicCntBurstError OBJECT-TYPE
	SYNTAX Counter
	ACCESS read-only
	STATUS mandatory
	DESCRIPTION
		"This entry is the number of frames containing five half bits with no transition."
	::= { ntNicTokenRingCounter 3 }

ntNicCntFrameCopiedError OBJECT-TYPE
	SYNTAX Counter
	ACCESS read-only
	STATUS mandatory
	DESCRIPTION
		"This entry is the number of frames addressed to the network interface card that another 
		NIC on the ring has also copied."
	::= { ntNicTokenRingCounter 4 }

ntNicCntFrequencyError OBJECT-TYPE
	SYNTAX Counter
	ACCESS read-only
	STATUS mandatory
	DESCRIPTION
		"This entry is the number of frequency errors on the ring."
	::= { ntNicTokenRingCounter 5 }

ntNicCntInternalError OBJECT-TYPE
	SYNTAX Counter
	ACCESS read-only
	STATUS mandatory
	DESCRIPTION
		"This entry is the number of internal errors the NIC has detected."
	::= { ntNicTokenRingCounter 6 }

ntNicCntLastRingStatus OBJECT-TYPE
	SYNTAX Counter
	ACCESS read-only
	STATUS mandatory
	DESCRIPTION
		"This entry is an NDIS_STATUS_RING_STATUS code indicates the last ring status."
	::= { ntNicTokenRingCounter 7 }

ntNicCntLineError OBJECT-TYPE
	SYNTAX Counter
	ACCESS read-only
	STATUS mandatory
	DESCRIPTION
		"This entry is the number of frames with an invalid FCS or a code violation."
	::= { ntNicTokenRingCounter 8 }

ntNicCntLostFrame OBJECT-TYPE
	SYNTAX Counter
	ACCESS read-only
	STATUS mandatory
	DESCRIPTION
		"This entry is the number of frames transmitted that have not circled the ring 
		within the maximum ring latency."
	::= { ntNicTokenRingCounter 9 }

ntNicCntTokenError OBJECT-TYPE
	SYNTAX Counter
	ACCESS read-only
	STATUS mandatory
	DESCRIPTION
		"This entry is the number of times the NIC has been the active monitor and 
		has had to recreate."
	::= { ntNicTokenRingCounter 10 }

-- NicTokenRingCounter Table End



ntNicTokenRingThresholdTable OBJECT-TYPE
	SYNTAX SEQUENCE OF NTNicTokenRingThreshold
	ACCESS not-accessible
	STATUS mandatory
	DESCRIPTION
		"This entry is a table of threshold values for Windows NT NIC Token Ring counters."
	::= { ntNic 6 }

--NicTokenRingThreshold Table Begin

ntNicTokenRingThreshold OBJECT-TYPE
	SYNTAX NTNicTokenRingThreshold
	ACCESS not-accessible
	STATUS mandatory
	DESCRIPTION
		"This entry contains the threshold value for each Windows NT NIC Token Ring counter."
	--INDEX  { INTEGER }
	::= { ntNicTokenRingThresholdTable 1 }

NTNicTokenRingThreshold ::= SEQUENCE {
	ntNicTldACError 	    INTEGER,
	ntNicTldAbortDelimiter	    INTEGER,
	ntNicTldBurstError	    INTEGER,
	ntNicTldFrameCopiedError    INTEGER,
	ntNicTldFrequencyError	    INTEGER,
	ntNicTldInternalError	    INTEGER,
	ntNicTldLastRingStatus	    INTEGER,
	ntNicTldLineError	    INTEGER,
	ntNicTldLostFrame	    INTEGER,
	ntNicTldTokenError	    INTEGER
}

-- Windows NT NIC Token-Ring thresholds

ntNicTldACError OBJECT-TYPE
	SYNTAX INTEGER
	ACCESS read-write
	STATUS mandatory
	DESCRIPTION
		"This entry is the threshold value of frames with A/C errors."
	::= { ntNicTokenRingThreshold 1 }

ntNicTldAbortDelimiter OBJECT-TYPE
	SYNTAX INTEGER
	ACCESS read-write
	STATUS mandatory
	DESCRIPTION
		"This entry is the threshold value of abort delimiters transmitted."
	::= { ntNicTokenRingThreshold 2 }

ntNicTldBurstError OBJECT-TYPE
	SYNTAX INTEGER
	ACCESS read-write
	STATUS mandatory
	DESCRIPTION
		"This entry is the threshold value of frames containing five half bits with no transition."
	::= { ntNicTokenRingThreshold 3 }

ntNicTldFrameCopiedError OBJECT-TYPE
	SYNTAX INTEGER
	ACCESS read-write
	STATUS mandatory
	DESCRIPTION
		"This entry is the threshold value of frames addressed to the network interface card 
		that another NIC on the ring has also copied."
	::= { ntNicTokenRingThreshold 4 }

ntNicTldFrequencyError OBJECT-TYPE
	SYNTAX INTEGER
	ACCESS read-write
	STATUS mandatory
	DESCRIPTION
		"This entry is the threshold value of frequency errors on the ring."
	::= { ntNicTokenRingThreshold 5 }

ntNicTldInternalError OBJECT-TYPE
	SYNTAX INTEGER
	ACCESS read-write
	STATUS mandatory
	DESCRIPTION
		"This entry is the threshold value of internal errors the NIC has detected."
	::= { ntNicTokenRingThreshold 6 }

ntNicTldLastRingStatus OBJECT-TYPE
	SYNTAX INTEGER
	ACCESS read-write
	STATUS mandatory
	DESCRIPTION
		"This entry is the threshold value of the last ring status."
	::= { ntNicTokenRingThreshold 7 }

ntNicTldLineError OBJECT-TYPE
	SYNTAX INTEGER
	ACCESS read-write
	STATUS mandatory
	DESCRIPTION
		"This entry is the threshold value of the number of frames with an invalid 
		FCS or a code violation."
	::= { ntNicTokenRingThreshold 8 }

ntNicTldLostFrame OBJECT-TYPE
	SYNTAX INTEGER
	ACCESS read-write
	STATUS mandatory
	DESCRIPTION
		"This entry is the threshold value for the number of frames transmitted that have 
		not circled the ring within the maximum ring latency."
	::= { ntNicTokenRingThreshold 9 }

ntNicTldTokenError OBJECT-TYPE
	SYNTAX INTEGER
	ACCESS read-write
	STATUS mandatory
	DESCRIPTION
		"This entry is the threshold value for the number of times the NIC has been the 
		active monitor and has had to recreate."
	::= { ntNicTokenRingThreshold 10 }



-- SCO UNIX NIC specific Information
-- ****************************************************************

scoNicGenericCounterTable OBJECT-TYPE
        SYNTAX SEQUENCE OF SCONicGenericCounter
        ACCESS not-accessible
        STATUS mandatory
        DESCRIPTION
        "This entry is a table of SCO NIC generic counters."
        ::= { scoNic 1 }

scoNicGenericCounter OBJECT-TYPE
        SYNTAX SCONicGenericCounter
        ACCESS not-accessible
        STATUS mandatory
        DESCRIPTION
        "This entry contains information about each SCO NIC generic counter."
--INDEX  { INTEGER }
        ::= { scoNicGenericCounterTable 1 }

SCONicGenericCounter     ::= SEQUENCE {
        scoNicNumRcvPkts         Gauge,
        scoNicNumRcvBytes        Gauge,
        scoNicNumSndPkts         Gauge,
        scoNicNumSndBytes        Gauge,
        scoNicFrameDef           Counter,
        scoNicCollisions         Counter,
        scoNicFrameColl          Counter,
        scoNicOFrameColl         Counter,
        scoNicXsColl             Counter,
        scoNicFrameNosr          Counter,
        scoNicNoResource         Counter,
        scoNicBadSum             Counter,
        scoNicAlign              Counter,
        scoNicBadLen             Counter,
        scoNicBadSap             Counter,
        scoNicMcastRjct          Counter,
        scoNicCarrier            Counter,
        scoNicBadCts             Counter,
        scoNicBadDma             Counter,
        scoNicTimeOuts           Counter
}

-- SCO UNIX Generic counters

scoNicNumRcvPkts OBJECT-TYPE
        SYNTAX Gauge
        ACCESS read-only
        STATUS mandatory
        DESCRIPTION
                "This entry is the current number of received packets in this
                 NIC card."
         ::= { scoNicGenericCounter 1 }

scoNicNumRcvBytes OBJECT-TYPE
        SYNTAX Gauge
        ACCESS read-only
        STATUS mandatory
        DESCRIPTION
                "This entry is the current number of received bytes in this
                 NIC card."
        ::= { scoNicGenericCounter 2 }

scoNicNumSndPkts OBJECT-TYPE
        SYNTAX Gauge
        ACCESS read-only
        STATUS mandatory
        DESCRIPTION
                "This entry is the current number of sent packets in this
                 NIC card."
        ::= { scoNicGenericCounter 3 }

scoNicNumSndBytes OBJECT-TYPE
        SYNTAX Gauge
        ACCESS read-only
        STATUS mandatory
        DESCRIPTION
                "This entry is the current number of sent bytes in this
                 NIC card."
        ::= { scoNicGenericCounter 4 }

scoNicFrameDef OBJECT-TYPE
        SYNTAX Counter
        ACCESS read-only
        STATUS mandatory
        DESCRIPTION
                "This entry is a variable that registers the number of frames deferred due to
                 data link traffic. "
        ::= { scoNicGenericCounter 5 }

scoNicCollisions OBJECT-TYPE
        SYNTAX Counter
        ACCESS read-only
        STATUS mandatory
        DESCRIPTION
                "This entry is a variable that registers the number of total
                 collisions in transmitted frames."
        ::= { scoNicGenericCounter 6 }

scoNicFrameColl OBJECT-TYPE
        SYNTAX Counter
        ACCESS read-only
        STATUS mandatory
        DESCRIPTION
                "This entry is a variable that registers the total collisions that
                 occurred when a frame was being transmitted."
        ::= { scoNicGenericCounter 7 }

scoNicOFrameColl OBJECT-TYPE
        SYNTAX Counter
        ACCESS read-only
        STATUS mandatory
        DESCRIPTION
                "This entry is a variable that registers the number of collisions that occurred
                 when a frame was not being transmitted (out-of-frame
                 collisions). "
        ::= { scoNicGenericCounter 8 }

scoNicXsColl OBJECT-TYPE
        SYNTAX Counter
        ACCESS read-only
        STATUS mandatory
        DESCRIPTION
                "This entry is a variable that registers the number of frames dropped due to
                 excessive collisions."
        ::= { scoNicGenericCounter 9 }

scoNicFrameNosr OBJECT-TYPE
        SYNTAX Counter
        ACCESS read-only
        STATUS mandatory
        DESCRIPTION
                "This entry is a variable that registers the number of frames dropped due to
                 allocb failure."
        ::= { scoNicGenericCounter 10 }

scoNicNoResource OBJECT-TYPE
        SYNTAX Counter
        ACCESS read-only
        STATUS mandatory
        DESCRIPTION
                "This entry is the number of frames dropped due to no resource."
        ::= { scoNicGenericCounter 11 }

scoNicBadSum OBJECT-TYPE
        SYNTAX Counter
        ACCESS read-only
        STATUS mandatory
        DESCRIPTION
                "This entry is a variable that registers the number of received frames with
                 a bad checksum."
        ::= { scoNicGenericCounter 12 }

scoNicAlign OBJECT-TYPE
        SYNTAX Counter
        ACCESS read-only
        STATUS mandatory
        DESCRIPTION
                "This entry is a variable that registers the number of received frames with
                 alignment errors."
        ::= { scoNicGenericCounter 13 }

scoNicBadLen OBJECT-TYPE
        SYNTAX Counter
        ACCESS read-only
        STATUS mandatory
        DESCRIPTION
                "This entry is a variable that registers the number of received frames with
                 a bad length."
        ::= { scoNicGenericCounter 14 }

scoNicBadSap OBJECT-TYPE
        SYNTAX Counter
        ACCESS read-only
        STATUS mandatory
        DESCRIPTION
                "This entry is a variable that registers the number of frames received
                 with no receiver above who desires to see those packets."
        ::= { scoNicGenericCounter 15 }

scoNicMcastRjct OBJECT-TYPE
        SYNTAX Counter
        ACCESS read-only
        STATUS mandatory
        DESCRIPTION
                "This entry is a variable that registers the number of multicast frames
                 received that were not in the multicast table."
        ::= { scoNicGenericCounter 16 }

scoNicCarrier OBJECT-TYPE
        SYNTAX Counter
        ACCESS read-only
        STATUS mandatory
        DESCRIPTION
                "This entry is a variable that registers the number of transmitted frames
                 aborted due to carrier loss during transmission."
        ::= { scoNicGenericCounter 17 }

scoNicBadCts OBJECT-TYPE
        SYNTAX Counter
        ACCESS read-only
        STATUS mandatory
        DESCRIPTION
                "This entry is a variable that registers the number of transmitted frames
                 aborted due to loss of the CTS signal during transmission."
        ::= { scoNicGenericCounter 18 }

scoNicBadDma OBJECT-TYPE
        SYNTAX Counter
        ACCESS read-only
        STATUS mandatory
        DESCRIPTION
                "This entry is a variable that registers the number of DMA over/under runs."
        ::= { scoNicGenericCounter 19 }

scoNicTimeOuts OBJECT-TYPE
        SYNTAX Counter
        ACCESS read-only
        STATUS mandatory
        DESCRIPTION
                "This entry is the number of device timeouts."
        ::= { scoNicGenericCounter 20 }

scoNicGenericThresholdTable OBJECT-TYPE
        SYNTAX SEQUENCE OF SCONicGenericThreshold
        ACCESS not-accessible
        STATUS mandatory
        DESCRIPTION
        "This entry is a table of SCO NIC generic threshold values."
::= { scoNic 2 }

scoNicGenericThreshold OBJECT-TYPE
        SYNTAX SCONicGenericThreshold
        ACCESS not-accessible
        STATUS mandatory
        DESCRIPTION
       "This entry is the threshold value for each SCO NIC generic counter."
--INDEX  { INTEGER }
        ::= { scoNicGenericThresholdTable 1 }


SCONicGenericThreshold   ::= SEQUENCE {
        scoNicNumRcvPktsThreshold          INTEGER,
        scoNicNumRcvBytesThreshold         INTEGER,
        scoNicNumSndPktsThreshold          INTEGER,
        scoNicNumSndBytesThreshold         INTEGER,
        scoNicFrameDefThreshold            INTEGER,
        scoNicCollisionsThreshold          INTEGER,
        scoNicFrameCollThreshold           INTEGER,
        scoNicOFrameCollThreshold          INTEGER,
        scoNicXsCollThreshold              INTEGER,
        scoNicFrameNosrThreshold           INTEGER,
        scoNicNoResourceThreshold          INTEGER,
        scoNicBadSumThreshold              INTEGER,
        scoNicAlignThreshold               INTEGER,
        scoNicBadLenThreshold              INTEGER,
        scoNicBadSapThreshold              INTEGER,
        scoNicMcastRjctThreshold           INTEGER,
        scoNicCarrierThreshold             INTEGER,
        scoNicBadCtsThreshold              INTEGER,
        scoNicBadDmaThreshold              INTEGER,
        scoNicTimeOutsThreshold            INTEGER
}


-- SCO UNIX NIC Threshold

scoNicNumRcvPktsThreshold OBJECT-TYPE
        SYNTAX INTEGER
        ACCESS read-write
        STATUS mandatory
        DESCRIPTION
                "This entry is the current threshold value of received packets in this
                 NIC card."
        ::= { scoNicGenericThreshold 1 }

scoNicNumRcvBytesThreshold OBJECT-TYPE
        SYNTAX INTEGER
        ACCESS read-write
        STATUS mandatory
        DESCRIPTION
                "This entry is the current threshold value of received bytes in this
                 NIC card."
        ::= { scoNicGenericThreshold 2 }

scoNicNumSndPktsThreshold OBJECT-TYPE
        SYNTAX INTEGER
        ACCESS read-write
        STATUS mandatory
        DESCRIPTION
                "This entry is the current threshold value of sent packets in this
                 NIC card."
        ::= { scoNicGenericThreshold 3 }

scoNicNumSndBytesThreshold OBJECT-TYPE
        SYNTAX INTEGER
        ACCESS read-write
        STATUS mandatory
        DESCRIPTION
                "This entry is the current threshold value of sent bytes in this
                 NIC card."
        ::= { scoNicGenericThreshold 4 }

scoNicFrameDefThreshold OBJECT-TYPE
        SYNTAX INTEGER
        ACCESS read-write
        STATUS mandatory
        DESCRIPTION
                "This entry is the current threshold value for deferred frames."
        ::= { scoNicGenericThreshold 5 }

scoNicCollisionsThreshold OBJECT-TYPE
        SYNTAX INTEGER
        ACCESS read-write
        STATUS mandatory
        DESCRIPTION
                "This entry is the current threshold value of total collisions."
        ::= { scoNicGenericThreshold 6 }

scoNicFrameCollThreshold OBJECT-TYPE
        SYNTAX INTEGER
        ACCESS read-write
        STATUS mandatory
        DESCRIPTION
                "This entry is the current threshold value of frames involved in a collision."
        ::= { scoNicGenericThreshold 7 }

scoNicOFrameCollThreshold OBJECT-TYPE
        SYNTAX INTEGER
        ACCESS read-write
        STATUS mandatory
        DESCRIPTION
                "This entry is the current threshold value for out of frame collisions."
        ::= { scoNicGenericThreshold 8 }

scoNicXsCollThreshold OBJECT-TYPE
        SYNTAX INTEGER
        ACCESS read-write
        STATUS mandatory
        DESCRIPTION
                "This entry is the current threshold value of frames dropped due to excessive collisions."
        ::= { scoNicGenericThreshold 9 }

scoNicFrameNosrThreshold OBJECT-TYPE
        SYNTAX INTEGER
        ACCESS read-write
        STATUS mandatory
        DESCRIPTION
                "This entry is the current threshold value of frames dropped due to no streams."
        ::= { scoNicGenericThreshold 10 }

scoNicNoResourceThreshold OBJECT-TYPE
        SYNTAX INTEGER
        ACCESS read-write
        STATUS mandatory
        DESCRIPTION
                "This entry is the current threshold value of frames dropped due to no resource."
        ::= { scoNicGenericThreshold 11 }

scoNicBadSumThreshold OBJECT-TYPE
        SYNTAX INTEGER
        ACCESS read-write
        STATUS mandatory
        DESCRIPTION
                "This entry is the current threshold value of bad checksums received."
        ::= { scoNicGenericThreshold 12 }

scoNicAlignThreshold OBJECT-TYPE
        SYNTAX INTEGER
        ACCESS read-write
        STATUS mandatory
        DESCRIPTION
                "This entry is the current threshold value of bad alignment received."
        ::= { scoNicGenericThreshold 13 }

scoNicBadLenThreshold OBJECT-TYPE
        SYNTAX INTEGER
        ACCESS read-write
        STATUS mandatory
        DESCRIPTION
                "This entry is the current threshold value of bad length received."
        ::= { scoNicGenericThreshold 14 }

scoNicBadSapThreshold OBJECT-TYPE
        SYNTAX INTEGER
        ACCESS read-write
        STATUS mandatory
        DESCRIPTION
                "This entry is the current threshold value of bad SAP received."
        ::= { scoNicGenericThreshold 15 }

scoNicMcastRjctThreshold OBJECT-TYPE
        SYNTAX INTEGER
        ACCESS read-write
        STATUS mandatory
        DESCRIPTION
                "This entry is the current threshold value of multicast frames rejected."
        ::= { scoNicGenericThreshold 16 }

scoNicCarrierThreshold OBJECT-TYPE
        SYNTAX INTEGER
        ACCESS read-write
        STATUS mandatory
        DESCRIPTION
                "This entry is the current threshold value of errors due to lost carriers."
        ::= { scoNicGenericThreshold 17 }

scoNicBadCtsThreshold OBJECT-TYPE
        SYNTAX INTEGER
        ACCESS read-write
        STATUS mandatory
        DESCRIPTION
                "This entry is the current threshold value of errors due to lost CTS."
        ::= { scoNicGenericThreshold 18 }

scoNicBadDmaThreshold OBJECT-TYPE
        SYNTAX INTEGER
        ACCESS read-write
        STATUS mandatory
        DESCRIPTION
                "This entry is the current threshold value of DMA over/under runs."
        ::= { scoNicGenericThreshold 19 }

scoNicTimeOutsThreshold OBJECT-TYPE
        SYNTAX INTEGER
        ACCESS read-write
        STATUS mandatory
        DESCRIPTION
                "This entry is the current threshold value for device timeouts."
        ::= { scoNicGenericThreshold 20 }


-- The following is used for SCO UNIX only, it will replace the sysVolTable in NetWare

totalSysFSNum OBJECT-TYPE
        SYNTAX INTEGER
        ACCESS read-only
        STATUS mandatory
        DESCRIPTION
                "This entry is the total number of SCO UNIX file systems."
        ::= { serverEnvrm 53 }

sysFSTable OBJECT-TYPE
        SYNTAX SEQUENCE OF SysFSEntry
        ACCESS not-accessible
        STATUS mandatory
        DESCRIPTION
                "This entry is a table containing all SCO UNIX file system information."
        ::= { serverEnvrm 54 }

sysFSEntry OBJECT-TYPE
        SYNTAX SysFSEntry
        ACCESS not-accessible
        STATUS mandatory
        DESCRIPTION
                "This entry contains information about each SCO UNIX file system."
        INDEX  { sysFSNumber }
        ::= { sysFSTable 1 }

SysFSEntry ::= SEQUENCE {
        sysFSNumber     INTEGER,
        sysFSName       DisplayString,
        totalFSSize     INTEGER,
        freeFSSize      INTEGER,
        usedFSSizeThreshold INTEGER,
        totalFSinode    INTEGER,
        freeFSinode     INTEGER,
        sysFSType       DisplayString,
        sysFSMountTime  DisplayString
}

sysFSNumber OBJECT-TYPE
        SYNTAX INTEGER
        ACCESS read-only
        STATUS mandatory
        DESCRIPTION
                "This entry is an index of file systems information."
        -- begin at 0
        ::= { sysFSEntry 1}

sysFSName OBJECT-TYPE
        SYNTAX DisplayString
        ACCESS read-only
        STATUS mandatory
        DESCRIPTION
                "This entry is the file system name."
        ::= { sysFSEntry 2}

totalFSSize OBJECT-TYPE
        SYNTAX INTEGER
        ACCESS read-only
        STATUS mandatory
        DESCRIPTION
                "This entry is the total size of a file system in KB."
        ::= { sysFSEntry 3}

freeFSSize OBJECT-TYPE
        SYNTAX INTEGER
        ACCESS read-only
        STATUS mandatory
        DESCRIPTION
                "This entry is the current free size of a file system in KB."
        ::= { sysFSEntry 4}

usedFSSizeThreshold OBJECT-TYPE
        SYNTAX INTEGER
        ACCESS read-write
        STATUS mandatory
        DESCRIPTION
                "This entry is the threshold value (%) of the file system currently in use."
        ::= { sysFSEntry 5}

totalFSinode OBJECT-TYPE
        SYNTAX INTEGER
        ACCESS read-only
        STATUS mandatory
        DESCRIPTION
                "This entry is the total inode counts of a file system."
        ::= { sysFSEntry 6}

freeFSinode OBJECT-TYPE
        SYNTAX INTEGER
        ACCESS read-only
        STATUS mandatory
        DESCRIPTION
                "This entry is the current free inode counts of a file system."         ::= { sysFSEntry 7}

sysFSType OBJECT-TYPE
        SYNTAX DisplayString
        ACCESS read-only
        STATUS mandatory
        DESCRIPTION
                "This entry is the type of a file system."
        ::= { sysFSEntry 8}

sysFSMountTime OBJECT-TYPE
        SYNTAX DisplayString
        ACCESS read-only
        STATUS mandatory
        DESCRIPTION
                "This entry is the mount time of a file system."
        ::= { sysFSEntry 9}

-- ******************************************************

-- The System Board group

systemIrqsInfoTable OBJECT-TYPE
        SYNTAX SEQUENCE OF SystemIrqsInfoEntry
        ACCESS not-accessible
        STATUS mandatory
        DESCRIPTION
                "This entry is a table containing  IRQ numbers and the
                devices occupying each IRQ."
        ::= { systemBoard 1 }

systemIrqsInfoEntry OBJECT-TYPE
        SYNTAX SystemIrqsInfoEntry
        ACCESS not-accessible
        STATUS mandatory
        DESCRIPTION
                "This entry contains information about each IRQ."
        INDEX  { irqNumber }
        ::= { systemIrqsInfoTable 1 }

SystemIrqsInfoEntry ::= SEQUENCE {
        irqNumber       INTEGER(0..15),
        irqOccupiedDes  DisplayString
}

irqNumber OBJECT-TYPE
        SYNTAX INTEGER(0..15)
        ACCESS read-only
        STATUS mandatory
        DESCRIPTION
                "This entry is the IRQ number."
        ::= { systemIrqsInfoEntry 1 }

irqOccupiedDes OBJECT-TYPE
        SYNTAX DisplayString
        ACCESS read-only
        STATUS mandatory
        DESCRIPTION
                "This entry contains information about the device occupying the IRQ."
        ::= { systemIrqsInfoEntry 2 }

systemDmasInfoTable OBJECT-TYPE
        SYNTAX SEQUENCE OF SystemDmasInfoEntry
        ACCESS not-accessible
        STATUS mandatory
        DESCRIPTION
                "This entry is a table containing DMA channels and the
                devices occupying each channel."
        ::= { systemBoard 2 }

systemDmasInfoEntry OBJECT-TYPE
        SYNTAX SystemDmasInfoEntry
        ACCESS not-accessible
        STATUS mandatory
        DESCRIPTION
                "This entry contains information about each DMA channel."
        INDEX  { dmaChannel }
        ::= { systemDmasInfoTable 1 }

SystemDmasInfoEntry ::= SEQUENCE {
        dmaChannel      INTEGER(0..7),
        dmaOccupiedDes  DisplayString
}

dmaChannel OBJECT-TYPE
        SYNTAX INTEGER(0..7)
        ACCESS read-only
        STATUS mandatory
        DESCRIPTION
                "This entry is the DMA channel."
        ::= { systemDmasInfoEntry 1 }

dmaOccupiedDes OBJECT-TYPE
        SYNTAX DisplayString
        ACCESS read-only
        STATUS mandatory
        DESCRIPTION
                "This entry contains information about the device occupying the DMA channel."
        ::= { systemDmasInfoEntry 2 }

totalIoPortsNum OBJECT-TYPE
        SYNTAX INTEGER
        ACCESS read-only
        STATUS mandatory
        DESCRIPTION
                "This entry shows the number of I/O ports."
        ::= { systemBoard 3 }


systemIoPortsInfoTable OBJECT-TYPE
        SYNTAX SEQUENCE OF SystemIoPortsInfoEntry
        ACCESS not-accessible
        STATUS mandatory
        DESCRIPTION
                "This entry is a table containing I/O port information and the
                devices occupying each port."
        ::= { systemBoard 4 }

systemIoPortsInfoEntry OBJECT-TYPE
        SYNTAX SystemIoPortsInfoEntry
        ACCESS not-accessible
        STATUS mandatory
        DESCRIPTION
                "This entry contains information about each I/O port."
        INDEX  { ioPortsIndex }
        ::= { systemIoPortsInfoTable 1 }

SystemIoPortsInfoEntry ::= SEQUENCE {
        ioPortsIndex    INTEGER,
        ioPortsBeginValue       INTEGER,
        ioPortsEndValue INTEGER,
        ioPortsOccupiedDes      DisplayString
}

ioPortsIndex OBJECT-TYPE
        SYNTAX INTEGER
        ACCESS read-only
        STATUS mandatory
        DESCRIPTION
                "This entry is an index to the I/O port table."
        ::= { systemIoPortsInfoEntry 1 }

ioPortsBeginValue OBJECT-TYPE
        SYNTAX INTEGER
        ACCESS read-only
        STATUS mandatory
        DESCRIPTION
                "This entry shows the starting address of the I/O port."
        ::= { systemIoPortsInfoEntry 2 }

ioPortsEndValue OBJECT-TYPE
        SYNTAX INTEGER
        ACCESS read-only
        STATUS mandatory
        DESCRIPTION
                "This entry shows the ending address of the I/O port."
        ::= { systemIoPortsInfoEntry 3 }

ioPortsOccupiedDes OBJECT-TYPE
        SYNTAX DisplayString
        ACCESS read-only
        STATUS mandatory
        DESCRIPTION
                "This entry contains information about the I/O device occupying the port."
        ::= { systemIoPortsInfoEntry 4 }

systemSlotsInfoTable OBJECT-TYPE
        SYNTAX SEQUENCE OF SystemSlotsInfoEntry
        ACCESS not-accessible
        STATUS mandatory
        DESCRIPTION
                "This entry is a table containing information about system slots."
        ::= { systemBoard 5 }

SlotsType ::= INTEGER
        {
       --   unknown(0),
          eisa(1),
       -- eisapci(2),
          isa(3),
       -- isapci(4),
          pci(5)
        }

systemSlotsInfoEntry OBJECT-TYPE
        SYNTAX SystemSlotsInfoEntry
        ACCESS not-accessible
        STATUS mandatory
        DESCRIPTION
                "This entry contains information about each system slot."
        INDEX  { slotsNumber }
        ::= { systemSlotsInfoTable 1 }

SystemSlotsInfoEntry ::= SEQUENCE {
        slotsNumber     INTEGER,
        slotsType       SlotsType,
        slotsOccupiedDes        DisplayString
}

slotsNumber OBJECT-TYPE
        SYNTAX INTEGER
        ACCESS read-only
        STATUS mandatory
        DESCRIPTION
                "This entry shows the slot number."
        ::= { systemSlotsInfoEntry 1 }

slotsType OBJECT-TYPE
        SYNTAX SlotsType
        ACCESS read-only
        STATUS mandatory
        DESCRIPTION
                "This entry shows the slot type, EISA, ISA, or PCI.
                0 = Unknown
                1 = EISA
                3 = ISA
                5 = PCI"
        ::= { systemSlotsInfoEntry 2 }

slotsOccupiedDes OBJECT-TYPE
        SYNTAX DisplayString
        ACCESS read-only
        STATUS mandatory
        DESCRIPTION
                "This entry shows the device installed on this slot."
        ::= { systemSlotsInfoEntry 3 }

MemoryEntry ::= SEQUENCE {
        memSlots        INTEGER(1..16),
        simmType        OCTET STRING (SIZE(4))
}

totalMemSlotsNum OBJECT-TYPE
        SYNTAX INTEGER(1..16)
        ACCESS read-only
        STATUS mandatory
        DESCRIPTION
                "This entry shows the number of SIMM slots."
        ::= { systemBoard 6 }

memoryTable OBJECT-TYPE
        SYNTAX SEQUENCE OF MemoryEntry
        ACCESS not-accessible
        STATUS mandatory
        DESCRIPTION
                "This entry is a table containing  system memory information."
        ::= { systemBoard 7 }

memoryEntry OBJECT-TYPE
        SYNTAX MemoryEntry
        ACCESS not-accessible
        STATUS mandatory
        DESCRIPTION
                "This entry contains information about each SIMM slot."
        INDEX  { memSlots }
        ::= { memoryTable 1 }

memSlots OBJECT-TYPE
        SYNTAX INTEGER(1..16)
        ACCESS read-only
        STATUS mandatory
        DESCRIPTION
                "This entry contains information about the memory module installed on the SIMM slot."
        ::= { memoryEntry 1 }

simmType OBJECT-TYPE
        SYNTAX OCTET STRING (SIZE(4))
        ACCESS read-only
        STATUS mandatory
        DESCRIPTION
                "This entry shows the memory module size in MB."
        ::= { memoryEntry 2 }

-- systemNvRamSize OBJECT-TYPE
--      SYNTAX INTEGER
--      ACCESS read-only
--      STATUS mandatory
--      DESCRIPTION
--              "This entry shows the size of the system nonvolatile RAM in bytes."
--      ::= { systemBoard 8 }
--
-- systemEcuRevision OBJECT-TYPE
--      SYNTAX DisplayString
--      ACCESS read-only
--      STATUS mandatory
--      DESCRIPTION
--              "This entry is the system ECU version."
--      ::= { systemBoard 9 }
--
-- systemSerialNumberInfo OBJECT-TYPE
--      SYNTAX DisplayString
--      ACCESS read-only
--      STATUS mandatory
--      DESCRIPTION
--              "This entry shows the system serial number."
--      ::= { systemBoard 10 }

systemBootControl OBJECT-TYPE
        SYNTAX DisplayString
        ACCESS read-only
        STATUS mandatory
        DESCRIPTION
                "This entry shows boot control information."
        ::= { systemBoard 11 }

systemFloppyControl OBJECT-TYPE
        SYNTAX DisplayString
        ACCESS read-only
        STATUS mandatory
        DESCRIPTION
                "This entry shows diskette drive control information."
        ::= { systemBoard 12 }

systemHddControl OBJECT-TYPE
        SYNTAX DisplayString
        ACCESS read-only
        STATUS mandatory
        DESCRIPTION
                "This entry shows hard disk control information."
        ::= { systemBoard 13 }

totalBaseMemNum OBJECT-TYPE
        SYNTAX INTEGER
        ACCESS read-only
        STATUS mandatory
        DESCRIPTION
                "This entry shows the number of base memory blocks used by I/O devices."
        ::= { systemBoard 14 }

systemBaseMemTable OBJECT-TYPE
        SYNTAX SEQUENCE OF SystemBaseMemInfoEntry
        ACCESS not-accessible
        STATUS mandatory
        DESCRIPTION
                "This entry is a table containing information about base memory used by I/O devices."
        ::= { systemBoard 15 }

systemBaseMemEntry OBJECT-TYPE
        SYNTAX SystemBaseMemInfoEntry
        ACCESS not-accessible
        STATUS mandatory
        DESCRIPTION
                "This entry contains information about each base memory block."
        INDEX  { baseMemIndex }
        ::= { systemBaseMemTable 1 }

SystemBaseMemInfoEntry ::= SEQUENCE {
        baseMemIndex    INTEGER,
        baseMemAddr     INTEGER,
        baseMemLength   INTEGER,
        baseMemOccupiedDes      DisplayString
}

baseMemIndex OBJECT-TYPE
        SYNTAX INTEGER
        ACCESS read-only
        STATUS mandatory
        DESCRIPTION
                "This entry is an index to the base memory table."
        -- Starting at 0
        ::= { systemBaseMemEntry 1 }

baseMemAddr OBJECT-TYPE
        SYNTAX INTEGER
        ACCESS read-only
        STATUS mandatory
        DESCRIPTION
                "This entry shows the starting address of the block of base memory used."
        ::= { systemBaseMemEntry 2 }

baseMemLength OBJECT-TYPE
        SYNTAX INTEGER
        ACCESS read-only
        STATUS mandatory
        DESCRIPTION
                "This entry shows the length of the block of base memory used."
        ::= { systemBaseMemEntry 3 }

baseMemOccupiedDes OBJECT-TYPE
        SYNTAX DisplayString
        ACCESS read-only
        STATUS mandatory
        DESCRIPTION
                "This entry contains a description of the device using the block of base memory."
        ::= { systemBaseMemEntry 4 }

-- The Server Environment group

productName OBJECT-TYPE
        SYNTAX DisplayString
        ACCESS read-only
        STATUS mandatory
        DESCRIPTION
                "This entry shows the machine product name."
        ::= { serverEnvrm 1 }

osVersion OBJECT-TYPE
        SYNTAX DisplayString
        ACCESS read-only
        STATUS mandatory
        DESCRIPTION
                "This entry shows information about the current operating system in use."
        ::= { serverEnvrm 2 }

expanBusType OBJECT-TYPE
        SYNTAX DisplayString
        ACCESS read-only
        STATUS mandatory
        DESCRIPTION
                "This entry shows information about expansion slots.  A system may contain
                 one or more of the following types:  ISA, EISA, PCI, VESA, etc."
        ::= { serverEnvrm 3 }

processorType OBJECT-TYPE
        SYNTAX DisplayString
        ACCESS read-only
        STATUS mandatory
        DESCRIPTION
                "This entry shows the server's CPU information."
        ::= { serverEnvrm 4 }


systemIntrlCache OBJECT-TYPE
        SYNTAX INTEGER
        ACCESS read-only
        STATUS mandatory
        DESCRIPTION
                "This entry shows the CPU's internal cache size in KB."
        ::= { serverEnvrm 5 }

systemExtrlCache OBJECT-TYPE
        SYNTAX INTEGER
        ACCESS read-only
        STATUS mandatory
        DESCRIPTION
                "This shows the server's external cache size in KB."
        ::= { serverEnvrm 6 }

systemTotalMemory OBJECT-TYPE
        SYNTAX INTEGER
        ACCESS read-only
        STATUS mandatory
        DESCRIPTION
                "This entry shows the system's total memory size in bytes."
        ::= { serverEnvrm 7 }

systemFreeMemory OBJECT-TYPE
        SYNTAX INTEGER
        ACCESS read-only
        STATUS mandatory
        DESCRIPTION
                "This entry shows the system's current free memory size in bytes."
        ::= { serverEnvrm 8 }

systemSerialPort1Info OBJECT-TYPE
        SYNTAX DisplayString
        ACCESS read-only
        STATUS mandatory
        DESCRIPTION
                "This entry contains information about the system's serial port 1."
        ::= { serverEnvrm 9 }

systemSerialPort2Info OBJECT-TYPE
        SYNTAX DisplayString
        ACCESS read-only
        STATUS mandatory
        DESCRIPTION
                "This entry contains information about the system's serial port 2."
        ::= { serverEnvrm 10 }

systemParallelPortInfo OBJECT-TYPE
        SYNTAX DisplayString
        ACCESS read-only
        STATUS mandatory
        DESCRIPTION
                "This entry contains information about the system's parallel port."
        ::= { serverEnvrm 11 }

keyboardType OBJECT-TYPE
        SYNTAX DisplayString
        ACCESS read-only
        STATUS mandatory
        DESCRIPTION
                "This entry shows the system's keyboard type."
        ::= { serverEnvrm 12 }

videoType OBJECT-TYPE
        SYNTAX DisplayString
        ACCESS read-only
        STATUS mandatory
        DESCRIPTION
                "This entry shows the system's display type."
        ::= { serverEnvrm 13 }

mouseType OBJECT-TYPE
        SYNTAX DisplayString
        ACCESS read-only
        STATUS mandatory
        DESCRIPTION
                "This entry shows the system's mouse type."
        ::= { serverEnvrm 14 }

sysBiosVer OBJECT-TYPE
        SYNTAX DisplayString
        ACCESS read-only
        STATUS mandatory
        DESCRIPTION
                "This entry shows the system BIOS version."
        ::= { serverEnvrm 15 }

serverName OBJECT-TYPE
        SYNTAX DisplayString
        ACCESS read-only
        STATUS mandatory
        DESCRIPTION
                "This entry shows the server name."
        ::= { serverEnvrm 16 }

serverUpTime OBJECT-TYPE
        SYNTAX DisplayString
        ACCESS read-only
        STATUS mandatory
        DESCRIPTION
                "This entry shows the amount of time the server has been running."
        ::= { serverEnvrm 17 }

ServerMgrContactInfoEntry ::= SEQUENCE {
        serverMgrNumber         INTEGER,
        serverMgrName           DisplayString,
        serverMgrOffPhone       DisplayString,
        serverMgrOffAddr        DisplayString,
        serverMgrHomePhone      DisplayString,
        serverMgrHomeAddr       DisplayString,
        serverMgrPagerNum       DisplayString,
        serverMgrEmailAddr      DisplayString
}

serverMgrContactInfoTable OBJECT-TYPE
        SYNTAX SEQUENCE OF ServerMgrContactInfoEntry
        ACCESS not-accessible
        STATUS mandatory
        DESCRIPTION
                "This entry is a table containing information about all server managers."
        ::= { serverEnvrm 18 }

serverMgrContactInfoEntry OBJECT-TYPE
        SYNTAX ServerMgrContactInfoEntry
        ACCESS not-accessible
        STATUS mandatory
        DESCRIPTION
                "This entry shows information about each server manager."
        INDEX  { serverMgrNumber }
        ::= { serverMgrContactInfoTable 1 }

serverMgrNumber OBJECT-TYPE
        SYNTAX INTEGER
        ACCESS read-only
        STATUS mandatory
        DESCRIPTION
                "This entry is the server manager number starting from 0."
        ::= { serverMgrContactInfoEntry 8 }

serverMgrName OBJECT-TYPE
        SYNTAX DisplayString
        ACCESS read-write
        STATUS mandatory
        DESCRIPTION
                "This entry shows the server manager's name."
        ::= { serverMgrContactInfoEntry 1 }

serverMgrOffPhone OBJECT-TYPE
        SYNTAX DisplayString
        ACCESS read-write
        STATUS mandatory
        DESCRIPTION
                "This entry shows the server manager's office phone number."
        ::= { serverMgrContactInfoEntry 2 }

serverMgrOffAddr OBJECT-TYPE
        SYNTAX DisplayString
        ACCESS read-write
        STATUS mandatory
        DESCRIPTION
                "This entry shows the server manager's office address."
        ::= { serverMgrContactInfoEntry 3 }

serverMgrHomePhone OBJECT-TYPE
        SYNTAX DisplayString
        ACCESS read-write
        STATUS mandatory
        DESCRIPTION
                "This entry shows the server manager's home phone number."
        ::= { serverMgrContactInfoEntry 4 }

serverMgrHomeAddr OBJECT-TYPE
        SYNTAX DisplayString
        ACCESS read-write
        STATUS mandatory
        DESCRIPTION
                "This entry shows the server manager's home address."
        ::= { serverMgrContactInfoEntry 5 }

serverMgrPagerNum OBJECT-TYPE
        SYNTAX DisplayString
        ACCESS read-write
        STATUS mandatory
        DESCRIPTION
                "This entry shows the server manager's pager number."
        ::= { serverMgrContactInfoEntry 6 }

serverMgrEmailAddr OBJECT-TYPE
        SYNTAX DisplayString
        ACCESS read-write
        STATUS mandatory
        DESCRIPTION
                "This entry shows the server manager's email address."
        ::= { serverMgrContactInfoEntry 7 }

serverLoc OBJECT-TYPE
        SYNTAX DisplayString
        ACCESS read-write
        STATUS mandatory
        DESCRIPTION
                "This entry shows the server's physical location."
        ::= { serverEnvrm 19 }

totalSysVolNum OBJECT-TYPE
	SYNTAX INTEGER
	ACCESS read-only
	STATUS mandatory
	DESCRIPTION
		"This entry shows the total number of system volumes."
	::= { serverEnvrm 20 }

sysVolTable OBJECT-TYPE
	SYNTAX SEQUENCE OF SysVolEntry
	ACCESS not-accessible
	STATUS mandatory
	DESCRIPTION
		"This entry is a table containing information about all system volumes."
	::= { serverEnvrm 21 }

sysVolEntry OBJECT-TYPE
	SYNTAX SysVolEntry
	ACCESS not-accessible
	STATUS mandatory
	DESCRIPTION
		"This entry shows information about each system volume."
	INDEX  { sysVolNum }
	::= { sysVolTable 1 }

SysVolEntry ::= SEQUENCE {
	sysVolNum	INTEGER,
	sysVolName	DisplayString,
	totalVolSize	INTEGER,
	freeVolSize	INTEGER,
	totalDirSize	INTEGER,
	freeDirSize	INTEGER,
	usedVolSizeThreshold	INTEGER
--	usedDirSizeThreshold	INTEGER
}

sysVolNum OBJECT-TYPE
	SYNTAX INTEGER
	ACCESS read-only
	STATUS mandatory
	DESCRIPTION
		"This entry is the volume number."
	::= { sysVolEntry 1 }
--
-- The volume number = 0..63
-- It could be not contiguous.
--

sysVolName OBJECT-TYPE
	SYNTAX DisplayString
	ACCESS read-only
	STATUS mandatory
	DESCRIPTION
		"This entry shows the system volume name."
	::= { sysVolEntry 2}

totalVolSize OBJECT-TYPE
	SYNTAX INTEGER
	ACCESS read-only
	STATUS mandatory
	DESCRIPTION
		"This entry shows the size of each system volume in KB."
	::= { sysVolEntry 3}

freeVolSize OBJECT-TYPE
	SYNTAX INTEGER
	ACCESS read-only
	STATUS mandatory
	DESCRIPTION
		"This entry shows the current free size of a system volume in KB."
	::= { sysVolEntry 4}

totalDirSize OBJECT-TYPE
	SYNTAX INTEGER
	ACCESS read-only
	STATUS mandatory
	DESCRIPTION
--              "This entry shows the maximum number of directories that can
--               be created in a system volume."
		"For NetWare, this entry shows the maximum number of 
                directories that can be created in a system volume. 
                For Windows NT, this entry shows the 
                number of allocation units in a system volume."
	::= { sysVolEntry 5}

freeDirSize OBJECT-TYPE
	SYNTAX INTEGER
	ACCESS read-only
	STATUS mandatory
	DESCRIPTION
--		"This entry shows the current number of directories that can 
--              still be created in a system volume."
                "For NetWare, this entry shows the current number of 
                directories that can still be created in a system volume.
                For Windows NT, this entry shows the current number of free 
                allocation units in a system volume."
	::= { sysVolEntry 6}

-- Threshold setting for  System Volume Entry

usedVolSizeThreshold OBJECT-TYPE
	SYNTAX INTEGER
	ACCESS read-write
	STATUS mandatory
	DESCRIPTION
		"This entry shows the threshold setting (%) for a volume's usage. "
	::= { sysVolEntry 7}

-- usedDirSizeThreshold OBJECT-TYPE
--	SYNTAX INTEGER
--	ACCESS read-write
--	STATUS mandatory
--	DESCRIPTION
--		"The threshold of used directory size in a volume in a server"
--	::= { sysVolEntry 8}

-- **********************************************************************

totalSysPartitionNum OBJECT-TYPE
	SYNTAX INTEGER
	ACCESS read-only
	STATUS mandatory
	DESCRIPTION
		"This entry shows the total number of NetWare partitions created in the system."
	::= { serverEnvrm 22 }

sysPartitionTable OBJECT-TYPE
	SYNTAX SEQUENCE OF SysPartitionEntry
	ACCESS not-accessible
	STATUS mandatory
	DESCRIPTION
		"This entry is a table containing information about all NetWare partitions in the system."
	::= { serverEnvrm 23 }

SysPartitionEntry ::= SEQUENCE {
	sysPartitionNum 	INTEGER,
	partitionDiskNum	INTEGER,
	dataAreaSize		INTEGER,
	redirectionAreaSize	INTEGER,
	redirectedSize		INTEGER,
	partitionName		DisplayString (SIZE(0..64))
-- 	redirectedSizeThreshold INTEGER
}

sysPartitionEntry OBJECT-TYPE
	SYNTAX SysPartitionEntry
	ACCESS not-accessible
	STATUS mandatory
	DESCRIPTION
		"This entry contains information about each NetWare partition."
	INDEX  { sysPartitionNum }
	::= { sysPartitionTable 1 }

sysPartitionNum OBJECT-TYPE
	SYNTAX INTEGER
	ACCESS read-only
	STATUS mandatory
	DESCRIPTION
		"This entry shows the system partition number assigned by the system."
	::= { sysPartitionEntry 1 }

partitionDiskNum OBJECT-TYPE
	SYNTAX INTEGER
	ACCESS read-only
	STATUS mandatory
	DESCRIPTION
		"This entry shows the disk number from which this partition is created."
	::= { sysPartitionEntry 2 }

dataAreaSize OBJECT-TYPE
	SYNTAX INTEGER
	ACCESS read-only
	STATUS mandatory
	DESCRIPTION
		"This entry shows the size of the partition's data area in sectors."
	::= { sysPartitionEntry 3 }

redirectionAreaSize OBJECT-TYPE
	SYNTAX INTEGER
	ACCESS read-only
	STATUS mandatory
	DESCRIPTION
		"This entry shows the size of the partition's redirection area in sectors."
	::= { sysPartitionEntry 4 }

redirectedSize OBJECT-TYPE
	SYNTAX INTEGER
	ACCESS read-only
	STATUS mandatory
	DESCRIPTION
		"This entry shows the number of sectors used in the partition's redirection area."
	::= { sysPartitionEntry 5 }

partitionName OBJECT-TYPE
	SYNTAX DisplayString (SIZE(0..64))
	ACCESS read-only
	STATUS mandatory
	DESCRIPTION
		"This entry shows the partition name."
	::= { sysPartitionEntry 6 }

-- redirectedSizeThreshold OBJECT-TYPE
-- 	SYNTAX INTEGER
-- 	ACCESS read-write
-- 	STATUS mandatory
-- 	DESCRIPTION
-- 		"This entry shows the threshold value in sectors for the partition's redirected area size."
-- 	::= { sysPartitionEntry 7}


-- eccErrTable OBJECT-TYPE
--      SYNTAX SEQUENCE OF EccErrEntry
--      ACCESS not-accessible
--      STATUS mandatory
--      DESCRIPTION
--              "Record the ECC memory 1-bit-error"
--      ::= { serverEnvrm 24 }
--
-- EccErrEntry ::= SEQUENCE {
--      eccErrNum       INTEGER,
--      eccErrAddr      INTEGER,
--      eccErrBank      INTEGER,
--      eccErrTime      DisplayString
-- }
--
-- eccErrEntry OBJECT-TYPE
--      SYNTAX EccErrEntry
--      ACCESS not-accessible
--      STATUS mandatory
--      DESCRIPTION
--              "Record the ECC memory reporting error"
--      INDEX  { eccErrNum }
--      ::= { eccErrTable 1 }
--
-- eccErrNum OBJECT-TYPE
--      SYNTAX INTEGER
--      ACCESS read-only
--      STATUS mandatory
--      DESCRIPTION
--              "The index number to the ECC memory error table"
--      ::= { eccErrEntry 1 }
--
-- eccErrAddr OBJECT-TYPE
--      SYNTAX INTEGER
--      ACCESS read-only
--      STATUS mandatory
--      DESCRIPTION
--              "The ECC memory error physical address"
--      ::= { eccErrEntry 2 }
--
-- eccErrBank OBJECT-TYPE
--      SYNTAX INTEGER
--      ACCESS read-only
--      STATUS mandatory
--      DESCRIPTION
--              "The bank number of ECC memory error"
--      ::= { eccErrEntry 3 }
--
-- eccErrTime OBJECT-TYPE
--      SYNTAX DisplayString
--      ACCESS read-only
--      STATUS mandatory
--      DESCRIPTION
--              "The ECC memory error date and time"
--      ::= { eccErrEntry 4 }

-- serverTemp OBJECT-TYPE
--      SYNTAX INTEGER
--      ACCESS read-only
--      STATUS mandatory
--      DESCRIPTION
--              "The server system temperature in 0.1oC increments"
--      ::= { serverEnvrm 25 }

-- hardPollingInterval  OBJECT-TYPE
--      SYNTAX INTEGER
--      ACCESS read-write
--      STATUS mandatory
--      DESCRIPTION
--          "The hard polling interval in seconds. Default is 1 second.
--           Agent polls the ASM hardware status according to this interval.
--           The ASM hardware status includes Fan, Thermometer, Voltage
--           and Bus Utilization."
--      ::= { serverEnvrm 26 }
--      May be later!

softPollingInterval     OBJECT-TYPE
        SYNTAX INTEGER
        ACCESS read-write
        STATUS mandatory
        DESCRIPTION
            "This entry shows the soft polling interval in seconds.
            By soft polling, it means that the Agent polls the system status
            (CPU Utilization, Memory Utilization, Volume Utilization and
            NIC Statistic Counters) based on a specified interval.
            Default is 1 second."
        ::= { serverEnvrm 27 }

glbThldVolUtil  OBJECT-TYPE
        SYNTAX INTEGER
        ACCESS read-write
        STATUS mandatory
        DESCRIPTION
                "This entry shows the global threshold value (%) for volume
                or file system utilization. Default is 100%."
        ::= { serverEnvrm 28 }

numberOfCpu OBJECT-TYPE
        SYNTAX INTEGER
        ACCESS read-only
        STATUS mandatory
        DESCRIPTION
                "This entry shows the number of CPUs in the system."
        ::= { serverEnvrm 29 }

cpuInfoTable OBJECT-TYPE
        SYNTAX SEQUENCE OF CpuInfo
        ACCESS not-accessible
        STATUS mandatory
        DESCRIPTION
                "This entry is a table containing information about all CPUs on the system."
        ::= { serverEnvrm 30 }

CpuInfo ::= SEQUENCE {
        cpuNum                  INTEGER,
        cpuUtilization          INTEGER,
--      cpuUtilizationThreshold INTEGER,
--      cpuTemperature          INTEGER,
--      cpuTemperatureWarningThreshold  INTEGER,
--      cpuTemperatureCriticalThreshold INTEGER,
--      cpuVoltage              INTEGER,
--      cpuFanStat              INTEGER(0..1),
        cpuSystemUtilization    INTEGER,
        cpuUserUtilization      INTEGER,
        cpuInterruptUtilization INTEGER
}

cpuInfo OBJECT-TYPE
        SYNTAX CpuInfo
        ACCESS not-accessible
        STATUS mandatory
        DESCRIPTION
                "This entry shows information about each CPU."
        INDEX  { cpuNum }
        ::= { cpuInfoTable 1 }

cpuNum OBJECT-TYPE
        SYNTAX INTEGER
        ACCESS read-only
        STATUS mandatory
        DESCRIPTION
                "This entry shows the CPU number starting at 0."
        ::= { cpuInfo 1 }

cpuUtilization OBJECT-TYPE
        SYNTAX INTEGER
        ACCESS read-only
        STATUS mandatory
        DESCRIPTION
                "This entry shows CPU utilization (%)."
        ::= { cpuInfo 2 }

-- cpuUtilizationThreshold OBJECT-TYPE
--      SYNTAX INTEGER
--      ACCESS read-write
--      STATUS mandatory
--      DESCRIPTION
--              "This entry shows the threshold value (%) for CPU utilization."
--      ::= { cpuInfo 3 }
--
-- cpuTemperature OBJECT-TYPE
--      SYNTAX INTEGER
--      ACCESS read-only
--      STATUS mandatory
--      DESCRIPTION
--              "This entry displays the CPU temperature.  Values displayed have to be divided
--  by ten (10) to show the temperature in degrees Celsius.  For example, a reading of 305
-- means that the temperature is at 30.5 degrees Celsius."
--      ::= { cpuInfo 4 }
--
-- cpuTemperatureWarningThreshold OBJECT-TYPE
--      SYNTAX INTEGER
--      ACCESS read-write
--      STATUS mandatory
--      DESCRIPTION
--              "This entry displays the first level threshold value for the CPU temperature.
--              Values displayed have to be divided by ten (10) to show the temperature in
--              degrees Celsius.  For example, a reading of 305 means that the temperature is at
--              30.5 degrees Celsius."
--      ::= { cpuInfo 5 }
--
-- cpuTemperatureCriticalThreshold OBJECT-TYPE
--      SYNTAX INTEGER
--      ACCESS read-write
--      STATUS mandatory
--      DESCRIPTION
--              "This entry displays the second level threshold value for the CPU temperature.
--              Values displayed have to be divided by ten (10) to show the temperature in
--              degrees Celsius.  For example, a reading of 305 means that the temperature is at
--              30.5 degrees Celsius."
--      ::= { cpuInfo 6 }
--
--cpuVoltage OBJECT-TYPE
--      SYNTAX INTEGER
--      ACCESS read-only
--      STATUS mandatory
--      DESCRIPTION
--              "The CPU VCC power supply voltage in milli-volt"
--      ::= { cpuInfo 7 }
--
--cpuFanStat OBJECT-TYPE
--      SYNTAX INTEGER(0..1)
--      ACCESS read-only
--      STATUS mandatory
--      DESCRIPTION
--              "The CPU FAN status. 0=normal 1=abnormal"
--      ::= { cpuInfo 8 }

cpuSystemUtilization OBJECT-TYPE
        SYNTAX INTEGER
        ACCESS read-only
        STATUS mandatory
        DESCRIPTION
                "This entry shows CPU utilization (%) by the operating system."
        ::= { cpuInfo 9 }

cpuUserUtilization OBJECT-TYPE
        SYNTAX INTEGER
        ACCESS read-only
        STATUS mandatory
        DESCRIPTION
                "This entry shows CPU utilization (%) by applications."
        ::= { cpuInfo 10 }

cpuInterruptUtilization OBJECT-TYPE
        SYNTAX INTEGER
        ACCESS read-only
        STATUS mandatory
        DESCRIPTION
                "This entry shows CPU utilization (%) by the interrupt services."
        ::= { cpuInfo 11 }


-- cpu1FanStat OBJECT-TYPE
--      SYNTAX INTEGER(0..1)
--      ACCESS read-only
--      STATUS mandatory
--      DESCRIPTION
--              "The 1st CPU FAN status. It is normal or abnormal"
--      ::= { serverEnvrm 29 }
--
-- cpu2FanStat OBJECT-TYPE
--      SYNTAX INTEGER(0..1)
--      ACCESS read-only
--      STATUS mandatory
--      DESCRIPTION
--              "The 2nd CPU FAN status. It is normal or abnormal"
--      ::= { serverEnvrm 30 }
--
-- cpu3FanStat OBJECT-TYPE
--      SYNTAX INTEGER(0..1)
--      ACCESS read-only
--      STATUS mandatory
--      DESCRIPTION
--              "The 3rd CPU FAN status. It is normal or abnormal"
--      ::= { serverEnvrm 31 }
--
-- cpu4FanStat OBJECT-TYPE
--      SYNTAX INTEGER(0..1)
--      ACCESS read-only
--      STATUS mandatory
--      DESCRIPTION
--              "The 4th CPU FAN status. It is normal or abnormal"
--      ::= { serverEnvrm 32 }
--
-- powerStat25v OBJECT-TYPE
--      SYNTAX INTEGER
--      ACCESS read-only
--      STATUS mandatory
--      DESCRIPTION
--              "The 2.5 VOLT power supply status in milli-volt"
--      ::= { serverEnvrm 33 }
--
-- powerStat33v OBJECT-TYPE
--      SYNTAX INTEGER
--      ACCESS read-only
--      STATUS mandatory
--      DESCRIPTION
--              "The 3.3 VOLT power supply status in milli-volt"
--      ::= { serverEnvrm 34 }
--
-- powerStat5v OBJECT-TYPE
--      SYNTAX INTEGER
--      ACCESS read-only
--      STATUS mandatory
--      DESCRIPTION
--              "The 5 VOLT power supply status in milli-volt"
--      ::= { serverEnvrm 35 }
--
-- powerStat12v OBJECT-TYPE
--      SYNTAX INTEGER
--      ACCESS read-only
--      STATUS mandatory
--      DESCRIPTION
--              "The 12 VOLT power supply status in milli-volt"
--      ::= { serverEnvrm 36 }
--
-- serverCpuUtilization OBJECT-TYPE
--      SYNTAX INTEGER
--      ACCESS read-only
--      STATUS mandatory
--      DESCRIPTION
--              "The server CPU utilization in percent"
--      ::= { serverEnvrm 37 }
--
-- hostIOBusUtilization OBJECT-TYPE
--      SYNTAX INTEGER
--      ACCESS read-only
--      STATUS mandatory
--      DESCRIPTION
--              "The host to IO bus utilization in percent"
--      ::= { serverEnvrm 38 }

--serverPassWord OBJECT-TYPE
--      SYNTAX DisplayString
--      ACCESS read-write
--      STATUS mandatory
--      DESCRIPTION
--              "This server password"
--      ::= { serverEnvrm 39 }

mgmtStationAddrSignIn OBJECT-TYPE
        SYNTAX OCTET STRING (SIZE(11..12))
        ACCESS read-write
        STATUS mandatory
        DESCRIPTION
                "This entry is the sign-in IPX address of the management station."
        ::= { serverEnvrm 42 }

mgmtStationAddrSignOut OBJECT-TYPE
        SYNTAX OCTET STRING (SIZE(10..12))
        ACCESS read-write
        STATUS mandatory
        DESCRIPTION
                "This entry is the sign-out IPX address of the management station."
        ::= { serverEnvrm 43 }

-- Threshold for environment parameter

serverTemp1Threshold OBJECT-TYPE
        SYNTAX INTEGER
        ACCESS read-write
        STATUS mandatory
        DESCRIPTION
                "This entry displays the first level threshold value for the system temperature.
                Values displayed have to be divided by ten (10) to show the temperature in
                degrees Celsius.  For example, a reading of 305 means that the temperature is at
                30.5 degrees Celsius."
        ::= { serverEnvrm 44 }

serverTemp2Threshold OBJECT-TYPE
        SYNTAX INTEGER
        ACCESS read-write
        STATUS mandatory
        DESCRIPTION
                "This entry displays the second level threshold value for the CPU temperature.
                Values displayed have to be divided by ten (10) to show the temperature in
                degrees Celsius.  For example, a reading of 305 means that the temperature is at
                30.5 degrees Celsius."
        ::= { serverEnvrm 45 }

serverCpuUtilizationThreshold OBJECT-TYPE
        SYNTAX INTEGER
        ACCESS read-write
        STATUS mandatory
        DESCRIPTION
                "This entry shows the threshold value (%) for the CPU utilization."
        ::= { serverEnvrm 46 }

hostIOBusUtilizationThreshold OBJECT-TYPE
        SYNTAX INTEGER
        ACCESS read-write
        STATUS mandatory
        DESCRIPTION
                "This entry displays the threshold value for bus utilization.
                Values displayed have to be divided by one hundred (100) to
                show the percentage of bus utilization. For example, a reading
                of 1234 means that bus utilization is at 12.34%."
        ::= { serverEnvrm 47 }

-- For memory cache buffer threshold

memoryUtilizedThreshold OBJECT-TYPE
        SYNTAX INTEGER
        ACCESS read-write
        STATUS mandatory
        DESCRIPTION
                "This entry shows the threshold value (%) for memory utilization."
        ::= { serverEnvrm 48 }


-- totalEccErrNum OBJECT-TYPE
--      SYNTAX INTEGER
--      ACCESS read-only
--      STATUS mandatory
--      DESCRIPTION
--              "The total number of ECC memory error"
--      ::= { serverEnvrm 49 }
--
-- eccErrThreshold OBJECT-TYPE
--      SYNTAX INTEGER
--      ACCESS read-write
--      STATUS mandatory
--      DESCRIPTION
--              "The ECC memory error threshold"
--      ::= { serverEnvrm 50 }


--mgmtStationIPAddrSignIn OBJECT-TYPE
--      SYNTAX IpAddress
--      ACCESS read-write
--      STATUS mandatory
--      DESCRIPTION
--              "The management station sign in IP address"
--      ::= { serverEnvrm 51 }

--mgmtStationIPAddrSignOut OBJECT-TYPE
--      SYNTAX IpAddress
--      ACCESS read-write
--      STATUS mandatory
--      DESCRIPTION
--              "The management station sign out IP address"
--      ::= { serverEnvrm 52 }


--
-- Start of DMI Information
-- Acer DMI BIOS V2.01
--
dmiInfo OBJECT IDENTIFIER ::= { serverEnvrm 55 }

-- DMIString ::= OCTET STRING (SIZE(0..64))
-- DMIString ::= DisplayString

--  BIOS Information

biosVendor      OBJECT-TYPE
        SYNTAX DisplayString
        ACCESS read-only
        STATUS mandatory
        DESCRIPTION
                "This entry displays the name of the BIOS vendor."
        ::= { dmiInfo 1 }

biosVersion     OBJECT-TYPE
        SYNTAX DisplayString
        ACCESS read-only
        STATUS mandatory
        DESCRIPTION
                "This entry displays the BIOS version."
        ::= { dmiInfo 2 }

biosStartingAddressSegment      OBJECT-TYPE
        SYNTAX INTEGER
        ACCESS read-only
        STATUS mandatory
        DESCRIPTION
                "This entry displays the segment location of the BIOS starting address, e.g. 0E800h."
        ::= { dmiInfo 3 }

biosReleaseDate OBJECT-TYPE
        SYNTAX DisplayString
        ACCESS read-only
        STATUS mandatory
        DESCRIPTION
                "This entry displays the BIOS release date in mm/dd/yy format."
        ::= { dmiInfo 4 }

biosROMSize     OBJECT-TYPE
        SYNTAX INTEGER
        ACCESS read-only
        STATUS mandatory
        DESCRIPTION
                "This entry displays the ROM size of the BIOS.
                 Size is 64K*(n+1). 0=64K, 1=128K, 2=256K, etc."
        ::= { dmiInfo 5 }

biosCharacteristics1    OBJECT-TYPE
        SYNTAX INTEGER
        ACCESS read-only
        STATUS mandatory
        DESCRIPTION
                "This entry displays the first 32 bits of BIOS characteristics.
                It defines which functions the BIOS supports.
                PCI, PCMCIA, Flash, etc.
        Bit 0   Reserved
        Bit 1   Reserved
        Bit 2   Unknown
        Bit 3   BIOS Characteristics Not Supported
        Bit 4   ISA is supported
        Bit 5   MCA is supported
        Bit 6   EISA is supported
        Bit 7   PCI is supported
        Bit 8   PCMCIA is supported
        Bit 9   Plug and Play is supported
        Bit 10  APM is supported
        Bit 11  BIOS is Upgradeable (Flash)
        Bit 12  BIOS shadowing is allowed
        Bit 13  VL-VESA is supported
        Bit 14  ESCD support is available
        Bit 15  Boot from CD is supported
        Bit 16  Selectable Boot is supported
        Bit 17  BIOS ROM is socketed
        Bit 18  Boot From PCMCIA is supported
        Bit 19  EDD (Enhanced Disk Drive) Specification is supported
        Bit 20  Int 13h - Japanese Floppy for NEC 9800 1.2mb (3.5 inch, 1k Bytes/Sector, 360 RPM) is supported
        Bit 21  Int 13h - Japanese Floppy for Toshiba 1.2mb (3.5 inch, 360 RPM) is supported
        Bit 22  Int 13h - 5.25 inch  / 360 KB Floppy Services are supported
        Bit 23  Int 13h - 5.25 inch  /1.2MB Floppy Services are supported
        Bit 24  Int 13h - 3.5 inch  / 720 KB Floppy Services are  supported
        Bit 25  Int 13h - 3.5 inch  / 2.88 MB Floppy Services are supported
        Bit 26  Int 5h, Print Screen Service is supported
        Bit 27  Int 9h, 8042 Keyboard services are supported
        Bit 28  Int 14h, Serial Services are supported
        Bit 29  Int 17h, Printer Services are supported
        Bit 30  Int 10h, CGA Video Services are supported
        Bit 31  PC-98
        Bits32:47       Reserved for BIOS Vendor
        Bits 48:63      Reserved for System Vendor
        "
        ::= { dmiInfo 6 }

biosCharacteristics2    OBJECT-TYPE
        SYNTAX INTEGER
        ACCESS read-only
        STATUS mandatory
        DESCRIPTION
                "This entry displays the second 32 bits of BIOS characteristics.
                 It defines which functions the BIOS supports.
                 PCI, PCMCIA, Flash, etc.
        Bit 0   Reserved
        Bit 1   Reserved
        Bit 2   Unknown
        Bit 3   BIOS Characteristics Not Supported
        Bit 4   ISA is supported
        Bit 5   MCA is supported
        Bit 6   EISA is supported
        Bit 7   PCI is supported
        Bit 8   PCMCIA is supported
        Bit 9   Plug and Play is supported
        Bit 10  APM is supported
        Bit 11  BIOS is Upgradeable (Flash)
        Bit 12  BIOS shadowing is allowed
        Bit 13  VL-VESA is supported
        Bit 14  ESCD support is available
        Bit 15  Boot from CD is supported
        Bit 16  Selectable Boot is supported
        Bit 17  BIOS ROM is socketed
        Bit 18  Boot From PCMCIA is supported
        Bit 19  EDD (Enhanced Disk Drive) Specification is supported
        Bit 20  Int 13h - Japanese Floppy for NEC 9800 1.2mb (3.5 inch, 1k Bytes/Sector, 360 RPM) is supported
        Bit 21  Int 13h - Japanese Floppy for Toshiba 1.2mb (3.5 inch, 360 RPM) is supported
        Bit 22  Int 13h - 5.25 inch  / 360 KB Floppy Services are supported
        Bit 23  Int 13h - 5.25 inch  /1.2MB Floppy Services are supported
        Bit 24  Int 13h - 3.5 inch  / 720 KB Floppy Services are  supported
        Bit 25  Int 13h - 3.5 inch  / 2.88 MB Floppy Services are supported
        Bit 26  Int 5h, Print Screen Service is supported
        Bit 27  Int 9h, 8042 Keyboard services are supported
        Bit 28  Int 14h, Serial Services are supported
        Bit 29  Int 17h, Printer Services are supported
        Bit 30  Int 10h, CGA Video Services are supported
        Bit 31  PC-98
        Bits32:47       Reserved for BIOS Vendor
        Bits 48:63      Reserved for System Vendor
        "
        ::= { dmiInfo 7 }

--  System Information (Component ID) Table
--
-- The information in this structure defines attributes of the
-- overall system and is intended to be associated with the
-- Component ID group of the system's MIF.
--

siManufacturer  OBJECT-TYPE
        SYNTAX DisplayString
        ACCESS read-only
        STATUS mandatory
        DESCRIPTION
                "This entry displays the manufacturer of this computer system."
        ::= { dmiInfo 8 }

siProductName   OBJECT-TYPE
        SYNTAX DisplayString
        ACCESS read-only
        STATUS mandatory
        DESCRIPTION
                "This entry displays the name of this product."
        ::= { dmiInfo 9 }

siVersion       OBJECT-TYPE
        SYNTAX DisplayString
        ACCESS read-only
        STATUS mandatory
        DESCRIPTION
                "This entry displays the version number of this system."
        ::= { dmiInfo 10 }

siSerialNumber  OBJECT-TYPE
        SYNTAX DisplayString
        ACCESS read-only
        STATUS mandatory
        DESCRIPTION
                "This entry displays the serial number of this system."
        ::= { dmiInfo 11 }

--  Base Board Information

bbManufacturer  OBJECT-TYPE
        SYNTAX DisplayString
        ACCESS read-only
        STATUS mandatory
        DESCRIPTION
                "This entry displays the base board manufacturer."
        ::= { dmiInfo 12 }

bbProductName   OBJECT-TYPE
        SYNTAX DisplayString
        ACCESS read-only
        STATUS mandatory
        DESCRIPTION
                "This entry displays the base board product name."
        ::= { dmiInfo 13 }

bbVersion       OBJECT-TYPE
        SYNTAX DisplayString
        ACCESS read-only
        STATUS mandatory
        DESCRIPTION
                "This entry displays the base board version."
        ::= { dmiInfo 14 }

bbSerialNumber  OBJECT-TYPE
        SYNTAX DisplayString
        ACCESS read-only
        STATUS mandatory
        DESCRIPTION
                "This entry displays the base board serial number."
        ::= { dmiInfo 15 }

--  Memory Controller Information

mcErrorDetectingMethod  OBJECT-TYPE
        SYNTAX INTEGER
        ACCESS read-only
        STATUS mandatory
        DESCRIPTION
                "This entry displays the supported error detection method
                 of the memory controller.
                 01h : Other
                 02h : Unknown
                 03h : None
                 04h : 8-bit Parity
                 05h : 32-bit ECC
                 06h : 64-bit ECC
                 07h : 128-bit ECC"
        ::= { dmiInfo 16 }

mcErrorCorrectingCapability     OBJECT-TYPE
        SYNTAX INTEGER
        ACCESS read-only
        STATUS mandatory
        DESCRIPTION
                "This entry displays the error correcting capability of
                 the memory controller.
                 Bit 0 : Other
                 Bit 1 : Unknown
                 Bit 2 : None
                 Bit 3 : Single Bit Error Correcting
                 Bit 4 : Double Bit Error Correcting
                 Bit 5 : Error Scrubbing"
        ::= { dmiInfo 17 }

mcSupportedInterleave   OBJECT-TYPE
        SYNTAX INTEGER
        ACCESS read-only
        STATUS mandatory
        DESCRIPTION
                "This entry displays the supported memory interleave
                 of the memory controller.
                 01h : Other
                 02h : Unknown
                 03h : One Way Interleave
                 04h : Two Way Interleave
                 05h : Four Way Interleave
                 06h : Eight Way Interleave
                 07h : Sixteen Way Interleave"
        ::= { dmiInfo 18 }

mcCurrentInterleave     OBJECT-TYPE
        SYNTAX INTEGER
        ACCESS read-only
        STATUS mandatory
        DESCRIPTION
                "This entry displays the current memory interleave
                 of the memory controller.
                 01h : Other
                 02h : Unknown
                 03h : One Way Interleave
                 04h : Two Way Interleave
                 05h : Four Way Interleave
                 06h : Eight Way Interleave
                 07h : Sixteen Way Interleave"
        ::= { dmiInfo 19 }

mcMaximumMemoryModuleSize       OBJECT-TYPE
        SYNTAX INTEGER
        ACCESS read-only
        STATUS mandatory
        DESCRIPTION
                "This entry displays the size of the largest memory module supported (per slot),
                 specified as n, where 2^n is the maximum size in MB."
        ::= { dmiInfo 20 }

mcSupportedSpeeds       OBJECT-TYPE
        SYNTAX INTEGER
        ACCESS read-only
        STATUS mandatory
        DESCRIPTION
                "This entry displays the supported memory speeds
                 of the memory controller.
                 Bit 0 : Other
                 Bit 1 : Unknown
                 Bit 2 : 70ns
                 Bit 3 : 60ns
                 Bit 4 : 50ns
                 Bit 5-15 : Reserved, must be zero"
        ::= { dmiInfo 21 }

mcSupportedMemoryTypes  OBJECT-TYPE
        SYNTAX INTEGER
        ACCESS read-only
        STATUS mandatory
        DESCRIPTION
                "This entry displays the supported memory types
                 of the memory controller.
                 Bit 0 : Other
                 Bit 1 : Unknown
                 Bit 2 : Standard
                 Bit 3 : Fast Page Mode
                 Bit 4 : EDO
                 Bit 5 : Parity
                 Bit 6 : ECC
                 Bit 7 : SIMM
                 Bit 8 : DIMM
                 Bit 9-15 : Reserved, must be zero"
        ::= { dmiInfo 22 }

mcMemoryModuleVoltage   OBJECT-TYPE
        SYNTAX INTEGER
        ACCESS read-only
        STATUS mandatory
        DESCRIPTION
                "This entry describes the required voltages for
                 each of the memory module sockets controlled
                 by the controller:
                 Bits 7:3  Reserved, must be zero
                 Bit 2     2.9V
                 Bit 1     3.3V
                 Bit 0     5V
                 NOTE: Setting of multiple bits indicates that
                 sockets are configurable."
        ::= { dmiInfo 23 }

mcNumberOfAssociatedMemorySlots OBJECT-TYPE
        SYNTAX INTEGER
        ACCESS read-only
        STATUS mandatory
        DESCRIPTION
                "This entry defines how many of the Memory Module
                 Information blocks are controlled by the controller."
        ::= { dmiInfo 24 }

-- mcMemoryModuleConfigurationHandleTable       OBJECT-TYPE
--      SYNTAX SEQUENCE OF McMemoryModuleConfigurationHandle
--      ACCESS not-accessible
--      STATUS mandatory
--      DESCRIPTION
--              "A memory information structure index controlled by this
--               controller. mcNumberOfAssociatedMemorySlots defines the
--               count"
--      ::= { dmiInfo 51 }
--
-- mcMemoryModuleConfigurationHandle    OBJECT-TYPE
--      SYNTAX McMemoryModuleConfigurationHandle
--      ACCESS not-accessible
--      STATUS mandatory
--      DESCRIPTION
--              "Memory Module Configuration Handle"
      --INDEX  { INTEGER }
--      ::= { mcMemoryModuleConfigurationHandleTable 1 }
--
-- McMemoryModuleConfigurationHandle ::= SEQUENCE {
--      mcMemoryModuleConfigHandle      INTEGER
-- }
--
-- mcMemoryModuleConfigHandle   OBJECT-TYPE
--      SYNTAX INTEGER
--      ACCESS read-only
--      STATUS mandatory
--      DESCRIPTION
--              "Memory Module Configuration Handle"
--      ::= { mcMemoryModuleConfigurationHandle 1 }

--  Processor Information (Table)

piNumberOfProcessorInfo OBJECT-TYPE
        SYNTAX INTEGER
        ACCESS read-only
        STATUS mandatory
        DESCRIPTION
                "This field shows the number of entries in the piProcessorInfoTable."
        ::= { dmiInfo 25 }

piProcessorInfoTable    OBJECT-TYPE
        SYNTAX SEQUENCE OF PiProcessorInfo
        ACCESS not-accessible
        STATUS mandatory
        DESCRIPTION
                "This entry is a table containing information about all types of
processors on the system."
        ::= { dmiInfo 52 }

piProcessorInfo OBJECT-TYPE
        SYNTAX PiProcessorInfo
        ACCESS not-accessible
        STATUS mandatory
        DESCRIPTION
                "This entry shows information about each processor."
        --INDEX  { INTEGER }
        ::= { piProcessorInfoTable 1 }

PiProcessorInfo ::= SEQUENCE {
        piSocketDesignation     DisplayString,
        piProcessorType         INTEGER,
        piProcessorFamily       INTEGER,
        piProcessorManufacturer DisplayString,
        piProcessorID           OCTET STRING (SIZE(8)),
        piProcessorVersion      DisplayString,
        piVoltage               INTEGER,
        piExternalClock         INTEGER,
        piMaxSpeed              INTEGER,
        piCurrentSpeed          INTEGER,
        piStatus                INTEGER,
        piProcessorUpgrade      INTEGER
}

piSocketDesignation     OBJECT-TYPE
        SYNTAX DisplayString
        ACCESS read-only
        STATUS mandatory
        DESCRIPTION
                "This entry displays the processor socket designation label
                 on top of the base board."
        ::= { piProcessorInfo 1 }

piProcessorType         OBJECT-TYPE
        SYNTAX INTEGER
        ACCESS read-only
        STATUS mandatory
        DESCRIPTION
                "This entry displays the processor type.
                 01H - other
                 02H - Unknown
                 03H - Central Processor
                 04H - Math Processor
                 05H - DSP Processor
                 06H - Video Processor"
        ::= { piProcessorInfo 2 }

piProcessorFamily       OBJECT-TYPE
        SYNTAX INTEGER
        ACCESS read-only
        STATUS mandatory
        DESCRIPTION
                "This entry displays the family to which this processor belongs to.
                 01H - other
                 02H - Unknown
                 03H - 8086
                 04H - 80286
                 05H - 80386
                 06H - 80486
                 07H - 8087
                 08H - 80287
                 09h - 80387
                 0AH - 80487
                 0BH - Pentium Family
                 0CH-11H  - Reserved for specific Pentium versions
                 12H  - M1 Family
                 13H-18H  - Reserved for specific M1 versions
                 19H  - K5 Family
                 1AH-1FH  - Reserved for specific K5 versions
                 0CH - Future X86 Class CPUs
                 0DH - OverDrive Family"
        ::= { piProcessorInfo 3 }

piProcessorManufacturer OBJECT-TYPE
        SYNTAX DisplayString
        ACCESS read-only
        STATUS mandatory
        DESCRIPTION
                "This entry displays the processor's manufacturer."
        ::= { piProcessorInfo 4 }

piProcessorID           OBJECT-TYPE
        SYNTAX OCTET STRING (SIZE(8))
        ACCESS read-only
        STATUS mandatory
        DESCRIPTION
                "This entry displays specific information
                 which describes the processor's features.
                 For x86 class CPUs. the field's format depends on the processor's
                 support of the CPUID instruction. If the instruction is supported,
                 the processor ID field contains 2 DWORD-formatted values.
                 The first(offsets 08h - 0Bh)is the EAX value returned by a CPUID
                 instruction with input EAX set to 1; the second(offset 0Ch-0Fh)
                 is the EDX value returned by that instruction.
                 Otherwise, only the first 2 bytes of the processor ID field are
                 significant and contain the contents of the DX register at CPU reset."
        ::= { piProcessorInfo 5 }

piProcessorVersion      OBJECT-TYPE
        SYNTAX DisplayString
        ACCESS read-only
        STATUS mandatory
        DESCRIPTION
                "This entry displays the processor version."
        ::= { piProcessorInfo 6 }

piVoltage               OBJECT-TYPE
        SYNTAX INTEGER
        ACCESS read-only
        STATUS mandatory
        DESCRIPTION
                "This entry shows the processor's voltage requirement.
                Bits 7:4        Reserved, must be zero
                Bits 3:0        Voltage Capability. A Set bit indicates
                                the voltage is supported.
                        Bit 0 - 5V
                        Bit 1 - 3.3V
                        Bit 2 - 2.9V
                        Bit 3 - Reserved, must be zero.
                        Note: Setting of multiple bits
                        indicates the socket is configurable.
                "
        ::= { piProcessorInfo 7 }

piExternalClock         OBJECT-TYPE
        SYNTAX INTEGER
        ACCESS read-only
        STATUS mandatory
        DESCRIPTION
                "This entry shows the processor's external clock frequency
                in MHz. If the value is unknown, the field is set to 0."
        ::= { piProcessorInfo 8 }

piMaxSpeed              OBJECT-TYPE
        SYNTAX INTEGER
        ACCESS read-only
        STATUS mandatory
        DESCRIPTION
                "This entry shows the processor's maximum speed
                in MHz. If the value is unknown, the field is set to 0."
        ::= { piProcessorInfo 9 }

piCurrentSpeed          OBJECT-TYPE
        SYNTAX INTEGER
        ACCESS read-only
        STATUS mandatory
        DESCRIPTION
                "This entry shows the processor's current speed
                in MHz. If the value is unknown, the field is set to 0."
        ::= { piProcessorInfo 10 }

piStatus                OBJECT-TYPE
        SYNTAX INTEGER
        ACCESS read-only
        STATUS mandatory
        DESCRIPTION
                "This entry shows the status of this processor.
                        Bit 6   CPU socket populated.
                                1 - CPU Socket Populated.
                                0 - CPU Socket Unpopulated.
                        Bits 2:0 CPU Status
                                0h - Unknown
                                1h - CPU Enabled
                                2h - CPU disabled by user
                                3h - CPU disabled by system BIOS
                                4h - CPU is idle
                                5-6h Reserved
                                7h - Other"
        ::= { piProcessorInfo 11 }

piProcessorUpgrade      OBJECT-TYPE
        SYNTAX INTEGER
        ACCESS read-only
        STATUS mandatory
        DESCRIPTION
                "This entry shows the processor upgrade method.
                        01h - other
                        02h - unknown
                        03h - daughter board
                        04h - ZIF socket
                        05h - replaceable piggy back
                        06h - None
                        07h - LIF socket"
        ::= { piProcessorInfo 12 }

--  Memory Modules Information (Table)

mmNumberOfMemoryModuleInfo      OBJECT-TYPE
        SYNTAX INTEGER
        ACCESS read-only
        STATUS mandatory
        DESCRIPTION
                "This entry shows the number of entries in the mmMemoryModuleInfoTable."
        ::= { dmiInfo 26 }

mmMemoryModuleInfoTable OBJECT-TYPE
        SYNTAX SEQUENCE OF MmMemoryModuleInfo
        ACCESS not-accessible
        STATUS mandatory
        DESCRIPTION
                "This entry is a table containing information about all memory module sockets"
        ::= { dmiInfo 53 }

mmMemoryModuleInfo      OBJECT-TYPE
        SYNTAX MmMemoryModuleInfo
        ACCESS not-accessible
        STATUS mandatory
        DESCRIPTION
                "This entry shows information about each memory module."
        --INDEX  { INTEGER }
        ::= { mmMemoryModuleInfoTable 1 }

MmMemoryModuleInfo ::= SEQUENCE {
        mmSocketDesignation     DisplayString,
        mmBankConnections       INTEGER,
        mmCurrentSpeed          INTEGER,
        mmCurrentMemoryType     INTEGER,
        mmInstalledSize         INTEGER,
        mmEnabledSize           INTEGER,
        mmErrorStatus           INTEGER
}

mmSocketDesignation     OBJECT-TYPE
        SYNTAX DisplayString
        ACCESS read-only
        STATUS mandatory
        DESCRIPTION
                "This entry shows the memory socket designation labels
                 on top of the base board."
        ::= { mmMemoryModuleInfo 1 }

mmBankConnections       OBJECT-TYPE
        SYNTAX INTEGER
        ACCESS read-only
        STATUS mandatory
        DESCRIPTION
                "This entry shows the socket to which a memory module is installed.
                 It is a single byte value, in this byte each nibble indicates a bank(RAS#)
                 connection, 0xF means no connection.
                 Example: If banks 1 & 3 (RAS# 1 & 3) were connected to a
                 SIMM socket the byte for that socket would be 13h.
                 If only bank 2 (RAS 2) were connected  the byte for
                 that socket would be 2Fh."
        ::= { mmMemoryModuleInfo 2 }

mmCurrentSpeed          OBJECT-TYPE
        SYNTAX INTEGER
        ACCESS read-only
        STATUS mandatory
        DESCRIPTION
                "This entry shows the speed of the memory module,
                , in ns (e.g. 70d for a 70ns module).
                If the speed is unknown, the field is set to 0."
        ::= { mmMemoryModuleInfo 3 }

mmCurrentMemoryType     OBJECT-TYPE
        SYNTAX INTEGER
        ACCESS read-only
        STATUS mandatory
        DESCRIPTION
                "This entry shows the type of memory module currently installed:
                        Bit 0 - other
                        Bit 1 - unknown
                        Bit 2 - Standard
                        Bit 3 - Fast Page Mode
                        Bit 4 - EDO
                        Bit 5 - Parity
                        Bit 6 - ECC
                        Bit 7 - SIMM
                        Bit 8 - DIMM
                        Bit 9:15 Reserved, must be 0"
        ::= { mmMemoryModuleInfo 4 }

mmInstalledSize         OBJECT-TYPE
        SYNTAX INTEGER
        ACCESS read-only
        STATUS mandatory
        DESCRIPTION
                "This entry shows the installed memory size.
                 Bits 0 - 6 represent the size(n), where 2^n is the size in MB."
        ::= { mmMemoryModuleInfo 5 }

mmEnabledSize           OBJECT-TYPE
        SYNTAX INTEGER
        ACCESS read-only
        STATUS mandatory
        DESCRIPTION
                "This entry shows the enabled memory size.
                 Bits 0 - 6 represent the size(n), where 2^n is the size in MB."
        ::= { mmMemoryModuleInfo 6 }

mmErrorStatus           OBJECT-TYPE
        SYNTAX INTEGER
        ACCESS read-only
        STATUS mandatory
        DESCRIPTION
                "This entry shows the memory error status.
                        Bit 1 - Correctable errors received for the module
                        Bit 0 - Uncorrectable errors received for the module "
        ::= { mmMemoryModuleInfo 7 }

--  Cache Information (Table)

ciNumberOfCacheInfo     OBJECT-TYPE
        SYNTAX INTEGER
        ACCESS read-only
        STATUS mandatory
        DESCRIPTION
                "This field shows the number of entries in the ciCacheInfoTable."
        ::= { dmiInfo 27 }

ciCacheInfoTable        OBJECT-TYPE
        SYNTAX SEQUENCE OF CiCacheInfo
        ACCESS not-accessible
        STATUS mandatory
        DESCRIPTION
                "This entry is a table containing information about CPU cache devices."
        ::= { dmiInfo 54 }

ciCacheInfo     OBJECT-TYPE
        SYNTAX CiCacheInfo
        ACCESS not-accessible
        STATUS mandatory
        DESCRIPTION
                "This entry shows information about each CPU cache device."
        --INDEX  { INTEGER }
        ::= { ciCacheInfoTable 1 }

CiCacheInfo ::= SEQUENCE {
        ciSocketDesignation     DisplayString,
        ciCacheConfiguration    INTEGER,
        ciMaximumCacheSize      INTEGER,
        ciInstalledSize         INTEGER,
        ciSupportedSRAMType     INTEGER,
        ciCurrentSRAMType       INTEGER
}

ciSocketDesignation     OBJECT-TYPE
        SYNTAX DisplayString
        ACCESS read-only
        STATUS mandatory
        DESCRIPTION
                "This entry shows the cache socket designation labels
                 on top of the base board."
        ::= { ciCacheInfo 1 }

ciCacheConfiguration    OBJECT-TYPE
        SYNTAX INTEGER
        ACCESS read-only
        STATUS mandatory
        DESCRIPTION
                "This entry shows the configuration of this cache module.
                        Bits 15:10 - Reserved, must be 0
                        Bits 9:8   - Operational Mode:
                                00b - Write through
                                01b - Write back
                                10b - Varies with memory address
                                11b - Unknown
                        Bit 7      - Enabled/Disabled
                                1b  - Enabled
                                0b  - Disabled
                        Bits 6:5   - Location
                                00b - Internal
                                01b - External
                                10b - Reserved
                                11b - Unknown
                        Bit 4      - Reserved
                        Bit 3      - Cache Socketed
                                1b  - Socketed
                                0b  - Not socketed
                        Bits 2:0   - Cache Level"
        ::= { ciCacheInfo 2 }

ciMaximumCacheSize      OBJECT-TYPE
        SYNTAX INTEGER
        ACCESS read-only
        STATUS mandatory
        DESCRIPTION
                "This entry shows the maximum cache size that can be installed.
                        Bits 14:0 : Max. size in given granularity
                        Bit 15 Granularity : 0 = 1K granularity
                                         1 = 64K granularity"
        ::= { ciCacheInfo 3 }

ciInstalledSize         OBJECT-TYPE
        SYNTAX INTEGER
        ACCESS read-only
        STATUS mandatory
        DESCRIPTION
                "This entry shows the installed cache size.
                        Bits 14:0 : Max. size in given granularity
                        Bit 15 Granularity : 0 = 1K granularity
                                         1 = 64K granularity"
        ::= { ciCacheInfo 4 }

ciSupportedSRAMType     OBJECT-TYPE
        SYNTAX INTEGER
        ACCESS read-only
        STATUS mandatory
        DESCRIPTION
                "This entry shows the supported SRAM type.
                        Bit 0 - Other
                        Bit 1 - Unknown
                        Bit 2 - Nonburst
                        Bit 3 - Burst
                        Bit 4 - Pipeline Burst
                        Bit 5 - Synchronous
                        Bit 6 - Asynchronous
                        Bits7:15 Reserved"
        ::= { ciCacheInfo 5 }

ciCurrentSRAMType       OBJECT-TYPE
        SYNTAX INTEGER
        ACCESS read-only
        STATUS mandatory
        DESCRIPTION
                "This entry shows the current SRAM type.
                        Bit 0 - Other
                        Bit 1 - Unknown
                        Bit 2 - Nonburst
                        Bit 3 - Burst
                        Bit 4 - Pipeline Burst
                        Bit 5 - Synchronous
                        Bit 6 - Asynchronous
                        Bits7:15 Reserved"
        ::= { ciCacheInfo 6 }

--  Port Connector Information (Table)

pcNumberOfPortConnectorInfo     OBJECT-TYPE
        SYNTAX INTEGER
        ACCESS read-only
        STATUS mandatory
        DESCRIPTION
                "This field shows the number of entries in the pcPortConnectorInfoTable"
        ::= { dmiInfo 28 }

pcPortConnectorInfoTable        OBJECT-TYPE
        SYNTAX SEQUENCE OF PcPortConnectorInfo
        ACCESS not-accessible
        STATUS mandatory
        DESCRIPTION
                "This entry is a table containing information about all port connectors."
        ::= { dmiInfo 55 }

pcPortConnectorInfo     OBJECT-TYPE
        SYNTAX PcPortConnectorInfo
        ACCESS not-accessible
        STATUS mandatory
        DESCRIPTION
                "This entry shows information about each port connector."
        --INDEX  { INTEGER }
        ::= { pcPortConnectorInfoTable 1 }

PcPortConnectorInfo ::= SEQUENCE {
        pcInternalReferenceDesignator       DisplayString,
        pcInternalConnectorType             INTEGER,
        pcExternalReferenceDesignator       DisplayString,
        pcExternalConnectorType             INTEGER,
        pcPortType                          INTEGER
}

pcInternalReferenceDesignator       OBJECT-TYPE
        SYNTAX DisplayString
        ACCESS read-only
        STATUS mandatory
        DESCRIPTION
                "This entry shows the internal reference designation labels
                 on top of the base board."
        ::= { pcPortConnectorInfo 1 }

pcInternalConnectorType             OBJECT-TYPE
        SYNTAX INTEGER
        ACCESS read-only
        STATUS mandatory
        DESCRIPTION
                "This entry shows the internal connector type.
                        00h  - None
                        01h  - Centronics
                        02h  - Mini Centronics
                        03h  - Proprietary
                        04h  - DB25 pin male
                        05h  - DB25 pin female
                        06h  - DB15 pin male
                        07h  - DB15 pin female
                        08h  - DB9 pin male
                        09h  - DB9 pin female
                        0Ah  - RJ-11
                        0Bh  - RJ-45
                        0Ch  - 50 pin Mini SCSI
                        0Dh  - Mini DIN
                        0Eh  - Micro DIN
                        0Fh  - PS/2
                        10h  - Infrared
                        11h  - HP-HIL
                        12h  - Access BUS
                        13h  - SSA SCSI
                        14h  - Circular DIN-8 male
                        15h  - Circular DIN-8 female
                        16h  - On board IDE
                        17h  - On board floppy
                        18h  - 9 pin dual Inline
                        19h  - 25 pin dual Inline
                        1Ah  - 50 pin dual Inline
                        1Bh  - 68 pin dual Inline
                        1Ch  - On board sound input for CD-ROM
                        1Dh  - Mini Centronics Type 14
                        1Eh  - Mini Centronics Type 26
                        A0h  - PC98
                        A1h  - PC98 Hireso
                        A2h  - PC H98
                        A3h  - PC98 Note
                        A4h  - PC 98 Full
                        FFh  - Other"
        ::= { pcPortConnectorInfo 2 }

pcExternalReferenceDesignator       OBJECT-TYPE
        SYNTAX DisplayString
        ACCESS read-only
        STATUS mandatory
        DESCRIPTION
                "This entry shows the external reference designation labels
                 on top of the base board."
        ::= { pcPortConnectorInfo 3 }

pcExternalConnectorType             OBJECT-TYPE
        SYNTAX INTEGER
        ACCESS read-only
        STATUS mandatory
        DESCRIPTION
                "This entry shows the external connector type.
                        00h  - None
                        01h  - Centronics
                        02h  - Mini Centronics
                        03h  - Proprietary
                        04h  - DB25 pin male
                        05h  - DB25 pin female
                        06h  - DB15 pin male
                        07h  - DB15 pin female
                        08h  - DB9 pin male
                        09h  - DB9 pin female
                        0Ah  - RJ-11
                        0Bh  - RJ-45
                        0Ch  - 50 pin Mini SCSI
                        0Dh  - Mini DIN
                        0Eh  - Micro DIN
                        0Fh  - PS/2
                        10h  - Infrared
                        11h  - HP-HIL
                        12h  - Access BUS
                        13h  - SSA SCSI
                        14h  - Circular DIN-8 male
                        15h  - Circular DIN-8 female
                        16h  - On board IDE
                        17h  - On board floppy
                        18h  - 9 pin dual Inline
                        19h  - 25 pin dual Inline
                        1Ah  - 50 pin dual Inline
                        1Bh  - 68 pin dual Inline
                        1Ch  - On board sound input for CD-ROM
                        1Dh  - Mini Centronics Type 14
                        1Eh  - Mini Centronics Type 26
                        A0h  - PC98
                        A1h  - PC98 Hireso
                        A2h  - PC H98
                        A3h  - PC98 Note
                        A4h  - PC98 Full
                        FFh  - Other"
        ::= { pcPortConnectorInfo 4 }

pcPortType                          OBJECT-TYPE
        SYNTAX INTEGER
        ACCESS read-only
        STATUS mandatory
        DESCRIPTION
                "This entry shows the port type
                        00h  - None
                        01h  - Parallel Port XT/AT Compatible
                        02h  - Parallel Port PS/2
                        03h  - Parallel Port ECP
                        04h  - Parallel Port EPP
                        05h  - Parallel Port ECP/EPP
                        06h  - Serial Port XT/AT Compatible
                        07h  - Serial Port 16450 Compatible
                        08h  - Serial Port 16650 Compatible
                        09h  - Serial Port 16650A Compatible
                        0Ah  - SCSI Port
                        0Bh  - MIDI Port
                        0Ch  - Joy stick port
                        0Dh  - Keyboard Port
                        0Eh  - Mouse Port
                        0Fh  - SSA SCSI
                        10h  - USB
                        11h  - FireWire
                        12h  - PCMCIA Type I
                        13h  - PCMCIA Type II
                        14h  - PCMCIA Type III
                        15h  - Cardbus
                        16h  - Access Bus Port
                        17h  - SCSI II
                        18h  - SCSI Wide
                        19h  - PC-98
                        1Ah  - PC-98 Hireso
                        1Bh  - OC-H98
                        A0h  - 8251 Compatible
                        A1h  - 8251 FIFO Compatible
                        FFh  - Other"
        ::= { pcPortConnectorInfo 5 }

--  System Slots (Table)

ssNumberOfSystemSlotInfo        OBJECT-TYPE
        SYNTAX INTEGER
        ACCESS read-only
        STATUS mandatory
        DESCRIPTION
                "This field shows the number of entries in ssSystemSlotInfoTable"
        ::= { dmiInfo 29 }

ssSystemSlotInfoTable   OBJECT-TYPE
        SYNTAX SEQUENCE OF SsSystemSlotInfo
        ACCESS not-accessible
        STATUS mandatory
        DESCRIPTION
                "This entry is a table containing information about all system slots."
        ::= { dmiInfo 56 }

ssSystemSlotInfo        OBJECT-TYPE
        SYNTAX SsSystemSlotInfo
        ACCESS not-accessible
        STATUS mandatory
        DESCRIPTION
                "This entry shows information about each system slot."
        --INDEX  { INTEGER }
        ::= { ssSystemSlotInfoTable 1 }

SsSystemSlotInfo ::= SEQUENCE {
        ssSlotDesignation       DisplayString,
        ssSlotType              INTEGER,
        ssSlotDataBusWidth      INTEGER,
        ssCurrentUsage          INTEGER,
        ssSlotLength            INTEGER,
        ssSlotID                INTEGER,
        ssSlotCharacteristics   INTEGER
}

ssSlotDesignation       OBJECT-TYPE
        SYNTAX DisplayString
        ACCESS read-only
        STATUS mandatory
        DESCRIPTION
                "This entry shows the slot designation label
                 on top of the base board."
        ::= { ssSystemSlotInfo 1 }

ssSlotType              OBJECT-TYPE
        SYNTAX INTEGER
        ACCESS read-only
        STATUS mandatory
        DESCRIPTION
                "This entry shows the slot type.
                        01h  - Other
                        02h  - Unknown
                        03h  - ISA
                        04h  - MCA
                        05h  - EISA
                        06h  - PCI
                        07h  - PCMCIA
                        08h  - VL VESA
                        09h  - Proprietary
                        0Ah  - Processor Card Slot
                        0Bh  - Proprietary Memory Card
                        0Ch  - I/O Riser Card Slot
                        0Dh  - NuBus
                        0Eh  - PCI- 66MHz Capable
                        A0h  - PC98/C20
                        A1h  - PC98/C24
                        A2h  - PC98/E
                        A3h  - PC98/Local Bus
                        A4h  - PC98/Card"
        ::= { ssSystemSlotInfo 2 }

ssSlotDataBusWidth      OBJECT-TYPE
        SYNTAX INTEGER
        ACCESS read-only
        STATUS mandatory
        DESCRIPTION
                "This entry shows the width of the data bus.
                        01h  - Other
                        02h  - Unknown
                        03h  - 8bit
                        04h  - 16bit
                        05h  - 32bit
                        06h  - 64bit
                        07h  - 128bit"
        ::= { ssSystemSlotInfo 3 }

ssCurrentUsage          OBJECT-TYPE
        SYNTAX INTEGER
        ACCESS read-only
        STATUS mandatory
        DESCRIPTION
                "This entry shows the current usage of this slot.
                        01h  - Other
                        02h  - Unknown
                        03h  - Available
                        04h  - In use"
        ::= { ssSystemSlotInfo 4 }

ssSlotLength            OBJECT-TYPE
        SYNTAX INTEGER
        ACCESS read-only
        STATUS mandatory
        DESCRIPTION
                "This entry shows the length of the slot.
                        01h  - Other
                        02h  - Unknown
                        03h  - Half Length
                        04h  - Full Length"
        ::= { ssSystemSlotInfo 5 }

ssSlotID                OBJECT-TYPE
        SYNTAX INTEGER
        ACCESS read-only
        STATUS mandatory
        DESCRIPTION
                "This entry shows the slot ID.
                        MCA     - Logical Micro Channel slot number
                        EISA    - Logical EISA slot number
                        PCI     - The value present in the slot number field
                                  of the PCI interrupt routing table entry that
                                  is associated with the slot.
                        PCMCIA- Identifies the adapter number and socket number
                                  to be passed to PCMCIA socket services to identify
                                  this slot."
        ::= { ssSystemSlotInfo 6 }

ssSlotCharacteristics   OBJECT-TYPE
        SYNTAX INTEGER
        ACCESS read-only
        STATUS mandatory
        DESCRIPTION
                "This entry shows the characteristics of this slot.
                        Bit 0 - Unknown
                        Bit 1 - Provide 5.0 Volts
                        Bit 2 - Provide 3.3 Volts
                        Bit 1 - Slot's opening is shared with another slot, e.g. PCI/EISA shared slot
                        Bits 4:7 - Reserved"
        ::= { ssSystemSlotInfo 7 }

--  On Board Devices Information (Table)

obNumberOfOnBoardDeviceInfo     OBJECT-TYPE
        SYNTAX INTEGER
        ACCESS read-only
        STATUS mandatory
        DESCRIPTION
                "This field shows the number of entries in the obOnBoardDeviceInfoTable."
        ::= { dmiInfo 30 }

obOnBoardDeviceInfoTable        OBJECT-TYPE
        SYNTAX SEQUENCE OF ObOnBoardDeviceInfo
        ACCESS not-accessible
        STATUS mandatory
        DESCRIPTION
                "This entry is a table containing information about all on board devices."
        ::= { dmiInfo 57 }

obOnBoardDeviceInfo     OBJECT-TYPE
        SYNTAX ObOnBoardDeviceInfo
        ACCESS not-accessible
        STATUS mandatory
        DESCRIPTION
                "This entry shows information about each on board device."
        --INDEX  { INTEGER }
        ::= { obOnBoardDeviceInfoTable 1 }

ObOnBoardDeviceInfo ::= SEQUENCE {
        obDeviceType    INTEGER,
        obDescription   DisplayString
}

obDeviceType    OBJECT-TYPE
        SYNTAX INTEGER
        ACCESS read-only
        STATUS mandatory
        DESCRIPTION
                "This entry shows the device type.
                        01H - Other
                        02H - Unknown
                        03H - Video
                        04H - SCSI
                        05H - Ethernet
                        06H - Token Ring
                        07H - Sound"
        ::= { obOnBoardDeviceInfo 1 }

obDescription   OBJECT-TYPE
        SYNTAX DisplayString
        ACCESS read-only
        STATUS mandatory
        DESCRIPTION
                "This entry shows the description of the on board device."
        ::= { obOnBoardDeviceInfo 2 }

--  OEM Strings (Table)

oemNumberOfOEMString    OBJECT-TYPE
        SYNTAX INTEGER
        ACCESS read-only
        STATUS mandatory
        DESCRIPTION
                "This field shows the number of entries in the oemStringTable."
        ::= { dmiInfo 31 }

oemStringTable  OBJECT-TYPE
        SYNTAX SEQUENCE OF OemStrings
        ACCESS not-accessible
        STATUS mandatory
        DESCRIPTION
                "This entry is a table showing OEM defined strings."
        ::= { dmiInfo 58 }

oemStrings      OBJECT-TYPE
        SYNTAX OemStrings
        ACCESS not-accessible
        STATUS mandatory
        DESCRIPTION
                "This entry shows information about each OEM string."
        --INDEX  { INTEGER }
        ::= { oemStringTable 1 }

OemStrings ::= SEQUENCE {
        oemString       DisplayString
}

oemString       OBJECT-TYPE
        SYNTAX DisplayString
        ACCESS read-only
        STATUS mandatory
        DESCRIPTION
                "This entry is an individual OEM string."
        ::= { oemStrings 1 }

smNumberOfEventLog	OBJECT-TYPE
	SYNTAX INTEGER
	ACCESS read-only
	STATUS mandatory
	DESCRIPTION
		"This field shows the number of entries in the smEventLogTable."
	::= { dmiInfo 32 }

smEventLogSupport OBJECT-TYPE
		SYNTAX INTEGER
		ACCESS read-only
		STATUS mandatory
		DESCRIPTION
		"This entry shows if BIOS supports System Event Log 
		function:
		0 = NO
		else  = YES"
		::= { dmiInfo 33 }

smEventLogTotalSize     OBJECT-TYPE
		SYNTAX INTEGER
		ACCESS read-only
		STATUS mandatory
		DESCRIPTION
		"This entry shows the total size of event log data area in 
		bytes."
		::= { dmiInfo 34 }

smEventLogUsedSize      OBJECT-TYPE
		SYNTAX INTEGER
		ACCESS read-only
		STATUS mandatory
		DESCRIPTION
		"This entry shows the used size of event log data area in 
		bytes."
		::= { dmiInfo 35 }

smEventLogUtilizationThreshold  OBJECT-TYPE
		SYNTAX INTEGER
		ACCESS read-write
		STATUS mandatory
		DESCRIPTION
		"This entry shows the threshold value (%) for event log 
		data area utilization."
		::= { dmiInfo 36 }

smEventLogTable	OBJECT-TYPE
	SYNTAX SEQUENCE OF SmEventLogEntry
	ACCESS not-accessible
	STATUS mandatory
	DESCRIPTION
		"This entry is a table of event log entries."
	::= { dmiInfo 59 }

smEventLogEntry	OBJECT-TYPE
	SYNTAX SmEventLogEntry
	ACCESS not-accessible
	STATUS mandatory
	DESCRIPTION
		"This entry contains information about each logged event."
	--INDEX  { INTEGER }
	::= { smEventLogTable 1 }

SmEventLogEntry ::= SEQUENCE {
	smLogTime	DisplayString,
	smLogType	INTEGER,
	smLogDescription	DisplayString
}

smLogTime	OBJECT-TYPE
	SYNTAX DisplayString
	ACCESS read-only
	STATUS mandatory
	DESCRIPTION
		"This entry shows the event log time."
	::= { smEventLogEntry 1 }

smLogType	OBJECT-TYPE
	SYNTAX INTEGER
	ACCESS read-only
	STATUS mandatory
	DESCRIPTION
		"This entry shows the event log type."
	::= { smEventLogEntry 2 }

smLogDescription	OBJECT-TYPE
	SYNTAX DisplayString
	ACCESS read-only
	STATUS mandatory
	DESCRIPTION
		"This entry shows the event log description."
	::= { smEventLogEntry 3 }

--
-- End of DMI Information
--

numberOfIPAddress       OBJECT-TYPE
        SYNTAX INTEGER
        ACCESS read-only
        STATUS mandatory
        DESCRIPTION
                "This entry shows the number of IP addresses assigned to this server."
        ::= { serverEnvrm 56 }

ipAddressTable  OBJECT-TYPE
        SYNTAX SEQUENCE OF IpAddresses
        ACCESS not-accessible
        STATUS mandatory
        DESCRIPTION
                "This entry is a table showing the IP addresses assigned to this server."
        ::= { serverEnvrm 57 }

ipAddresses     OBJECT-TYPE
        SYNTAX IpAddresses
        ACCESS not-accessible
        STATUS mandatory
        DESCRIPTION
                "This entry shows information about each IP address assigned to this server."
        --INDEX  { INTEGER }
        ::= { ipAddressTable 1 }

IpAddresses ::= SEQUENCE {
        ipAddress       IpAddress
}

ipAddress       OBJECT-TYPE
        SYNTAX IpAddress
        ACCESS read-only
        STATUS mandatory
        DESCRIPTION
                "This entry is the individual IP address assigned to this server."
        ::= { ipAddresses 1 }

ipxAddress      OBJECT-TYPE
        SYNTAX OCTET STRING (SIZE(10))
        ACCESS read-only
        STATUS mandatory
        DESCRIPTION
                "This entry is the internal IPX address assigned to this server."
        ::= { serverEnvrm 58 }

numberOfLoginUser       OBJECT-TYPE
        SYNTAX INTEGER
        ACCESS read-only
        STATUS mandatory
        DESCRIPTION
                "This field shows the number of entries in the loginUserTable."
        ::= { serverEnvrm 59 }

loginUserTable  OBJECT-TYPE
        SYNTAX SEQUENCE OF LoginUser
        ACCESS not-accessible
        STATUS mandatory
        DESCRIPTION
                "This entry is a table containing information about all logged in users."
        ::= { serverEnvrm 60 }

loginUser       OBJECT-TYPE
        SYNTAX LoginUser
        ACCESS not-accessible
        STATUS mandatory
        DESCRIPTION
                "This entry shows information about each logged in user."
        --INDEX  { INTEGER }
        ::= { loginUserTable 1 }

LoginUser ::= SEQUENCE {
        loginUserName   DisplayString,
        loginTime       DisplayString
}

loginUserName   OBJECT-TYPE
        SYNTAX DisplayString
        ACCESS read-only
        STATUS mandatory
        DESCRIPTION
                "This entry shows the logged in user's name."
        ::= { loginUser 1 }

loginTime       OBJECT-TYPE
        SYNTAX DisplayString
        ACCESS read-only
        STATUS mandatory
        DESCRIPTION
                "This entry shows the user's login time."
        ::= { loginUser 2 }


numberOfDriverLoaded    OBJECT-TYPE
        SYNTAX INTEGER
        ACCESS read-only
        STATUS mandatory
        DESCRIPTION
                "This field shows the number of entries in the driverLoadedTable."
        ::= { serverEnvrm 61 }

driverLoadedTable       OBJECT-TYPE
        SYNTAX SEQUENCE OF DriverLoaded
        ACCESS not-accessible
        STATUS mandatory
        DESCRIPTION
                "This entry is a table containing information about all software
 (including drivers) currently running on the server. "
        ::= { serverEnvrm 62 }

driverLoaded    OBJECT-TYPE
        SYNTAX DriverLoaded
        ACCESS not-accessible
        STATUS mandatory
        DESCRIPTION
                "This entry contains information about each software running on the server."
        --INDEX  { INTEGER }
        ::= { driverLoadedTable 1 }

DriverLoaded ::= SEQUENCE {
        driverName              DisplayString,
        driverDescription       DisplayString
}

driverName              OBJECT-TYPE
        SYNTAX DisplayString
        ACCESS read-only
        STATUS mandatory
        DESCRIPTION
                "This entry shows the name of the software running on the server."
        ::= { driverLoaded 1 }

driverDescription       OBJECT-TYPE
        SYNTAX DisplayString
        ACCESS read-only
        STATUS mandatory
        DESCRIPTION
                "This entry shows a description of the software running on the server."
        ::= { driverLoaded 2 }

--
-- Start of Performance Information
-- Common for SCO UNIX and Windows NT
--
performance OBJECT IDENTIFIER ::= { serverEnvrm 63 }

---     Paging
numberOfPageIn  OBJECT-TYPE
        SYNTAX INTEGER
        ACCESS read-only
        STATUS mandatory
        DESCRIPTION
                "This entry shows the number of page-ins during the last sampling."
        ::= { performance 1 }

byteOfPageIn    OBJECT-TYPE
        SYNTAX INTEGER
        ACCESS read-only
        STATUS mandatory
        DESCRIPTION
                "This entry shows the number of page-in bytes during the last sampling."
        ::= { performance 2 }

numberOfPageOut OBJECT-TYPE
        SYNTAX INTEGER
        ACCESS read-only
        STATUS mandatory
        DESCRIPTION
                "This entry shows the number of page-out during the last sampling."
        ::= { performance 3 }

byteOfPageOut   OBJECT-TYPE
        SYNTAX INTEGER
        ACCESS read-only
        STATUS mandatory
        DESCRIPTION
                "This entry shows the number of page-out bytes during the last sampling."
        ::= { performance 4 }

numberOfPageFault       OBJECT-TYPE
        SYNTAX INTEGER
        ACCESS read-only
        STATUS mandatory
        DESCRIPTION
                "This entry shows the total number of page-faults during the last sampling."
        ::= { performance 5 }

diskCacheReadHitRatio   OBJECT-TYPE
        SYNTAX INTEGER
        ACCESS read-only
        STATUS mandatory
        DESCRIPTION
                "This entry shows the ratio of disk cache read hits
                  in the last sampling."
        ::= { performance 6 }

diskCacheWriteHitRatio  OBJECT-TYPE
        SYNTAX INTEGER
        ACCESS read-only
        STATUS mandatory
        DESCRIPTION
                "This entry shows the ratio of disk cache write hits
                  in the last sampling"
        ::= { performance 7 }

numberOfFreeMem  OBJECT-TYPE
        SYNTAX INTEGER
        ACCESS read-only
        STATUS mandatory
        DESCRIPTION
                "This entry shows the number of 4KB pages available
                 to user processes"
        ::= { performance 8 }

numberOfTotalSwap  OBJECT-TYPE
        SYNTAX INTEGER
        ACCESS read-only
        STATUS mandatory
        DESCRIPTION
                "This entry shows the total number of physical disk (512-byte)
                 blocks available for swapping and paging"
        ::= { performance 9 }

numberOfFreeSwap  OBJECT-TYPE
        SYNTAX INTEGER
        ACCESS read-only
        STATUS mandatory
        DESCRIPTION
                "This entry shows the free number of physical disk (512-byte)
                 blocks available for swapping and paging"
        ::= { performance 10 }

numberOfSwapIn  OBJECT-TYPE
        SYNTAX INTEGER
        ACCESS read-only
        STATUS mandatory
        DESCRIPTION
                "This entry shows the number of transfers from swap into
                 memory per second"
        ::= { performance 11 }

numberOfSwapInPages  OBJECT-TYPE
        SYNTAX INTEGER
        ACCESS read-only
        STATUS mandatory
        DESCRIPTION
                "This entry shows the number of 4KB pages transfers from swap
                 into memory per second"
        ::= { performance 12 }

numberOfSwapOut  OBJECT-TYPE
        SYNTAX INTEGER
        ACCESS read-only
        STATUS mandatory
        DESCRIPTION
                "This entry shows the number of transfers from memory into
                 swap per second. If this value is greater than zero, you
                 may need to increase the amount of memory or reduce the
                 number of buffers."
        ::= { performance 13 }

numberOfSwapOutPages  OBJECT-TYPE
        SYNTAX INTEGER
        ACCESS read-only
        STATUS mandatory
        DESCRIPTION
                "This entry shows the number of 4KB pages transfers from memory
                 into swap per second"
        ::= { performance 14 }

numberOfContextSwitch  OBJECT-TYPE
        SYNTAX INTEGER
        ACCESS read-only
        STATUS mandatory
        DESCRIPTION
                "This entry shows the number of context switch per second"
        ::= { performance 15 }

-- Windows NT Performance {}
--
ntPerf		OBJECT IDENTIFIER ::= { serverEnvrm 65 }
systemPerf	OBJECT IDENTIFIER ::= { ntPerf 1 }
cachePerf	OBJECT IDENTIFIER ::= { ntPerf 2 }
memoryPerf	OBJECT IDENTIFIER ::= { ntPerf 3 }
--processorPerfTbl OBJECT-TYPE
--	SYNTAX SEQUENCE OF ProcessorPerf
--	ACCESS not-accessible
--	STATUS mandatory
--	DESCRIPTION ""
--	::= { ntPerf 4 }

physicalDiskPerfTbl OBJECT-TYPE
	SYNTAX SEQUENCE OF PhysicalDiskPerf
	ACCESS not-accessible
	STATUS mandatory
	DESCRIPTION
		"This entry is a table containing the performance counters of physical disk drives."
	::= { ntPerf 5 }

logicalDiskPerfTbl OBJECT-TYPE
	SYNTAX SEQUENCE OF LogicalDiskPerf
	ACCESS not-accessible
	STATUS mandatory
	DESCRIPTION 
		"This entry is a table containing the performance counters of logical disk drives."
	::= { ntPerf 6 }

-- System Performance { ntPerf 1 }
--
processorTime OBJECT-TYPE
	SYNTAX Gauge
	ACCESS read-only
	STATUS mandatory
	DESCRIPTION
		"This entry is the average percentage of time all the processors on the system 
		are busy to execute non-idle threads."
	::= { systemPerf 1 }

privilegedTime OBJECT-TYPE
	SYNTAX Gauge
	ACCESS read-only
	STATUS mandatory
	DESCRIPTION 
		"This entry is the average percentage of time spent in Privileged mode by all processors."
	::= { systemPerf 2 }

userTime OBJECT-TYPE
	SYNTAX Gauge
	ACCESS read-only
	STATUS mandatory
	DESCRIPTION 
		"This entry is the average percentage of time spent in User mode by all processors."
	::= { systemPerf 3 }

interruptTime OBJECT-TYPE
	SYNTAX Gauge
	ACCESS read-only
	STATUS mandatory
	DESCRIPTION 
		"This entry is the average percentage of the Interrupt Time of all processors."
	::= { systemPerf 4 }

interruptsPerSec OBJECT-TYPE
	SYNTAX INTEGER
	ACCESS read-only
	STATUS mandatory
	DESCRIPTION 
		"This entry is the hardware interrupts received and serviced by the system
		 per second."
	::= { systemPerf 5 }

contextSwitchesPerSec OBJECT-TYPE
	SYNTAX INTEGER
	ACCESS read-only
	STATUS mandatory
	DESCRIPTION 
		"This entry is the context switches from one thread to another per second."
	::= { systemPerf 6 }

exceptionDispatchesPerSec OBJECT-TYPE
	SYNTAX INTEGER
	ACCESS read-only
	STATUS mandatory
	DESCRIPTION 
		"This entry is the exceptions dispatched by the system per second."
	::= { systemPerf 7 }

systemCallsPerSec OBJECT-TYPE
	SYNTAX INTEGER
	ACCESS read-only
	STATUS mandatory
	DESCRIPTION 
		"This entry is the calls to Windows NT system service routines per second."
	::= { systemPerf 8 }

fileControlOpsPerSec OBJECT-TYPE
	SYNTAX INTEGER
	ACCESS read-only
	STATUS mandatory
	DESCRIPTION 
		"This entry is all file system operations that are neither reads nor writes per second."
	::= { systemPerf 9 }

fileControlBytesPerSec OBJECT-TYPE
	SYNTAX INTEGER
	ACCESS read-only
	STATUS mandatory
	DESCRIPTION 
		"This entry is bytes transferred for all file system operations that are neither 
		reads nor writes per second."
	::= { systemPerf 10 }

fileDataOpsPerSec OBJECT-TYPE
	SYNTAX INTEGER
	ACCESS read-only
	STATUS mandatory
	DESCRIPTION 
		"This entry is the read and write operations to file system devices per second."
	::= { systemPerf 11 }

fileReadOpsPerSec OBJECT-TYPE
	SYNTAX INTEGER
	ACCESS read-only
	STATUS mandatory
	DESCRIPTION 
		"This entry is the read operations of all the file system per second."
	::= { systemPerf 12 }

fileWriteOpsPerSec OBJECT-TYPE
	SYNTAX INTEGER
	ACCESS read-only
	STATUS mandatory
	DESCRIPTION 
		"This entry is the number of write operations of all the file system per second."
	::= { systemPerf 13 }

fileReadBytesPerSec OBJECT-TYPE
	SYNTAX INTEGER
	ACCESS read-only
	STATUS mandatory
	DESCRIPTION 
		"This entry is the bytes transferred for all the file system read operations 
		per second."
	::= { systemPerf 14 }

fileWriteBytesPerSec OBJECT-TYPE
	SYNTAX INTEGER
	ACCESS read-only
	STATUS mandatory
	DESCRIPTION 
		"This entry is the bytes transferred for all the file system write operations
		per second."
	::= { systemPerf 15 }

-- Cache Performance { ntPerf 2 }
--
copyReadsHitRatio OBJECT-TYPE
	SYNTAX Gauge
	ACCESS read-only
	STATUS mandatory
	DESCRIPTION 
		"This entry is the percentage of Cache Copy Read requests that hit the cache."
	::= { cachePerf 1 }

copyReadsPerSec OBJECT-TYPE
	SYNTAX INTEGER
	ACCESS read-only
	STATUS mandatory
	DESCRIPTION 
		"This entry is the number of copy reads per second."
	::= { cachePerf 2 }

dataMapHitRatio OBJECT-TYPE
	SYNTAX Gauge
	ACCESS read-only
	STATUS mandatory
	DESCRIPTION 
		"This entry is the percentage of Data Maps in the cache."
	::= { cachePerf 3 }

dataMapsPerSec OBJECT-TYPE
	SYNTAX INTEGER
	ACCESS read-only
	STATUS mandatory
	DESCRIPTION 
		"This entry is the frequency (per second) that a file system maps a page of 
		a file into the cache to read the page."
	::= { cachePerf 4 }

dataFlushesPerSec OBJECT-TYPE
	SYNTAX INTEGER
	ACCESS read-only
	STATUS mandatory
	DESCRIPTION 
		"This entry is the frequency (per second) that the cache has flushed its contents
		to disk.  More than one page can be transferred on each flush operation."
	::= { cachePerf 5 }

dataFlushPagesPerSec OBJECT-TYPE
	SYNTAX INTEGER
	ACCESS read-only
	STATUS mandatory
	DESCRIPTION 
		"This entry is the number of pages per second the cache has flushed to disk.
		More than one page can be transferred on each flush operation."
	::= { cachePerf 6 }

lazeWriteFlushesPerSec OBJECT-TYPE
	SYNTAX INTEGER
	ACCESS read-only
	STATUS mandatory
	DESCRIPTION 
		"This entry is the frequency (per second) that the cache's Lazy Write thread has
		written to disk. More than one page can be transferred on each write operation."
	::= { cachePerf 7 }

lazeWritePagesPerSec OBJECT-TYPE
	SYNTAX INTEGER
	ACCESS read-only
	STATUS mandatory
	DESCRIPTION
		"This entry is the frequency (per second) the cache's Lazy Write thread has written
		to disk. More than one page can be transferred on a single disk write operation."
	::= { cachePerf 8 }

-- Memory Performance { ntPerf 3 }
--
pageFaultsPerSec	OBJECT-TYPE
	SYNTAX INTEGER
	ACCESS read-only
	STATUS mandatory
	DESCRIPTION 
		"This entry is the number of page faults per second in the processor."
	::= { memoryPerf 1 }

transitionFaultsPerSec	OBJECT-TYPE
	SYNTAX INTEGER
	ACCESS read-only
	STATUS mandatory
	DESCRIPTION 
		"This entry is the number of page faults resolved per second by recovering pages 
		that were in transition. The pages were recovered without additional disk activity."
	::= { memoryPerf 2 }

writeCopiesPerSec	OBJECT-TYPE
	SYNTAX INTEGER
	ACCESS read-only
	STATUS mandatory
	DESCRIPTION 
		"This entry is the number of page faults per second that have been satisfied by making
		a copy of a page when an attempt to write to the page is made."
	::= { memoryPerf 3 }

pageReadPerSec		OBJECT-TYPE
	SYNTAX INTEGER
	ACCESS read-only
	STATUS mandatory
	DESCRIPTION 
		"This entry is the number of times the disk was read per second to retrieve pages of
		virtual memory necessary to resolve page faults. Multiple pages can be read during a 
		disk read operation."
	::= { memoryPerf 4 }

pageWritePerSec 	OBJECT-TYPE
	SYNTAX INTEGER
	ACCESS read-only
	STATUS mandatory
	DESCRIPTION 
		"This entry is the number of times per second that pages have been written to the disk.
		Each such write operation may transfer a number of pages."
	::= { memoryPerf 5 }

pagesInputPerSec	OBJECT-TYPE
	SYNTAX INTEGER
	ACCESS read-only
	STATUS mandatory
	DESCRIPTION 
		"This entry is the number of pages read per second from the disk to resolve memory 
		references to pages. This counter includes paging traffic on behalf of the system 
		cache to access file data for applications."
	::= { memoryPerf 6 }

pagesOutputPerSec	OBJECT-TYPE
	SYNTAX INTEGER
	ACCESS read-only
	STATUS mandatory
	DESCRIPTION 
		"This entry is the number of pages written to the disk per second because the pages 
		have been modified in main memory."
	::= { memoryPerf 7 }

pagesPerSec		OBJECT-TYPE
	SYNTAX INTEGER
	ACCESS read-only
	STATUS mandatory
	DESCRIPTION 
		"This entry is the number of pages read from or written to the disk per second to 
		resolve memory references to pages that were not in memory."
	::= { memoryPerf 8 }

systemCodeBytes 	OBJECT-TYPE
	SYNTAX INTEGER
	ACCESS read-only
	STATUS mandatory
	DESCRIPTION 
		"This entry is the number of pagable bytes of System Code Total Bytes currently 
		resident in core memory. There is another ~300k bytes of non-paged kernel code."
	::= { memoryPerf 9 }

systemDriverBytes	OBJECT-TYPE
	SYNTAX INTEGER
	ACCESS read-only
	STATUS mandatory
	DESCRIPTION 
		"This entry is the number of pagable bytes of System Driver Total Bytes currently
		resident in core memory. There is another ~700k bytes of non-paged driver code."
	::= { memoryPerf 10 }
 
PhysicalDiskPerf	::= SEQUENCE {
	physicalDiskId		INTEGER,
	avgBytesPerRead 	INTEGER,
	avgBytesPerWrite	INTEGER,
	avgBytesPerTransfer	INTEGER,
	avgSecPerRead		INTEGER,
	avgSecPerWrite		INTEGER,
	avgSecPerTransfer	INTEGER,
	diskReadBytesPerSec	INTEGER,
	diskWriteBytesPerSec	INTEGER,
	diskBytesPerSec 	INTEGER,
	diskReadPerSec		INTEGER,
	diskWritePerSec 	INTEGER,
	diskTransferPerSec	INTEGER
}

physicalDiskPerf OBJECT-TYPE
	SYNTAX PhysicalDiskPerf
	ACCESS not-accessible
	STATUS mandatory
	DESCRIPTION 
		"This entry contains information about each performance counter of a physical disk drive."
	INDEX { physicalDiskId }
	::= { physicalDiskPerfTbl 1 }

physicalDiskId		OBJECT-TYPE
	SYNTAX INTEGER
	ACCESS read-only
	STATUS mandatory
	DESCRIPTION 
		"This entry is the index for physical disk drives starting from 1.  A 0 value will report an average value of all physical disk drives."
	::= { physicalDiskPerf 1 }

avgBytesPerRead 	OBJECT-TYPE
	SYNTAX INTEGER
	ACCESS read-only
	STATUS mandatory
	DESCRIPTION 
		"This entry is the average number of bytes transferred from the disk during read operations."
	::= { physicalDiskPerf 2 }

avgBytesPerWrite	OBJECT-TYPE
	SYNTAX INTEGER
	ACCESS read-only
	STATUS mandatory
	DESCRIPTION 
		"This entry is the average number of bytes transferred to the disk during write operations."
	::= { physicalDiskPerf 3 }

avgBytesPerTransfer	OBJECT-TYPE
	SYNTAX INTEGER
	ACCESS read-only
	STATUS mandatory
	DESCRIPTION 
		"This entry is the average number of bytes transferred to or from the disk during write or read operations."
	::= { physicalDiskPerf 4 }

avgSecPerRead		OBJECT-TYPE
	SYNTAX INTEGER
	ACCESS read-only
	STATUS mandatory
	DESCRIPTION 
		"This entry is the average time in seconds of a read of data from the disk."
	::= { physicalDiskPerf 5 }

avgSecPerWrite		OBJECT-TYPE
	SYNTAX INTEGER
	ACCESS read-only
	STATUS mandatory
	DESCRIPTION 
		"This entry is the average time in seconds of a write of data to the disk."
	::= { physicalDiskPerf 6 }

avgSecPerTransfer	OBJECT-TYPE
	SYNTAX INTEGER
	ACCESS read-only
	STATUS mandatory
	DESCRIPTION 
		"This entry is the time in seconds of the average disk transfer."
	::= { physicalDiskPerf 7 }

diskReadBytesPerSec	OBJECT-TYPE
	SYNTAX INTEGER
	ACCESS read-only
	STATUS mandatory
	DESCRIPTION 
		"This entry is the number of bytes transferred from the disk during read operations per second."
	::= { physicalDiskPerf 8 }

diskWriteBytesPerSec	OBJECT-TYPE
	SYNTAX INTEGER
	ACCESS read-only
	STATUS mandatory
	DESCRIPTION 
		"This entry is the number of bytes transferred to the disk during write operations per second."
	::= { physicalDiskPerf 9 }

diskBytesPerSec 	OBJECT-TYPE
	SYNTAX INTEGER
	ACCESS read-only
	STATUS mandatory
	DESCRIPTION 
		"This entry is the number of bytes transferred to or from the disk during write or read operations per second."
	::= { physicalDiskPerf 10 }

diskReadPerSec		OBJECT-TYPE
	SYNTAX INTEGER
	ACCESS read-only
	STATUS mandatory
	DESCRIPTION 
		"This entry is the number of read operations on the disk per second."
	::= { physicalDiskPerf 11 }

diskWritePerSec 	OBJECT-TYPE
	SYNTAX INTEGER
	ACCESS read-only
	STATUS mandatory
	DESCRIPTION 
		"This entry is the number of write operations on the disk per second."
	::= { physicalDiskPerf 12 }

diskTransferPerSec	OBJECT-TYPE
	SYNTAX INTEGER
	ACCESS read-only
	STATUS mandatory
	DESCRIPTION 
		"This entry is the number of read and write operations on the disk per second."
	::= { physicalDiskPerf 13 }

-- LogicalDisk Performance { ntPerf 6 }
--
LogicalDiskPerf 	::= SEQUENCE {
	logicalDiskId		INTEGER,
	lavgBytesPerRead 	INTEGER,
	lavgBytesPerWrite	INTEGER,
	lavgBytesPerTransfer	INTEGER,
	lavgSecPerRead		INTEGER,
	lavgSecPerWrite		INTEGER,
	lavgSecPerTransfer	INTEGER,
	ldiskReadBytesPerSec	INTEGER,
	ldiskWriteBytesPerSec	INTEGER,
	ldiskBytesPerSec 	INTEGER,
	ldiskReadPerSec		INTEGER,
	ldiskWritePerSec 	INTEGER,
	ldiskTransferPerSec	INTEGER
}

logicalDiskPerf OBJECT-TYPE
	SYNTAX LogicalDiskPerf
	ACCESS not-accessible
	STATUS mandatory
	DESCRIPTION 
		"This entry contains information about each performance counter of a logical disk drive."
	INDEX { logicalDiskId }
	::= { logicalDiskPerfTbl 1 }

logicalDiskId		OBJECT-TYPE
	SYNTAX INTEGER
	ACCESS read-only
	STATUS mandatory
	DESCRIPTION 
		"This entry is the index for logical disk drives starting from 1.  A 0 value will report an average value of all physical disk drives."
	::= { logicalDiskPerf 1 }

lavgBytesPerRead 	OBJECT-TYPE
	SYNTAX INTEGER
	ACCESS read-only
	STATUS mandatory
	DESCRIPTION 
		"This entry is the average number of bytes transferred from the disk during read operations."
	::= { logicalDiskPerf 2 }

lavgBytesPerWrite	OBJECT-TYPE
	SYNTAX INTEGER
	ACCESS read-only
	STATUS mandatory
	DESCRIPTION 
		"This entry is the average number of bytes transferred to the disk during write operations."
	::= { logicalDiskPerf 3 }

lavgBytesPerTransfer	OBJECT-TYPE
	SYNTAX INTEGER
	ACCESS read-only
	STATUS mandatory
	DESCRIPTION 
		"This entry is the average number of bytes transferred to or from the disk during write or read operations."
	::= { logicalDiskPerf 4 }

lavgSecPerRead		OBJECT-TYPE
	SYNTAX INTEGER
	ACCESS read-only
	STATUS mandatory
	DESCRIPTION 
		"This entry is the average time in seconds of a read of data from the disk."
	::= { logicalDiskPerf 5 }

lavgSecPerWrite		OBJECT-TYPE
	SYNTAX INTEGER
	ACCESS read-only
	STATUS mandatory
	DESCRIPTION 
		"This entry is the average time in seconds of a write of data to the disk."
	::= { logicalDiskPerf 6 }

lavgSecPerTransfer	OBJECT-TYPE
	SYNTAX INTEGER
	ACCESS read-only
	STATUS mandatory
	DESCRIPTION 
		"This entry is the time in seconds of the average disk transfer."
	::= { logicalDiskPerf 7 }

ldiskReadBytesPerSec	OBJECT-TYPE
	SYNTAX INTEGER
	ACCESS read-only
	STATUS mandatory
	DESCRIPTION 
		"This entry is the number of bytes transferred from the disk during read operations per second."
	::= { logicalDiskPerf 8 }

ldiskWriteBytesPerSec	OBJECT-TYPE
	SYNTAX INTEGER
	ACCESS read-only
	STATUS mandatory
	DESCRIPTION 
		"This entry is the number of bytes transferred to the disk during write operations per second."
	::= { logicalDiskPerf 9 }

ldiskBytesPerSec 	OBJECT-TYPE
	SYNTAX INTEGER
	ACCESS read-only
	STATUS mandatory
	DESCRIPTION 
		"This entry is the number of bytes transferred to or from the disk during write or read operations per second."
	::= { logicalDiskPerf 10 }

ldiskReadPerSec		OBJECT-TYPE
	SYNTAX INTEGER
	ACCESS read-only
	STATUS mandatory
	DESCRIPTION 
		"This entry is the number of read operations on the disk per second."
	::= { logicalDiskPerf 11 }

ldiskWritePerSec 	OBJECT-TYPE
	SYNTAX INTEGER
	ACCESS read-only
	STATUS mandatory
	DESCRIPTION 
		"This entry is the number of write operations on the disk per second."
	::= { logicalDiskPerf 12 }

ldiskTransferPerSec	OBJECT-TYPE
	SYNTAX INTEGER
	ACCESS read-only
	STATUS mandatory
	DESCRIPTION 
		"This entry is the number of read and write operations on the disk per second."
	::= { logicalDiskPerf 13 }

-- End of Performance Information

serverLocalTime    OBJECT-TYPE
        SYNTAX DisplayString
        ACCESS read-only
        STATUS mandatory
        DESCRIPTION
                "This field shows the real local time on each server."
        ::= { serverEnvrm 66 }

-- numberOfProcess    OBJECT-TYPE
--        SYNTAX INTEGER
--        ACCESS read-only
--        STATUS mandatory
--        DESCRIPTION
--                "This field shows the number of entries in the
--loginUserTable."         ::= { serverEnvrm 67 }
--
--processTable  OBJECT-TYPE
--        SYNTAX SEQUENCE OF ProcessData
--        ACCESS not-accessible
--        STATUS mandatory
--        DESCRIPTION
--                "This entry is a table containing information about all
--logged in users."         ::= { serverEnvrm 68 }
--
--processes   OBJECT-TYPE
--        SYNTAX ProcessData
--        ACCESS not-accessible
--        STATUS mandatory
--        DESCRIPTION
--                "This entry shows information about each logged in user."
        --INDEX  { INTEGER }
--        ::= { processTable 1 }
--
--ProcessData ::= SEQUENCE {
--        processOwnerName       DisplayString,
--        processID              INTEGER,
--        processParentID        INTEGER,
--        processCommandLine     DisplayString,
--        processStartTime       INTEGER
--}

--processOwnerName   OBJECT-TYPE
--        SYNTAX DisplayString
--        ACCESS read-only
--        STATUS mandatory
--        DESCRIPTION
--                "This entry shows the user's name of this process."
--        ::= { processes 1 }
--
--processID       OBJECT-TYPE
--        SYNTAX INTEGER
--        ACCESS read-only
--        STATUS mandatory
--        DESCRIPTION
--                "This entry shows the process ID."
--        ::= { processes 2 }
--
--processParentID       OBJECT-TYPE
--        SYNTAX INTEGER
--        ACCESS read-only
--        STATUS mandatory
--        DESCRIPTION
--                "This entry shows the parent process ID."
--        ::= { processes 3 }
--
--processCommandLine       OBJECT-TYPE
--        SYNTAX DisplayString
--        ACCESS read-only
--        STATUS mandatory
--        DESCRIPTION
--                "This entry shows the command line of this process."
--        ::= { processes 4 }

--processStartTime       OBJECT-TYPE
--        SYNTAX INTEGER
--        ACCESS read-only
--        STATUS mandatory
--        DESCRIPTION
--                "This entry shows the process's starting time."
--        ::= { processes 5 }

-- End of Performance Information

osType OBJECT-TYPE
        SYNTAX INTEGER {
                netWare    (0),
                scoUnix    (1),
                windowsNt  (2),
                unixWare   (3)
        }
        ACCESS read-only
        STATUS mandatory
        DESCRIPTION
                "This entry displays the server's operating system:
                0 = NetWare
                1 = SCO UNIX
                2 = Windows NT
                3 = UnixWare"
        ::= { asmsystem 1 }

asmHardware OBJECT-TYPE
        SYNTAX INTEGER
        ACCESS read-only
        STATUS mandatory
        DESCRIPTION
                "This shows whether or not the system supports ASM
                proprietary hardware:
                0 = NO
                1 = YES"
        ::= { asmsystem 2 }

asmDmiVersion OBJECT-TYPE
        SYNTAX INTEGER
        ACCESS read-only
        STATUS mandatory
        DESCRIPTION
                "This entry shows the Acer DMI BIOS version number:
                     0 = not supported
                     110 = version 1.1
                     200 = version 2.0"
        ::= { asmsystem 3 }

asmHW   OBJECT IDENTIFIER ::= { asmsystem 4 }
--
-- ASM Hardware Objects
--

numberOfFans OBJECT-TYPE
        SYNTAX INTEGER
        ACCESS read-only
        STATUS mandatory
        DESCRIPTION
                "This entry shows the number of fans installed."
        ::= { asmHW 1 }

numberOfThermometers OBJECT-TYPE
        SYNTAX INTEGER
        ACCESS read-only
        STATUS mandatory
        DESCRIPTION
            "This entry shows the number of system thermometers installed."
        ::= { asmHW 2 }

numberOfVoltages OBJECT-TYPE
        SYNTAX INTEGER
        ACCESS read-only
        STATUS mandatory
        DESCRIPTION
                "This entry shows the number of voltage sensors installed."
        ::= { asmHW 3 }

numberOfBusCounters OBJECT-TYPE
        SYNTAX INTEGER
        ACCESS read-only
        STATUS mandatory
        DESCRIPTION
                "This entry shows the number of bus utilization counters."
        ::= { asmHW 4 }

numberOfCpuSlot OBJECT-TYPE
		SYNTAX INTEGER
		ACCESS read-only
		STATUS mandatory
		DESCRIPTION
		"This entry shows the number of CPU slots: 0 = unknown
		1-8 = number of CPU slots."
		::= { asmHW 10 }

chassisIntrusion OBJECT-TYPE
                SYNTAX INTEGER
                ACCESS read-only
                STATUS mandatory
                DESCRIPTION
                        "The status of chassis intrusion:
                        -1 = Not supported,
                         0 = normal,
                         1 = abnormal."
                ::= { asmHW 7 }

fuseStatus OBJECT-TYPE
        SYNTAX INTEGER
        ACCESS read-only
        STATUS mandatory
        DESCRIPTION
                "This entry displays the status of fuses. Each bit indicates
                separate status of one fuse, 1 is failed, 0 is noraml.
                If system has no fuse at all, the entry shows -1.
                 bit0: Keyboard/Mouse fuse
                 bit1: USB1 fuse
                 bit2: USB2 fuse
                 bit3: SCSI1 fuse
                 bit4: SCSI2 fuse"
        ::= { asmHW 8 }

redundantPowerSupplyStatus OBJECT-TYPE
                SYNTAX INTEGER
                ACCESS read-only
                STATUS mandatory
                DESCRIPTION
                "This entry displays the status of redundant power subsystem.
                If system has no such equipment installed, bit31 of this value will be set to 1.
                Bit 0: power supply 1 status, 1=OK
                Bit 1: power supply 2 status, 1=OK
                Bit 2: power supply 1 fan status, 1=OK Bit 3: power supply 2 fan status, 1=OK Bit 4: power supply 1 present, 1=YES Bit 5: power supply 2 present, 1=YES"
                ::= { asmHW 9 }

fanTable        OBJECT-TYPE
        SYNTAX SEQUENCE OF FanInfo
        ACCESS not-accessible
        STATUS mandatory
        DESCRIPTION
            "This entry is a table containing information about all fans."
        ::= { asmHW 11 }

fanInfo OBJECT-TYPE
        SYNTAX FanInfo
        ACCESS not-accessible
        STATUS mandatory
        DESCRIPTION
                "This entry contains information about each fan."
        --INDEX  { INTEGER }
        ::= { fanTable 1 }

FanInfo ::= SEQUENCE {
        fanLocation     DisplayString,
        fanStatus       INTEGER
}

fanLocation     OBJECT-TYPE
        SYNTAX DisplayString
        ACCESS read-only
        STATUS mandatory
        DESCRIPTION
                "This entry shows the fan's location in the server system,
                e.g. 'CPU1', 'CPU2' or 'HOUSING'."
        ::= { fanInfo 1 }

fanStatus       OBJECT-TYPE
        SYNTAX INTEGER
        ACCESS read-only
        STATUS mandatory
        DESCRIPTION
        "This entry displays the fan's working status:  0=normal 1=abnormal.
        When the fan is not rotating or is not installed, the status will be
        considered abnormal."
        ::= { fanInfo 2 }


fanRPM  OBJECT-TYPE
                SYNTAX INTEGER
                ACCESS read-only
                STATUS optional
                DESCRIPTION
                "This entry displays the fan's rotation speed in RPM.
                If the fan doesn't provide RPM information, the value will be -1."
                ::= { fanInfo 3 }

thermometerTable        OBJECT-TYPE
        SYNTAX SEQUENCE OF ThermometerInfo
        ACCESS not-accessible
        STATUS mandatory
        DESCRIPTION
                "This entry is a table containing information about all
                system thermometers installed."
        ::= { asmHW 12 }

thermometerInfo OBJECT-TYPE
        SYNTAX ThermometerInfo
        ACCESS not-accessible
        STATUS mandatory
        DESCRIPTION
                "This entry contains information about each thermometer."
        --INDEX  { INTEGER }
        ::= { thermometerTable 1 }

ThermometerInfo ::= SEQUENCE {
        thermometerLocation     DisplayString,
        thermometerDegree       INTEGER
}

thermometerLocation     OBJECT-TYPE
        SYNTAX DisplayString
        ACCESS read-only
        STATUS mandatory
        DESCRIPTION
                "This entry shows the thermometer's location in the server
                system, e.g. 'CPU1', 'CPU2' or 'SYSTEM'."
        ::= { thermometerInfo 1 }

thermometerDegree       OBJECT-TYPE
        SYNTAX INTEGER
        ACCESS read-only
        STATUS mandatory
        DESCRIPTION
                "This entry displays the thermometer reading. Values
                displayed have to be divided by ten (10) to show the
                temperature in degrees Celsius. For example, a reading
                of 305 means that the temperature is at 30.5 degrees
                Celsius."
        ::= { thermometerInfo 2 }


voltageTable    OBJECT-TYPE
        SYNTAX SEQUENCE OF VoltageInfo
        ACCESS not-accessible
        STATUS mandatory
        DESCRIPTION
                "This entry is a table containing information about all
                voltage sensors installed."
        ::= { asmHW 13 }

voltageInfo OBJECT-TYPE
        SYNTAX VoltageInfo
        ACCESS not-accessible
        STATUS mandatory
        DESCRIPTION
                "This entry contains information about each voltage sensor."
        --INDEX  { INTEGER }
        ::= { voltageTable 1 }

VoltageInfo ::= SEQUENCE {
        voltageLocation DisplayString,
        currentVoltage  INTEGER,
        validVoltage    INTEGER,
        maxVoltage      INTEGER,
        minVoltage      INTEGER
}

voltageLocation OBJECT-TYPE
        SYNTAX DisplayString
        ACCESS read-only
        STATUS mandatory
        DESCRIPTION
        "This entry shows the voltage sensor's location in the server
        system, e.g. 'CPU1', 'CPU2' or 'SYSTEM'."
        ::= { voltageInfo 1 }

currentVoltage  OBJECT-TYPE
        SYNTAX INTEGER
        ACCESS read-only
        STATUS mandatory
        DESCRIPTION
        "This entry displays the current voltage reading in milli-volts."
        ::= { voltageInfo 2 }

validVoltage    OBJECT-TYPE
        SYNTAX INTEGER
        ACCESS read-only
        STATUS mandatory
        DESCRIPTION
        "This entry displays the ideal voltage reading in milli-volts."
        ::= { voltageInfo 3 }

maxVoltage      OBJECT-TYPE
        SYNTAX INTEGER
        ACCESS read-only
        STATUS mandatory
        DESCRIPTION
                "This entry displays the maximum safe operating voltage in
                milli-volts. If the voltage goes above this value, the system
                may not work properly."
        ::= { voltageInfo 4 }

minVoltage      OBJECT-TYPE
        SYNTAX INTEGER
        ACCESS read-only
        STATUS mandatory
        DESCRIPTION
                "This entry displays the minimum safe operating voltage in
                milli-volts. If the voltage goes below this value, the system
                may not work properly."
        ::= { voltageInfo 5 }

busCounterTable OBJECT-TYPE
        SYNTAX SEQUENCE OF BusCounterInfo
        ACCESS not-accessible
        STATUS mandatory
        DESCRIPTION
                "This entry is a table containing information about all bus
                utilization counters installed."
        ::= { asmHW 14 }

busCounterInfo OBJECT-TYPE
        SYNTAX BusCounterInfo
        ACCESS not-accessible
        STATUS mandatory
        DESCRIPTION
                "This entry contains information about each bus utilization
                counter."
        --INDEX  { INTEGER }
        ::= { busCounterTable 1 }

BusCounterInfo ::= SEQUENCE {
        busCounterLocation      DisplayString,
        busUtilization          INTEGER
}

busCounterLocation      OBJECT-TYPE
        SYNTAX DisplayString
        ACCESS read-only
        STATUS mandatory
        DESCRIPTION
                "The system bus monitored by the counter
                 e.g. 'PCI1', 'PCI2', 'EISA1' or 'EISA2'."
        ::= { busCounterInfo 1 }

busUtilization          OBJECT-TYPE
        SYNTAX INTEGER
        ACCESS read-only
        STATUS mandatory
        DESCRIPTION
                "This entry displays the bus utilization. Values displayed
                have to be divided by one hundred (100) to show the percentage
                of bus utilization. For example, a reading of 1234 means that
                bus utilization is at 12.34%."
        ::= { busCounterInfo 2 }

cpuSlotStatus OBJECT-TYPE
		SYNTAX INTEGER
		ACCESS read-only
		STATUS mandatory
		DESCRIPTION
		"This entry is partitioned into nibbles, each shows status 
		of one CPU slot:
		bit0: CPU is present
		bit1: CPU is enabled
		bit2: CPU error (IERR#, Thermtrip# issued)."
		::= { asmHW 17 }

---
--- UPS and Front Panel Controller
---
asmUPS  OBJECT-TYPE
        SYNTAX INTEGER
        ACCESS read-only
        STATUS mandatory
        DESCRIPTION
                "This entry shows the UPS device condition:
                1 = server with UPS device
                0 = server without UPS device"
        ::= { asmHW 5 }

asmUPSInfo   OBJECT IDENTIFIER ::= { asmHW 15 }

upsPower1Exist      OBJECT-TYPE
        SYNTAX INTEGER
        ACCESS read-only
        STATUS mandatory
        DESCRIPTION
                "This entry shows the power supply condition:
                1 = power supply #1 exists
                0 = power supply #1 doesn't exist."
        ::= { asmUPSInfo 1 }

upsPower2Exist      OBJECT-TYPE
        SYNTAX INTEGER
        ACCESS read-only
        STATUS mandatory
        DESCRIPTION
                "This entry shows the power supply condition:
                1 = power supply #2 exists
                0 = power supply #2 doesn't exist."
        ::= { asmUPSInfo 2 }

upsPower3Exist      OBJECT-TYPE
        SYNTAX INTEGER
        ACCESS read-only
        STATUS mandatory
        DESCRIPTION
                "This entry shows the power supply condition:
                1 = power supply #3 exists
                0 = power supply #3 doesn't exist."
        ::= { asmUPSInfo 3 }

upsPower1Status      OBJECT-TYPE
        SYNTAX INTEGER
        ACCESS read-only
        STATUS mandatory
        DESCRIPTION
                "This entry shows the power supply condition:
                0 = power supply #1 is abnormal
                1 = power supply #1 is normal."
        ::= { asmUPSInfo 4 }

upsPower2Status      OBJECT-TYPE
        SYNTAX INTEGER
        ACCESS read-only
        STATUS mandatory
        DESCRIPTION
                "This entry shows the power supply condition:
                0 = power supply #2 is abnormal
                1 = power supply #2 is normal."
        ::= { asmUPSInfo 5 }

upsPower3Status      OBJECT-TYPE
        SYNTAX INTEGER
        ACCESS read-only
        STATUS mandatory
        DESCRIPTION
                "This entry shows the power supply condition:
                0 = power supply #3 is abnormal
                1 = power supply #3 is normal."
        ::= { asmUPSInfo 6 }

upsBatteryExist      OBJECT-TYPE
        SYNTAX INTEGER
        ACCESS read-only
        STATUS mandatory
        DESCRIPTION
                "This entry shows the battery condition:
                1 = battery exists
                0 = battery doesn't exist."
        ::= { asmUPSInfo 7 }

upsBatteryStatus      OBJECT-TYPE
        SYNTAX INTEGER
        ACCESS read-only
        STATUS mandatory
        DESCRIPTION
                "This entry shows the power supply condition:
                0 = power supply #3 is abnormal
                1 = power supply #3 is normal."
        ::= { asmUPSInfo 8 }

upsACStatus      OBJECT-TYPE
        SYNTAX INTEGER
        ACCESS read-only
        STATUS mandatory
        DESCRIPTION
                "This entry shows the AC power condition:
                0 = AC power is abnormal
                1 = AC power is normal."
        ::= { asmUPSInfo 9 }

upsFanStatus      OBJECT-TYPE
        SYNTAX INTEGER
        ACCESS read-only
        STATUS mandatory
        DESCRIPTION
                "This entry shows the fan condition:
                0 = power ups fan is abnormal
                1 = power ups fan is normal."
        ::= { asmUPSInfo 10 }

-- upsBackPlaneBoardAExist      OBJECT-TYPE
--        SYNTAX INTEGER
--        ACCESS read-only
--        STATUS mandatory
--        DESCRIPTION
--                "This entry shows the Back Plane Borad A condition:
--                1 = Back Plane Borad A exists
--                0 = Back Plane Borad A doesn't exist."
--        ::= { asmUPSInfo 11 }
--
-- upsBackPlaneBoardASplitStatus      OBJECT-TYPE
--        SYNTAX INTEGER
--        ACCESS read-only
--        STATUS mandatory
--        DESCRIPTION
--                "This entry shows the Back Plane Borad A Split condition:
--                1 = Back Plane Borad A is in Split mode
--                0 = Back Plane Borad A isn't in Split mode."
--        ::= { asmUPSInfo 12 }

-- upsBackPlaneBoardBExist      OBJECT-TYPE
--        SYNTAX INTEGER
--        ACCESS read-only
--        STATUS mandatory
--        DESCRIPTION
--                "This entry shows the Back Plane Borad B condition:
--                1 = Back Plane Borad B exists
--                0 = Back Plane Borad B doesn't exist."
--        ::= { asmUPSInfo 13 }

-- upsBackPlaneBoardBSplitStatus      OBJECT-TYPE
--        SYNTAX INTEGER
--        ACCESS read-only
--        STATUS mandatory
--        DESCRIPTION
--                "This entry shows the Back Plane Borad B Split condition:
--                1 = Back Plane Borad B is in Split mode
--                0 = Back Plane Borad B isn't in Split mode."
--        ::= { asmUPSInfo 14 }

asmAgentVersion OBJECT-TYPE
        SYNTAX INTEGER
        ACCESS read-only
        STATUS mandatory
        DESCRIPTION
                "This entry shows the ASM Agent version number:
                120 = version 1.2,
                200 = version 2.0, etc."
        ::= { asmsystem 5 }

passwordProtected OBJECT-TYPE
        SYNTAX INTEGER
        ACCESS read-only
        STATUS mandatory
        DESCRIPTION
                "This entry shows if the ASM Agent requires password for SNMP Set:
                1 = YES
                0 = NO"
        ::= { asmsystem 6 }

numberOfTrapTargets OBJECT-TYPE
        SYNTAX INTEGER
        ACCESS read-only
        STATUS mandatory
        DESCRIPTION
                "This entry shows the number of targets of SNMP Trap."
        ::= { asmsystem 7 }

trapTargetTable OBJECT-TYPE
        SYNTAX SEQUENCE OF TrapTargetInfo
        ACCESS not-accessible
        STATUS mandatory
        DESCRIPTION
            "This entry is a table containing information about all trap targets."
        ::= { asmsystem 8 }

trapTargetInfo OBJECT-TYPE
        SYNTAX TrapTargetInfo
        ACCESS not-accessible
        STATUS mandatory
        DESCRIPTION
                "This entry contains information about each trap target.
                Index starts at 0."
        --INDEX  { INTEGER }
        ::= { trapTargetTable 1 }

TrapTargetInfo ::= SEQUENCE {
        targetAddress DisplayString
}

targetAddress OBJECT-TYPE
        SYNTAX DisplayString
        ACCESS read-only
        STATUS mandatory
        DESCRIPTION
                "This entry shows the trap target's IP/IPX address in ASCII format.
                For example,
                00ABCDEF:000000000001  for IPX
                192.9.210.99           for IP "
        ::= { trapTargetInfo 1 }

RdmStatus ::= INTEGER
        {
                notExist(0),
                good(1),
                bad(2),
                disabled(3)
        }

rdmStatus OBJECT-TYPE
        SYNTAX RdmStatus
        ACCESS read-only
        STATUS mandatory
        DESCRIPTION
                "This entry shows the status of RDM daughter board."
        ::= { asmsystem 9 }

healthStatus OBJECT-TYPE
	SYNTAX OCTET STRING (SIZE(4..8))
	ACCESS read-only
	STATUS mandatory
	DESCRIPTION
		"This entry shows the health status of system. Each bit indicates one
		health index"
	::= { asmsystem 10 }

fileTransferPortTCP OBJECT-TYPE
	SYNTAX INTEGER
	ACCESS read-only
	STATUS mandatory
	DESCRIPTION
		"TCP port of FTU deamon. -1=N/A"
	::= { asmsystem 11 }

fileTransferPortIPX OBJECT-TYPE
	SYNTAX INTEGER
	ACCESS read-only
	STATUS mandatory
	DESCRIPTION
		"IPX port of FTU deamon. -1=N/A"
	::= { asmsystem 12 }

fileCommand OBJECT-TYPE
	SYNTAX INTEGER
	ACCESS write-only
	STATUS mandatory
	DESCRIPTION
		"0 : Clear Event Log
		 1 : Update Asset Log
		 2 : Clear Statistics Log
		 3 : Start Statistics recording
		 4 : Stop Statistics recording"
	::= { asmsystem 13 }

disableEventHandling OBJECT-TYPE
	SYNTAX INTEGER
	ACCESS read-write
	STATUS mandatory
	DESCRIPTION
		"If this object is set to non-zero, Agent won't handle any event
		and runs quietly."
	::= { asmsystem 14 }

--                      Alarm Group
trapDescription OBJECT-TYPE
        SYNTAX DisplayString
        ACCESS read-only
        STATUS optional
        DESCRIPTION
                "This entry contains information about the last trap sent."
        ::= { asmalarm 1 }


eventNotificationTable  OBJECT-TYPE
        SYNTAX SEQUENCE OF EventNotification
        ACCESS not-accessible
        STATUS mandatory
        DESCRIPTION
                "This entry is a table containing all event notification settings. "
        ::= { asmalarm 2 }

eventNotification       OBJECT-TYPE
        SYNTAX EventNotification
        ACCESS not-accessible
        STATUS mandatory
        DESCRIPTION
                "This entry contains information about each event notification setting."
        --INDEX  { INTEGER }
        ::= { eventNotificationTable 1 }

EventNotification ::= SEQUENCE {
        asmEventType    INTEGER,
        eventAction     INTEGER,
        eventProgram    DisplayString (SIZE(0..120)),
        eventPager      DisplayString (SIZE(0..40))
}

asmEventType    OBJECT-TYPE
        SYNTAX INTEGER
        ACCESS read-only
        STATUS mandatory
        DESCRIPTION
                "This entry shows the event type:
                 1 : Temperature Warning
                 2 : Temperature Critical
                 3 : ECC Memory 1-Bit-Error
                 4 : ECC Memory Multiple-Bit-Error
                 5 : Fan Stops
                 6 : Voltage Exceeds Safe Range
                 7 : CPU Utilization High
                 8 : BUS Utilization High
                 9 : Memory Utilization High
                 10: Volume or File System Utilization High
                 11: NIC Counters High
                "
        ::= { eventNotification 1 }

eventAction     OBJECT-TYPE
        SYNTAX INTEGER
        ACCESS read-write
        STATUS mandatory
        DESCRIPTION
        "This entry describes the actions to be taken by the agent or station when
        a particular event occurs.
            Station Side:
                Bit 0 : Audio Alarm
                Bit 1 : Flash Title Bar
                Bit 2 : Warning Dialog Box
                Bit 3 : Pager

            Agent Side:
                Bit 16: Broadcasting a message to all login users
                Bit 17: Shutdown the server automatically.
                        File system will first be flushed.
                Bit 19: Launch a user defined program"
        ::= { eventNotification 2 }

eventProgram    OBJECT-TYPE
        SYNTAX DisplayString (SIZE(0..120))
        ACCESS read-write
        STATUS mandatory
        DESCRIPTION
                "This entry shows the command string used to launch a user defined program."
        ::= { eventNotification 3 }

eventPager      OBJECT-TYPE
        SYNTAX DisplayString (SIZE(0..40))
        ACCESS read-write
        STATUS mandatory
        DESCRIPTION
                "This entry shows the pager string including telephone number and pager code."
        ::= { eventNotification 4 }


-- -------------------------------------
--      Trap Type Definitions
-- -------------------------------------
trapTemperatureWarning TRAP-TYPE
        ENTERPRISE asm
        VARIABLES {
                        serverName, trapDescription, eventAction, eventPager
                  }
        DESCRIPTION
                "The agent will send a trap of this type when
                temperatures exceed the first level threshold value."
        ::= 1

trapTemperatureCritical TRAP-TYPE
        ENTERPRISE asm
        VARIABLES {
                        serverName, trapDescription, eventAction, eventPager
                  }
        DESCRIPTION
                "The agent will send a trap of this type when
                temperatures exceed the second level threshold value."
        ::= 2

trapECC1BitError TRAP-TYPE
        ENTERPRISE asm
        VARIABLES {
                        serverName, trapDescription, eventAction, eventPager
                  }
        DESCRIPTION
                "The agent will send a trap of this type when an
                ECC 1-bit error occurs."
        ::= 3

trapECCMBitError TRAP-TYPE
        ENTERPRISE asm
        VARIABLES {
                        serverName, trapDescription, eventAction, eventPager
                  }
        DESCRIPTION
                "The agent will send a trap of this type when an
                ECC multiple-bit error occurs."
        ::= 4

trapFanStop TRAP-TYPE
        ENTERPRISE asm
        VARIABLES {
                        serverName, trapDescription, eventAction, eventPager
                  }
        DESCRIPTION
                "The agent will send a trap of this type when any
                fan stops functioning."
        ::= 5

trapVoltage TRAP-TYPE
        ENTERPRISE asm
        VARIABLES {
                        serverName, trapDescription, eventAction, eventPager
                  }
        DESCRIPTION
                "The agent will send a trap of this type when any
                voltage reading exceeds the safe operating range."
        ::= 6

trapCPUUtilization  TRAP-TYPE
        ENTERPRISE asm
        VARIABLES {
                        serverName, trapDescription, eventAction, eventPager
                  }
        DESCRIPTION
                "The agent will send a trap of this type when percent
                CPU utilization exceeds the threshold value."
        ::= 7

trapBusUtilization TRAP-TYPE
        ENTERPRISE asm
        VARIABLES {
                        serverName, trapDescription, eventAction, eventPager
                  }
        DESCRIPTION
                "The agent will send a trap of this type when percent
                bus utilization exceeds the threshold value."
        ::= 8

trapMemoryUtilization TRAP-TYPE
        ENTERPRISE asm
        VARIABLES {
                        serverName, trapDescription, eventAction, eventPager
                  }
        DESCRIPTION
                "The agent will send a trap of this type when percent
                memory utilization exceeds the threshold value."
        ::= 9

trapVolumeUtilization TRAP-TYPE
        ENTERPRISE asm
        VARIABLES {
                        serverName, trapDescription, eventAction, eventPager
                  }
        DESCRIPTION
                "The agent will send a trap of this type when percent
                volume utilization exceeds the threshold value."
        ::= 10

trapNICCounter TRAP-TYPE
        ENTERPRISE asm
        VARIABLES {
                        serverName, trapDescription, eventAction, eventPager
                  }
        DESCRIPTION
                "The agent will send a trap of this type when any NIC
                statistical counter exceeds the threshold value."
        ::= 11

---
--- UPS Power Subsystem
---
trapPSFail TRAP-TYPE
        ENTERPRISE asm
        VARIABLES {
                        serverName, trapDescription, eventAction, eventPager
                  }
        DESCRIPTION
                "The agent will send a trap of this type when any power supply
                fails."
        ::= 12

trapACFail TRAP-TYPE
        ENTERPRISE asm
        VARIABLES {
                        serverName, trapDescription, eventAction, eventPager
                  }
        DESCRIPTION
                "The agent will send a trap of this type when AC power fails."
        ::= 13

trapPowerFanFail TRAP-TYPE
        ENTERPRISE asm
        VARIABLES {
                        serverName, trapDescription, eventAction, eventPager
                  }
        DESCRIPTION
                "The agent will send a trap of this type when any power
                sub-system fan fails."
        ::= 14

trapBatteryFail TRAP-TYPE
        ENTERPRISE asm
        VARIABLES {
                        serverName, trapDescription, eventAction, eventPager
                  }
        DESCRIPTION
                "The agent will send a trap of this type when UPS battery fails."
        ::= 15

trapChassisIntrusion TRAP-TYPE
        ENTERPRISE asm
        VARIABLES {
                        serverName, trapDescription, eventAction, eventPager
                  }
        DESCRIPTION
                "The agent will send a trap of this type when chassis intrusion occurs."
        ::= 16

trapFuseFail TRAP-TYPE
        ENTERPRISE asm
        VARIABLES {
                        serverName, trapDescription, eventAction, eventPager
                  }
        DESCRIPTION
                "The agent will send a trap of this type when fuse failed."
        ::= 17

trapRPSFail TRAP-TYPE
        ENTERPRISE asm
        VARIABLES {
                        serverName, trapDescription, eventAction, eventPager
                  }
        DESCRIPTION
                "The agent will send a trap of this type when redundant power supply is failed."
        ::= 18

trapRPSFanFail TRAP-TYPE
        ENTERPRISE asm
        VARIABLES {
                        serverName, trapDescription, eventAction, eventPager
                  }
        DESCRIPTION
                "The agent will send a trap of this type when redundant power supply fan is failed."
        ::= 19

trapBiosEventLog TRAP-TYPE
        ENTERPRISE asm
        VARIABLES {
                        serverName, trapDescription, eventAction, eventPager
                  }
        DESCRIPTION
                "The agent will send a trap of this type when bios has new eventlog."
        ::= 20

trapBiosEventLogUtilization TRAP-TYPE
        ENTERPRISE asm
        VARIABLES {
                        serverName, trapDescription, eventAction, eventPager
                  }
        DESCRIPTION
                "The agent will send a trap of this type when bios eventlog utilization exceeds threshold."
        ::= 21

trapCPUAbnormal TRAP-TYPE
        ENTERPRISE asm
        VARIABLES {
                        serverName, trapDescription, eventAction, eventPager
                  }
        DESCRIPTION
                "The agent will send a trap of this type when CPU has internal error."
        ::= 22

trapAssetChange TRAP-TYPE
        ENTERPRISE asm
        VARIABLES {
                        serverName, trapDescription, eventAction, eventPager
                  }
        DESCRIPTION
                "The agent will send a trap of this type when asset is changed."
        ::= 23

END
