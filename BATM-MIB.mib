BATM-MIB DEFINITIONS ::= BEGIN

IMPORTS
     MODULE-IDENTITY, OBJECT-TYPE, enterprises
        FROM SNMPv2-SMI
	; 
          
batm MODULE-IDENTITY
        LAST-UPDATED "200711270000Z"
        ORGANIZATION "BATM Advanced Communication"
        CONTACT-INFO   

        "BATM/Telco Systems Support team
				Email: 
				For North America: techsupport@telco.com
				For North Europe: support@batm.de, info@batm.de
				For the rest of the world: techsupport@telco.com"

        DESCRIPTION
        "Initial version. This MIB provides external-alarm management and notifications"
        
         -- revision history         
        REVISION     "200711270000Z"
         DESCRIPTION
         "Compilation fixes"
         
       ::= { enterprises 2697 }
   
END
