-- file:  traps1.0-09.30.91

SYNOPTICS-TRAP-MIB

-- Trap MIB Release 1.0
-- Revision 9/30/91
-- Printed 9/30/91

-- Copyright 1991 SynOptics Communications, Inc.  All Rights
-- Reserved.  Reproduction of this document is authorized on
-- condition that the foregoing copyright notice is included.
-- This SynOptics SNMP Management Information Base Specification
-- (Specification) embodies SynOptics' confidential and
-- proprietary intellectual property.  SynOptics retains all
-- title and ownership in the Specification, including any
-- revisions.  
--
-- It is SynOptics intent to encourage the widespread use of
-- this Specification in connection with the management of
-- SynOptics products. SynOptics grants vendors, end-users,
-- and other interested parties a non-exclusive license to
-- use this Specification in connection with the management
-- of SynOptics products.
--
-- This Specification is supplied "AS IS," and SynOptics makes
-- no warranty, either express or implied, as to the use,
-- operation, condition, or performance of the Specification.


DEFINITIONS ::= BEGIN

-- SECTION 1: Top Level Definitions

-- Imports

IMPORTS
	snmp, ifIndex, egpNeighAddr
					FROM RFC1213-MIB
	TRAP-TYPE			FROM RFC-1215
	synoptics, s3ChassisPsStatus,
	s3ChassisFanStatus, s3CommonBoardPsStatus
					FROM SYNOPTICS-COMMON-MIB
	s3EnetBoardStatus, s3EnetBoardPsStatus,
	s3EnetPortPartStatus, s3EnetPortJabberStatus,
	s3EnetLocBridgePortOpSts, s3EnetLocBridgeDiagSts,
	s3EnetRemBridgePortOpSts, s3EnetRemBridgeDiagSts,
	s3EnetRouterStandbySts, s3EnetRouterDiagSts
					FROM SYNOPTICS-ETHERNET-MIB
	ieee8023PromRxStatus
					FROM SYNOPTICS-IEEE8023-MIB
	s3TrNmmRingNum, s3TrNodeEntUna,
	s3TrNodeEntBeaconType, s3TrNodeEntPhysDrop
					FROM SYNOPTICS-TOKENRING-MIB;

-- SECTION 2: Generic Trap Definitions


coldStart TRAP-TYPE
	ENTERPRISE	snmp
--	STATUS		mandatory for all SynOptics agents
	DESCRIPTION
		"A coldStart trap signifies that the sending protocol entity 
		is reinitializing itself such that the agent's configuration 
		or the protocol entity implementation may be altered."
	::= 0

warmStart TRAP-TYPE
	ENTERPRISE	snmp
--	STATUS		implemented by TR 3.1 only, not supported in future
	DESCRIPTION
		"A warmStart trap signifies that the sending protocol entity 
		is reinitializing itself such that neither the agent 
		configuration nor the protocol entity implementation is 
		altered."
	::= 1

linkDown TRAP-TYPE
	ENTERPRISE	snmp
	VARIABLES	{ ifIndex }
--	STATUS		not used by TR or Enet
	DESCRIPTION
		"A linkDown trap signifies that the sending protocol entity 
		recognizes a failure in one of the communication links 
		represented in the agent's configuration."
	::= 2

linkUp TRAP-TYPE
	ENTERPRISE	snmp
	VARIABLES	{ ifIndex }
--	STATUS		not used by TR or Enet
	DESCRIPTION
		"A linkUp trap signifies that the sending protocol entity 
		recognizes that one of the communication links represented in 
		the agent's configuration has come up."
	::= 3

authenticationFailure TRAP-TYPE
	ENTERPRISE	snmp
--	STATUS		mandatory for all SynOptics agents
	DESCRIPTION
		"An authenticationFailure trap signifies that the sending 
		protocol entity is the addressee of a protocol message that is
		not properly authenticated. While implementations of the SNMP 
		must be capable of generating this trap, they must also be 
		capable of suppressing the emission of such traps via an 
		implementation-specific mechanism."
	::= 4

egpNeighborLoss TRAP-TYPE
	ENTERPRISE	snmp
	VARIABLES	{ egpNeighAddr }
--	STATUS		mandatory if EGP implemented (routers only)
	DESCRIPTION
		"An egpNeighborLoss trap signifies that an EGP neighbor for 
		whom the sending protocol entity was an EGP peer has been 
		marked down and the peer relationship no longer obtains."
	::= 5

-- SECTION 3: SynOptics Enterprise Trap Definitions



chassisPowerSupplyFailure TRAP-TYPE
	ENTERPRISE	synoptics
	VARIABLES	{ s3ChassisPsStatus }
--	STATUS		mandatory for all SynOptics agents
	DESCRIPTION
		"Concentrator power supply failure."
	::= 0		-- 0x00

chassisFanFailure TRAP-TYPE
	ENTERPRISE	synoptics
	VARIABLES	{ s3ChassisFanStatus }
--	STATUS		mandatory for all SynOptics agents
	DESCRIPTION
		"Concentrator fan failure."
	::= 1		-- 0x01

boardFailure TRAP-TYPE
	ENTERPRISE	synoptics
	VARIABLES	{ s3EnetBoardStatus }
--	STATUS		mandatory for 3.x Ethernet agents.
	DESCRIPTION
		"General board failure detected by Ethernet NMM."
	::= 2		-- 0x02

enetBoardPowerSupplyFailure TRAP-TYPE
	ENTERPRISE	synoptics
	VARIABLES	{ s3EnetBoardPsStatus }
--	STATUS		mandatory for 3.x Ethernet agents.
--				Token ring agents use
--				boardPowerSupplyFailure (27) instead.
	DESCRIPTION
		"Ethernet board power supply failure."
	::= 3		-- 0x03

portAutoPartition TRAP-TYPE
	ENTERPRISE	synoptics
	VARIABLES	{ s3EnetPortPartStatus, s3EnetPortJabberStatus }
--	STATUS		mandatory for all Ethernet agents
	DESCRIPTION
		"Port auto partitions."
	::= 4		-- 0x04

portDTEJabbering TRAP-TYPE
	ENTERPRISE	synoptics
	VARIABLES	{ s3EnetPortJabberStatus }
--	STATUS		mandatory for all Ethernet agents
	DESCRIPTION
		"Ethernet DTE jabbering detected."
	::= 5		-- 0x05

nmmSaturation TRAP-TYPE
	ENTERPRISE	synoptics
	VARIABLES	{ ieee8023PromRxStatus }
--	STATUS		mandatory for 3.x Ethernet agents
	DESCRIPTION
		"NMM is dropping packets due to overload."
	::= 6		-- 0x06

localBridgePortOperationChanged TRAP-TYPE
	ENTERPRISE	synoptics
	VARIABLES	{ s3EnetLocBridgePortOpSts }
--	STATUS		mandatory for 3.x Ethernet agents
	DESCRIPTION
		"Bridge changes from standby <-> operation."
	::= 7		-- 0x07

localBridgeDiagnostic TRAP-TYPE
	ENTERPRISE	synoptics
	VARIABLES	{ s3EnetLocBridgeDiagSts }
--	STATUS		mandatory for 3.x Ethernet agents
	DESCRIPTION
		"NMM detects bridge failure."
	::= 8		-- 0x08

remoteBridgePortOperationChanged TRAP-TYPE
	ENTERPRISE	synoptics
	VARIABLES	{ s3EnetRemBridgePortOpSts }
--	STATUS		mandatory for 3.x Ethernet agents
	DESCRIPTION
		"Bridge changes from standby <-> operation."
	::= 9		-- 0x09

remoteBridgeDiagnostic TRAP-TYPE
	ENTERPRISE	synoptics
	VARIABLES	{ s3EnetRemBridgeDiagSts }
--	STATUS		mandatory for 3.x Ethernet agents
	DESCRIPTION
		"NMM detects remote bridge failure."
	::= 10		-- 0x0a

stationBeacons TRAP-TYPE
	ENTERPRISE	synoptics
	VARIABLES	{ s3TrNmmRingNum, s3TrNodeEntUna, 
			  s3TrNodeEntBeaconType }
--	STATUS		mandatory for all Token Ring agents
	DESCRIPTION
		"Station on the ring is beaconing."
	::= 14		-- 0x0e

newActMonDetect TRAP-TYPE
	ENTERPRISE	synoptics
	VARIABLES	{ s3TrNmmRingNum,
			  s3TrNodeEntUna, s3TrNodeEntPhysDrop }
--	STATUS		mandatory for all Token Ring agents
	DESCRIPTION
		"A new active monitor has been detected."
	::= 22		-- 0x16


boardPowerSupplyFailure TRAP-TYPE
	ENTERPRISE	synoptics
	VARIABLES	{ s3CommonBoardPsStatus }
--	STATUS		mandatory for all Token Ring agents
	DESCRIPTION
		"Board power supply failure."
	::= 27		-- 0x1b

routerOperationChanged TRAP-TYPE
	ENTERPRISE	synoptics
	VARIABLES	{ s3EnetRouterStandbySts }
--	STATUS		mandatory for 3.3 Ethernet agents
	DESCRIPTION
		"Router changes from standby <-> operation."
	::= 33		-- 0x21

routerDiagnostic TRAP-TYPE
	ENTERPRISE	synoptics
	VARIABLES	{ s3EnetRouterDiagSts }
--	STATUS		mandatory for 3.3 Ethernet agents
	DESCRIPTION
		"NMM detects router failure."
	::= 34		-- 0x22

END
