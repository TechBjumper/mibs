--
-- genutil.my
-- MIB generated by MG-SOFT Visual MIB Builder Version 3.0 Build 253
-- Wednesday, May 14, 2003 at 09:10:20
--

    UTILIZATION-MANAGEMENT-MIB DEFINITIONS ::= BEGIN
 
        IMPORTS
            avayaSystemStats            
                FROM AVAYAGEN-MIB            
            Integer32, OBJECT-TYPE, MODULE-IDENTITY            
                FROM SNMPv2-SMI            
            TEXTUAL-CONVENTION            
                FROM SNMPv2-TC;
    
    
--  Referencing the parent branch.
-- August 20, 2002
        genStats MODULE-IDENTITY 
            LAST-UPDATED "190208200000Z"		-- August 20, 1902 at 00:00 GMT
            ORGANIZATION 
                "Avaya's Concord Technology Center (CTC)"
            CONTACT-INFO 
                "Keling Sun -- kelingsun@avaya.com"
            DESCRIPTION 
                "Generic Utilization Mib."
            ::= { avayaSystemStats 1 }
        
    
--
-- Textual conventions
--
    
--  textual conventions
        MBytes ::= TEXTUAL-CONVENTION
            STATUS current
            DESCRIPTION 
                "Storage size, expressed in units of megabytes."
            SYNTAX Integer32
            
    
--
-- Node definitions
--
    
        -- 1.3.6.1.4.1.6889.2.1.11.1.1
        genCpuUtilization OBJECT IDENTIFIER ::= { genStats 1 }
        
        -- 1.3.6.1.4.1.6889.2.1.11.1.1.1
        genCpuUtilizationTable OBJECT-TYPE
            SYNTAX SEQUENCE OF GenCpuUtilizationEntry
            MAX-ACCESS not-accessible
            STATUS current
            DESCRIPTION
                "A list of CPU utilization entries."
            ::= { genCpuUtilization 1 }
        
        -- 1.3.6.1.4.1.6889.2.1.11.1.1.1.1
        genCpuUtilizationEntry OBJECT-TYPE
            SYNTAX GenCpuUtilizationEntry
            MAX-ACCESS not-accessible
            STATUS current
            DESCRIPTION
                "A collection of CPU utilization."
            INDEX { genCpuIndex }
            ::= { genCpuUtilizationTable 1 }
        
        GenCpuUtilizationEntry ::=
            SEQUENCE { 
                genCpuIndex
                    INTEGER,
                genCpuUtilizationEnableMonitoring
                    INTEGER,
                genCpuUtilizationEnableEventGeneration
                    INTEGER,
                genCpuUtilizationHighThreshold
                    INTEGER,
                genCpuAverageUtilization
                    INTEGER,
                genCpuCurrentUtilization
                    INTEGER
             }

        -- 1.3.6.1.4.1.6889.2.1.11.1.1.1.1.1
        genCpuIndex OBJECT-TYPE
            SYNTAX INTEGER
            MAX-ACCESS read-only
            STATUS current
            DESCRIPTION
                "An index that uniquely identifies the CPU."
            ::= { genCpuUtilizationEntry 1 }
        
--  default
        -- 1.3.6.1.4.1.6889.2.1.11.1.1.1.1.2
        genCpuUtilizationEnableMonitoring OBJECT-TYPE
            SYNTAX INTEGER
                {
                disabled(1),
                enabled(2)
                }
            MAX-ACCESS read-write
            STATUS current
            DESCRIPTION
                "Enable or disable CPU utilization monitoring. The default  
                is disabled(1)."
            ::= { genCpuUtilizationEntry 2 }
        
--  default
        -- 1.3.6.1.4.1.6889.2.1.11.1.1.1.1.3
        genCpuUtilizationEnableEventGeneration OBJECT-TYPE
            SYNTAX INTEGER
                {
                disabled(1),
                enabled(2)
                }
            MAX-ACCESS read-write
            STATUS current
            DESCRIPTION
                "Enable or disable event generation for CPU utilization. The default
                is disable (1)."
            ::= { genCpuUtilizationEntry 3 }
        
        -- 1.3.6.1.4.1.6889.2.1.11.1.1.1.1.4
        genCpuUtilizationHighThreshold OBJECT-TYPE
            SYNTAX INTEGER (50..99)
            MAX-ACCESS read-write
            STATUS current
            DESCRIPTION
                "The high threshold of CPU utilization in percentage, which can be 
                from 50% to 99%. If event generation is enabled while the utilization
                is above the threshold, an event will be generated. The default value 
                of this threshold is 95%. No event will be generated when the utilization 
                crosses below the high threshold."
            ::= { genCpuUtilizationEntry 4 }
        
        -- 1.3.6.1.4.1.6889.2.1.11.1.1.1.1.5
        genCpuAverageUtilization OBJECT-TYPE
            SYNTAX INTEGER (0..100)
            MAX-ACCESS read-only
            STATUS current
            DESCRIPTION
                "The curent average CPU utilization in percentage if the 
                monitoring is enabled and full window of results has been captured.
                Sample window is 60 seconds. Number of samples is 12, which results 
                a sample interval of 5 seconds."
            ::= { genCpuUtilizationEntry 5 }
        
        -- 1.3.6.1.4.1.6889.2.1.11.1.1.1.1.6
        genCpuCurrentUtilization OBJECT-TYPE
            SYNTAX INTEGER (0..100)
            MAX-ACCESS read-only
            STATUS obsolete
            DESCRIPTION
                "The current  CPU utilization in percentage if the monitoring is enabled.
                The sample interval is 5 seconds."
            ::= { genCpuUtilizationEntry 6 }
        
        -- 1.3.6.1.4.1.6889.2.1.11.1.1.2
        genCpuUtilizationHistoryTable OBJECT-TYPE
            SYNTAX SEQUENCE OF GenCpuUtilizationHistoryEntry
            MAX-ACCESS not-accessible
            STATUS current
            DESCRIPTION
                "A list of CPU utilization history entries."
            ::= { genCpuUtilization 2 }
        
        -- 1.3.6.1.4.1.6889.2.1.11.1.1.2.1
        genCpuUtilizationHistoryEntry OBJECT-TYPE
            SYNTAX GenCpuUtilizationHistoryEntry
            MAX-ACCESS not-accessible
            STATUS current
            DESCRIPTION
                "A collection of CPU utilization history."
            INDEX { genCpuIndex, genCpuUtilizationHistorySampleIndex }
            ::= { genCpuUtilizationHistoryTable 1 }
        
        GenCpuUtilizationHistoryEntry ::=
            SEQUENCE { 
                genCpuUtilizationHistorySampleIndex
                    INTEGER,
                genCpuHistoryUtilization
                    INTEGER
             }

        -- 1.3.6.1.4.1.6889.2.1.11.1.1.2.1.1
        genCpuUtilizationHistorySampleIndex OBJECT-TYPE
            SYNTAX INTEGER
            MAX-ACCESS read-only
            STATUS current
            DESCRIPTION
                "An index that uniquely identifies the particular sample.
                This index starts at 1 and increases by one as each new 
                sample is taken."
            ::= { genCpuUtilizationHistoryEntry 1 }
        
        -- 1.3.6.1.4.1.6889.2.1.11.1.1.2.1.2
        genCpuHistoryUtilization OBJECT-TYPE
            SYNTAX INTEGER
            MAX-ACCESS read-only
            STATUS current
            DESCRIPTION
                "The cpu utiliztion in percentage of a particular sample.
                The number of samples is 12, which results in a sample 
                interval of 5 seconds. The sample window is 60 seconds."
            ::= { genCpuUtilizationHistoryEntry 2 }
        
        -- 1.3.6.1.4.1.6889.2.1.11.1.2
        genMemUtilization OBJECT IDENTIFIER ::= { genStats 2 }
        
        -- 1.3.6.1.4.1.6889.2.1.11.1.2.1
        genMemUtilizationTotalRAM OBJECT-TYPE
            SYNTAX MBytes
            MAX-ACCESS read-only
            STATUS current
            DESCRIPTION
                "The total size of the ram in MBytes."
            ::= { genMemUtilization 1 }
        
        -- 1.3.6.1.4.1.6889.2.1.11.1.2.2
        genMemUtilizationOperationalImage OBJECT-TYPE
            SYNTAX MBytes
            MAX-ACCESS read-only
            STATUS current
            DESCRIPTION
                "The total size of the operational image in Bytes."
            ::= { genMemUtilization 2 }
        
        -- 1.3.6.1.4.1.6889.2.1.11.1.2.3
        genMemUtilizationDynAllocMem OBJECT IDENTIFIER ::= { genMemUtilization 3 }
        
        -- 1.3.6.1.4.1.6889.2.1.11.1.2.3.1
        genMemUtilizationDynAllocMemUsed OBJECT-TYPE
            SYNTAX MBytes
            MAX-ACCESS read-only
            STATUS current
            DESCRIPTION
                "The dynamically allocated memory has been used in Bytes."
            ::= { genMemUtilizationDynAllocMem 1 }
        
        -- 1.3.6.1.4.1.6889.2.1.11.1.2.3.2
        genMemUtilizationDynAllocMemMaxUsed OBJECT-TYPE
            SYNTAX MBytes
            MAX-ACCESS read-only
            STATUS current
            DESCRIPTION
                "The dynamically allocated memory has been used maximally in Bytes."
            ::= { genMemUtilizationDynAllocMem 2 }
        
        -- 1.3.6.1.4.1.6889.2.1.11.1.2.3.3
        genMemUtilizationDynAllocMemAvailable OBJECT-TYPE
            SYNTAX MBytes
            MAX-ACCESS read-only
            STATUS current
            DESCRIPTION
                "The available dynamically allocated memory in Bytes."
            ::= { genMemUtilizationDynAllocMem 3 }
        
        -- 1.3.6.1.4.1.6889.2.1.11.1.2.4
        genMemUtilizationAllocationFailures OBJECT-TYPE
            SYNTAX MBytes
            MAX-ACCESS read-only
            STATUS current
            DESCRIPTION
                "The total number of the memory that fails allocation."
            ::= { genMemUtilization 4 }
        
        -- 1.3.6.1.4.1.6889.2.1.11.1.2.5
        genMemUtilizationSysRAMTrap OBJECT IDENTIFIER ::= { genMemUtilization 5 }
        
        -- 1.3.6.1.4.1.6889.2.1.11.1.2.5.1
        genMemUtilizationSysRAMNotificationHighWaterMark OBJECT-TYPE
            SYNTAX MBytes
            MAX-ACCESS read-write
            STATUS current
            DESCRIPTION
                "The high water mark for ram allocation in Bytes. If this value has 
                been exceeded, a trap will be generated. This value can't be higher 
                than Total System RAM."
            ::= { genMemUtilizationSysRAMTrap 1 }
        
        -- 1.3.6.1.4.1.6889.2.1.11.1.2.6
        genMemUtilizationTable OBJECT-TYPE
            SYNTAX SEQUENCE OF GenMemUtilizationEntry
            MAX-ACCESS not-accessible
            STATUS current
            DESCRIPTION
                "Memory Utilization by module in stack or blade in modular solution"
            ::= { genMemUtilization 6 }
        
        -- 1.3.6.1.4.1.6889.2.1.11.1.2.6.1
        genMemUtilizationEntry OBJECT-TYPE
            SYNTAX GenMemUtilizationEntry
            MAX-ACCESS not-accessible
            STATUS current
            DESCRIPTION
                "Memory Utilization Table indexed by Module ID"
            INDEX { genMemUtilizationID  }
            ::= { genMemUtilizationTable 1 }
        
        GenMemUtilizationEntry ::=
            SEQUENCE { 
                genMemUtilizationID
                    INTEGER,
                genMemUtilizationPhyRam
                    MBytes,
                genMemUtilizationPercentUsed
                    INTEGER
             }

        -- 1.3.6.1.4.1.6889.2.1.11.1.2.6.1.1
        genMemUtilizationID OBJECT-TYPE
            SYNTAX INTEGER (1..20)
            MAX-ACCESS not-accessible
            STATUS current
            DESCRIPTION
                "Module/Blade/SubAgent ID index"
            ::= { genMemUtilizationEntry 1 }
        
        -- 1.3.6.1.4.1.6889.2.1.11.1.2.6.1.2
        genMemUtilizationPhyRam OBJECT-TYPE
            SYNTAX MBytes
            MAX-ACCESS read-only
            STATUS current
            DESCRIPTION
                "The total size of the physical ram in Bytes."
            ::= { genMemUtilizationEntry 2 }
        
        -- 1.3.6.1.4.1.6889.2.1.11.1.2.6.1.3
        genMemUtilizationPercentUsed OBJECT-TYPE
            SYNTAX INTEGER (0..100)
            MAX-ACCESS read-only
            STATUS current
            DESCRIPTION
                "The percenatge of memory used."
            ::= { genMemUtilizationEntry 3 }
        
    
    END

--
-- genutil.my
--
