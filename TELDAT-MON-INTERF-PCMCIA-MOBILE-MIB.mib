-- Teldat, S.A.

                -- Parque Tecnolgico de Madrid

                -- 28760, Tres Cantos (Madrid)

                -- Tlf: +34-918076565

                -- Fax: +34-918076521

                -- e-mail: id@teldat.com


            -- MIB privada de Teldat

            -- Monitorizacin del interfaz PCMCIA Mobile


    -- Historial:
    --      07-02-14    M.A. Pastor     XH 3523. Errors with HP Openview 9.20
    -- 1.3  11-01-13    E. Amorena      XH 2610. MIBs compilation.
    -- 1.2  20-11-08    P. Nogueira     Variables obsoletas
    -- 1.1  26-06-08    FDMB            Incluido SIM ICC
    -- 1.0  17-07-07    M.A. Berrojo    Implementacin inicial
--------------------------------------------------------------------------------

TELDAT-MON-INTERF-PCMCIA-MOBILE-MIB DEFINITIONS ::= BEGIN

IMPORTS
    OBJECT-TYPE
        FROM RFC-1212
    DisplayString
        FROM RFC1213-MIB
    telProdNpMonInterfRouter
        FROM TELDAT-SW-STRUCTURE-MIB;


-- Monitorizacin privada del interfaz PCMCIA-MOBILE

telProdNpMonInterfPCMCIAMobile OBJECT IDENTIFIER ::= { telProdNpMonInterfRouter 19 }


--  = = = = = = = = = = = = = = = = = = = = = = = = = = = = = = = = = = = = = =
--  Global PCMCIAMobile monitoring variables
--  = = = = = = = = = = = = = = = = = = = = = = = = = = = = = = = = = = = = = =


--  = = = = = = = = = = = = = = = = = = = = = = = = = = = = = = = = = = = = = =
--  Global Info PCMCIAMobile monitoring variables
--  = = = = = = = = = = = = = = = = = = = = = = = = = = = = = = = = = = = = = =

teldatPCMCIAMobileInfoInterfaceTable OBJECT-TYPE
    SYNTAX  SEQUENCE OF TeldatPCMCIAMobileInfoInterfaceEntry
    ACCESS  not-accessible
    STATUS  mandatory
    DESCRIPTION
        "Table of information available for PCMCIAMobile interfaces.
        Each row represents an interface"
    ::= { telProdNpMonInterfPCMCIAMobile 1 }

teldatPCMCIAMobileInfoInterfaceEntry OBJECT-TYPE
    SYNTAX  TeldatPCMCIAMobileInfoInterfaceEntry
    ACCESS  not-accessible
    STATUS  mandatory
    DESCRIPTION
        "A base list of objects that are information about a PCMCIAMobile interface.
        The inex is the number of the interface"
    INDEX   { teldatPCMCIAMobileInfoInterfaceIndex }
    ::= { teldatPCMCIAMobileInfoInterfaceTable 1 }

TeldatPCMCIAMobileInfoInterfaceEntry ::= SEQUENCE
{
    teldatPCMCIAMobileInfoInterfaceIndex                INTEGER,
    teldatPCMCIAMobileInfoInterfaceModuleManufacturer   DisplayString,
    teldatPCMCIAMobileInfoInterfaceModuleModel          DisplayString,
    teldatPCMCIAMobileInfoInterfaceModuleFirmware       DisplayString,
    teldatPCMCIAMobileInfoInterfaceModuleIMEI           DisplayString,
    teldatPCMCIAMobileInfoInterfaceModuleIMSI           DisplayString,
    teldatPCMCIAMobileInfoInterfaceSIMId                DisplayString,
    teldatPCMCIAMobileInfoInterfaceSIMIcc               DisplayString
}

teldatPCMCIAMobileInfoInterfaceIndex OBJECT-TYPE
    SYNTAX  INTEGER(1 .. 255)
    ACCESS  read-only
    STATUS  mandatory
    DESCRIPTION
        "Interface index"
    ::= { teldatPCMCIAMobileInfoInterfaceEntry 1 }

teldatPCMCIAMobileInfoInterfaceModuleManufacturer OBJECT-TYPE
    SYNTAX  DisplayString
    ACCESS  read-only
    STATUS  mandatory
    DESCRIPTION
        "PCMCIAMobile module manufacturer."
    ::={ teldatPCMCIAMobileInfoInterfaceEntry 2 }

teldatPCMCIAMobileInfoInterfaceModuleModel OBJECT-TYPE
    SYNTAX  DisplayString
    ACCESS  read-only
    STATUS  mandatory
    DESCRIPTION
        "PCMCIAMobile module model."
    ::={ teldatPCMCIAMobileInfoInterfaceEntry 3 }

teldatPCMCIAMobileInfoInterfaceModuleFirmware OBJECT-TYPE
    SYNTAX  DisplayString
    ACCESS  read-only
    STATUS  mandatory
    DESCRIPTION
        "PCMCIAMobile module firmware release."
    ::={ teldatPCMCIAMobileInfoInterfaceEntry 4 }

teldatPCMCIAMobileInfoInterfaceModuleIMEI OBJECT-TYPE
    SYNTAX  DisplayString
    ACCESS  read-only
    STATUS  mandatory
    DESCRIPTION
        "PCMCIAMobile module IMEI."
    ::={ teldatPCMCIAMobileInfoInterfaceEntry 5 }

teldatPCMCIAMobileInfoInterfaceModuleIMSI OBJECT-TYPE
    SYNTAX  DisplayString
    ACCESS  read-only
    STATUS  mandatory
    DESCRIPTION
        "PCMCIAMobile module IMSI."
    ::={ teldatPCMCIAMobileInfoInterfaceEntry 6 }

teldatPCMCIAMobileInfoInterfaceSIMId OBJECT-TYPE
    SYNTAX  DisplayString
    ACCESS  read-only
    STATUS  mandatory
    DESCRIPTION
        "PCMCIAMobile active SIM ID."
    ::={ teldatPCMCIAMobileInfoInterfaceEntry 7 }

teldatPCMCIAMobileInfoInterfaceSIMIcc OBJECT-TYPE
    SYNTAX  DisplayString
    ACCESS  read-only
    STATUS  mandatory
    DESCRIPTION
        "PCMCIAMobile active SIM ICC."
    ::={ teldatPCMCIAMobileInfoInterfaceEntry 8 }


--  = = = = = = = = = = = = = = = = = = = = = = = = = = = = = = = = = = = = = =
--  Global Stats group PCMCIAMobile monitoring variables
--  = = = = = = = = = = = = = = = = = = = = = = = = = = = = = = = = = = = = = =

teldatPCMCIAMobileStatObject    OBJECT IDENTIFIER ::= { telProdNpMonInterfPCMCIAMobile 3 }

--  - - - - - - - - - - - - - - - - - - - - - - - - - - - - - - - - - - - - - -
--   PCMCIAMobile State Table, interface variables
--  - - - - - - - - - - - - - - - - - - - - - - - - - - - - - - - - - - - - - -

teldatPCMCIAMobileStateInterfaceTable OBJECT-TYPE
    SYNTAX  SEQUENCE OF TeldatPCMCIAMobileStateInterfaceEntry
    ACCESS  not-accessible
    STATUS  mandatory
    DESCRIPTION
        "Table of PCMCIAMobile interface state information."
    ::= { teldatPCMCIAMobileStatObject 1 }

teldatPCMCIAMobileStateInterfaceEntry OBJECT-TYPE
    SYNTAX  TeldatPCMCIAMobileStateInterfaceEntry
    ACCESS  not-accessible
    STATUS  mandatory
    DESCRIPTION
        "A base list of objects that are interface state information."
    INDEX   { teldatPCMCIAMobileStateInterfaceIndex}
    ::= { teldatPCMCIAMobileStateInterfaceTable 1 }

TeldatPCMCIAMobileStateInterfaceEntry ::= SEQUENCE
{
    teldatPCMCIAMobileStateInterfaceIndex           INTEGER,
    teldatPCMCIAMobileStateInterfaceState           INTEGER,
    teldatPCMCIAMobileStateInterfaceDropPing        INTEGER,
    teldatPCMCIAMobileStateInterfaceDropTrace       INTEGER,
    teldatPCMCIAMobileStateInterfaceDropTraffic     INTEGER,
    teldatPCMCIAMobileStateInterfaceTConnTime       INTEGER,
    teldatPCMCIAMobileStateInterfaceCConnTime       INTEGER,
    teldatPCMCIAMobileStateInterfaceCurDial         DisplayString,
    teldatPCMCIAMobileStateInterfaceNCall           INTEGER,
    teldatPCMCIAMobileStateInterfaceDestination     DisplayString,
    teldatPCMCIAMobileStateInterfaceTime2Sp         INTEGER
}

teldatPCMCIAMobileStateInterfaceIndex OBJECT-TYPE
    SYNTAX  INTEGER(1 .. 255)
    ACCESS  read-only
    STATUS  mandatory
    DESCRIPTION
        "PCMCIAMobile Interface index."
    ::={ teldatPCMCIAMobileStateInterfaceEntry 1 }

teldatPCMCIAMobileStateInterfaceState OBJECT-TYPE
    SYNTAX  INTEGER {
        initial(0),
        disconnect(1),
        trying-to-connect-ini(2),
        trying-to-connect-mk(3),
        trying-to-connect-cp(4),
        connect(5),
        waiting-call(6),
        hanging-up-ini(7),
        hanging-up(8),
        hanging-up-wta(9),
        hanging-up-wtar(10),
        discconnect-n-wait-call(11),
        wait-attach-wapn(12),
        wait-attach(13),
        wait-detach(14),
        wakeup-machine(15),
        command-mode(16),
        trying-to-connect-con(17),
        hanging-up-wesc(18),
        hanging-up-wt(19),
        disconnect-clcc(20),
        connect-wesc(21),
        connect-clcc(22),
        connect-ron(23),
        trying-to-connect-wgic(24),
        trying-to-connect-ucsq(25),
        trying-to-connect-unet(26),
        trying-to-connect-watc(27),
        establish-audio(28),
        gsm-incom-notify(29),
        wait-gsm-incom-notify(30),
        hanging-up-wdt(31)
        }
    ACCESS  read-only
    STATUS  mandatory
    DESCRIPTION
        "Call state."
    ::={ teldatPCMCIAMobileStateInterfaceEntry 2 }


teldatPCMCIAMobileStateInterfaceDropPing OBJECT-TYPE
    SYNTAX  INTEGER
    ACCESS  read-only
    STATUS  mandatory
    DESCRIPTION
        "Number of calls dropped due to ping supervision."
    ::={ teldatPCMCIAMobileStateInterfaceEntry 3 }

teldatPCMCIAMobileStateInterfaceDropTrace OBJECT-TYPE
    SYNTAX  INTEGER
    ACCESS  read-only
    STATUS  mandatory
    DESCRIPTION
        "Number of calls dropped due to traceroute supervision."
    ::={ teldatPCMCIAMobileStateInterfaceEntry 4 }

teldatPCMCIAMobileStateInterfaceDropTraffic OBJECT-TYPE
    SYNTAX  INTEGER
    ACCESS  read-only
    STATUS  mandatory
    DESCRIPTION
        "Number of calls dropped due to traffic supervision."
    ::={ teldatPCMCIAMobileStateInterfaceEntry 5 }

teldatPCMCIAMobileStateInterfaceTConnTime OBJECT-TYPE
    SYNTAX  INTEGER
    ACCESS  read-only
    STATUS  mandatory
    DESCRIPTION
        "Total connection time ."
    ::={ teldatPCMCIAMobileStateInterfaceEntry 6 }

teldatPCMCIAMobileStateInterfaceCConnTime OBJECT-TYPE
    SYNTAX  INTEGER
    ACCESS  read-only
    STATUS  mandatory
    DESCRIPTION
        "Current connection time."
    ::={ teldatPCMCIAMobileStateInterfaceEntry 7 }

teldatPCMCIAMobileStateInterfaceCurDial OBJECT-TYPE
    SYNTAX  DisplayString
    ACCESS  read-only
    STATUS  mandatory
    DESCRIPTION
        "Current dial-profile used."
    ::={ teldatPCMCIAMobileStateInterfaceEntry 8 }

teldatPCMCIAMobileStateInterfaceNCall OBJECT-TYPE
    SYNTAX  INTEGER
    ACCESS  read-only
    STATUS  mandatory
    DESCRIPTION
        "Number of processed calls."
    ::={ teldatPCMCIAMobileStateInterfaceEntry 9 }

teldatPCMCIAMobileStateInterfaceDestination OBJECT-TYPE
    SYNTAX  DisplayString
    ACCESS  read-only
    STATUS  mandatory
    DESCRIPTION
        "Connection destination."
    ::={ teldatPCMCIAMobileStateInterfaceEntry 10 }

teldatPCMCIAMobileStateInterfaceTime2Sp OBJECT-TYPE
    SYNTAX  INTEGER
    ACCESS  read-only
    STATUS  mandatory
    DESCRIPTION
        "Time to establish the call."
    ::={ teldatPCMCIAMobileStateInterfaceEntry 11 }


--  - - - - - - - - - - - - - - - - - - - - - - - - - - - - - - - - - - - - - -
--   PCMCIAMobile State Table, Mobile variables
--  - - - - - - - - - - - - - - - - - - - - - - - - - - - - - - - - - - - - - -

teldatPCMCIAMobileStateMobileTable OBJECT-TYPE
    SYNTAX  SEQUENCE OF TeldatPCMCIAMobileStateMobileEntry
    ACCESS  not-accessible
    STATUS  mandatory
    DESCRIPTION
        "Table of PCMCIAMobile mobile state information."
    ::= { teldatPCMCIAMobileStatObject 2 }

teldatPCMCIAMobileStateMobileEntry OBJECT-TYPE
    SYNTAX  TeldatPCMCIAMobileStateMobileEntry
    ACCESS  not-accessible
    STATUS  mandatory
    DESCRIPTION
        "A base list of objects that are mobile state information."
    INDEX   { teldatPCMCIAMobileStateMobileIndex }
    ::= { teldatPCMCIAMobileStateMobileTable 1 }

TeldatPCMCIAMobileStateMobileEntry ::= SEQUENCE
{
    teldatPCMCIAMobileStateMobileIndex                      INTEGER,
    teldatPCMCIAMobileStateMobileRegistrationState          INTEGER,
    teldatPCMCIAMobileStateMobilePublicLandMobileNtwCode    INTEGER,
    teldatPCMCIAMobileStateMobileCellLocationAreaCode       INTEGER,
    teldatPCMCIAMobileStateMobileCellId                     INTEGER,
    teldatPCMCIAMobileStateMobileRadioTechnology            DisplayString,
    teldatPCMCIAMobileStateMobileRadioBand                  DisplayString,
    teldatPCMCIAMobileStateMobileRxSignalCodePwr            INTEGER,
    teldatPCMCIAMobileStateMobileEnergyChipByPwrdnsty       INTEGER,
    teldatPCMCIAMobileStateMobileSignalQuality              INTEGER
}

teldatPCMCIAMobileStateMobileIndex OBJECT-TYPE
    SYNTAX  INTEGER(1 .. 255)
    ACCESS  read-only
    STATUS  mandatory
    DESCRIPTION
        "PCMCIAMobile mobile state index."
    ::={ teldatPCMCIAMobileStateMobileEntry 1 }

teldatPCMCIAMobileStateMobileRegistrationState OBJECT-TYPE
    SYNTAX  INTEGER {
        searching(0),
        home-network(1),
        attaching(2),
        denied(3),
        unknown(4),
        roaming(5)
        }
    ACCESS  read-only
    STATUS  obsolete
    DESCRIPTION
        "PCMCIAMobile mobile registration state ()."
    ::={ teldatPCMCIAMobileStateMobileEntry  2 }

teldatPCMCIAMobileStateMobilePublicLandMobileNtwCode OBJECT-TYPE
    SYNTAX  INTEGER
    ACCESS  read-only
    STATUS  obsolete
    DESCRIPTION
        "Public land mobile network used (+COPS)."
    ::={ teldatPCMCIAMobileStateMobileEntry  3 }


teldatPCMCIAMobileStateMobileCellLocationAreaCode OBJECT-TYPE
    SYNTAX  INTEGER
    ACCESS  read-only
    STATUS  obsolete
    DESCRIPTION
        "PCMCIAMobile mobile cell location area code (+CGREG)."
    ::={ teldatPCMCIAMobileStateMobileEntry  4 }

teldatPCMCIAMobileStateMobileCellId OBJECT-TYPE
    SYNTAX  INTEGER
    ACCESS  read-only
    STATUS  obsolete
    DESCRIPTION
        "PCMCIAMobile mobile used cell id (+CGREG)."
    ::={ teldatPCMCIAMobileStateMobileEntry  5 }


teldatPCMCIAMobileStateMobileRadioTechnology OBJECT-TYPE
    SYNTAX  DisplayString
    ACCESS  read-only
    STATUS  obsolete
    DESCRIPTION
        "PCMCIAMobile mobile current radio access tecnology used (!GETRAT)."
    ::={ teldatPCMCIAMobileStateMobileEntry  6 }

teldatPCMCIAMobileStateMobileRadioBand OBJECT-TYPE
    SYNTAX  DisplayString
    ACCESS  read-only
    STATUS  obsolete
    DESCRIPTION
        "PCMCIAMobile mobile current active band (!GETBAND)."
    ::={ teldatPCMCIAMobileStateMobileEntry  7 }


teldatPCMCIAMobileStateMobileRxSignalCodePwr OBJECT-TYPE
    SYNTAX  INTEGER
    ACCESS  read-only
    STATUS  obsolete
    DESCRIPTION
        "PCMCIAMobile mobile received signal code power (RSCP)."
    ::={ teldatPCMCIAMobileStateMobileEntry  8 }

teldatPCMCIAMobileStateMobileEnergyChipByPwrdnsty OBJECT-TYPE
    SYNTAX  INTEGER
    ACCESS  read-only
    STATUS  obsolete
    DESCRIPTION
        "PCMCIAMobile mobile total energy per chip per power density (EcNo)."
    ::={ teldatPCMCIAMobileStateMobileEntry  9 }

teldatPCMCIAMobileStateMobileSignalQuality OBJECT-TYPE
    SYNTAX  INTEGER
    ACCESS  read-only
    STATUS  mandatory
    DESCRIPTION
        "PCMCIAMobile mobile reception signal quality (+CSQ)."
    ::={ teldatPCMCIAMobileStateMobileEntry  10 }


END
