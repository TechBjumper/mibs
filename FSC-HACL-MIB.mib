-- #ident "@(#)$Header: v1_FSC_HACL_MIB.mib,v 12.1 2002/11/29 $ SNI"
-- automatically generated by mosy 7.1 #1 (rathaus), do not edit!

FSC-HACL-MIB DEFINITIONS ::= BEGIN


IMPORTS
	SnmpAdminString
		FROM SNMP-FRAMEWORK-MIB
	NOTIFICATION-GROUP
		FROM SNMPv2-CONF
	VariablePointer, StorageType, RowStatus, DateAndTime
		FROM SNMPv2-TC
	enterprises	FROM RFC1155-SMI;
-- created from fscHaClMIB (200105041000Z)
-- modified from B.S. (15.11.2002)

SnmpAdminString   ::= OCTET STRING
Gauge32           ::= INTEGER

-- fscHaClMIB OBJECT IDENTIFIER ::= { enterprises  sni  sniProductMibs  42 }

sni			OBJECT IDENTIFIER       ::= { enterprises    231 }
sniProductMibs		OBJECT IDENTIFIER       ::= { sni              2 }

fscHaClMIB OBJECT IDENTIFIER ::= { sniProductMibs  42 }

fscHaClObjects OBJECT IDENTIFIER ::= { fscHaClMIB  1 }

fscHaClNotifications OBJECT IDENTIFIER ::= { fscHaClMIB  2 }

fscHaClConformance OBJECT IDENTIFIER ::= { fscHaClMIB  3 }

fscHaClSubAgentInfo OBJECT IDENTIFIER ::= { fscHaClObjects  1 }

fscHaClSubAgentVersion OBJECT-TYPE
    SYNTAX  SnmpAdminString
    ACCESS  read-only
    STATUS  mandatory
    DESCRIPTION
           "Version of SNMP Agent"
    ::= { fscHaClSubAgentInfo  1 }

fscHaClSubAgentDescription OBJECT-TYPE
    SYNTAX  SnmpAdminString
    ACCESS  read-write
    STATUS  mandatory
    DESCRIPTION
           "Description text for the Cluster"
    ::= { fscHaClSubAgentInfo  2 }

fscHaClSubAgentType OBJECT-TYPE
    SYNTAX  INTEGER {
                 unknown(1),
                 other(2),
                 emanate(3)
               }
    ACCESS  read-only
    STATUS  mandatory
    DESCRIPTION
           "Type of Subagent:
             - unknown:
               Information cannot be supplied.
             - other:
               Information does not correspond to the other enumerated values.
             - emanate:
               The cluster agent is a EMANATE Subagent"
    ::= { fscHaClSubAgentInfo  3 }

fscHaClSubAgentInfoOperScope OBJECT-TYPE
    SYNTAX  INTEGER {
                 unknown(1),
                 other(2),
                 all(3),
                 subset(4),
                 local(5),
                 no(6)
               }
    ACCESS  read-only
    STATUS  mandatory
    DESCRIPTION
           "Scope of Information supplied by the subagent:
             - unknown:
               The Information cannot be supplied.
             - other:
               The Information does not correspond to the other enumerated
               values.
             - all:
               The agent is capable to supply the complete information
               about the cluster and the cluster entities: systems, 
               applications, and resources.
             - subset:
               The agent has only a restricted view. It supplies complete
               information only about applications which run on a subset of
               nodes.
             - local:
               The agent supplies information only about applications which
               run on the local node.
             - no:
               No Information about the Cluster is available."
    ::= { fscHaClSubAgentInfo  4 }

fscHaClSubAgentNotificationOperScope OBJECT-TYPE
    SYNTAX  INTEGER {
                 unknown(1),
                 other(2),
                 all(3),
                 subset(4),
                 local(5),
                 no(6)
               }
    ACCESS  read-only
    STATUS  mandatory
    DESCRIPTION
           "Set of Notifications sent by the subagent:
             - unknown:
               The Information cannot be supplied.
             - other:
               The Information does not correspond to the other enumerated
               values.
             - all:
               The subagent sends notifications for all events in the cluster.
               This requires access to all informations about the cluster
               constallation by the agent.
             - local:
               The subagent sends notifications for all events concerning a
               subset of systems including the local node. This value
               corresponds to 'fscHaClSubAgentInfoScope' = 'local'.
             - no:
               The subagent sends no notifications, but those which indicate a
               change of the availabilty  of cluster information."
    ::= { fscHaClSubAgentInfo  5 }

fscHaClSubAgentInfoAdminScope OBJECT-TYPE
    SYNTAX  INTEGER {
                 all(3),
                 subset(4),
                 local(5),
                 no(6)
               }
    ACCESS  read-write
    STATUS  mandatory
    DESCRIPTION
           "The desired Scope of Information supplied by the subagent:
             - all:
               The agent should supply the complete information
               about all applications and their resources which run on the
               cluster nodes. The value of 'fscHaClSubAgentInfoOperScope'
               should be 'all'.
             - subset:
               The agent should only supply informations about applications
               and their resources which run on a subset of nodes. The value
               of 'fscHaClSubAgentInfoOperScope' should be 'subset'.
             - local:
               The agent should only supply informations about applications
               and their resources which run on the local node. The value of
               'fscHaClSubAgentInfoOperScope' should be 'local'.
             - no:
               The agent should not supply any Information. The value of
               'fscHaClSubAgentInfoOperScope' should be 'no'."
    ::= { fscHaClSubAgentInfo  6 }

fscHaClSubAgentNotificationAdminScope OBJECT-TYPE
    SYNTAX  INTEGER {
                 all(3),
                 subset(4),
                 local(5),
                 no(6)
               }
    ACCESS  read-write
    STATUS  mandatory
    DESCRIPTION
           "The desired set of notifications sent by the subagent:
             - all:
               The subagent should send notifications for all events in the cluster.
               This requires access to all informations about the cluster
               constallation by the agent. The value of
               'fscHaClSubAgentNotificationOperScope' should be 'all'.
             - subset:
               The subagent should send notifications for all events concerning a
               subset of systems. The value of 'fscHaClSubAgentNotificationOperScope'
               should be 'subset'.
             - local:
               The subagent should send notifications for all events concerning a
               the local node. The value of 'fscHaClSubAgentNotificationOperScope'
               should be 'local'.
             - no:
               The subagent should send no notifications, but those which indicate a
               change of the availabilty  of cluster informations. The value of
               'fscHaClSubAgentNotificationOperScope' should be 'no'."
    ::= { fscHaClSubAgentInfo  7 }

fscHaClSubAgentLocalNodeName OBJECT-TYPE
    SYNTAX  SnmpAdminString
    ACCESS  read-only
    STATUS  mandatory
    DESCRIPTION
           "Node name of the local node of the subagent. This should be the
             same as sysnamein MIB-II."
    ::= { fscHaClSubAgentInfo  8 }

fscHaClClusterInfo OBJECT IDENTIFIER ::= { fscHaClObjects  2 }

fscHaClClusterName OBJECT-TYPE
    SYNTAX  SnmpAdminString
    ACCESS  read-only
    STATUS  mandatory
    DESCRIPTION
           "Name of the Cluster"
    ::= { fscHaClClusterInfo  1 }

fscHaClClusterDescription OBJECT-TYPE
    SYNTAX  SnmpAdminString
    ACCESS  read-only
    STATUS  mandatory
    DESCRIPTION
           "Description text for the Cluster"
    ::= { fscHaClClusterInfo  2 }

fscHaClClusterType OBJECT-TYPE
    SYNTAX  INTEGER {
                 unknown(1),
                 other(2),
                 rms(3),
                 hiplexAF(4)
               }
    ACCESS  read-only
    STATUS  mandatory
    DESCRIPTION
           "Type of the Cluster:
             - unknown:
               The Information cannot be supplied.
             - other:
               The Information does not correspond to the other enumerated
               values.
             - RMS:
               Reliant Monitor Software Cluster
             - HiplexAF:
               HiplexAF Cluster (BS2000)"
    ::= { fscHaClClusterInfo  3 }

fscHaClClusterVersion OBJECT-TYPE
    SYNTAX  SnmpAdminString
    ACCESS  read-only
    STATUS  mandatory
    DESCRIPTION
           "Version of the Cluster"
    ::= { fscHaClClusterInfo  4 }

fscHaClClusterVendor OBJECT-TYPE
    SYNTAX  SnmpAdminString
    ACCESS  read-only
    STATUS  mandatory
    DESCRIPTION
           "Vendor of the Cluster"
    ::= { fscHaClClusterInfo  5 }

fscHaClClusterMonitoringState OBJECT-TYPE
    SYNTAX  INTEGER {
                 unknown(1),
                 other(2),
                 up(3),
                 down(4),
                 runningUp(5),
                 runningDown(6),
                 pending(7)
               }
    ACCESS  read-only
    STATUS  mandatory
    DESCRIPTION
           "State of Cluster Monitoring:
             - unknown:
               The Information cannot be supplied.
             - other:
               The Information does not correspond to the other enumerated values.
             - up:
               The cluster monitoring is active. Informations about the cluster
               can be supplied.
             - down:
               No cluster monitoring is active. No informations about the cluster
               can be supplied.
             - runningUp:
               The cluster monitoring has been started but is not completely
               operating yet.
             - runningDown:
               The cluster monitoring has been stopped and is coming down. No
               informations about the cluster can be supplied.
             - The state of the cluster monitoring is presently pending. It is
               not operating for the moment. Presently no informations about
               the cluster can be supplied."
    ::= { fscHaClClusterInfo  6 }

fscHaClSystems OBJECT IDENTIFIER ::= { fscHaClObjects  3 }

fscHaClSystemNumber OBJECT-TYPE
    SYNTAX  Gauge32
    ACCESS  read-only
    STATUS  mandatory
    DESCRIPTION
           "Number of entries in the system table."
    ::= { fscHaClSystems  1 }

fscHaClSystemTable OBJECT-TYPE
    SYNTAX  SEQUENCE OF FscHaClSystemEntry
    ACCESS  not-accessible
    STATUS  mandatory
    DESCRIPTION
           "The table of systems which are member of the cluster. If the
             cluster monitoring is active, at least one system shall be member
             of the cluster. "
    ::= { fscHaClSystems  2 }

fscHaClSystemEntry OBJECT-TYPE
    SYNTAX  FscHaClSystemEntry
    ACCESS  not-accessible
    STATUS  mandatory
    DESCRIPTION
           "An entry giving information about a particular system."
    INDEX   { fscHaClSystemName }
    ::= { fscHaClSystemTable  1 }

FscHaClSystemEntry ::=
    SEQUENCE {
    fscHaClSystemName
        SnmpAdminString,

    fscHaClSystemDescription
        SnmpAdminString,

    fscHaClSystemState
        INTEGER,

    fscHaClSystemOS
        SnmpAdminString,

    fscHaClSystemOSVersion
        SnmpAdminString
    }

fscHaClSystemName OBJECT-TYPE
    SYNTAX  SnmpAdminString
    ACCESS  read-only
    STATUS  mandatory
    DESCRIPTION
           "The Hostname of the System. The value of this object must be
             identical with the value of the object 'fscHaClSubAgentLocalNodeName'
             which would be supplied by a SNMP cluster agent running on
             that system."
    ::= { fscHaClSystemEntry  1 }

fscHaClSystemDescription OBJECT-TYPE
    SYNTAX  SnmpAdminString
    ACCESS  read-only
    STATUS  mandatory
    DESCRIPTION
           "A short description text on the system"
    ::= { fscHaClSystemEntry  2 }

fscHaClSystemState OBJECT-TYPE
    SYNTAX  INTEGER {
                 unknown(1),
                 other(2),
                 up(3),
                 down(4),
                 crashed(5)
               }
    ACCESS  read-only
    STATUS  mandatory
    DESCRIPTION
           "The system's state.
             - unknown:
               The Information cannot be supplied.
             - other:
               The Information does not correspond to the other enumerated 
               values.
             - up:
               The system is running.
             - down:
               The system has been terminated normally.
             - crashed:
               A system failure occurred. It has been terminated abnormally."
    ::= { fscHaClSystemEntry  3 }

fscHaClSystemOS OBJECT-TYPE
    SYNTAX  SnmpAdminString
    ACCESS  read-only
    STATUS  mandatory
    DESCRIPTION
           "The operating system which is installed on the system."
    ::= { fscHaClSystemEntry  4 }

fscHaClSystemOSVersion OBJECT-TYPE
    SYNTAX  SnmpAdminString
    ACCESS  read-only
    STATUS  mandatory
    DESCRIPTION
           "The version of the operating system which is installed on the
             system."
    ::= { fscHaClSystemEntry  5 }

fscHaClApplications OBJECT IDENTIFIER ::= { fscHaClObjects  4 }

fscHaClApplicationNumber OBJECT-TYPE
    SYNTAX  Gauge32
    ACCESS  read-only
    STATUS  mandatory
    DESCRIPTION
           "Number of entries in the Application table."
    ::= { fscHaClApplications  1 }

fscHaClApplicationTable OBJECT-TYPE
    SYNTAX  SEQUENCE OF FscHaClApplicationEntry
    ACCESS  not-accessible
    STATUS  mandatory
    DESCRIPTION
           "The table of applications controlled by the cluster monitoring.
             Applications are also called 'resource groups' by other cluster
             concepts, because they are defined as collections of resources.
             Applications are the software units which will be switched over
             in the case of a system failure.
             In HiplexAF those units are called 'Switch-Units'."
    ::= { fscHaClApplications  2 }

fscHaClApplicationEntry OBJECT-TYPE
    SYNTAX  FscHaClApplicationEntry
    ACCESS  not-accessible
    STATUS  mandatory
    DESCRIPTION
           "An entry describing a particular Application."
    INDEX   { fscHaClApplicationName }
    ::= { fscHaClApplicationTable  1 }

FscHaClApplicationEntry ::=
    SEQUENCE {
    fscHaClApplicationName
        SnmpAdminString,

    fscHaClApplicationDescription
        SnmpAdminString,

    fscHaClApplicationState
        INTEGER,

    fscHaClApplicationWorkSystem
        SnmpAdminString
    }

fscHaClApplicationName OBJECT-TYPE
    SYNTAX  SnmpAdminString
    ACCESS  read-only
    STATUS  mandatory
    DESCRIPTION
           "The Name of the application."
    ::= { fscHaClApplicationEntry  1 }

fscHaClApplicationDescription OBJECT-TYPE
    SYNTAX  SnmpAdminString
    ACCESS  read-only
    STATUS  mandatory
    DESCRIPTION
           "A short text which describes the application."
    ::= { fscHaClApplicationEntry  2 }

fscHaClApplicationState OBJECT-TYPE
    SYNTAX  INTEGER {
                 unknown(1),
                 other(2),
                 undefined(3),
                 online(4),
                 offline(5),
                 down(6),
                 faulted(7)
               }
    ACCESS  read-only
    STATUS  mandatory
    DESCRIPTION
           "State of the application.
             - unknown:
               The Information cannot be supplied.
             - other:
               The Information does not correspond to the other enumerated
               values.
             - undefined:
               The application does not have a defined state.
             - online:
               The application is running on one member system.
               This value corresponds to the state 'work' in HiplexAF.
             - offline:
               The application is not running on any member system,
               but at least one system is ready to take over the application.
               This value corresponds to the state 'standby' in HiplexAF.
             - down:
               The application is stopped on all systems of the cluster.
               This value corresponds to the state 'terminated' in HiplexAF
             - faulted:
               The application was terminated because of a failure. It has
               not yet been restarted on any member system.
               This value corresponds to the state 'crashed' in HiplexAF.
             "
    ::= { fscHaClApplicationEntry  3 }

fscHaClApplicationWorkSystem OBJECT-TYPE
    SYNTAX  SnmpAdminString
    ACCESS  read-only
    STATUS  mandatory
    DESCRIPTION
           "Hostname of the system, where the application is presently running.
             The value must be 'NONE' if the state of the application is not
             'online'."
    ::= { fscHaClApplicationEntry  4 }

fscHaClResources OBJECT IDENTIFIER ::= { fscHaClObjects  5 }

fscHaClResourceNumber OBJECT-TYPE
    SYNTAX  Gauge32
    ACCESS  read-only
    STATUS  mandatory
    DESCRIPTION
           "Number of entries in the Resource table."
    ::= { fscHaClResources  1 }

fscHaClResourceTable OBJECT-TYPE
    SYNTAX  SEQUENCE OF FscHaClResourceEntry
    ACCESS  not-accessible
    STATUS  mandatory
    DESCRIPTION
           "This table of Resources in the cluster. (In HiplexAF resources
             are called 'objects'.)"
    ::= { fscHaClResources  2 }

fscHaClResourceEntry OBJECT-TYPE
    SYNTAX  FscHaClResourceEntry
    ACCESS  not-accessible
    STATUS  mandatory
    DESCRIPTION
           "An entry describing a particular Resource."
    INDEX   { fscHaClApplicationName,  fscHaClResourceName }
    ::= { fscHaClResourceTable  1 }

FscHaClResourceEntry ::=
    SEQUENCE {
    fscHaClResourceName
        SnmpAdminString,

    fscHaClResourceDescription
        SnmpAdminString,

    fscHaClResourceState
        INTEGER,

    fscHaClResourceTypeDescr
        SnmpAdminString
    }

fscHaClResourceName OBJECT-TYPE
    SYNTAX  SnmpAdminString
    ACCESS  read-only
    STATUS  mandatory
    DESCRIPTION
           "The Name of the resource"
    ::= { fscHaClResourceEntry  1 }

fscHaClResourceDescription OBJECT-TYPE
    SYNTAX  SnmpAdminString
    ACCESS  read-only
    STATUS  mandatory
    DESCRIPTION
           "A short text which describes the resource"
    ::= { fscHaClResourceEntry  2 }

fscHaClResourceState OBJECT-TYPE
    SYNTAX  INTEGER {
                 unknown(1),
                 other(2),
                 undefined(3),
                 notMonitored(4),
                 online(5),
                 offline(6),
                 faulted(7)
               }
    ACCESS  read-only
    STATUS  mandatory
    DESCRIPTION
           "State of the resource.
             - unknown:
               The Information cannot be supplied.
             - other:
               The Information does not correspond to the other enumerated
               values.
             - undefined:
               The resource does not have a defined state.
             - notMonitored:
               The resource is not monitored. Its state has no impact on the
               state of an application.
             - online:
               The resource is available.
               This value corresponds to the state 'running' in HiplexAF.
             - offline:
               The resource is not available.
               This value corresponds to the state 'terminated' in HiplexAF.
             - faulted:
               The resource is unavailable, because of a failure.
               This value corresponds to the state 'crashed' in HiplexAF.             "
    ::= { fscHaClResourceEntry  3 }

fscHaClResourceTypeDescr OBJECT-TYPE
    SYNTAX  SnmpAdminString
    ACCESS  read-only
    STATUS  mandatory
    DESCRIPTION
           "A text describing the resource type of the resource.
             This may be devices, file systems, etc. ."
    ::= { fscHaClResourceEntry  4 }

fscHaClAppSysRelTable OBJECT-TYPE
    SYNTAX  SEQUENCE OF FscHaClAppSysRelEntry
    ACCESS  not-accessible
    STATUS  mandatory
    DESCRIPTION
           "This table describes the relations between the applications and
             the systems.
             The main information of this table is the state of the applications
             concerning the member systems. The table contains the information
             on which system an application is running and on which system it
             can be restarted in the case of a failure"
    ::= { fscHaClObjects  6 }

fscHaClAppSysRelEntry OBJECT-TYPE
    SYNTAX  FscHaClAppSysRelEntry
    ACCESS  not-accessible
    STATUS  mandatory
    DESCRIPTION
           "An entry describing a particular relation between an application
             and a system."
    INDEX   { fscHaClApplicationName,  fscHaClSystemName }
    ::= { fscHaClAppSysRelTable  1 }

FscHaClAppSysRelEntry ::=
    SEQUENCE {
    fscHaClAppSysRelState
        INTEGER
    }

fscHaClAppSysRelState OBJECT-TYPE
    SYNTAX  INTEGER {
                 unknown(1),
                 other(2),
                 undefined(3),
                 online(4),
                 offline(5),
                 down(6),
                 faulted(7)
               }
    ACCESS  read-only
    STATUS  mandatory
    DESCRIPTION
           "State of the application concerning the system.
             - unknown:
               The Information cannot be supplied.
             - other:
               The Information does not correspond to the other enumerated
               values.
             - undefined:
               The application does not have a defined state.
             - online:
               The application is running on this system.
               This value corresponds to the state 'work' in HiplexAF.
             - offline:
               The application is not running on the system,
               but the system is ready to take over the application.
               This value corresponds to the state 'standby' in HiplexAF.
             - down:
               The application is stopped on the system. The system is not
               ready to take over the application.
               This value corresponds to the state 'terminated' in HiplexAF.
             - faulted:
               The last run of the application was terminated by a failure.
               The system is not ready to take over the application.
               This value corresponds to the state 'crashed' in HiplexAF."
    ::= { fscHaClAppSysRelEntry  1 }

fscHaClResSysRelTable OBJECT-TYPE
    SYNTAX  SEQUENCE OF FscHaClResSysRelEntry
    ACCESS  not-accessible
    STATUS  mandatory
    DESCRIPTION
           "This table describes the relations between resources and systems.
             The main information is the state of the resources concerning
             the systems. If all resources belong only to a single application,
             the table will not provide additional information. It need not be
             supported in this case."
    ::= { fscHaClObjects  7 }

fscHaClResSysRelEntry OBJECT-TYPE
    SYNTAX  FscHaClResSysRelEntry
    ACCESS  not-accessible
    STATUS  mandatory
    DESCRIPTION
           "An entry describing a particular relation between a resource and
             a system."
    INDEX   {                 fscHaClApplicationName,                 fscHaClResourceName,                 fscHaClSystemName               }
    ::= { fscHaClResSysRelTable  1 }

FscHaClResSysRelEntry ::=
    SEQUENCE {
    fscHaClResSysRelState
        INTEGER
    }

fscHaClResSysRelState OBJECT-TYPE
    SYNTAX  INTEGER {
                 unknown(1),
                 other(2),
                 undefined(3),
                 notMonitored(4),
                 online(5),
                 offline(6),
                 faulted(7)
               }
    ACCESS  read-only
    STATUS  mandatory
    DESCRIPTION
           "State of the resource.
             - unknown:
               The Information cannot be supplied.
             - other:
               The Information does not correspond to the other enumerated 
               values.
             - undefined:
               The resource does not have a defined state.
             - notMonitored:
               The resource is not monitored. Its state has no impact on the
               state of an application.
             - online:
               The resource is available.
             - offline:
               The resource is not available.
             - faulted:
               The resource is unavailable, because a failure occurred."
    ::= { fscHaClResSysRelEntry  1 }

fscHaClTraps OBJECT IDENTIFIER ::= { fscHaClNotifications  0 }

fscHaClClusterInfAvailable TRAP-TYPE
    ENTERPRISE  { fscHaClTraps }
    VARIABLES   { fscHaClClusterName,  fscHaClSubAgentInfoOperScope }
    DESCRIPTION
           "Informations about a cluster have become available for the agent.
         The value of the object 'fscHaClSubAgentInfoOperScope' has been
         changed to 'all', 'subset' or 'local'."
      --#TYPE            "Cluster Information Available"
      --#SUMMARY         "%s: Cluster information available, InfoOperScope: %s"
      --#ARGUMENTS       {0, 1}
      --#SEVERITY        INFORMATIONAL
      --#TIMEINDEX       1
      --#STATE           OPERATIONAL
    ::= 1

fscHaClClusterInfNotAvailable TRAP-TYPE
    ENTERPRISE  { fscHaClTraps }
    VARIABLES   { fscHaClClusterName,  fscHaClSubAgentInfoOperScope }
    DESCRIPTION
           "Informations about a cluster are no longer available for the agent.
         The value of the object 'fscHaClSubAgentInfoOperScope' has been
         changed to 'noInformation' 'unknown', or 'other'."
      --#TYPE            "Cluster Information No Longer Available"
      --#SUMMARY         "%s: Cluster information no longer available, InfoOperScope: %s"
      --#ARGUMENTS       {0, 1}
      --#SEVERITY        MAJOR
      --#TIMEINDEX       1
      --#STATE           OPERATIONAL
    ::= 2

fscHaClMonitorStateChanged TRAP-TYPE
    ENTERPRISE  { fscHaClTraps }
    VARIABLES   { fscHaClClusterName,  fscHaClClusterMonitoringState }
    DESCRIPTION
           "The cluster monitoring, which is the main source of informations
         for the agent has changed its state."
      --#TYPE            "Monitor State Changed"
      --#SUMMARY         "%s: Cluster monitoring state changed to: %s"
      --#ARGUMENTS       {0, 1}
      --#SEVERITY        MAJOR
      --#TIMEINDEX       1
      --#STATE           OPERATIONAL
    ::= 3

fscHaClSystemStateChanged TRAP-TYPE
    ENTERPRISE  { fscHaClTraps }
    VARIABLES   {                 fscHaClClusterName,                 fscHaClSystemName,                 fscHaClSystemState               }
    DESCRIPTION
           "The state of a system has changed."
      --#TYPE            "System State Changed"
      --#SUMMARY         "%s: %s - System state changed to: %s"
      --#ARGUMENTS       {0, 1, 2}
      --#SEVERITY        CRITICAL
      --#TIMEINDEX       1
      --#STATE           OPERATIONAL
    ::= 4

fscHaClApplicationStateChanged TRAP-TYPE
    ENTERPRISE  { fscHaClTraps }
    VARIABLES   {                 fscHaClClusterName,                 fscHaClApplicationName,                 fscHaClSystemName,                 fscHaClAppSysRelState               }
    DESCRIPTION
           "The state of an application has changed on a system."
      --#TYPE            "Application State Changed"
      --#SUMMARY         "%s: %s on %s - Application state changed to: %s"
      --#ARGUMENTS       {0, 1, 2, 3}
      --#SEVERITY        MAJOR
      --#TIMEINDEX       1
      --#STATE           OPERATIONAL
    ::= 5

fscHaClResourceStateChanged TRAP-TYPE
    ENTERPRISE  { fscHaClTraps }
    VARIABLES   {                 fscHaClClusterName,                 fscHaClResourceName,                 fscHaClResourceState,                 fscHaClApplicationName,                 fscHaClSystemName               }
    DESCRIPTION
           "The state of a resource which belongs to an online application
         has changed. "
      --#TYPE            "Resource State Changed"
      --#SUMMARY         "%s: %s of %s on %s - Resource state changed to: %s"
      --#ARGUMENTS       {0, 1, 3, 4, 2}
      --#SEVERITY        MINOR
      --#TIMEINDEX       1
      --#STATE           OPERATIONAL
    ::= 6

fscHaClCompliances OBJECT IDENTIFIER ::= { fscHaClConformance  1 }

fscHaClGroups OBJECT IDENTIFIER ::= { fscHaClConformance  2 }

fscHaClCompliance OBJECT IDENTIFIER ::= { fscHaClCompliances  1 }

fscHaClSubAgentGroup OBJECT IDENTIFIER ::= { fscHaClGroups  1 }

fscHaClClusterGroup OBJECT IDENTIFIER ::= { fscHaClGroups  2 }

fscHaClTableNumberGroup OBJECT IDENTIFIER ::= { fscHaClGroups  3 }

fscHaClSystemGroup OBJECT IDENTIFIER ::= { fscHaClGroups  4 }

fscHaClApplicationGroup OBJECT IDENTIFIER ::= { fscHaClGroups  5 }

fscHaClResourceGroup OBJECT IDENTIFIER ::= { fscHaClGroups  6 }

fscHaClApplSysRelGroup OBJECT IDENTIFIER ::= { fscHaClGroups  7 }

fscHaClResSysRelGroup OBJECT IDENTIFIER ::= { fscHaClGroups  9 }

fscHaClNotificationsGroup1 OBJECT IDENTIFIER ::= { fscHaClGroups  10 }

fscHaClNotificationsGroup2 OBJECT IDENTIFIER ::= { fscHaClGroups  11 }

END
