--
    -- Title: Plexcom Private MIB, Plexcom enterprise branch
    -- Filename: plexcom.mib
    -- Revision: 1.24
    -- Date: February 2, 1995
    -- Contact: B. Miller
    --
    -- Plexcom, Inc.
    -- 2255 Agate Court
    -- Simi Valley, CA  93065
    -- TEL (805) 522-3333
    -- FAX (805) 583-4764
    --
    -- Parts of this MIB are supported by the following Plexcom device
    -- SNMP agents: 8025SX Series, 8029, 8029SX, 8039, 8039SX, 8091E,
    -- 8091SX, 8093SX, and PlexSTACK Series
    --

    PLEXCOM-MIB

    DEFINITIONS ::= BEGIN

    IMPORTS
       enterprises, Counter   FROM RFC1155-SMI
       TRAP-TYPE              FROM RFC-1215
       OBJECT-TYPE            FROM RFC-1212
       DisplayString          FROM RFC1213-MIB;

    plexcom             OBJECT IDENTIFIER   ::= { enterprises 465 }

    plxNode             OBJECT IDENTIFIER   ::= { plexcom 1 }

    -- Plexcom agent object identifiers
    plxAgent            OBJECT IDENTIFIER   ::= { plxNode 1 }
    plxStBridgeagent    OBJECT IDENTIFIER   ::= { plxAgent 1 }
    plxStBridgesnmpd    OBJECT IDENTIFIER   ::= { plxStBridgeagent 1 }
    plxPlexcomHub8091   OBJECT IDENTIFIER   ::= { plxStBridgesnmpd 4 }
    plxPlexcomHub8039   OBJECT IDENTIFIER   ::= { plxStBridgesnmpd 5 }
    plxPlexcomHub8029   OBJECT IDENTIFIER   ::= { plxStBridgesnmpd 6 }
    plxPlexcomHub8093   OBJECT IDENTIFIER   ::= { plxStBridgesnmpd 7 }
    plxRepeaterAgent    OBJECT IDENTIFIER   ::= { plxAgent 2 }
    plxPlexcom8025      OBJECT IDENTIFIER   ::= { plxRepeaterAgent 1 }
    plxPlexcom8025SX    OBJECT IDENTIFIER   ::= { plxPlexcom8025 1 }
    plxPlexcom8025SXT   OBJECT IDENTIFIER   ::= { plxPlexcom8025 2 }
    plxPlexcomH8025SXT  OBJECT IDENTIFIER   ::= { plxPlexcom8025 3 }
    plxPlexcomH8025SX   OBJECT IDENTIFIER   ::= { plxPlexcom8025 4 }
    plxPlexcomS8025SXT  OBJECT IDENTIFIER   ::= { plxPlexcom8025 5 }
    plxPlexcomS8025SX   OBJECT IDENTIFIER   ::= { plxPlexcom8025 6 }
    plxPlexcomPlexSTACK OBJECT IDENTIFIER   ::= { plxRepeaterAgent 2 }
    plxPlexcom4000i     OBJECT IDENTIFIER   ::= { plxPlexcomPlexSTACK 1 }
    plxPlexcom4000iR    OBJECT IDENTIFIER   ::= { plxPlexcomPlexSTACK 2 }
    plxSwitchAgent      OBJECT IDENTIFIER   ::= { plxAgent 3 }
    plxPlexcom5108      OBJECT IDENTIFIER   ::= { plxSwitchAgent 1 }

    -- Plexcom module object identifiers
    plxModule           OBJECT IDENTIFIER   ::= { plxNode 2 }
    plxModuleUnknown    OBJECT IDENTIFIER   ::= { plxModule 1 }
    plxModule8010       OBJECT IDENTIFIER   ::= { plxModule 2 }
    plxModule8011       OBJECT IDENTIFIER   ::= { plxModule 3 }
    plxModule8023A      OBJECT IDENTIFIER   ::= { plxModule 4 }
    plxModule8024A      OBJECT IDENTIFIER   ::= { plxModule 5 }
    plxModule8024T      OBJECT IDENTIFIER   ::= { plxModule 6 }
    plxModule8026A      OBJECT IDENTIFIER   ::= { plxModule 7 }
    plxModule8026T      OBJECT IDENTIFIER   ::= { plxModule 8 }
    plxModule8029M      OBJECT IDENTIFIER   ::= { plxModule 9 }
    plxModule8091M      OBJECT IDENTIFIER   ::= { plxModule 10 }
    plxModule8023       OBJECT IDENTIFIER   ::= { plxModule 11 }
    plxModule8031       OBJECT IDENTIFIER   ::= { plxModule 13 }
    plxModule8031A      OBJECT IDENTIFIER   ::= { plxModule 14 }
    plxModule8033       OBJECT IDENTIFIER   ::= { plxModule 15 }
    plxModule8034       OBJECT IDENTIFIER   ::= { plxModule 16 }
    plxModule8033A      OBJECT IDENTIFIER   ::= { plxModule 17 }
    plxModule8024FO     OBJECT IDENTIFIER   ::= { plxModule 24 }
    plxModule8039M      OBJECT IDENTIFIER   ::= { plxModule 32 }
    plxModule8039S      OBJECT IDENTIFIER   ::= { plxModule 33 }
    plxModule8026FO     OBJECT IDENTIFIER   ::= { plxModule 34 }
    plxModule8408       OBJECT IDENTIFIER   ::= { plxModule 35 }
    plxModule8400FO     OBJECT IDENTIFIER   ::= { plxModule 36 }
    plxModule8032-R     OBJECT IDENTIFIER   ::= { plxModule 43 }
    plxModule8032-1P    OBJECT IDENTIFIER   ::= { plxModule 45 }
    plxModule8032-2P    OBJECT IDENTIFIER   ::= { plxModule 47 }
    plxModule8032-4P    OBJECT IDENTIFIER   ::= { plxModule 51 }
    plxModule8032-6P    OBJECT IDENTIFIER   ::= { plxModule 55 }
    plxModule2008SX     OBJECT IDENTIFIER   ::= { plxModule 56 }
    plxModule8035       OBJECT IDENTIFIER   ::= { plxModule 58 }
    plxModule8035STP    OBJECT IDENTIFIER   ::= { plxModule 59 }
    plxModule8036       OBJECT IDENTIFIER   ::= { plxModule 60 }
    plxModule8023SX     OBJECT IDENTIFIER   ::= { plxModule 70 }
    plxModule8012SX-1   OBJECT IDENTIFIER   ::= { plxModule 71 }
    plxModule8012SX-6   OBJECT IDENTIFIER   ::= { plxModule 72 }
    plxModule8024SX     OBJECT IDENTIFIER   ::= { plxModule 73 }
    plxModule8027SX     OBJECT IDENTIFIER   ::= { plxModule 74 }
    plxModule8091SXM    OBJECT IDENTIFIER   ::= { plxModule 75 }
    plxModule8029SX-3M  OBJECT IDENTIFIER   ::= { plxModule 76 }
    plxModule8029SX-3S  OBJECT IDENTIFIER   ::= { plxModule 77 }
    plxModule8025SX     OBJECT IDENTIFIER   ::= { plxModule 78 }
    plxModule8025SXT    OBJECT IDENTIFIER   ::= { plxModule 79 }
    plxModuleH8025SX    OBJECT IDENTIFIER   ::= { plxModule 81 }
    plxModuleS8025SXT   OBJECT IDENTIFIER   ::= { plxModule 82 }
    plxModuleS8025SX    OBJECT IDENTIFIER   ::= { plxModule 83 }
    plxModule8408FO     OBJECT IDENTIFIER   ::= { plxModule 84 }
    plxModule8012SX-2   OBJECT IDENTIFIER   ::= { plxModule 85 }
    plxModule8012SX-4   OBJECT IDENTIFIER   ::= { plxModule 86 }
    plxModule8026SX     OBJECT IDENTIFIER   ::= { plxModule 88 }
    plxModule8035SX     OBJECT IDENTIFIER   ::= { plxModule 89 }
    plxModuleP8035SX    OBJECT IDENTIFIER   ::= { plxModule 90 }
    plxModule8093SXM    OBJECT IDENTIFIER   ::= { plxModule 91 }
    plxModule8093SXS    OBJECT IDENTIFIER   ::= { plxModule 92 }
    plxModule8039SXM    OBJECT IDENTIFIER   ::= { plxModule 93 }
    plxModule8039SXS    OBJECT IDENTIFIER   ::= { plxModule 94 }

    plxFilterTable      OBJECT IDENTIFIER   ::= { plexcom 2 }
    plxFtConfig         OBJECT IDENTIFIER   ::= { plxFilterTable 1 }

    plxFtMaxAge OBJECT-TYPE
       SYNTAX  INTEGER
       ACCESS  read-write
       STATUS  mandatory
       DESCRIPTION
          "Maximum age of a filter table entry before it is
          deleted from the table. The value is multiplied by
          plxFtAgeTime (update timer interval) to form the
          timer value in seconds."
       ::=  { plxFtConfig 1 }
     
    plxFtMaxRemove OBJECT-TYPE
       SYNTAX  INTEGER
       ACCESS  read-write
       STATUS  mandatory
       DESCRIPTION
          "When the filter table is full and new entries need to
          be made, the oldest plxFtMaxRemove number of entries
          are removed."
       ::=  { plxFtConfig 2 }

    plxFtMaxFilter OBJECT-TYPE
       SYNTAX  INTEGER
       ACCESS  read-only
       STATUS  mandatory
       DESCRIPTION
          "Size of the filter table."
       ::=  { plxFtConfig 3 }

    plxFtAgeTime OBJECT-TYPE
       SYNTAX  INTEGER
       ACCESS  read-write
       STATUS  mandatory
       DESCRIPTION
          "Filter table age timer interval. The filter entry
          age is incremented every plxFtAgeTime seconds."
       ::=  { plxFtConfig 4 }

    plxFtMaxPerm OBJECT-TYPE
       SYNTAX  INTEGER
       ACCESS  read-write
       STATUS  mandatory
       DESCRIPTION
          "Max number of permanent filter table entries.
          Setting this value to zero clears all permanent
          and dynamic entries from the filter table. Any
          other set is ignored."
       ::=  { plxFtConfig 5 }

    plxFtForwMBcast OBJECT-TYPE
       SYNTAX  INTEGER {
          noForward(0),
          forward(1)
       }
       ACCESS  read-write
       STATUS  mandatory
       DESCRIPTION
          "Enable or disable forwarding of broadcasts
          and multicasts."
       ::=  { plxFtConfig 6 }

    plxFtSecureMode OBJECT-TYPE
       SYNTAX  INTEGER {
          normal(0),
          secure(1)
       }
       ACCESS  read-write
       STATUS  mandatory
       DESCRIPTION
          "Enable or disable 'secure' mode. In 'secure' mode the
          bridge does not learn filter table entries dynamically."
       ::=  { plxFtConfig 7 }

    --
    -- The filter table. Instance is a six element
    -- object identifier representing the MAC address.
    --
    plxFtEntry OBJECT IDENTIFIER ::= { plxFilterTable 2 }

    plxFtAge OBJECT-TYPE
       SYNTAX  INTEGER
       ACCESS  read-write
       STATUS  mandatory
       DESCRIPTION
          "Filter table entry age. Instance is a six element
          object identifier representing the MAC address."
       ::=  { plxFtEntry 1 }

    plxFtDisp OBJECT-TYPE
       SYNTAX  INTEGER {
          dynamforw1(4),
          dynamforw2(8),
          dynamflood(16),
          dynamdiscard(32),
          statforw1(5),
          statforw2(9),
          statflood(17),
          statdiscard(33),
          syssendup(67),
          sysdiscard(35),
          sysflood(83)
       }
       ACCESS  read-write
       STATUS  mandatory
       DESCRIPTION
          "Filter table entry disposition. Instance is a six element
          object identifier representing the MAC address."
       ::=  { plxFtEntry 2 }

    plxInterfaceErrors OBJECT IDENTIFIER ::= { plexcom 3 }

    plxIfeInBusErr OBJECT-TYPE
       SYNTAX  Counter
       ACCESS  read-only
       STATUS  mandatory
       DESCRIPTION
          "Bus read errors (Ethernet chip error)."
       ::=  { plxInterfaceErrors 1 }

    plxIfeInShortPkt OBJECT-TYPE
       SYNTAX  Counter
       ACCESS  read-only
       STATUS  mandatory
       DESCRIPTION
          "Short frames received."
       ::=  { plxInterfaceErrors 2 }

    plxIfeInAlgError OBJECT-TYPE
       SYNTAX  Counter
       ACCESS  read-only
       STATUS  mandatory
       DESCRIPTION
          "Frames received with bad alignment."
       ::=  { plxInterfaceErrors 3 }

    plxIfeInBadSize OBJECT-TYPE
       SYNTAX  Counter
       ACCESS  read-only
       STATUS  mandatory
       DESCRIPTION
          "Frames received with bad length."
       ::=  { plxInterfaceErrors 4 }
     
    plxIfeInOverflow OBJECT-TYPE
       SYNTAX  Counter
       ACCESS  read-only
       STATUS  mandatory
       DESCRIPTION
          "Receive buffer overflow errors."
       ::=  { plxInterfaceErrors 5 }

    plxIfeInCRCErr OBJECT-TYPE
       SYNTAX  Counter
       ACCESS  read-only
       STATUS  mandatory
       DESCRIPTION
          "Frames received with CRC errors."
       ::=  { plxInterfaceErrors 6 }

    plxIfeOutCol16 OBJECT-TYPE
       SYNTAX  Counter
       ACCESS  read-only
       STATUS  mandatory
       DESCRIPTION
          "Frames discarded due to excess collisions."
       ::=  { plxInterfaceErrors 7 }

    plxIfeOutCol OBJECT-TYPE
       SYNTAX  Counter
       ACCESS  read-only
       STATUS  mandatory
       DESCRIPTION
          "Transmit collisions."
       ::=  { plxInterfaceErrors 8 }

    plxIfeOutShortPkt OBJECT-TYPE
       SYNTAX  Counter
       ACCESS  read-only
       STATUS  mandatory
       DESCRIPTION
          "Short packets transmitted (Ethernet chip error)."
       ::=  { plxInterfaceErrors 9 }

    plxIfeOutUnderflow OBJECT-TYPE
       SYNTAX  Counter
       ACCESS  read-only
       STATUS  mandatory
       DESCRIPTION
          "Transmit buffer underflow."
       ::=  { plxInterfaceErrors 10 }

    plxIfeOutBusErr OBJECT-TYPE
       SYNTAX  Counter
       ACCESS  read-only
       STATUS  mandatory
       DESCRIPTION
          "Bus write errors (Ethernet chip error)."
       ::=  { plxInterfaceErrors 11 }
     
    plxForwardCounters OBJECT IDENTIFIER ::= { plexcom 4 }

    plxFcInOctets OBJECT-TYPE
       SYNTAX  Counter
       ACCESS  read-only
       STATUS  mandatory
       DESCRIPTION
          "Received bytes."
       ::=  { plxForwardCounters 1 }

    plxFcInPkts OBJECT-TYPE
       SYNTAX  Counter
       ACCESS  read-only
       STATUS  mandatory
       DESCRIPTION
          "Received frames."
       ::=  { plxForwardCounters 2 }
     
    plxFcInNUcastPkts OBJECT-TYPE
       SYNTAX  Counter
       ACCESS  read-only
       STATUS  mandatory
       DESCRIPTION
          "Received multicast and broadcast frames."
       ::=  { plxForwardCounters 3 }
     
    plxFcForwOctets OBJECT-TYPE
       SYNTAX  Counter
       ACCESS  read-only
       STATUS  mandatory
       DESCRIPTION
          "Forwarded bytes."
       ::=  { plxForwardCounters 4 }
     
    plxFcForwPkts OBJECT-TYPE
       SYNTAX  Counter
       ACCESS  read-only
       STATUS  mandatory
       DESCRIPTION
          "Forward frames."
       ::=  { plxForwardCounters 5 }
     
    plxFcFiltOctets OBJECT-TYPE
       SYNTAX  Counter
       ACCESS  read-only
       STATUS  mandatory
       DESCRIPTION
          "Filtered bytes."
       ::=  { plxForwardCounters 6 }

    plxFcFiltPkts OBJECT-TYPE
       SYNTAX  Counter
       ACCESS  read-only
       STATUS  mandatory
       DESCRIPTION
          "Filtered frames."
       ::=  { plxForwardCounters 7 }
     
    --
    -- System information
    --
    plxSystemCounters OBJECT IDENTIFIER ::= { plexcom 5 }

    plxSysMemFree OBJECT-TYPE
       SYNTAX  Counter
       ACCESS  read-only
       STATUS  mandatory
       DESCRIPTION
          "Amount of memory free of a particular size. Instance is
          the memory block size."
       ::=  { plxSystemCounters 1 }

    plxSysMemAllocFail OBJECT-TYPE
       SYNTAX  Counter
       ACCESS  read-only
       STATUS  mandatory
       DESCRIPTION
          "Number of times an allocation of a particular size
          was denied due to no buffers. Instance is the buffer
          size."
       ::=  { plxSystemCounters 2 }

    plxSysMemTotAllocFail OBJECT-TYPE
       SYNTAX  Counter
       ACCESS  read-only
       STATUS  mandatory
       DESCRIPTION
          "Total number of memory allocation failures."
       ::=  { plxSystemCounters 3 }
     
    --
    -- Count of deallocation failures due to inconsistent
    -- function arguments.
    --
    plxSysMemFreeFail OBJECT-TYPE
       SYNTAX  Counter
       ACCESS  read-only
       STATUS  mandatory
       DESCRIPTION
          "Count of deallocation failures due to inconsistent
          function arguments."
       ::=  { plxSystemCounters 4 }
     
    plxSysMemAllocTooBig OBJECT-TYPE
       SYNTAX  Counter
       ACCESS  read-only
       STATUS  mandatory
       DESCRIPTION
          "Number of times a memory allocation was denied because
          the buffer size was too large."
       ::=  { plxSystemCounters 5 }
     
    plxSysTimeToReset OBJECT-TYPE
       SYNTAX  Counter
       ACCESS  read-write
       STATUS  mandatory
       DESCRIPTION
          "Amount of time (seconds) until the agent will reset.
          Setting this to any non-zero value will cause a reset."
       ::=  { plxSystemCounters 6 }
     
     -- Changed from OCTET STRING -> DisplayString, 2-16-94, B. Miller.
    plxSysPanicMesg OBJECT-TYPE
       SYNTAX  DisplayString (SIZE (0..32))
       ACCESS  read-only
       STATUS  mandatory
       DESCRIPTION
          "The message printed on the console before the last system
          crash, or a probable cause of the last crash."
       ::=  { plxSystemCounters 7 }
     
    plxSysResetCount OBJECT-TYPE
       SYNTAX  Counter
       ACCESS  read-only
       STATUS  mandatory
       DESCRIPTION
          "Number of times the device has been reset (not including
          power recycles)."
       ::=  { plxSystemCounters 8 }
     
    plxSysSoftwareVersion OBJECT-TYPE
       SYNTAX  DisplayString (SIZE (0..32))
       ACCESS  read-only
       STATUS  mandatory
       DESCRIPTION
          "The version of software currently functioning in the system."
       ::=  { plxSystemCounters 10 }

    --
    -- Spanning Tree Protocol information
    --
    plxSpanningTree OBJECT IDENTIFIER ::= { plexcom 6 }

    --
    -- Default info used by this bridge when it is the root
    --
    plxStBridge OBJECT IDENTIFIER ::= { plxSpanningTree 1 }

    plxStBrName OBJECT-TYPE
       SYNTAX  OCTET STRING
       ACCESS  read-write
       STATUS  mandatory
       DESCRIPTION
          "Printable bridge name."
       ::=  { plxStBridge 1 }

    plxStBrIdent OBJECT-TYPE
       SYNTAX  OCTET STRING
       ACCESS  read-write
       STATUS  mandatory
       DESCRIPTION
          "Bridge identifier (8 bytes)."
       ::=  { plxStBridge 2 }
     
    plxStBrMaxAge OBJECT-TYPE
       SYNTAX  INTEGER
       ACCESS  read-write
       STATUS  mandatory
       DESCRIPTION
          "Bridge default 802.1 Max Age parameter."
       ::=  { plxStBridge 3 }

    plxStBrHelloTime OBJECT-TYPE
       SYNTAX  INTEGER
       ACCESS  read-write
       STATUS  mandatory
       DESCRIPTION
          "Bridge default 802.1 Hello Time parameter."
       ::=  { plxStBridge 4 }
     
    plxStBrForwDelay OBJECT-TYPE
       SYNTAX  INTEGER
       ACCESS  read-write
       STATUS  mandatory
       DESCRIPTION
          "Bridge default 802.1 Forward Delay parameter."
       ::=  { plxStBridge 5 }
     
    plxStBrIsRoot OBJECT-TYPE
       SYNTAX  INTEGER {
          notroot(0),
          isroot(1)
       }
       ACCESS  read-only
       STATUS  mandatory
       DESCRIPTION
          "Flag indicating if the bridge is the root."
       ::=  { plxStBridge 6 }
     
    plxStBrIsDesig OBJECT-TYPE
       SYNTAX  INTEGER {
          notdesig(0),
          isdesig(1)
       }
       ACCESS  read-only
       STATUS  mandatory
       DESCRIPTION
          "Flag indicating if the bridge is designated for a LAN."
       ::=  { plxStBridge 7 }

    plxStBrSpanAddr OBJECT-TYPE
       SYNTAX  OCTET STRING (SIZE(6))
       ACCESS  read-only
       STATUS  mandatory
       DESCRIPTION
          "MAC address used by the Spanning Tree Protocol for
          sending and receiving Config and Topology change frames."
       ::=  { plxStBridge 8 }

    plxStBrPriority OBJECT-TYPE
       SYNTAX  INTEGER
       ACCESS  read-write
       STATUS  mandatory
       DESCRIPTION
          "802.1 Bridge Priority parameter."
       ::=  { plxStBridge 9 }

    plxStBrSTPDisabled OBJECT-TYPE
       SYNTAX  INTEGER {
          enabled(0),
          disabled(1)
       }
       ACCESS  read-write
       STATUS  mandatory
       DESCRIPTION
          "Flag used to enable or disable 802.1 Spanning Tree Protocol
          operation."
       ::=  { plxStBridge 10 }

    --
    -- Information relating to the bridges current idea of the Root.
    --
    plxStRoot OBJECT IDENTIFIER ::= { plxSpanningTree 2 }

    plxStRtIdent OBJECT-TYPE
       SYNTAX  OCTET STRING
       ACCESS  read-only
       STATUS  mandatory
       DESCRIPTION
          "Root 802.1 Bridge Identifier."
       ::=  { plxStRoot 1 }
     
    plxStRtCost OBJECT-TYPE
       SYNTAX  INTEGER
       ACCESS  read-only
       STATUS  mandatory
       DESCRIPTION
          "Root path cost."
       ::=  { plxStRoot 2 }

    plxStRtPort OBJECT-TYPE
       SYNTAX  INTEGER {
          rootPort1(1),
          rootPort2(2)
       }
       ACCESS  read-only
       STATUS  mandatory
       DESCRIPTION
          "Root port number."
       ::=  { plxStRoot 3 }
     
    plxStRtMaxAge OBJECT-TYPE
       SYNTAX  INTEGER
       ACCESS  read-only
       STATUS  mandatory
       DESCRIPTION
          "Root 802.1 Max Age parameter."
       ::=  { plxStRoot 4 }
     
    plxStRtHelloTime OBJECT-TYPE
       SYNTAX  INTEGER
       ACCESS  read-only
       STATUS  mandatory
       DESCRIPTION
          "Root 802.1 Hello Time parameter."
       ::=  { plxStRoot 5 }
     
    plxStRtForwDelay OBJECT-TYPE
       SYNTAX  INTEGER
       ACCESS  read-only
       STATUS  mandatory
       DESCRIPTION
          "Root 802.1 Forward Delay parameter."
       ::=  { plxStRoot 6 }
     
    plxStPort OBJECT IDENTIFIER ::= { plxSpanningTree 3 }

    plxStPrtState OBJECT-TYPE
       SYNTAX  INTEGER {
          disabled(0),
          blocking(1),
          listening(2),
          learning(4),
          forwarding(8)
       }
       ACCESS  read-write
       STATUS  mandatory
       DESCRIPTION
          "802.1 Port State."
       ::=  { plxStPort 1 }
     
    plxStPrtCost OBJECT-TYPE
       SYNTAX  INTEGER
       ACCESS  read-only
       STATUS  mandatory
       DESCRIPTION
          "802.1 Port cost parameter."
       ::=  { plxStPort 2 }
     
    plxStPrtIsDesig OBJECT-TYPE
       SYNTAX  INTEGER {
          notdesig(0),
          isdesig(1)
       }
       ACCESS  read-only
       STATUS  mandatory
       DESCRIPTION
          "Flag indicating if this port is designated."
       ::=  { plxStPort 3 }

    plxStPrtIsRoot OBJECT-TYPE
       SYNTAX  INTEGER {
          notroot(0),
          isroot(1)
       }
       ACCESS  read-only
       STATUS  mandatory
       DESCRIPTION
          "Flag indicating if this is the root port."
       ::=  { plxStPort 4 }
     
    plxStPrtDesigRoot OBJECT-TYPE
       SYNTAX  OCTET STRING
       ACCESS  read-only
       STATUS  mandatory
       DESCRIPTION
          "802.1 Bridge Identifier of the Designated Root
          for this port."
       ::=  { plxStPort 5 }

    plxStPrtDesigCost OBJECT-TYPE
       SYNTAX  INTEGER
       ACCESS  read-only
       STATUS  mandatory
       DESCRIPTION
          "Designated cost for this port."
       ::=  { plxStPort 6 }

    plxStPrtDesigBridge OBJECT-TYPE
       SYNTAX  OCTET STRING
       ACCESS  read-only
       STATUS  mandatory
       DESCRIPTION
          "Designated bridge for this port."
       ::=  { plxStPort 7 }

    plxStPrtDesigPort OBJECT-TYPE
       SYNTAX  INTEGER
       ACCESS  read-only
       STATUS  mandatory
       DESCRIPTION
          "Designated port."
       ::=  { plxStPort 8 }
     
    plxStPrtPriority OBJECT-TYPE
       SYNTAX  INTEGER
       ACCESS  read-only
       STATUS  mandatory
       DESCRIPTION
          "Port priority."
       ::=  { plxStPort 9 }
     
    plxSpanTreeStats OBJECT IDENTIFIER ::= { plxSpanningTree 4 }

    plxStsTopoChanges OBJECT-TYPE
       SYNTAX  Counter
       ACCESS  read-only
       STATUS  mandatory
       DESCRIPTION
          "Topology changes detected."
       ::=  { plxSpanTreeStats 1 }
     
    plxStsConfigTimeout OBJECT-TYPE
       SYNTAX  Counter
       ACCESS  read-only
       STATUS  mandatory
       DESCRIPTION
          "Configuration timeouts."
       ::=  { plxSpanTreeStats 2 }
     
    plxStsPortDisable OBJECT-TYPE
       SYNTAX  Counter
       ACCESS  read-only
       STATUS  mandatory
       DESCRIPTION
          "Count of port disables."
       ::=  { plxSpanTreeStats 3 }
     
    plxStsPortEnable OBJECT-TYPE
       SYNTAX  Counter
       ACCESS  read-only
       STATUS  mandatory
       DESCRIPTION
          "Count of port enables."
       ::=  { plxSpanTreeStats 4 }
     
    plxStsInBadLen OBJECT-TYPE
       SYNTAX  Counter
       ACCESS  read-only
       STATUS  mandatory
       DESCRIPTION
          "802.1 frames received with bad length."
       ::=  { plxSpanTreeStats 5 }
     
    plxStsInUnknown OBJECT-TYPE
       SYNTAX  Counter
       ACCESS  read-only
       STATUS  mandatory
       DESCRIPTION
          "802.1 frames received with bad frame type."
       ::=  { plxSpanTreeStats 6 }
     
    plxStsIn8021Man OBJECT-TYPE
       SYNTAX  Counter
       ACCESS  read-only
       STATUS  mandatory
       DESCRIPTION
          "802.1 Management frames received (discarded by bridge)."
       ::=  { plxSpanTreeStats 7 }

    plxStsInConfig OBJECT-TYPE
       SYNTAX  Counter
       ACCESS  read-only
       STATUS  mandatory
       DESCRIPTION
          "802.1 Config frames received."
       ::=  { plxSpanTreeStats 8 }
     
    plxStsInTopoChg OBJECT-TYPE
       SYNTAX  Counter
       ACCESS  read-only
       STATUS  mandatory
       DESCRIPTION
          "802.1 Topology change notification frames received."
       ::=  { plxSpanTreeStats 9 }
     
    plxStsOutConfig OBJECT-TYPE
       SYNTAX  Counter
       ACCESS  read-only
       STATUS  mandatory
       DESCRIPTION
          "802.1 Config frames sent."
       ::=  { plxSpanTreeStats 10 }
     
    plxStsOutTopoChg OBJECT-TYPE
       SYNTAX  Counter
       ACCESS  read-only
       STATUS  mandatory
       DESCRIPTION
          "802.1 Topology change notification frames sent."
       ::=  { plxSpanTreeStats 11 }

    --
    -- Filter range table
    --
    plxFilterRange OBJECT IDENTIFIER ::= { plexcom 7 }

    plxFrNumRange OBJECT-TYPE
       SYNTAX  INTEGER
       ACCESS  read-write
       STATUS  mandatory
       DESCRIPTION
          "The maximum number of filter range table entries when read
          (GET). Set to zero to delete all filter range table entries.
          A set with any other value is ignored."
       ::=  { plxFilterRange 1 }

    plxFrEntry OBJECT-TYPE
       SYNTAX  OCTET STRING
       ACCESS  read-write
       STATUS  mandatory
       DESCRIPTION
          "Filter range table entry. Instance is the range table number
          (1 to plxFrNumRange). Each entry has the following format:
              uchar   frLowDest[6];    /* low bound of destination */
              uchar   frLowSrc[6];     /* low bound of source */
              ushort    frLowType;     /* low bound of type */
              uchar   frHighDest[6];   /* high bound of destination */
              uchar     frHighSrc[6];  /* high bound of source */
              ushort    frHighType;    /* high bound of type */
              uchar     frflag;        /* disposition flag */
              unchar    frfill;        /* round up size */
          The LowType and  HighType are in network byte order
          (Motorola 68K). The flag is one of the bridge filter
          table disposition values."
       ::=  { plxFilterRange 2 }

    --
    -- Variables for management of Plexcom Hub using
    -- proprietary interchange with 8090 management module.
    --

    plxPlexcomProp  OBJECT IDENTIFIER ::= { plexcom 9 }

    plxPlexAsync OBJECT-TYPE
       SYNTAX  OCTET STRING
       ACCESS  read-write
       STATUS  mandatory
       DESCRIPTION
          "Plexcom 8090 proprietary management frame. Instance is '0'.
          This info is available in published form by using
          the 'plxHub' variables."
       ::= { plxPlexcomProp 1 }
	
    plxPlexStat OBJECT-TYPE
       SYNTAX  INTEGER {
          down(0),
          up(1)
       }
       ACCESS  read-only
       STATUS  mandatory
       DESCRIPTION
          "Status of Plexcom 8090 management module as deduced by
          response to poll. Instance is '0'."
       ::= { plxPlexcomProp 2 }

    plxPlexBkBits OBJECT-TYPE
       SYNTAX  OCTET STRING
       ACCESS  read-write
       STATUS  mandatory
       DESCRIPTION
          "Plexcom 8091 proprietary management frame. Instance is '0'.
          This info is available in a decoded form by using the 'plxHub'
          variables.

          Structure for SET (size 104):
             #define MAX_SLOTS        13
             #define SLOT_INFO_SIZE   8
             char module_set_prop[MAX_SLOTS][SLOT_INFO_SIZE]

          Structure for GET (size 208):
             char module_set_prop[MAX_SLOTS][SLOT_INFO_SIZE]
             char module_get_prop[MAX_SLOTS][SLOT_INFO_SIZE]

          Contents of 'module_set_prop' and 'module_get_prop' is
          proprietary."
       ::= { plxPlexcomProp 3 }

    --
    -- Plexcom Module definition. Instance is module type,
    -- 'plxGroupType'. 'Sets' to this variable are saved in NVRAM
    -- but must be reloaded if the NVRAM is cleared. Definitions
    -- may be permanently embedded in the hub software.
    --
    -- Structure is:
    --    #define MAXP      16            /* max ports per module */
    --    struct group_def {
    --      char  g_GroupType;            /* module type  (instance)*/
    --      char  g_bk_id;                /* backplane ID */
    --      char  g_nport;                /* number of ports */
    --      char  g_AutoPart_polarity;    /* polarity of AutoPart bit*/
    --      char  g_LinkStat_polarity;    /* polarity of Link State bit*/
    --      char  g_AdminStat_polarity;   /* polarity of Admin bit */
    --      char  g_MauTypes[MAXP];       /* Port Mau Type */
    --      char  g_AutoPart_Bits[MAXP];  /* Port Auto Partition bit #'s */
    --      char  g_LinkStat_Bits[MAXP];  /* Port Link State bit #'s */
    --      char  g_AdminStat_Bits[MAXP]; /* Port Enable bit #'s */
    --    };
    -- This structure defines the contents of each eight byte
    -- 'module_set_prop' and 'module_get_prop' array used by the
    -- PlexBkBits variable.
    --
    -- g_GroupType is one of the plxGroupType variable values defined
    -- below.
    --
    -- g_bk_id is the one identifier byte returned by the
    -- Plexcom backplane for the module.
    --
    -- g_nport is the total number of ports for this type of module.
    --
    -- g_MauTypes is an array of values defining the type of each port
    -- on the module. Each type value is one of the values defined
    -- by the plxPortMauType variable below. g_MauTypes[0] is the Mau
    -- type for port 1, g_MauTypes[1] is the Mau type for port 2, and
    -- so on.
    --
    -- g_AutoPart_Bits[MAXP] is an array of bit numbers for the
    -- 'Auto Partition State' of each port (see below for an explanation
    -- of 'bit numbers').
    --
    -- g_LinkStat_Bits[MAXP] is an array of bit numbers for the
    -- 'Link State' of each port.
    --
    -- g_AdminStat_Bits[MAXP] is an array of bit numbers for the
    -- 'Admin State' (i.e. port enable) of each port.
    --
    -- The XXXX_Bits elements are arrays of bit numbers. Each element of
    --   the array refers to a port number (0 == port 1, 1 == port 2, etc).
    --
    --   The bit number is a value between 0 and 63 which identifies a
    --   bit position in the plxPlexBkBits variable, according to the
    --   following table:
    --
    --              Byte       Bit
    --              0       7   ....  0
    --              1       15  ....  8
    --              ...         ....
    --              7       63  .... 56
    --
    --   An example of bit numbering:
    --
    --      char bkbuf[13][8], buf[8], mod_ident;
    --      int bit0, bit1, bit7, bit8, bit56, bit63;
    --
    --  get_variable('plxPlexBkBits.0', bkbuf);
    --      bcopy(bkbuf[0], buf, 8);
    --
    --      bit0  = buf[0] & 1;
    --      bit1  = (buf[0] >> 1) & 1;
    --      bit7  = (buf[0] >> 8) & 1
    --      bit8  = buf[1] & 1;
    --      bit56 = buf[7] & 1;
    --      bit63 = (buf[7] >> 8) & 1;
    --      mod_ident = buf[0];             /* bits 0..7 */
    --
    --   An example usage:
    --   Consider a module which has two ports. To enable the first
    --   port bit 3 of the 'module_set_prop' array must be set and
    --   to enable port two, bit 6 must be set.
    --   The following value for g_AdminStat_Bits[] defines this:
    --
    --      g_AdminStat_Bits[] = { 3, 6 };
    --
    -- The XXXX_Bits elements also represent the presence or absence
    --   of a feature on a port basis. Setting the value to 255 indicates
    --   that the corresponding feature is not supported for the port.
    --
    -- The XXX_polarity[] elements are arrays that define the active
    --   polarity of each of the XXX_Bits definitions. A 1 value
    --   indicates that the coressponding bit type is active high. A
    --   0 value indicates the bit is active low. Using the previous
    --   example, if bit 3 and 6 must be set to 0 to enable the
    --   ports then 'g_AdminStat_polarity should be set to 0.
    --
    -- The XXX_polarity elements also define if a particular variable
    --   is available. By setting the polarity to 255 (-1) the
    --   corresponding variable is assumed to be unsupported. For
    --   example, for a module that does not support port enable/
    --   disable, g_AdminStat_polarity should be set to 255.
    --
    plxPlexBkDef OBJECT-TYPE
       SYNTAX  OCTET STRING
       ACCESS  read-write
       STATUS  mandatory
       DESCRIPTION
          "Plexcom module definition. Instance is module type,
          'plxGroupType'."
       ::= { plxPlexcomProp 4 }

    --
    -- Network Hub variables. Modeled after IEEE Hub MIB.
    --
    plxHub  OBJECT IDENTIFIER ::= { plexcom 10 }

    plxHmBasicHubTable OBJECT-TYPE
       SYNTAX  SEQUENCE OF PlxHmBasicHubEntry
       ACCESS  not-accessible
       STATUS  mandatory
       DESCRIPTION
          "Table containing global info for a hub."
       ::= { plxHub 1 }

    plxHmBasicHubEntry OBJECT-TYPE
       SYNTAX  PlxHmBasicHubEntry
       ACCESS  not-accessible
       STATUS  mandatory
DESCRIPTION ""
       INDEX   { plxHubBasicID }
       ::= { plxHmBasicHubTable 1 }
	
    PlxHmBasicHubEntry ::= SEQUENCE  {
       plxHubBasicID        OCTET STRING (SIZE (6)),
       plxHubGroupCapacity  INTEGER,
       plxHubGroupMap       OCTET STRING,
       plxHubGroupCount     INTEGER
    }
	
    plxHubBasicID OBJECT-TYPE
       SYNTAX  OCTET STRING (SIZE (6))
       ACCESS  read-only
       STATUS  mandatory
       DESCRIPTION
          "Hub ID (MAC address of management port)."
       ::= { plxHmBasicHubEntry 1 }
		
    plxHubGroupCapacity OBJECT-TYPE
       SYNTAX  INTEGER (1..255)
       ACCESS  read-only
       STATUS  mandatory
       DESCRIPTION
          "The number of slots available in the hub."
       ::= { plxHmBasicHubEntry 2 }
	
    plxHubGroupMap OBJECT-TYPE
       SYNTAX  OCTET STRING
       ACCESS  read-only
       STATUS  mandatory
       DESCRIPTION
          "A sequence of bytes defining which hub slots are
          populated with groups (cards or groups).  The first byte
          of the sequence represents slot 1, the second byte
          slot 2, etc. A value of '1' indicates presence of a group
          and '0' indicates an absence."
       ::= { plxHmBasicHubEntry 3 }

    plxHubGroupCount OBJECT-TYPE
       SYNTAX  INTEGER (1..255)
       ACCESS  read-only
       STATUS  mandatory
       DESCRIPTION
          "The number of groups currently active in the hub."
       ::= { plxHmBasicHubEntry 4 }

    plxHmBasicGroupTable OBJECT-TYPE
       SYNTAX  SEQUENCE OF PlxHmBasicGroupEntry
       ACCESS  not-accessible
       STATUS  mandatory
       DESCRIPTION
          "A table of info for each hub module."
       ::= { plxHub 2 }
	
    plxHmBasicGroupEntry OBJECT-TYPE
       SYNTAX  PlxHmBasicGroupEntry
       ACCESS  not-accessible
       STATUS  mandatory
DESCRIPTION ""
       INDEX   { plxGroupBasicID }
       ::= { plxHmBasicGroupTable 1 }

    PlxHmBasicGroupEntry ::= SEQUENCE {
       plxGroupHubBasicID         OCTET STRING (SIZE (6)),
       plxGroupBasicID            INTEGER,
       plxGroupNumberOfPorts      INTEGER,
       plxGroupType               INTEGER,
       plxGroupAutoPartState      OCTET STRING,
       plxGroupAdminState         OCTET STRING,
       plxGroupCascadeConfig      INTEGER,
       plxGroupCascadeNetwork     OCTET STRING,
       plxGroupLinkState          OCTET STRING,
       plxGroupLinkPartTrapEnable OCTET STRING,
       plxGroupNetworkSegment     OCTET STRING,
       plxGroupChassisNo          INTEGER
    }
    -- plxGroupCascadeConfig and plxGroupCascadeNetwork added 10-7-92
    -- plxGroupLinkState added 7-28-93
    -- plxGroupLinkPartTrapEnable added 9-15-93
    -- plxGroupNetworkSegment added 2-17-94
    -- plxGroupChassisNo added 3-29-94

    plxGroupHubBasicID OBJECT-TYPE
       SYNTAX  OCTET STRING (SIZE (6))
       ACCESS  read-only
       STATUS  mandatory
       DESCRIPTION
          "Hub identifier (MAC address of management port)."
       ::= { plxHmBasicGroupEntry 1 }
	
    plxGroupBasicID OBJECT-TYPE
       SYNTAX  INTEGER {
          slot1(1),
          slot2(2),
          slot3(3),
          slot4(4),
          slot5(5),
          slot6(6),
          slot7(7),
          slot8(8),
          slot9(9),
          slot10(10),
          slot11(11),
          slot12(12),
          slot13(13),
          slot14(14),
          slot15(15),
          slot16(16)
       }
       ACCESS  read-only
       STATUS  mandatory
       DESCRIPTION
          "Group identifier (module or slot number). First (left/bottom)
          slot is 1."
       ::= { plxHmBasicGroupEntry 2 }
	
    plxGroupNumberOfPorts OBJECT-TYPE
       SYNTAX  INTEGER (1..16)
       ACCESS  read-only
       STATUS  mandatory
       DESCRIPTION
          "Number of ports in this group."
       ::= { plxHmBasicGroupEntry 3 }
	
    plxGroupType OBJECT-TYPE
       SYNTAX  INTEGER {
          removed(0),
          unknown(1),

          -- PlexNet product series
          m8010(2),
          m8011(3),
          m8023A(4),
          m8024A(5),
          m8024T(6),
          m8026A(7),
          m8026T(8),
          m8029M(9),
          m8091M(10),
          m8023(11),
          m8031(13),
          m8031A(14),
          m8033(15),
          m8034(16),
          m8033A(17),
          m8024FO(24),
          m8039M(32),
          m8039S(33),
          m8026FO(34),
          m8408(35),
          m8400FO(36),
          m8032-R(43),
          m8032-1P(44),
          m8032-1PR(45),
          m8032-2P(46),
          m8032-2PR(47),
          m8032-3P(48),
          m8032-3PR(49),
          m8032-4P(50),
          m8032-4PR(51),
          m8032-5P(52),
          m8032-5PR(53),
          m8032-6P(54),
          m8032-6PR(55),
          m2008SX(56),
          m8035(58),
          m8035STP(59),
          m8036(60),
          m8023SX(70),
          m8012SX-1(71),
          m8012SX-6(72),
          m8024SX(73),
          m8027SX(74),
          m8091SXM(75),
          m8029SX-3M(76),
          m8029SX-3S(77),
          m8025SX(78),
          m8025SXT(79),
          mH8025SX(81),
          mS8025SXT(82),
          mS8025SX(83),
          m8408FO(84),
          m8012SX-2(85),
          m8012SX-4(86),
          m8012SX-12(87),
          m8026SX(88),
          m8035SX(89),
          mP8035SX(90),
          m8093SXM(91),
          m8093SXS(92),
          m8039SXM(93),
          m8039SXS(94),

          -- PlexSTACK product series
          m4000i(1000),
          m4000iR(1001),
          m4012(1010),
          m4012i(1011),
          m4012iR(1012),
          m4024(1020),
          m4024i(1021),
          m4024iR(1022),
          m4036(1030),
          m4036i(1031),
          m4036iR(1032),
          m4112(1110),
          m4112i(1111),
          m4112iR(1112),
          m4124(1120),
          m4124i(1121),
          m4124iR(1122),
          m4136(1130),
          m4136i(1131),
          m4136iR(1132)
       }
       ACCESS  read-only
       STATUS  mandatory
       DESCRIPTION
          "Group (module) type."
       ::= { plxHmBasicGroupEntry 4 }
	
    plxGroupAutoPartState OBJECT-TYPE
       SYNTAX  OCTET STRING
       ACCESS  read-only
       STATUS  mandatory
       DESCRIPTION
          "A sequence of bytes defining the auto-partition state
          of each port.  The first byte corresponds to port 1, the
          second byte to port 2, etc. The value of each element
          is of the same type as the 'plxPortAutoPartState' variable."
       ::= { plxHmBasicGroupEntry 5 }
	
    plxGroupAdminState OBJECT-TYPE
       SYNTAX  OCTET STRING
       ACCESS  read-write
       STATUS  mandatory
       DESCRIPTION
          "A sequence of bytes defining the enable state of each
          port.  The first byte corresponds to port 1, the second
          byte to port 2, etc.  The value of each element is of the
          same type as the 'plxPortAdminState' variable."
       ::= { plxHmBasicGroupEntry 6 }
	
    plxGroupCascadeConfig OBJECT-TYPE
       SYNTAX  INTEGER {
          unknown(1),
          local(2),
          remote(3)
       }
       ACCESS  read-only
       STATUS  mandatory
       DESCRIPTION
          "An integer defining the configuration control of bussed
          cascade networks.  For PlexNet SX products, this variable
          is only applicable to 23SX, 24SX, 27SX, etc. modules, and
          not the 91SX, 29SX, etc. modules.  A value of '1' is returned
          for modules which don't support the variable.  A '2' indicates
          local configuration, meaning the hardware switch has been set
          on the board to control the cascade network based on hardware
          switches, and to disallow setting of the cascade network
          by remote management.  A value of '3' indicates remote
          configuration, meaning the hardware switch is set to allow
          remote configuration of the cascade networks."
       ::= { plxHmBasicGroupEntry 7 }

    plxGroupCascadeNetwork OBJECT-TYPE
       SYNTAX  OCTET STRING
       ACCESS  read-write
       STATUS  mandatory
       DESCRIPTION
          "A sequence of bytes defining the selected bussed cascade
          network.  A value of '9' indicates no cascade network
          selected.  This can be SET only on device types. A
          value of '1' through '4' indicates the selected cascade
          network.  A value of '8' (SET only) is used to set the
          device to use its hardware switches to select the
          cascade network.  For PlexNet 8091SX and 8029SX type
          modules, the first byte represents port 1's internal network
          and the second byte port 2's internal network.  A value of '10'
          (hex a) is returned for any module which does not support
          bussed cascade networks."
       ::= { plxHmBasicGroupEntry 8 }

    plxGroupLinkState OBJECT-TYPE
       SYNTAX  OCTET STRING
       ACCESS  read-only
       STATUS  mandatory
       DESCRIPTION
          "A sequence of bytes defining the link state of each port.
          The first byte corresponds to port 1, the second byte to
          port 2, etc.  The value of each element is of the same type
          as the 'plxPortLinkState' variable."
       ::= { plxHmBasicGroupEntry 9 }

    plxGroupLinkPartTrapEnable OBJECT-TYPE
       SYNTAX  OCTET STRING
       ACCESS  read-write
       STATUS  mandatory
       DESCRIPTION
          "A sequence of bytes defining the enabling state for
          generation of link and partition change traps from each
          port.  The first byte corresponds to port 1, the second
          byte to port 2, etc.  A value of '2' indicates trap generation
          for the corresponding port is disabled and a value of '3'
          indicates enabled."
       ::= { plxHmBasicGroupEntry 10 }

    plxGroupNetworkSegment OBJECT-TYPE
       SYNTAX  OCTET STRING
       ACCESS  read-only
       STATUS  mandatory
       DESCRIPTION
          "The network segment that the corresponding group is
          currently operating on.  This is the 'repeater' number
          used when accessing statistical information from the
          agent via other standard MIBs.  The value '255' (hex ff)
          is returned if not applicable."
       ::= { plxHmBasicGroupEntry 11 }

    plxGroupChassisNo OBJECT-TYPE
       SYNTAX  INTEGER
       ACCESS  read-only
       STATUS  mandatory
       DESCRIPTION
          "The number or id of the physical enclosure that the
          corresponding group is operating in.  This variable maps
          a logical grouping of ports into a physical grouping.
          The value '1' is returned for systems in which all groups
          reside in the same physical enclosure."
       ::= { plxHmBasicGroupEntry 12 }

    plxHmBasicPortTable OBJECT-TYPE
       SYNTAX  SEQUENCE OF PlxHmBasicPortEntry
       ACCESS  not-accessible
       STATUS  mandatory
       DESCRIPTION
          "A table of info for the ports within a hub module.
          The instance of each element is 'GroupID.PortID'. For
          example, the Admin State of port 3 of slot 2 is
          'plxPortAdminState.2.3'."
       ::= { plxHub 3 }
	
    plxHmBasicPortEntry OBJECT-TYPE
       SYNTAX  PlxHmBasicPortEntry
       ACCESS  not-accessible
       STATUS  mandatory
DESCRIPTION ""
       INDEX  { plxPortGroupBasicID, plxPortBasicID }
       ::= { plxHmBasicPortTable 1 }

    PlxHmBasicPortEntry ::= SEQUENCE {
       plxPortHubBasicID    OCTET STRING (SIZE (6)),
       plxPortGroupBasicID  INTEGER,
       plxPortBasicID       INTEGER,
       plxPortMauType       INTEGER,
       plxPortAdminState    INTEGER,
       plxPortAutoPartState INTEGER,
       plxPortLinkState     INTEGER
    }
	
    plxPortHubBasicID OBJECT-TYPE
       SYNTAX  OCTET STRING (SIZE (6))
       ACCESS  read-only
       STATUS  mandatory
       DESCRIPTION
          "Hub identifier (MAC address of management port)."
       ::= { plxHmBasicPortEntry 1 }
	
    plxPortGroupBasicID OBJECT-TYPE
       SYNTAX  INTEGER {
          slot1(1),
          slot2(2),
          slot3(3),
          slot4(4),
          slot5(5),
          slot6(6),
          slot7(7),
          slot8(8),
          slot9(9),
          slot10(10),
          slot11(11),
          slot12(12),
          slot13(13),
          slot14(14),
          slot15(15),
          slot16(16)
       }
       ACCESS  read-only
       STATUS  mandatory
       DESCRIPTION
          "Group identifier (module or slot number). First slot is 1."
       ::= { plxHmBasicPortEntry 2 }
		
    plxPortBasicID OBJECT-TYPE
       SYNTAX  INTEGER {
          port1(1), port2(2), port3(3), port4(4), port5(5), port6(6),
          port7(7), port8(8), port9(9), port10(10), port11(11),
          port12(12), port13(13), port14(14), port15(15), port16(16),
          port17(17), port18(18), port19(19), port20(20), port21(21),
          port22(22), port23(23), port24(24), port25(25), port26(26),
          port27(27), port28(28), port29(29), port30(30), port31(31),
          port32(32), port33(33), port34(34), port35(35), port36(36),
          port37(37), port38(38)
       }
       ACCESS  read-only
       STATUS  mandatory
       DESCRIPTION
          "Port identifier (number). First port is the leftmost or
          topmost port of a card and is number 1."
       ::= { plxHmBasicPortEntry 3 }
		
    plxPortMauType OBJECT-TYPE
       SYNTAX  INTEGER {
          unknown(1),
          ieeeAui(2),
          ieeeThin(3),
          ieee10baseT(4),
          ieee10base2(5),
          foirl(6),
          telco50(7),
          tokenringutp(10),
          tokenringstp(11),
          tokenringcoax(12),
          tokenringfiber(13),
          tokenringtelco50(14),
          internalNet(15),
          serial(16),
          as400utp(17),
          as400fiber(18)
       }
       ACCESS  read-only
       STATUS  mandatory
       DESCRIPTION
          "Port physical interface type."
       ::= { plxHmBasicPortEntry 4 }
		
    plxPortAdminState OBJECT-TYPE
       SYNTAX  INTEGER {
          unknown(1),
          disabled(2),
          enabled(3)
       }
       ACCESS  read-write
       STATUS  mandatory
       DESCRIPTION
          "Port enable state."
       ::= { plxHmBasicPortEntry 5 }
		
    plxPortAutoPartState OBJECT-TYPE
       SYNTAX  INTEGER {
          unknown(1),
          notPart(2),
          part(3)
       }
       ACCESS  read-only
       STATUS  mandatory
       DESCRIPTION
          "Port auto-partition state."
       ::= { plxHmBasicPortEntry 6 }

    plxPortLinkState OBJECT-TYPE
       SYNTAX  INTEGER {
          unknown(1),
          up(2),
          down(3)
       }
       ACCESS  read-only
       STATUS  mandatory
       DESCRIPTION
          "Port link state."
       ::= { plxHmBasicPortEntry 7 }

    --
    -- Administrative control and information.
    --
    plxSystemAdmin            OBJECT IDENTIFIER ::= { plexcom 11 }

    plxSysAdmCommunityTable OBJECT-TYPE
       SYNTAX    SEQUENCE OF PlxSysAdmCommunityEntry
       ACCESS    not-accessible
       STATUS    mandatory
       DESCRIPTION
          "A table of SNMP community name entries allowing different
          levels of SNMP access.  A maximum of 5 entries are allowed."
       ::= { plxSystemAdmin 1 }

    plxSysAdmCommunityEntry  OBJECT-TYPE
       SYNTAX    PlxSysAdmCommunityEntry
       ACCESS    not-accessible
       STATUS    mandatory
       DESCRIPTION
          "An entry in the SNMP community table."
       INDEX { plxCommunityIndex }
       ::= { plxSysAdmCommunityTable 1 }

    PlxSysAdmCommunityEntry ::= SEQUENCE {
       plxCommunityIndex        INTEGER (1..5),
       plxCommunityName         DisplayString (SIZE(0..32)),
       plxCommunityAccess       INTEGER
    }

    plxCommunityIndex  OBJECT-TYPE
       SYNTAX    INTEGER (1..5)
       ACCESS    read-only
       STATUS    mandatory
       DESCRIPTION
          "A unique index for this community table entry."
       ::= { plxSysAdmCommunityEntry 1 }

    plxCommunityName  OBJECT-TYPE
       SYNTAX    DisplayString (SIZE(0..32))
       ACCESS    read-write
       STATUS    mandatory
       DESCRIPTION
          "The community name to which this entry grants access.
          This string must be unique among the community names
          defined in all entries of this table.  A community name
          entry does not become effective until the corresponding
          plxCommunityAccess variable is set to a value other than
          invalid(100)."
       ::= { plxSysAdmCommunityEntry 2 }

    plxCommunityAccess  OBJECT-TYPE
       SYNTAX    INTEGER {
          readOnly(1),
          readWrite(2),
          superUser(3),
          invalid(100)
       }
       ACCESS    read-write
       STATUS    mandatory
       DESCRIPTION
          "The access level for the community name.  This variable
          must be set to a value of readOnly(1), readWrite(2), or
          superUser(3) for the corresponding plxCommunityName variable
          in the table to be valid.  A value of readOnly(1) allows
          'GET' only privleges on all MIB objects except the community
          table.  A value of readWrite(2) allows 'GET' and 'SET'
          privleges on all MIB objects except the community table.
          A value of superUser(3) allows 'GET' and 'SET' privleges on
          all MIB objects including the community table.  The value
          invalid(100) is returned for invalid table entries.  A
          'SET' with this value clears the entry from the table."
       ::= { plxSysAdmCommunityEntry 3 }

    --
    -- Variables for configuring and initiating a download of system
    -- software to the device.
    --
    plxSysAdmDownload          OBJECT IDENTIFIER ::= { plxSystemAdmin 2 }

    plxDownloadFileName OBJECT-TYPE
       SYNTAX  DisplayString (SIZE (0..128))
       ACCESS  read-write
       STATUS  mandatory
       DESCRIPTION
          "Name of the file to download via the network to Flash."
       ::=  { plxSysAdmDownload 1 }

    plxDownloadServerAddress OBJECT-TYPE
       SYNTAX  DisplayString (SIZE (0..16))
       ACCESS  read-write
       STATUS  mandatory
       DESCRIPTION
          "The IP address of the server that contains the file to
          download."
       ::=  { plxSysAdmDownload 2 }

    plxDownloadAction OBJECT-TYPE
       SYNTAX  INTEGER {
          noDownload(1),
          download(2)
       }
       ACCESS  read-write
       STATUS  mandatory
       DESCRIPTION
          "Setting this object to download(2) initiates a download of
          system software.  The variables plxDownloadServerAddress and
          plxDownloadFileName must be first set before starting a
          download.  The agent will return the value download(2) when
          a download is currently in progress.  Setting this object to
          noDownload(1) has no effect.  The agent will return this value
          unless a download is in progress."
       ::=  { plxSysAdmDownload 3 }

    plxDownloadStatus OBJECT-TYPE
       SYNTAX  INTEGER {
          downloadSuccess(1),
          downloadNotOccurred(2),
          badFlash(3),
          badServerAddress(4),
          badFile(5),
          tftpUndefined(6),
          tftpFileNotFound(7),
          tftpAccessViolation(8),
          tftpIllegalOperation(10),
          tftpUnknownTransferID(11),
          downloadInProgress(14)
       }
       ACCESS  read-only
       STATUS  mandatory
       DESCRIPTION
          "The status of the last download performed.  The value
          downloadSuccess(1) indicates a successful download, and that
          the device is operating from the downloaded firmware.
          noDownloadOccurred(2) is returned if no firmware download has yet
          been performed.  If Flash EPROM is not present on the board
          or is bad, badFlash(3) is returned.  The value
          badServerAddress(4) indicates the IP address of the server
          configured by the plxDownloadServerAddress variable is bad.
          badFile(5) indicates the downloaded file had a bad checksum
          or is corrupt.  The value downloadInProgress(14) indicates that
          a download is currently being performed.  The remaining values
          indicate a TFTP protocol specific failure during the most recent
          download, and are the error codes defined in RFC 783, offset
          by six."
       ::=  { plxSysAdmDownload 4 }

    --
    -- Variables for configuring trap generation from the managed device.
    --
    plxSysAdmTrapTable OBJECT-TYPE
       SYNTAX  SEQUENCE OF PlxSysAdmTrapEntry
       ACCESS  not-accessible
       STATUS  mandatory
DESCRIPTION ""
       ::= { plxSystemAdmin 3 }

    plxSysAdmTrapEntry OBJECT-TYPE
       SYNTAX  PlxSysAdmTrapEntry
       ACCESS  not-accessible
       STATUS  mandatory
DESCRIPTION ""
       INDEX  { plxTrapIndex }
       ::= { plxSysAdmTrapTable 1 }

    PlxSysAdmTrapEntry ::= SEQUENCE {
       plxTrapIndex              INTEGER,
       plxTrapStandardEnable     INTEGER,
       plxTrapPlexcomEnable      INTEGER,
       plxTrapRepeaterEnable     INTEGER,
       plxTrapNovellEnable       INTEGER
    }

    plxTrapIndex OBJECT-TYPE
       SYNTAX  INTEGER
       ACCESS  read-only
       STATUS  mandatory
       DESCRIPTION
          "This object identifies the entry within the trap table."
       ::= { plxSysAdmTrapEntry 1 }

    plxTrapStandardEnable OBJECT-TYPE
       SYNTAX  INTEGER {
          other(1),
          disabled(2),
          enabled(3)
       }
       ACCESS  read-write
       STATUS  mandatory
       DESCRIPTION
          "Enable or disable generation of standard traps for this
          entry."
       ::= { plxSysAdmTrapEntry 4 }

    plxTrapPlexcomEnable OBJECT-TYPE
       SYNTAX  INTEGER {
          other(1),
          disabled(2),
          enabled(3)
       }
       ACCESS  read-write
       STATUS  mandatory
       DESCRIPTION
          "Enable or disable Plexcom specific trap generation
          for this entry."
       ::= { plxSysAdmTrapEntry 5 }

    plxTrapRepeaterEnable OBJECT-TYPE
       SYNTAX  INTEGER {
          other(1),
          disabled(2),
          enabled(3)
       }
       ACCESS  read-write
       STATUS  mandatory
       DESCRIPTION
          "Enable or disable Repeater MIB specific trap generation
          for this entry."
       ::= { plxSysAdmTrapEntry 6 }

    plxTrapNovellEnable OBJECT-TYPE
       SYNTAX  INTEGER {
          other(1),
          disabled(2),
          enabled(3)
       }
       ACCESS  read-write
       STATUS  mandatory
       DESCRIPTION
          "Enable or disable Novell HMI MIB specific trap generation
          for this entry."
       ::= { plxSysAdmTrapEntry 7 }
	
    --
    -- Variables for controlling access to and parameters of other MIB
    -- specifications supported by the managed device.
    --
    plxSysAdmMibControl     OBJECT IDENTIFIER ::= { plxSystemAdmin 4 }

    plxMcZeroStatCounters OBJECT-TYPE
       SYNTAX  INTEGER {
          noZero(1),
          zeroCounters(2)
       }
       ACCESS  read-write
       STATUS  mandatory
       DESCRIPTION
          "Zero statistical counters maintained by the managed device.
          This zeros the port- and network-level performance stats
          maintained in all MIBs supported by the device.  The variable
          should be set to 'zeroCounters' to clear statistical entries.
          A value of 'noZero' is returned when this variable is read."
       ::= { plxSysAdmMibControl 1 }
	
    plxMcNetworkSelectRptrMib OBJECT-TYPE
       SYNTAX  INTEGER
       ACCESS  read-write
       STATUS  mandatory
       DESCRIPTION
          "Select the 'repeater number' that the information in the
          Repeater MIB on the managed device represents.  This variable
          is used for agents which manage multiple repeaters."
       ::= { plxSysAdmMibControl 2 }
	
    plxMcNetworkSelectRmonMib OBJECT-TYPE
       SYNTAX  INTEGER
       ACCESS  read-write
       STATUS  mandatory
       DESCRIPTION
          "Select the 'repeater number' that the information in the
          RMON MIB on the managed device represents.  This variable
          is used for agents which manage multiple repeaters."
       ::= { plxSysAdmMibControl 3 }
	
    --
    -- Configuration of security-related features.
    --
    plxSecurity		OBJECT IDENTIFIER ::= { plexcom 12 }

    plxIntruderControlGroupTable OBJECT-TYPE
       SYNTAX    SEQUENCE OF PlxIntruderControlGroupEntry
       ACCESS    not-accessible
       STATUS    mandatory
       DESCRIPTION
          "A table of parameters for configuring software-controlled
          intruder detection for groups of ports."
       ::= { plxSecurity 1 }

    plxIntruderControlGroupEntry  OBJECT-TYPE
       SYNTAX    PlxIntruderControlGroupEntry
       ACCESS    not-accessible
       STATUS    mandatory
       DESCRIPTION
          "An entry in the intruder detection group table."
       INDEX { plxIcGroupGroupIndex }
       ::= { plxIntruderControlGroupTable 1 }

    PlxIntruderControlGroupEntry ::= SEQUENCE {
       plxIcGroupGroupIndex               INTEGER,
       plxIcGroupAuthorizationType        INTEGER,
       plxIcGroupAlarmAction              INTEGER,
       plxIcGroupAuthorizedAddressMode    INTEGER,
       plxIcGroupDetectionStatus          INTEGER
    }

    plxIcGroupGroupIndex  OBJECT-TYPE
       SYNTAX    INTEGER
       ACCESS    read-only
       STATUS    mandatory
       DESCRIPTION
          "A unique group index for which this intruder control table
          entry represents."
       ::= { plxIntruderControlGroupEntry 1 }

    plxIcGroupAuthorizationType  OBJECT-TYPE
       SYNTAX  INTEGER {
          noUser(1),
          singleUser(2),
          multiValue(9)
       }
       ACCESS    read-write
       STATUS    mandatory
       DESCRIPTION
          "The authorization level of the intruder detection on the
          corresponding group of ports.  If set to singleUser(2) (the
          initial default), alarms will be triggered when more than
          one source address is detected on a given port.  If set to
          noUser(1), no users are allowed on any port, and an alarm
          will be triggered if any traffic is generated on a port."
       ::= { plxIntruderControlGroupEntry 2 }

    plxIcGroupAlarmAction  OBJECT-TYPE
       SYNTAX  INTEGER {
          none(1),
          trapOnly(2),
          disableOnly(3),
          trapAndDisable(4),
          multiValue(9)
       }
       ACCESS    read-write
       STATUS    mandatory
       DESCRIPTION
          "The action to be taken when an alarm occurs on any port in
          the corresponding group.  If this variable is set to trapOnly(2),
          the initial default, an SNMP trap will be generated when an
          intruder detect alarm occurs.  If set to disableOnly(3), the
          port will be disabled when an alarm occurs.  If set to
          trapAndDisable(4), both a trap will be generated and the port
          will be disabled.  If set to none(1), no action will be taken."
       ::= { plxIntruderControlGroupEntry 3 }

    plxIcGroupAuthorizedAddressMode  OBJECT-TYPE
       SYNTAX  INTEGER {
          autoLearn(1),
          useAuthorized(2),
          multiValue(9)
       }
       ACCESS    read-write
       STATUS    mandatory
       DESCRIPTION
          "The method by which the plxIcAuthorizedSourceAddress
          variable for the corresponding port should be configured.  If
          this variable is set to autoLearn(1), the initial default, the
          allowed single source address on the port will be configured
          automatically by the address of the next valid packet on that
          port.  If set to useAuthorized(2), the address as configured by
          an SNMP SET operation on the plxIcAuthorizedSourceAddress
          variable will be used."
       ::= { plxIntruderControlGroupEntry 4 }

    plxIcGroupDetectionStatus  OBJECT-TYPE
       SYNTAX  INTEGER {
          inactive(1),
          active(2),
          triggered(3),
          multiValue(9)
       }
       ACCESS    read-write
       STATUS    mandatory
       DESCRIPTION
          "The current status of the intruder detection on the
          corresponding port.  The initial default for all ports is
          inactive(1), meaning that intruder detection is not active
          on the port.  If set to active(2), intruder detection is
          enabled, and this value will then also be returned for an
          SNMP GET operation.  If an alarm is generated, this variable
          will take on the value triggered(3).  A set with the value
          active(2) will clear the triggered condition back to active.
          Intruder detection on the port is effectively still active in
          the triggered condition.  The value triggered(3) is illegal
          for a SET operation."
       ::= { plxIntruderControlGroupEntry 5 }


    plxIntruderControlTable OBJECT-TYPE
       SYNTAX    SEQUENCE OF PlxIntruderControlEntry
       ACCESS    not-accessible
       STATUS    mandatory
       DESCRIPTION
          "A table of parameters for configuring software-controlled
          intruder detection."
       ::= { plxSecurity 2 }

    plxIntruderControlEntry  OBJECT-TYPE
       SYNTAX    PlxIntruderControlEntry
       ACCESS    not-accessible
       STATUS    mandatory
       DESCRIPTION
          "An entry in the intruder detection table."
       INDEX { plxIcGroupIndex, plxIcPortIndex }
       ::= { plxIntruderControlTable 1 }

    PlxIntruderControlEntry ::= SEQUENCE {
       plxIcGroupIndex               INTEGER,
       plxIcPortIndex                INTEGER,
       plxIcAuthorizationType        INTEGER,
       plxIcAlarmAction              INTEGER,
       plxIcAuthorizedAddressMode    INTEGER,
       plxIcAuthorizedSourceAddress  OCTET STRING (SIZE (6)),
       plxIcCurrentSourceAddress     OCTET STRING (SIZE (6)),
       plxIcDetectionStatus          INTEGER
    }

    plxIcGroupIndex  OBJECT-TYPE
       SYNTAX    INTEGER
       ACCESS    read-only
       STATUS    mandatory
       DESCRIPTION
          "A unique group index for which this intruder control table
          entry represents."
       ::= { plxIntruderControlEntry 1 }

    plxIcPortIndex  OBJECT-TYPE
       SYNTAX    INTEGER
       ACCESS    read-only
       STATUS    mandatory
       DESCRIPTION
          "A unique port index for which this intruder control table
          entry represents."
       ::= { plxIntruderControlEntry 2 }

    plxIcAuthorizationType  OBJECT-TYPE
       SYNTAX  INTEGER {
          noUser(1),
          singleUser(2)
       }
       ACCESS    read-write
       STATUS    mandatory
       DESCRIPTION
          "The authorization level of the intruder detection on the
          corresponding port.  If set to singleUser(2) (the initial
          default), an alarm will be triggered when more than one source
          address is detected on the port.  If set to noUser(1), no
          users are allowed on the port, and an alarm will be triggered
          if any traffic is generated on the port."
       ::= { plxIntruderControlEntry 3 }

    plxIcAlarmAction  OBJECT-TYPE
       SYNTAX  INTEGER {
          none(1),
          trapOnly(2),
          disableOnly(3),
          trapAndDisable(4)
       }
       ACCESS    read-write
       STATUS    mandatory
       DESCRIPTION
          "The action to be taken when an alarm occurs on the
          corresponding port.  If this variable is set to trapOnly(2),
          the initial default, an SNMP trap will be generated when an
          intruder detect alarm occurs.  If set to disableOnly(3), the
          port will be disabled when an alarm occurs.  If set to
          trapAndDisable(4), both a trap will be generated and the port
          will be disabled.  If set to none(1), no action will be taken."
       ::= { plxIntruderControlEntry 4 }

    plxIcAuthorizedAddressMode  OBJECT-TYPE
       SYNTAX  INTEGER {
          autoLearn(1),
          useAuthorized(2)
       }
       ACCESS    read-write
       STATUS    mandatory
       DESCRIPTION
          "The method by which the plxIcAuthorizedSourceAddress
          variable for the corresponding port should be configured.  If
          this variable is set to autoLearn(1), the initial default, the
          allowed single source address on the port will be configured
          automatically by the address of the next valid packet on that
          port.  If set to useAuthorized(2), the address as configured by
          an SNMP SET operation on the plxIcAuthorizedSourceAddress
          variable will be used."
       ::= { plxIntruderControlEntry 5 }

    plxIcAuthorizedSourceAddress  OBJECT-TYPE
       SYNTAX    OCTET STRING (SIZE (6))
       ACCESS    read-write
       STATUS    mandatory
       DESCRIPTION
          "The current authorized source address allowed by intruder
          detection on the corresponding port.  This variable is only
          valid if the plxIcAuthorizationType variable for the port
          is singleUser(2).  This variable must be configured if the
          plxIcAuthorizedAddressMode variable is set to useAuthorized.
          If plxIcAuthorizedAddressMode is set to autoLearn, the
          authorized source address will be automatically configured to be
          the source address of the last valid packet that was generated
          from the port (or the next valid packet if the port has had no
          traffic) after setting the plxIcDetectionStatus variable to
          active(2)."
       ::= { plxIntruderControlEntry 6 }

    plxIcCurrentSourceAddress  OBJECT-TYPE
       SYNTAX    OCTET STRING (SIZE (6))
       ACCESS    read-only
       STATUS    mandatory
       DESCRIPTION
          "The source address of the last valid packet that was generated
          on the corresponding port.  If an alarm was generated on the
          port and the port was disabled based on the setting of
          plxIcAlarmAction, this variable will contain the source
          address of the intruding device."
       ::= { plxIntruderControlEntry 7 }

    plxIcDetectionStatus  OBJECT-TYPE
       SYNTAX  INTEGER {
          inactive(1),
          active(2),
          triggered(3)
       }
       ACCESS    read-write
       STATUS    mandatory
       DESCRIPTION
          "The current status of the intruder detection on the
          corresponding port.  The initial default for all ports is
          inactive(1), meaning that intruder detection is not active
          on the port.  If set to active(2), intruder detection is
          enabled, and this value will then also be returned for an
          SNMP GET operation.  If an alarm is generated, this variable
          will take on the value triggered(3).  A set with the value
          active(2) will clear the triggered condition back to active.
          Intruder detection on the port is effectively still active in
          the triggered condition.  The value triggered(3) is illegal
          for a SET operation."
       ::= { plxIntruderControlEntry 8 }

	
    --
    -- Plexcom enterprise trap definitions, defined using the conventions
    -- in RFC 1215 [8].
    --
    plxPanicMesgTrap TRAP-TYPE
       ENTERPRISE  plexcom
       VARIABLES   { plxSysPanicMesg }
       DESCRIPTION
          "The plxPanicMesgTrap trap is generated when the agent
          resets for a reason other than a normal hardware reset
          or restart condition.  The plxSysPanicMesg variable
          contains a textual explanation for the reset, as saved
          in non-volatile memory."
       ::= 4

    plxGenericHubTrap TRAP-TYPE
       ENTERPRISE  plexcom
       VARIABLES   { plxPortLinkState, plxPortAutoPartState, plxGroupType }
       DESCRIPTION
          "The generic hub trap is sent when one of several
          changes occurs in the status of the agent.  There are
          three conditions which may cause this: the addition or
          deletion of a group (usually a module) from the agent (or
          chassis), in which case the plxGroupType variable is
          returned, and changes in the autopartition or link states
          of a given port, in which case the plxPortAutoPartState or
          plxPortLinkState variables are returned, respectively."
       ::= 5

    plxSecurityViolationTrap TRAP-TYPE
       ENTERPRISE  plexcom
       VARIABLES   { plxIcCurrentSourceAddress }
       DESCRIPTION
          "The security violation trap is sent when an alarm
          occurs in the agent that indicates a configured security
          provision has been violated.  In conjunture with the
          plxIntruderControlTable, this trap is sent when an
          non-allowed intruder source address is detected on a
          port.  In this case, the plxIcCurrentSourceAddress
          variable is returned indicating the violating address
          on the affected port."
       ::= 6

    END
