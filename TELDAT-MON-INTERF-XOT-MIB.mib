-- Teldat, S.A.

    -- Parque Tecnolgico de Madrid

    -- 28760, Tres Cantos (Madrid)

    -- Tlf: 34-918076565

    -- Fax: 34-918076521

    -- e-mail: id@teldat.es


    -- MIB privada de Teldat

    -- Historial:
    --      07/02/14    M.A. Pastor     XH 3523. Errors with HP Openview 9.20
    -- 1.2  04/02/08    M.A. Berrojo    HIT 2802
    -- 1.1  03/10/07    M.A. Berrojo    Actualizacion con nuevos parametros
    -- 1.0  01/07/04    J. Molina       Archivo procedente de XOT.mib

    -- Historial de XOT.mib:
    -- 01/10/01  N. Villaseor  Traduccin a ingles
    -- 01/12/00  M.A. Pastor    Modificaciones para que pueda ser compilada
    --                          utilizando compiladores distintos del de Teldat
    -- 14/11/00  J. Alvarez     Implementacion inicial

-------------------------------------------------------------------------------

 TELDAT-MON-INTERF-XOT-MIB DEFINITIONS ::= BEGIN

    IMPORTS
            Gauge, Counter
        FROM RFC1155-SMI
            OBJECT-TYPE
        FROM RFC-1212
            telProdNpMonInterfNodo
        FROM TELDAT-SW-STRUCTURE-MIB;


    -- XOT protocol

    telProdNpMonInterfXot   OBJECT IDENTIFIER ::= { telProdNpMonInterfNodo 3 }

    telProdNpMonInterfXotStategroup OBJECT IDENTIFIER ::= { telProdNpMonInterfXot 1 }

    telProdNpMonInterfXotStateTotalserv OBJECT-TYPE
        SYNTAX Gauge
        ACCESS read-only
        STATUS mandatory
        DESCRIPTION
        "Max number of XOT connections"
        ::={ telProdNpMonInterfXotStategroup 1 }

    telProdNpMonInterfXotStateServlistening OBJECT-TYPE
        SYNTAX Gauge
        ACCESS read-only
        STATUS mandatory
        DESCRIPTION
        "Number of listening servers."
        ::={ telProdNpMonInterfXotStategroup 2 }

    telProdNpMonInterfXotStateServopened OBJECT-TYPE
        SYNTAX Gauge
        ACCESS read-only
        STATUS mandatory
        DESCRIPTION
        "Number of open servers."
        ::={ telProdNpMonInterfXotStategroup 3 }

    telProdNpMonInterfXotStateServclients OBJECT-TYPE
        SYNTAX Gauge
        ACCESS read-only
        STATUS mandatory
        DESCRIPTION
        "Number of client servers."
        ::={ telProdNpMonInterfXotStategroup 4 }

    telProdNpMonInterfXotStateCurrentCallRequest OBJECT-TYPE
        SYNTAX Gauge
        ACCESS read-only
        STATUS mandatory
        DESCRIPTION
        "Current number of XOT calls requested."
        ::={ telProdNpMonInterfXotStategroup 5 }

    telProdNpMonInterfXotStateCurrentCallActive OBJECT-TYPE
        SYNTAX Gauge
        ACCESS read-only
        STATUS mandatory
        DESCRIPTION
        "Current number of XOT calls established."
        ::={ telProdNpMonInterfXotStategroup 6 }

    telProdNpMonInterfXotStateTotalCallRefused OBJECT-TYPE
        SYNTAX Gauge
        ACCESS read-only
        STATUS obsolete
        DESCRIPTION
        "Total Number of refused XOT calls."
        ::={ telProdNpMonInterfXotStategroup 7 }

    telProdNpMonInterfXotStateTCPOpenConnection OBJECT-TYPE
        SYNTAX Gauge
        ACCESS read-only
        STATUS mandatory
        DESCRIPTION
        "Number of TCP connection established: in calls or in standby."
        ::={ telProdNpMonInterfXotStategroup 8 }

    telProdNpMonInterfXotStateTCPStandbyConnection OBJECT-TYPE
        SYNTAX Gauge
        ACCESS read-only
        STATUS mandatory
        DESCRIPTION
        "Number of TCP connection in standby."
        ::={ telProdNpMonInterfXotStategroup 9 }

    telProdNpMonInterfXotStateTotalCallRefusedCounter OBJECT-TYPE
        SYNTAX Counter
        ACCESS read-only
        STATUS mandatory
        DESCRIPTION
        "Total Number of refused XOT calls."
        ::={ telProdNpMonInterfXotStategroup 10 }

END
