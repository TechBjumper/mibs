--
-- MODULE-IDENTITY
--  OrgName
--    Fortinet, Inc.
--  ContactInfo
--     Technical Support
--     e-mail: support@fortinet.com
--     http://www.fortinet.com
--

FORTIMAIL-MIB-220 DEFINITIONS ::= BEGIN
	IMPORTS
		DisplayString
			FROM SNMPv2-TC
		MODULE-IDENTITY, OBJECT-TYPE, Integer32, Gauge32, Counter32, 
		enterprises, IpAddress
			FROM SNMPv2-SMI;

	--
	-- Textual conventions --
	--

	FmlBoolState ::= INTEGER { 
		disabled ( 1 ),
		enabled  ( 2 )
	} 

	FmlIndex ::= INTEGER (
		0 .. 2147483647
	)

	FmlOpMode ::= INTEGER { 
		gateway     ( 1 ),
		transparent ( 2 ),
		server		( 3 )
	}

	FmlSessProto ::= INTEGER  {
		ip   ( 0 ) ,
		icmp ( 1 ) ,
		igmp ( 2 ) ,
		ipip ( 4 ) ,
		tcp  ( 6 ) , 
		egp  ( 8 ) ,
		pup  ( 12 ) ,				
		udp  ( 17 ) ,
		idp  ( 22 ) ,
		ipv6 ( 41 ) ,
		rsvp ( 46 ) ,
		gre  ( 47 ) ,
		esp  ( 50 ) ,
		ah   ( 51 ) ,
		ospf ( 89 ) ,
		pim  ( 103 ) ,
		comp ( 108 ) ,
		raw  ( 255 )
	}

	FmlLanguageCode ::= INTEGER  { 
		western ( 1 ) , 
		simplifiedChinese ( 2 ) , 
		traditionalChinese ( 3 ) , 
		japanese ( 4 ) , 
		kerean ( 5 ) , 
		default ( 6 ) 
	} 

	FmlSysEventCode ::= INTEGER {
		systemHalt (1),
		systemReboot (2),
		systemReload (3),
		systemUpgrade (4),
		guiUpgrade (5),
		logdiskFormat (6),
		maildiskFormat (7),
		avdbUpdate (8) 
	}

	FmlRAIDCode ::= INTEGER {
		degradedArray (1),
		sparesMissing (2),
		rebuildStarted (3),
		rebuildFinished (4),
		fail (5),
		failSpare (6),
		spareActive (7)
	}	
	
	FmlHAEventId ::= INTEGER {
		masterUnitSwitch (1),
		slaveUnitSwitch  (2),
		unitShutdown (3)
	}	
	
	
	--
	--
	--

	fortinet        OBJECT IDENTIFIER ::=  { enterprises  12356 }
	fortimail		OBJECT IDENTIFIER ::=  { fortinet  1688 }
	
	fmlSystem       OBJECT IDENTIFIER ::=  { fortimail  1 }
--	fmlAntivirus    OBJECT IDENTIFIER ::=  { fortimail  2 }
--	fmlAntispam     OBJECT IDENTIFIER ::=  { fortimail  3 }
	fmlTraps        OBJECT IDENTIFIER ::=  { fortimail  0 }

	fmlSysOptions   OBJECT IDENTIFIER ::=  { fmlSystem 101 }
	fmlIp			OBJECT IDENTIFIER ::=  { fmlSystem 102 }
	fmlMailOptions  OBJECT IDENTIFIER ::=  { fmlSystem 103 }
	
	-- fmlSystem

	fmlSysModel          OBJECT-TYPE
		SYNTAX          DisplayString  ( SIZE ( 0 .. 64  ) ) 
		MAX-ACCESS      read-only
		STATUS          current
		DESCRIPTION     "System model string"
		::= { fmlSystem    1 }

	fmlSysSerial         OBJECT-TYPE
		SYNTAX          DisplayString  ( SIZE ( 0 .. 32  ) ) 
		MAX-ACCESS      read-only
		STATUS          current
		DESCRIPTION     "Device serial number"
		::= { fmlSystem    2 }

	fmlSysVersion        OBJECT-TYPE
		SYNTAX          DisplayString  ( SIZE ( 0 .. 128 ) ) 
		MAX-ACCESS      read-only
		STATUS          current
		DESCRIPTION     "Device firmware version"
		::= { fmlSystem    3 }

	fmlSysVersionAv      OBJECT-TYPE
		SYNTAX          DisplayString  ( SIZE ( 0 .. 128 ) ) 
		MAX-ACCESS      read-only
		STATUS          current
		DESCRIPTION     "Antivirus DB version"
		::= { fmlSystem    4 }

	fmlSysOpMode         OBJECT-TYPE
		SYNTAX          FmlOpMode
		MAX-ACCESS      read-only
		STATUS          current
		DESCRIPTION     "Operational mode (Gateway, Transparent or Server)"
		::= { fmlSystem    5 }

	fmlSysCpuUsage       OBJECT-TYPE
		SYNTAX          Gauge32
		MAX-ACCESS      read-only
		STATUS          current
		DESCRIPTION     "Instantaneous CPU usage"
		::= { fmlSystem    6 }

	fmlSysMemUsage       OBJECT-TYPE
		SYNTAX          Gauge32
		MAX-ACCESS      read-only
		STATUS          current
		DESCRIPTION     "Instantaneous memory utilization"
		::= { fmlSystem    7 }

	fmlSysLogDiskUsage   OBJECT-TYPE
		SYNTAX          Gauge32
		MAX-ACCESS      read-only
		STATUS          current
		DESCRIPTION     "Instantaneous log disk usage"
		::= { fmlSystem    8 }

	fmlSysMailDiskUsage  OBJECT-TYPE
		SYNTAX          Gauge32
		MAX-ACCESS      read-only
		STATUS          current
		DESCRIPTION     "Instantaneous mail disk usage"
		::= { fmlSystem    9 }

	fmlSysSesCount       OBJECT-TYPE
		SYNTAX          Gauge32
		MAX-ACCESS      read-only
		STATUS          current
		DESCRIPTION     "Instantaneous session count"
		::= { fmlSystem    10 }

	fmlSysEventCode OBJECT-TYPE
		SYNTAX          FmlSysEventCode
		MAX-ACCESS      read-only
		STATUS          current
		DESCRIPTION     "System component events"
		::= { fmlSystem  11 }

	fmlRAIDCode OBJECT-TYPE
		SYNTAX          FmlRAIDCode
		MAX-ACCESS      read-only
		STATUS          current
		DESCRIPTION     "RAID system events"
		::= { fmlSystem  12 }

	fmlRAIDDevName      OBJECT-TYPE
		SYNTAX          DisplayString  ( SIZE ( 0 .. 32  ) ) 
		MAX-ACCESS      read-only
		STATUS          current
		DESCRIPTION     "RAID Device name"
		::= { fmlSystem    13 }

	fmlHAEventId OBJECT-TYPE
		SYNTAX          FmlHAEventId
		MAX-ACCESS      read-only
		STATUS          current
		DESCRIPTION     "HA event type ID"
		::= { fmlSystem  14 }

	fmlHAUnitIp OBJECT-TYPE
		SYNTAX          IpAddress
		MAX-ACCESS      read-only
		STATUS          current
		DESCRIPTION     "Unit IP address where event occurs "
		::= { fmlSystem  15 }

	fmlHAEventReason      OBJECT-TYPE
		SYNTAX          DisplayString  ( SIZE ( 0 .. 32  ) ) 
		MAX-ACCESS      read-only
		STATUS          current
		DESCRIPTION     "The reason for the HA event"
		::= { fmlSystem    16 }

	fmlArchiveServerIp OBJECT-TYPE
		SYNTAX          IpAddress
		MAX-ACCESS      read-only
		STATUS          current
		DESCRIPTION     "IP address of the remote Archive Server"
		::= { fmlSystem  18 }
		
		
	fmlArchiveFilename      OBJECT-TYPE
		SYNTAX          DisplayString  ( SIZE ( 0 .. 32  ) ) 
		MAX-ACCESS      read-only
		STATUS          current
		DESCRIPTION     "Archive mail file name"
		::= { fmlSystem    19 }


	-- fmlSystem . fmlSysOptions

	fmlSysOptIdleTimeout OBJECT-TYPE
		SYNTAX          Integer32
		MAX-ACCESS      read-only
		STATUS          current
		DESCRIPTION     "Idle period after which the administrator
		                 is automatically logged out off the system"
		::= { fmlSysOptions  1 }

	fmlSysOptAuthTimeout	OBJECT-TYPE	
		SYNTAX          Integer32
		MAX-ACCESS      read-only
		STATUS          current
		DESCRIPTION     "Authentication idle timeout value"
		::= { fmlSysOptions  2 }
		
	fmlSysOptsLan	OBJECT-TYPE	
		SYNTAX			FmlLanguageCode  
		MAX-ACCESS      read-only
		STATUS          current
		DESCRIPTION		"Web administration language"
		::=  { fmlSysOptions 3 }			

	fmlSysOptsLcdProt	OBJECT-TYPE	
		SYNTAX			FmlBoolState 
		MAX-ACCESS      read-only
		STATUS          current
		DESCRIPTION		"Enable or disable LCD control buttons protection"
		::=  { fmlSysOptions 4 }		
		
	-- fmlSystem . fmlIp
	
	fmlIpSessTable       OBJECT-TYPE
        	SYNTAX      SEQUENCE OF FmlIpSessEntry
	        MAX-ACCESS  not-accessible
        	STATUS      current
	        DESCRIPTION "IP Sessions Info"
        	::= { fmlIp        2 }

	fmlIpSessEntry	OBJECT-TYPE
        	SYNTAX      FmlIpSessEntry
	        MAX-ACCESS  not-accessible
        	STATUS      current
	        DESCRIPTION "Particular IP Session info"
	        INDEX       { fmlIpSessIndex }
        	::= { fmlIpSessTable 1 }

	FmlIpSessEntry ::=
        	SEQUENCE {
		    fmlIpSessIndex	FmlIndex,
		    fmlIpSessProto	FmlSessProto,
		    fmlIpSessFromAddr	IpAddress,
		    fmlIpSessFromPort	INTEGER,
		    fmlIpSessToAddr	IpAddress,
		    fmlIpSessToPort	INTEGER,
		    fmlIpSessExp		Counter32
        	}

	fmlIpSessIndex	OBJECT-TYPE	
		SYNTAX      FmlIndex
		MAX-ACCESS  read-only
		STATUS      current
		DESCRIPTION "An index value that uniquely identifies
                	     an IP session"
		::=  { fmlIpSessEntry  1 }

	fmlIpSessProto	OBJECT-TYPE	
		SYNTAX      FmlSessProto
		MAX-ACCESS  read-only
		STATUS      current
		DESCRIPTION "The protocol of the connection"
		::=  { fmlIpSessEntry  2 }

	fmlIpSessFromAddr	OBJECT-TYPE	
		SYNTAX      IpAddress
		MAX-ACCESS  read-only
		STATUS      current
		DESCRIPTION "Source IP address"
		::=  { fmlIpSessEntry  3 }

	fmlIpSessFromPort	OBJECT-TYPE	
		SYNTAX      INTEGER  ( 0 .. 65535  )
		MAX-ACCESS  read-only
		STATUS      current
		DESCRIPTION "Source Port number"
		::=  { fmlIpSessEntry  4 }

	fmlIpSessToAddr	OBJECT-TYPE	
		SYNTAX      IpAddress
		MAX-ACCESS  read-only
		STATUS      current
		DESCRIPTION "Destination IP address"
		::=  { fmlIpSessEntry  5 }

	fmlIpSessToPort	OBJECT-TYPE	
		SYNTAX      INTEGER  ( 0 .. 65535  )
		MAX-ACCESS  read-only
		STATUS      current
		DESCRIPTION "Destination Port number"
		::=  { fmlIpSessEntry  6 }

	fmlIpSessExp	OBJECT-TYPE	
		SYNTAX      Counter32
		MAX-ACCESS  read-only
		STATUS      current
		DESCRIPTION "Time (in seconds) before connection expires"
		::=  { fmlIpSessEntry  7 }

	-- fmlSystem . fmlMailOptions

	fmlMailOptionsDeferQueue OBJECT-TYPE
		SYNTAX          Counter32
		MAX-ACCESS      read-only
		STATUS          current
		DESCRIPTION     "Instantaneous deferred emails number"
		::= { fmlMailOptions  1 }
			
END
