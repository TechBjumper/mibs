-- file automatically created


TELDAT-TRAP-BSPF-MIB DEFINITIONS ::= BEGIN


IMPORTS
	MODULE-IDENTITY,OBJECT-TYPE,OBJECT-IDENTITY,NOTIFICATION-TYPE,Integer32,IpAddress
		FROM SNMPv2-SMI
	DisplayString
		FROM SNMPv2-TC
	telEventTraps
		FROM TELDAT-MIB;


bspfTrapsMIB MODULE-IDENTITY
    LAST-UPDATED "201401200930Z"
    ORGANIZATION "Teldat, S.A."
    CONTACT-INFO 
        "Teldat, S.A.
        Customer Service

        Postal: Parque Tecnologico de Madrid
                Tres Cantos 28760
                Madrid, SPAIN

        Tel.: +34 918 076 565

        http://www.teldat.com"
    DESCRIPTION
        "This Module Information Base file is defined for managing received
        SNMP notifications generated by the BSPF event subsystem."
    REVISION "201401200930Z"
    DESCRIPTION "Initial implementation"
        ::= { telEventTraps 194 }


bspfEventsGroup	OBJECT IDENTIFIER	::= { bspfTrapsMIB 1 }

bspfNotifications	OBJECT IDENTIFIER	::= { bspfTrapsMIB 2 }
bspfNotificationsPrefix	OBJECT IDENTIFIER	::= { bspfNotifications 0 }

bspfEventObjects1 OBJECT-IDENTITY
    STATUS current
    DESCRIPTION
        "Event BSPF.1
        Bridge has detected an incoming packet whose destination matches a
        spoofed MAC address."
    ::= { bspfEventsGroup 1 }

bspf1-src-mac OBJECT-TYPE
    SYNTAX DisplayString
    MAX-ACCESS accessible-for-notify
    STATUS current
    DESCRIPTION
        "Parameter 'src-mac' in event BSPF.1"
    ::= { bspfEventObjects1 1 }

bspf1-src-port OBJECT-TYPE
    SYNTAX Integer32
    MAX-ACCESS accessible-for-notify
    STATUS current
    DESCRIPTION
        "Parameter 'src-port' in event BSPF.1"
    ::= { bspfEventObjects1 2 }

bspf1-dst-mac OBJECT-TYPE
    SYNTAX DisplayString
    MAX-ACCESS accessible-for-notify
    STATUS current
    DESCRIPTION
        "Parameter 'dst-mac' in event BSPF.1"
    ::= { bspfEventObjects1 3 }

bspf1-dst-port OBJECT-TYPE
    SYNTAX Integer32
    MAX-ACCESS accessible-for-notify
    STATUS current
    DESCRIPTION
        "Parameter 'dst-port' in event BSPF.1"
    ::= { bspfEventObjects1 4 }

bspf1-protocol OBJECT-TYPE
    SYNTAX Integer32
    MAX-ACCESS accessible-for-notify
    STATUS current
    DESCRIPTION
        "Parameter 'protocol' in event BSPF.1"
    ::= { bspfEventObjects1 5 }

bspf1-interface OBJECT-TYPE
    SYNTAX DisplayString
    MAX-ACCESS accessible-for-notify
    STATUS current
    DESCRIPTION
        "Parameter 'interface' in event BSPF.1"
    ::= { bspfEventObjects1 6 }

bspfEventObjects2 OBJECT-IDENTITY
    STATUS current
    DESCRIPTION
        "Event BSPF.2
        Bridge has intercepted an incoming packet destined for a spoofed MAC.
        If its protocol is IP, the destination ip address does not match the
        one	spoofed. If it is ARP, the operation code must be request."
    ::= { bspfEventsGroup 2 }

bspf2-spoof-addr OBJECT-TYPE
    SYNTAX IpAddress
    MAX-ACCESS accessible-for-notify
    STATUS current
    DESCRIPTION
        "Parameter 'spoof-addr' in event BSPF.2"
    ::= { bspfEventObjects2 1 }

bspf2-protocol OBJECT-TYPE
    SYNTAX Integer32
    MAX-ACCESS accessible-for-notify
    STATUS current
    DESCRIPTION
        "Parameter 'protocol' in event BSPF.2"
    ::= { bspfEventObjects2 2 }

bspf2-interface OBJECT-TYPE
    SYNTAX DisplayString
    MAX-ACCESS accessible-for-notify
    STATUS current
    DESCRIPTION
        "Parameter 'interface' in event BSPF.2"
    ::= { bspfEventObjects2 3 }

bspfEventObjects3 OBJECT-IDENTITY
    STATUS current
    DESCRIPTION
        "Event BSPF.3
        The MAC address associated with a spoofed address has been updated."
    ::= { bspfEventsGroup 3 }

bspf3-mac-addr OBJECT-TYPE
    SYNTAX DisplayString
    MAX-ACCESS accessible-for-notify
    STATUS current
    DESCRIPTION
        "Parameter 'mac-addr' in event BSPF.3"
    ::= { bspfEventObjects3 1 }

bspf3-spoof-addr OBJECT-TYPE
    SYNTAX IpAddress
    MAX-ACCESS accessible-for-notify
    STATUS current
    DESCRIPTION
        "Parameter 'spoof-addr' in event BSPF.3"
    ::= { bspfEventObjects3 2 }

bspf3-interface OBJECT-TYPE
    SYNTAX DisplayString
    MAX-ACCESS accessible-for-notify
    STATUS current
    DESCRIPTION
        "Parameter 'interface' in event BSPF.3"
    ::= { bspfEventObjects3 3 }

bspfEventObjects4 OBJECT-IDENTITY
    STATUS current
    DESCRIPTION
        "Event BSPF.4
        The port associated with a spoofed address has been updated."
    ::= { bspfEventsGroup 4 }

bspf4-port OBJECT-TYPE
    SYNTAX Integer32
    MAX-ACCESS accessible-for-notify
    STATUS current
    DESCRIPTION
        "Parameter 'port' in event BSPF.4"
    ::= { bspfEventObjects4 1 }

bspf4-spoof-addr OBJECT-TYPE
    SYNTAX IpAddress
    MAX-ACCESS accessible-for-notify
    STATUS current
    DESCRIPTION
        "Parameter 'spoof-addr' in event BSPF.4"
    ::= { bspfEventObjects4 2 }

bspf4-interface OBJECT-TYPE
    SYNTAX DisplayString
    MAX-ACCESS accessible-for-notify
    STATUS current
    DESCRIPTION
        "Parameter 'interface' in event BSPF.4"
    ::= { bspfEventObjects4 3 }

bspfEventObjects5 OBJECT-IDENTITY
    STATUS current
    DESCRIPTION
        "Event BSPF.5
        Bridge-spoofing sends an ARP packet periodically requesting the MAC
        address associated with every spoofed address configured."
    ::= { bspfEventsGroup 5 }

bspf5-spoof-addr OBJECT-TYPE
    SYNTAX IpAddress
    MAX-ACCESS accessible-for-notify
    STATUS current
    DESCRIPTION
        "Parameter 'spoof-addr' in event BSPF.5"
    ::= { bspfEventObjects5 1 }

bspf5-interface OBJECT-TYPE
    SYNTAX DisplayString
    MAX-ACCESS accessible-for-notify
    STATUS current
    DESCRIPTION
        "Parameter 'interface' in event BSPF.5"
    ::= { bspfEventObjects5 2 }

bspfEventObjects6 OBJECT-IDENTITY
    STATUS current
    DESCRIPTION
        "Event BSPF.6
        Bridge-spoofing broadcasts an ARP gratuitous packet after changing
        the MAC address associated with a configured spoofed address."
    ::= { bspfEventsGroup 6 }

bspf6-mac-addr OBJECT-TYPE
    SYNTAX DisplayString
    MAX-ACCESS accessible-for-notify
    STATUS current
    DESCRIPTION
        "Parameter 'mac-addr' in event BSPF.6"
    ::= { bspfEventObjects6 1 }

bspf6-spoof-addr OBJECT-TYPE
    SYNTAX IpAddress
    MAX-ACCESS accessible-for-notify
    STATUS current
    DESCRIPTION
        "Parameter 'spoof-addr' in event BSPF.6"
    ::= { bspfEventObjects6 2 }

bspf6-interface OBJECT-TYPE
    SYNTAX DisplayString
    MAX-ACCESS accessible-for-notify
    STATUS current
    DESCRIPTION
        "Parameter 'interface' in event BSPF.6"
    ::= { bspfEventObjects6 3 }

bspfEventObjects7 OBJECT-IDENTITY
    STATUS current
    DESCRIPTION
        "Event BSPF.7
        Received an ARP request packet asking for a spoofed configured address."
    ::= { bspfEventsGroup 7 }

bspf7-mac-addr OBJECT-TYPE
    SYNTAX DisplayString
    MAX-ACCESS accessible-for-notify
    STATUS current
    DESCRIPTION
        "Parameter 'mac-addr' in event BSPF.7"
    ::= { bspfEventObjects7 1 }

bspf7-spoof-addr OBJECT-TYPE
    SYNTAX IpAddress
    MAX-ACCESS accessible-for-notify
    STATUS current
    DESCRIPTION
        "Parameter 'spoof-addr' in event BSPF.7"
    ::= { bspfEventObjects7 2 }

bspf7-interface OBJECT-TYPE
    SYNTAX DisplayString
    MAX-ACCESS accessible-for-notify
    STATUS current
    DESCRIPTION
        "Parameter 'interface' in event BSPF.7"
    ::= { bspfEventObjects7 3 }

bspfEventObjects8 OBJECT-IDENTITY
    STATUS current
    DESCRIPTION
        "Event BSPF.8
        Sent a reply to an ARP request asking for a spoofed configured address."
    ::= { bspfEventsGroup 8 }

bspf8-spoof-addr OBJECT-TYPE
    SYNTAX IpAddress
    MAX-ACCESS accessible-for-notify
    STATUS current
    DESCRIPTION
        "Parameter 'spoof-addr' in event BSPF.8"
    ::= { bspfEventObjects8 1 }

bspf8-src-mac OBJECT-TYPE
    SYNTAX DisplayString
    MAX-ACCESS accessible-for-notify
    STATUS current
    DESCRIPTION
        "Parameter 'src-mac' in event BSPF.8"
    ::= { bspfEventObjects8 2 }

bspf8-dst-mac OBJECT-TYPE
    SYNTAX DisplayString
    MAX-ACCESS accessible-for-notify
    STATUS current
    DESCRIPTION
        "Parameter 'dst-mac' in event BSPF.8"
    ::= { bspfEventObjects8 3 }

bspf8-interface OBJECT-TYPE
    SYNTAX DisplayString
    MAX-ACCESS accessible-for-notify
    STATUS current
    DESCRIPTION
        "Parameter 'interface' in event BSPF.8"
    ::= { bspfEventObjects8 4 }

bspfEventObjects9 OBJECT-IDENTITY
    STATUS current
    DESCRIPTION
        "Event BSPF.9
        A bridge must be defined before a spoofing ip address can be
        configured."
    ::= { bspfEventsGroup 9 }

bspf9-spoof-addr OBJECT-TYPE
    SYNTAX IpAddress
    MAX-ACCESS accessible-for-notify
    STATUS current
    DESCRIPTION
        "Parameter 'spoof-addr' in event BSPF.9"
    ::= { bspfEventObjects9 1 }

bspf9-interface OBJECT-TYPE
    SYNTAX DisplayString
    MAX-ACCESS accessible-for-notify
    STATUS current
    DESCRIPTION
        "Parameter 'interface' in event BSPF.9"
    ::= { bspfEventObjects9 2 }

bspfEventObjects10 OBJECT-IDENTITY
    STATUS current
    DESCRIPTION
        "Event BSPF.10
        There is no enough free memory to configure a new spoofing ip address."
    ::= { bspfEventsGroup 10 }

bspf10-spoof-addr OBJECT-TYPE
    SYNTAX IpAddress
    MAX-ACCESS accessible-for-notify
    STATUS current
    DESCRIPTION
        "Parameter 'spoof-addr' in event BSPF.10"
    ::= { bspfEventObjects10 1 }

bspf10-interface OBJECT-TYPE
    SYNTAX DisplayString
    MAX-ACCESS accessible-for-notify
    STATUS current
    DESCRIPTION
        "Parameter 'interface' in event BSPF.10"
    ::= { bspfEventObjects10 2 }


bspfNotification1 NOTIFICATION-TYPE
    OBJECTS { 
              bspf1-src-mac, 
              bspf1-src-port,
              bspf1-dst-mac,
              bspf1-dst-port,
              bspf1-protocol,
              bspf1-interface 
            }
    STATUS current
    DESCRIPTION
        "Notification of Event BSPF.1

        Message: 'Packet from $1 port $2 to $3 port $4 protocol 0x$5, interface $6'

        Parameters list:
              $1: bspf1-src-mac
              $2: bspf1-src-port
              $3: bspf1-dst-mac
              $4: bspf1-dst-port
              $5: bspf1-protocol
              $6: bspf1-interface

        Bridge has detected an incoming packet whose destination matches a
        spoofed MAC address."
    ::= { bspfNotificationsPrefix 1 }

bspfNotification2 NOTIFICATION-TYPE
    OBJECTS { 
              bspf2-spoof-addr, 
              bspf2-protocol,
              bspf2-interface 
            }
    STATUS current
    DESCRIPTION
        "Notification of Event BSPF.2

        Message: 'Packet intercepted, spoofed address $1 protocol 0x$2, interface $3'

        Parameters list:
              $1: bspf2-spoof-addr
              $2: bspf2-protocol
              $3: bspf2-interface

        Bridge has intercepted an incoming packet destined for a spoofed MAC.
        If its protocol is IP, the destination ip address does not match the
        one	spoofed. If it is ARP, the operation code must be request."
    ::= { bspfNotificationsPrefix 2 }

bspfNotification3 NOTIFICATION-TYPE
    OBJECTS { 
              bspf3-mac-addr, 
              bspf3-spoof-addr,
              bspf3-interface 
            }
    STATUS current
    DESCRIPTION
        "Notification of Event BSPF.3

        Message: 'New MAC $1 learned, spoofed address $2, interface $3'

        Parameters list:
              $1: bspf3-mac-addr
              $2: bspf3-spoof-addr
              $3: bspf3-interface

        The MAC address associated with a spoofed address has been updated."
    ::= { bspfNotificationsPrefix 3 }

bspfNotification4 NOTIFICATION-TYPE
    OBJECTS { 
              bspf4-port, 
              bspf4-spoof-addr,
              bspf4-interface 
            }
    STATUS current
    DESCRIPTION
        "Notification of Event BSPF.4

        Message: 'New port $1 learned, spoofed address $2, interface $3'

        Parameters list:
              $1: bspf4-port
              $2: bspf4-spoof-addr
              $3: bspf4-interface

        The port associated with a spoofed address has been updated."
    ::= { bspfNotificationsPrefix 4 }

bspfNotification5 NOTIFICATION-TYPE
    OBJECTS { 
              bspf5-spoof-addr, 
              bspf5-interface 
            }
    STATUS current
    DESCRIPTION
        "Notification of Event BSPF.5

        Message: 'Discovering MAC and port associated with spoofed address $1, interface $2'

        Parameters list:
              $1: bspf5-spoof-addr
              $2: bspf5-interface

        Bridge-spoofing sends an ARP packet periodically requesting the MAC
        address associated with every spoofed address configured."
    ::= { bspfNotificationsPrefix 5 }

bspfNotification6 NOTIFICATION-TYPE
    OBJECTS { 
              bspf6-mac-addr, 
              bspf6-spoof-addr,
              bspf6-interface 
            }
    STATUS current
    DESCRIPTION
        "Notification of Event BSPF.6

        Message: 'Broadcasting new MAC $1 associated with spoofed address $2, interface $3'

        Parameters list:
              $1: bspf6-mac-addr
              $2: bspf6-spoof-addr
              $3: bspf6-interface

        Bridge-spoofing broadcasts an ARP gratuitous packet after changing
        the MAC address associated with a configured spoofed address."
    ::= { bspfNotificationsPrefix 6 }

bspfNotification7 NOTIFICATION-TYPE
    OBJECTS { 
              bspf7-mac-addr, 
              bspf7-spoof-addr,
              bspf7-interface 
            }
    STATUS current
    DESCRIPTION
        "Notification of Event BSPF.7

        Message: 'ARP request from MAC $1 for spoofed address $2, interface $3'

        Parameters list:
              $1: bspf7-mac-addr
              $2: bspf7-spoof-addr
              $3: bspf7-interface

        Received an ARP request packet asking for a spoofed configured address."
    ::= { bspfNotificationsPrefix 7 }

bspfNotification8 NOTIFICATION-TYPE
    OBJECTS { 
              bspf8-spoof-addr, 
              bspf8-src-mac,
              bspf8-dst-mac,
              bspf8-interface 
            }
    STATUS current
    DESCRIPTION
        "Notification of Event BSPF.8

        Message: 'ARP reply for address $1 is MAC $2, destination MAC $3, interface $4'

        Parameters list:
              $1: bspf8-spoof-addr
              $2: bspf8-src-mac
              $3: bspf8-dst-mac
              $4: bspf8-interface

        Sent a reply to an ARP request asking for a spoofed configured address."
    ::= { bspfNotificationsPrefix 8 }

bspfNotification9 NOTIFICATION-TYPE
    OBJECTS { 
              bspf9-spoof-addr, 
              bspf9-interface 
            }
    STATUS current
    DESCRIPTION
        "Notification of Event BSPF.9

        Message: 'Error adding address $1, bridge must be enabled, interface $2'

        Parameters list:
              $1: bspf9-spoof-addr
              $2: bspf9-interface

        A bridge must be defined before a spoofing ip address can be
        configured."
    ::= { bspfNotificationsPrefix 9 }

bspfNotification10 NOTIFICATION-TYPE
    OBJECTS { 
              bspf10-spoof-addr, 
              bspf10-interface 
            }
    STATUS current
    DESCRIPTION
        "Notification of Event BSPF.10

        Message: 'Error adding address $1, out of memory, interface $2'

        Parameters list:
              $1: bspf10-spoof-addr
              $2: bspf10-interface

        There is no enough free memory to configure a new spoofing ip address."
    ::= { bspfNotificationsPrefix 10 }


END
