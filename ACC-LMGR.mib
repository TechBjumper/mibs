ACC-LMGR DEFINITIONS ::= BEGIN

    IMPORTS
	 OBJECT-TYPE, IpAddress, TimeTicks, Gauge, Counter FROM RFC1155-SMI
        accTrapLogSeqNum FROM ACC-SYSTEM
	accBRG, DisplayString, RowStatus, IfIndex, SmdsAddress
             FROM ACC-MIB;

-- ACC License Manager (Lmgr) MIB Group
accLmgr		OBJECT IDENTIFIER  ::= { accBRG 78 }
-- System level License Manager objects
        accLicMgrParms  OBJECT IDENTIFIER ::= { accLmgr 1 }
            accLicMgrMessageLevel       OBJECT-TYPE
                SYNTAX  INTEGER (1..7)
                ACCESS  read-write
                STATUS  mandatory
                DESCRIPTION
                  "License management information message level"
                ::= { accLicMgrParms 1 }
-- License Manager Parameter (Table) Objects
        accLicMgrParmTable OBJECT-TYPE
                SYNTAX SEQUENCE OF AccLicMgrParmEntry
                ACCESS not-accessible
                STATUS mandatory
                DESCRIPTION
                        "License Manager Parameters"
                ::= { accLmgr 2 }
        accLicMgrParmEntry OBJECT-TYPE
                SYNTAX AccLicMgrParmEntry
                ACCESS not-accessible
                STATUS mandatory
                DESCRIPTION
                        "License Manager Parameters entry"
--                INDEX { INTEGER }
                ::= { accLicMgrParmTable 1 }
        AccLicMgrParmEntry ::= SEQUENCE {
                accLicMgrLictype      INTEGER,
         	accLicMgrLicGroup     INTEGER,
                accLicMgrLicKey       OCTET STRING,
                accLicMgrNumInst      INTEGER
                }
        accLicMgrLictype    OBJECT-TYPE
                SYNTAX  INTEGER {
                    acc56k(53),
                    none(78),
                    voip(86)
                    }
                ACCESS  read-only
                STATUS  mandatory
                DESCRIPTION
                        "License type."
                ::= { accLicMgrParmEntry 1 }
        accLicMgrLicGroup    OBJECT-TYPE
                SYNTAX  INTEGER {
                    supplemental(80),
                    standard(84)
                    }
                ACCESS  read-only
                STATUS  mandatory
                DESCRIPTION
                        "License group 
			(STANDARD or SUPPLEMENTAL)."
                ::= { accLicMgrParmEntry 2 }
        accLicMgrLicKey    OBJECT-TYPE
                SYNTAX  OCTET STRING
                ACCESS  read-only
                STATUS  mandatory
                DESCRIPTION
                        "License key string."
                ::= { accLicMgrParmEntry 3 }
        accLicMgrNumInst    OBJECT-TYPE
                SYNTAX  INTEGER
                ACCESS  read-only
                STATUS  mandatory
                DESCRIPTION
                        "Number of license instances."
                ::= { accLicMgrParmEntry 4 }
-- License Manager Statistics (Table) Objects
        accLicMgrStatTable OBJECT-TYPE
                SYNTAX SEQUENCE OF AccLicMgrStatEntry
                ACCESS not-accessible
                STATUS mandatory
                DESCRIPTION
                        "License Manager Statistics"
                ::= { accLmgr 3 }
        accLicMgrStatEntry OBJECT-TYPE
                SYNTAX AccLicMgrStatEntry
                ACCESS not-accessible
                STATUS mandatory
                DESCRIPTION
                        "License Manager Statistics entry"  
--                INDEX { INTEGER }
                ::= { accLicMgrStatTable 1 }
        AccLicMgrStatEntry ::= SEQUENCE {
                accLicMgr56kAlloc     INTEGER,
                accLicMgr56kAvails    Counter,
                accLicMgr56kCurrents  Counter,
                accLicMgr56kTotals    Counter,
                accLicMgr56kPeaks     Counter,
                accLicMgr56kDenials   Counter,
                accLicMgrVoIPAllocs   Counter,
                accLicMgrVoIPAvails   Counter,
                accLicMgrVoIPCurrents Counter,
                accLicMgrVoIPTotals   Counter,
                accLicMgrVoIPPeaks    Counter,
                accLicMgrVoIPDenials  Counter
                }
        accLicMgr56kAlloc	OBJECT-TYPE
                SYNTAX  INTEGER
                ACCESS  read-only
                STATUS  mandatory
                DESCRIPTION
                        "Allocated - indicates the entire 
			number of licenses of the displayed 
			license type provisioned for this 
			router."
                ::= { accLicMgrStatEntry 1 }
        accLicMgr56kAvails	OBJECT-TYPE
                SYNTAX  Counter
                ACCESS  read-only
                STATUS  mandatory
                DESCRIPTION
                        "Available - indicates the number of 
			licenses, not currently in use, 
			available to be assigned."
                ::= { accLicMgrStatEntry 2 }
        accLicMgr56kCurrents	OBJECT-TYPE
                SYNTAX  Counter
                ACCESS  read-only
                STATUS  mandatory
                DESCRIPTION
                        "Current - indicates the number of 
			currently assigned licenses."
                ::= { accLicMgrStatEntry 3 }
        accLicMgr56kTotals	OBJECT-TYPE
                SYNTAX  Counter
                ACCESS  read-only
                STATUS  mandatory
                DESCRIPTION
                        "Total - indicates the total number of 
			times a license of this license type 
			has been assigned."
                ::= { accLicMgrStatEntry 4 }
        accLicMgr56kPeaks	OBJECT-TYPE
                SYNTAX  Counter
                ACCESS  read-only
                STATUS  mandatory
                DESCRIPTION
                        "Peak - indicates the peak or maximum 
			number of licenses assigned of this 
			license type at one time."
                ::= { accLicMgrStatEntry 5 }
        accLicMgr56kDenials	OBJECT-TYPE
                SYNTAX  Counter
                ACCESS  read-only
                STATUS  mandatory
                DESCRIPTION
                        "Denial - indicates the total number of 
			times a license of this type has been 
			denied due to lack of available licenses."
                ::= { accLicMgrStatEntry 6 }
        accLicMgrVoIPAllocs	OBJECT-TYPE
                SYNTAX  Counter
                ACCESS  read-only
                STATUS  mandatory
                DESCRIPTION
                        "Allocated - indicates the entire
                        number of licenses of the displayed
                        license type provisioned for this
                        router."
                ::= { accLicMgrStatEntry 7 }
        accLicMgrVoIPAvails	OBJECT-TYPE
                SYNTAX  Counter
                ACCESS  read-only
                STATUS  mandatory
                DESCRIPTION
                        "Available - indicates the number of
                        licenses, not currently in use,
                        available to be assigned."
                ::= { accLicMgrStatEntry 8 }
        accLicMgrVoIPCurrents	OBJECT-TYPE
                SYNTAX  Counter
                ACCESS  read-only
                STATUS  mandatory
                DESCRIPTION
                        "Current - indicates the number of
                        currently assigned licenses."
                ::= { accLicMgrStatEntry 9 }
        accLicMgrVoIPTotals	OBJECT-TYPE
                SYNTAX  Counter
                ACCESS  read-only
                STATUS  mandatory
                DESCRIPTION
                        "Total - indicates the total number of
                        times a license of this license type
                        has been assigned."
                ::= { accLicMgrStatEntry 10 }
        accLicMgrVoIPPeaks	OBJECT-TYPE
                SYNTAX  Counter
                ACCESS  read-only
                STATUS  mandatory
                DESCRIPTION
                        "Peak - indicates the peak or maximum
                        number of licenses assigned of this
                        license type at one time."
                ::= { accLicMgrStatEntry 11 }
        accLicMgrVoIPDenials	OBJECT-TYPE
                SYNTAX  Counter
                ACCESS  read-only
                STATUS  mandatory
                DESCRIPTION
                        "Denial - indicates the total number of
                        times a license of this type has been
                        denied due to lack of available licenses."
                ::= { accLicMgrStatEntry 12 }

END
