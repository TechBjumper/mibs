AVUPDATE-STATISTICS-MIB DEFINITIONS ::= BEGIN

--	

IMPORTS
	MODULE-IDENTITY, OBJECT-TYPE, Integer32,
	NOTIFICATION-TYPE, Unsigned32, Counter64, Counter32
		FROM SNMPv2-SMI
	DateAndTime, DisplayString,TimeStamp
		FROM SNMPv2-TC
	SnmpAdminString
		FROM SNMP-FRAMEWORK-MIB
	statistics
		FROM KAV4FS-STATISTICS-MIB
;

avUpdateStatistics MODULE-IDENTITY
	LAST-UPDATED "201602241200Z"
	ORGANIZATION "www.kaspersky.com"
	CONTACT-INFO "Kaspersky Lab"
	DESCRIPTION "Update statistics till current time period"
	-- revisions
	REVISION "201602241200Z"
	DESCRIPTION  "Automatically generated."
 ::= { statistics 7 }


	avUpdateStatisticsCurrentAVBasesDate OBJECT-TYPE
	SYNTAX DateAndTime
	MAX-ACCESS read-only
	STATUS current
	DESCRIPTION
		""
	::= { avUpdateStatistics 1 }

	avUpdateStatisticsLastUpdateAVBasesDate OBJECT-TYPE
	SYNTAX DateAndTime
	MAX-ACCESS read-only
	STATUS current
	DESCRIPTION
		""
	::= { avUpdateStatistics 2 }

	avUpdateStatisticsCurrentBasesState OBJECT-TYPE
	SYNTAX DisplayString
	MAX-ACCESS read-only
	STATUS current
	DESCRIPTION
		""
	::= { avUpdateStatistics 3 }

	avUpdateStatisticsCurrentBasesRecords OBJECT-TYPE
	SYNTAX Counter64
	MAX-ACCESS read-only
	STATUS current
	DESCRIPTION
		""
	::= { avUpdateStatistics 4 }

	avUpdateStatisticsUpdateAttempts OBJECT-TYPE
	SYNTAX Counter64
	MAX-ACCESS read-only
	STATUS current
	DESCRIPTION
		""
	::= { avUpdateStatistics 5 }

	avUpdateStatisticsSuccessfulUpdates OBJECT-TYPE
	SYNTAX Counter64
	MAX-ACCESS read-only
	STATUS current
	DESCRIPTION
		""
	::= { avUpdateStatistics 6 }

	avUpdateStatisticsUpdateManualStops OBJECT-TYPE
	SYNTAX Counter64
	MAX-ACCESS read-only
	STATUS current
	DESCRIPTION
		""
	::= { avUpdateStatistics 7 }

	avUpdateStatisticsFailedUpdates OBJECT-TYPE
	SYNTAX Counter64
	MAX-ACCESS read-only
	STATUS current
	DESCRIPTION
		""
	::= { avUpdateStatistics 8 }


END
