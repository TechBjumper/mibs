--MibName=rcSystem
------------------------------------------------------------------------------
------------------------------------------------------------------------------
--
--  File         : syscli.mib
--  Description  : rose software system command  mib defination 
--  Version      : 0.1   
--  Date         : July 2, 2003     
--
--  Copyright (c) 2003-2004 Beijing Raisecom Science & Technology Co., ltd  All Rights Reserved.

--Modify Record    
--10,20120705,huzhiwen,modify the oid of rcPortMappingInfoConfig 
--09,20120711,liweixing, add backboard information   
--08,20120628,yangkw,Add  rcPortStormControlTable
--07,20120508,liweixing,modify USP mib                    
--06,20110723,baiguangyu,set rcStormControlDlfEnable default value as disable
--05,20110723,baiguangyu,set rcStormControlBcastEnable default value as enable
--04,20100324,huochao, RcPortEntry ::= SEQUENCE {...
--  rcPortMDIXMode                 Integer32,   ->INTEGER.
--  rcPortMDIXStatus               Integer32,   ->INTEGER. 
--04, 20110628, baiguangyu, add "rcSwitchProductVersion" "rcSwitchCmpAbName" 
--                   "rcSwitchCmpFullName" "rcSwitchDeviceName" in group "rcSwitchInformation"
--03, 20090331, yingjiangang,rcConsoleEnable
--01, 20090225, guoxiaodan, rcSwitchLastErrorCode
------------------------------------------------------------------------------
--01, lq, 20090227, change rcMaxAllowedFrameLength from 9000 to 65535
------------------------------------------------------------------------------

    SWITCH-SYSTEM-MIB DEFINITIONS ::= BEGIN

    IMPORTS
        MODULE-IDENTITY, OBJECT-TYPE,
        Integer32, Counter32,  
        NOTIFICATION-TYPE                       FROM SNMPv2-SMI
        
        MacAddress,
        RowStatus,TruthValue                   FROM SNMPv2-TC
        
        OBJECT-GROUP         FROM SNMPv2-CONF                
        iscomSwitch               				FROM RAISECOM-BASE-MIB  
        ifIndex             FROM IF-MIB 
        PortList,EnableVar,Vlanset				FROM SWITCH-TC;
        
    rcSystem MODULE-IDENTITY
    
        LAST-UPDATED    "0412170000Z"  -- Dec 17, 2004
        ORGANIZATION    "Raisecom Science & Technology Co., ltd"
        CONTACT-INFO    "Raisecom Science & Technology Co., ltd.
                         E-mail: support@raisecom.com"

        DESCRIPTION     "iscom switch system Enterprise MIB definition."

        REVISION        "0412170000Z"  -- Dec 17, 2004
        DESCRIPTION     "Initial MIB creation."

                ::= { iscomSwitch 1 }

rcSwitchInformation     OBJECT IDENTIFIER ::= { rcSystem 1 }  
rcSlotInformation       OBJECT IDENTIFIER ::= { rcSystem 2 }
rcSwitchConfig          OBJECT IDENTIFIER ::= { rcSystem 3 }
rcPortInfoConfig     	OBJECT IDENTIFIER ::= { rcSystem 4 }
rcLoopbackTrap      	OBJECT IDENTIFIER ::= { rcSystem 5 } 
rcPorConnectorChangeTrap      	OBJECT IDENTIFIER ::= { rcSystem 6 }  
rcPortMappingInfoConfig      	OBJECT IDENTIFIER ::= { rcSystem 8 }  



------------------------------------------------------------------------------

-- switch information group    "rcSwitchInformation"  
--rcSwitchInformation
	--rcSwitchRoseVersion
	--rcSwitchHardwareVersion
	--rcSwitchServiceInfo
	--rcSwitchLastErrorCode
	--rcSwitchMaxPhysicalPortNum
	--rcSwitchMaxAggregationPortNum
	--rcSwitchMaxL3IpSubnetNum	
	--rcSwitchMacTableCapability
	--rcSwitchMacAddress
	--rcSwitchVlanSpaceSize
	-- rcSwitchPvidSpaceSize
	-- rcSwitchDefaultVlan
	-- rcSwitchBootstrapVersion
	-- rcSwitchSerialNumber  
	-- rcSwitchFpgaVersion
	-- rcSwitchProductVersion
	-- rcSwitchCmpAbName
	-- rcSwitchCmpFullName
	-- rcSwitchDeviceName
	-- rcSwitchBackBoardVendorName
	-- rcSwitchBackBoardSerialNumber
	-- rcSwitchBackBoardName
	-- rcSwitchBackBoardVersion 

rcSwitchRoseVersion    OBJECT-TYPE
        SYNTAX OCTET STRING  
        MAX-ACCESS read-only
        STATUS current
        DESCRIPTION
            "rose software version  ."
        ::= { rcSwitchInformation 1 }

rcSwitchHardwareVersion    OBJECT-TYPE
        SYNTAX OCTET STRING   
        MAX-ACCESS read-only
        STATUS current
        DESCRIPTION
            "rose hardware version  ."
        ::= { rcSwitchInformation 2 }
                                          
rcSwitchServiceInfo 	OBJECT-TYPE
        SYNTAX Integer32 
        MAX-ACCESS read-only
        STATUS deprecated
        DESCRIPTION
            "rose software service information version .   
            every bit stand for one type of service and , 
            '0' stand for service is up, '1' stand for not start
            Qos-- bit(0)
            Filter -- bit(1)
            Storm control -- bit(2)
            Authentication-- bit(3)
            IGMP Snooping-- bit(4)
            STP-- bit(5)
            RIP-- bit(6)
            OSPF-- bit(7)
            PIM-DM-- bit(8)
            PIM-SM-- bit(9)           
            ....
            "
        ::= { rcSwitchInformation 3 }

rcSwitchLastErrorCode OBJECT-TYPE
        SYNTAX Integer32 (0..2147483647)
        MAX-ACCESS read-only
        STATUS deprecated
        DESCRIPTION
            "This mib object stand for system last error code ,for system analysis
            0 for  no error
            1 ...0x7fffffff for error code  
            "
        ::= { rcSwitchInformation 4 }  
          
rcSwitchMaxPhysicalPortNum OBJECT-TYPE
        SYNTAX INTEGER
        MAX-ACCESS read-only
        STATUS current
        DESCRIPTION
            "The physical port number which system supports."
        ::= { rcSwitchInformation 5 }

rcSwitchMaxAggregationPortNum OBJECT-TYPE
        SYNTAX INTEGER
        MAX-ACCESS read-only
        STATUS current
        DESCRIPTION
            "The aggregation port number which system supports."
        ::= { rcSwitchInformation 6 }

rcSwitchMaxL3IpSubnetNum OBJECT-TYPE
        SYNTAX INTEGER
        MAX-ACCESS read-only
        STATUS current
        DESCRIPTION
            "The layer 3 port number which system supports."
        ::= { rcSwitchInformation 7 }  
            
rcSwitchMacTableCapability OBJECT-TYPE 
        SYNTAX Integer32 
        MAX-ACCESS read-only
        STATUS current
        DESCRIPTION
            "The capability of MAC table."
        ::= { rcSwitchInformation 8}
                                        
rcSwitchMacAddress OBJECT-TYPE 
        SYNTAX   MacAddress
        MAX-ACCESS read-only
        STATUS current
        DESCRIPTION
            "MAC address."
        ::= { rcSwitchInformation 9} 
          
rcSwitchVlanSpaceSize OBJECT-TYPE 
        SYNTAX   INTEGER 
        MAX-ACCESS read-only
        STATUS current                        
        DESCRIPTION
            "the number of vlans in a vlan "
        ::= { rcSwitchInformation 10}  
                  
rcSwitchPvidSpaceSize OBJECT-TYPE 
        SYNTAX   INTEGER 
        MAX-ACCESS read-only
        STATUS current
        DESCRIPTION
            ""
        ::= { rcSwitchInformation 11}   
                 
rcSwitchDefaultVlan OBJECT-TYPE 
        SYNTAX   INTEGER  
        MAX-ACCESS read-only
        STATUS current
        DESCRIPTION
            "Default vlan"
        ::= { rcSwitchInformation 12}

rcSwitchBootstrapVersion    OBJECT-TYPE
        SYNTAX OCTET STRING  
        MAX-ACCESS read-only
        STATUS current
        DESCRIPTION
            "rose bootstrap version  ."
        ::= { rcSwitchInformation 13 }
        
rcSwitchSerialNumber OBJECT-TYPE
        SYNTAX OCTET STRING  
        MAX-ACCESS read-only
        STATUS current
        DESCRIPTION
            "The serial number of the motherboard."
        ::= { rcSwitchInformation 14 }    
        
rcSwitchFpgaVersion OBJECT-TYPE
        SYNTAX OCTET STRING  
        MAX-ACCESS read-only
        STATUS current
        DESCRIPTION
            "rose fpga version."
        ::= { rcSwitchInformation 15 }
        
rcSwitchProductVersion OBJECT-TYPE
        SYNTAX OCTET STRING
        MAX-ACCESS read-only
        STATUS current
        DESCRIPTION
            "product version"
        ::= { rcSwitchInformation 16 }  
        
rcSwitchCmpAbName OBJECT-TYPE
        SYNTAX OCTET STRING
        MAX-ACCESS read-only
        STATUS current
        DESCRIPTION
            "manufacturer abbreviated name"
        ::= { rcSwitchInformation 17 }
        
rcSwitchCmpFullName OBJECT-TYPE
        SYNTAX OCTET STRING
        MAX-ACCESS read-only
        STATUS current
        DESCRIPTION
            "manufacturer full name"
        ::= { rcSwitchInformation 18 } 
        
rcSwitchDeviceName OBJECT-TYPE
        SYNTAX OCTET STRING
        MAX-ACCESS read-only
        STATUS current
        DESCRIPTION
            "device name"
        ::= { rcSwitchInformation 19 }        

rcSwitchBackBoardVendorName OBJECT-TYPE
        SYNTAX OCTET STRING
        MAX-ACCESS read-only
        STATUS current
        DESCRIPTION
            "Backboard vendor name."
        ::= { rcSwitchInformation 20 }

rcSwitchBackBoardSerialNumber OBJECT-TYPE
        SYNTAX OCTET STRING
        MAX-ACCESS read-only
        STATUS current
        DESCRIPTION
            "Serial number of the backboard."
        ::= { rcSwitchInformation 21 }

rcSwitchBackBoardName OBJECT-TYPE
        SYNTAX OCTET STRING
        MAX-ACCESS read-only
        STATUS current
        DESCRIPTION
            "Backboard name."
        ::= { rcSwitchInformation 22 }

rcSwitchBackBoardVersion OBJECT-TYPE
        SYNTAX OCTET STRING
        MAX-ACCESS read-only
        STATUS current
        DESCRIPTION
            "Backboard version."
        ::= { rcSwitchInformation 23 }
        
        
----------------------- rcSlotInformation  -----------------------------  
--rcSlotInfoConfig
	--rcSlotNum
	--rcSlotStateTable
		--rcSlotStateEntry
			--rcSlotIndex
			-- rcSlotPortStart
			--rcSlotPortNum
			--rcSlotType

rcSlotNum OBJECT-TYPE 
        SYNTAX   INTEGER
        MAX-ACCESS read-only
        STATUS current
        DESCRIPTION
            "Total number of slot"
        ::= { rcSlotInformation 1}  
        
rcSlotStateTable OBJECT-TYPE  
        SYNTAX SEQUENCE OF RcSlotStateEntry
        MAX-ACCESS not-accessible
        STATUS current
        DESCRIPTION
            "A table of slot ."    
        ::= { rcSlotInformation 2}

rcSlotStateEntry OBJECT-TYPE
        SYNTAX RcSlotStateEntry
        MAX-ACCESS not-accessible
        STATUS current
        DESCRIPTION
            "A list of slot."
        INDEX {rcSlotIndex  }
        ::= { rcSlotStateTable 1 }

RcSlotStateEntry ::= SEQUENCE {
         rcSlotIndex     INTEGER,
         rcSlotPortStart INTEGER,
         rcSlotPortNum   INTEGER,
         rcSlotType  	INTEGER
        }      
 
rcSlotIndex OBJECT-TYPE 
        SYNTAX   INTEGER
        MAX-ACCESS not-accessible
        STATUS current
        DESCRIPTION
            "slot index based 0"
        ::= { rcSlotStateEntry 1}        

rcSlotPortStart OBJECT-TYPE 
        SYNTAX   INTEGER
        MAX-ACCESS read-only
        STATUS current
        DESCRIPTION
            "the start number of port in this slot"
        ::= { rcSlotStateEntry 2} 
        	 
rcSlotPortNum OBJECT-TYPE 
        SYNTAX   INTEGER
        MAX-ACCESS read-only
        STATUS current
        DESCRIPTION
            "the number of ports in this slot"
        ::= { rcSlotStateEntry 3} 
                	 
rcSlotType OBJECT-TYPE 
        SYNTAX   INTEGER {
        		inexistence(0),
        		fx-DulMode-1000M(1), 
        		tx-1000M(2), 
        		fx-SigMode-1000M(3), 
        		fx-DulMode-100M(4), 
        		fx-SigMode-100M(5), 
        		tx-100M(6),
        		px-1000M(7)
        }   
	  	MAX-ACCESS read-only
        STATUS current
        DESCRIPTION
            "slot type"
        ::= { rcSlotStateEntry 4}    
        
--rcSwitchConfig
--rcSwitchConfig
	--rcMacAgingTime
	--rcStormControlBcastEnable
	--rcStormControlMcastEnable
	--rcStormControlDlfEnable
	--rcStormControlpps
	--rcStormControlbps
	--rcStormControlRatio
	--rcStormControlBurst
	--rcStpEnable	
	--rcSvlEnable
	--rcGarpEnable
	--rcLacpEnable
	--rcVlanSpaceNum
	--rcPvidSpaceNum
	--rcLoopbackDetectInterval
	--rcArpAgingTime
	--rcBpduTransPorts	
	--rcDot1xTransPorts	
	--rcLacpTransPorts	
	--rcGarpTransPorts	
	--rcGmrpTransPorts	
	--rcGvrpTransPorts	
	--rcIpRouting
	--rcStaticRouteDistance
	--rcFastRoute
	--rcDlfForwardingEnable
	--rcLoopbackDetectVlan
	--rcLoopbackDetectDestAddr
	--rcMaxAllowedFrameLength
	--rcSvlDefaultVlan
	--rcTelnetMaxSessions
	--rcTelnetAcceptPorts
	--rcVlanMacLearning
	--rcConsoleEnable
	--rcStormControlOperpps
	--rcStormControlOperbps
 	--rcOperMaxAllowedFrameLength
	--rcTrapBindipEnable

	rcMacAgingTime  OBJECT-TYPE 
        SYNTAX Integer32 (0..2147483647)   ------aging time  
        UNITS "second"
        MAX-ACCESS read-write
        STATUS current
        DESCRIPTION
            "The value based 10 is the aging time for MAC address.
            Aging will be disable when aging time was (0)"
        DEFVAL { 300 }
        ::= { rcSwitchConfig 1}
              
	rcStormControlBcastEnable OBJECT-TYPE
        SYNTAX  EnableVar
        ACCESS read-write
        STATUS mandatory
        DESCRIPTION
                "Set the Storm control for broadcast on the interface to enable(1) or disable(2)."
         DEFVAL  { enable }       
        ::= { rcSwitchConfig 2 }
        
	rcStormControlMcastEnable OBJECT-TYPE
        SYNTAX  EnableVar
        ACCESS read-write
        STATUS mandatory
        DESCRIPTION
                "Set the Storm control for multicast on the interface to enable(1) or disable(2)."
        DEFVAL  { disable }
        ::= { rcSwitchConfig 3 }
        
    rcStormControlDlfEnable OBJECT-TYPE
        SYNTAX  EnableVar
        ACCESS read-write
        STATUS mandatory
        DESCRIPTION
                "Set the Storm control for DLF on the interface to enable(1) or disable(2)."
        DEFVAL  { disable }
        ::= { rcSwitchConfig 4 }
             
    rcStormControlpps OBJECT-TYPE
        SYNTAX  INTEGER  (1..262143)
        UNITS	"pps"      
        ACCESS read-write
        STATUS mandatory
        DESCRIPTION
                " The limit number for storm control on the interface ."    
        ::= { rcSwitchConfig 5 }
                                             
    rcStormControlbps OBJECT-TYPE
        SYNTAX  INTEGER  (0..1073741823)
        UNITS	"bps"      
        ACCESS read-write
        STATUS mandatory
        DESCRIPTION
                " The limit number for storm control on the interface ."    
        ::= { rcSwitchConfig 6 }

    rcStormControlRatio OBJECT-TYPE
        SYNTAX  INTEGER (1..100)        
        UNITS	"percent"    
        ACCESS read-write
        STATUS mandatory
        DESCRIPTION
                "storm control limit ratio"
        ::= { rcSwitchConfig 7 } 
        
    rcStormControlBurst OBJECT-TYPE
        SYNTAX  INTEGER (0..512)   
        UNITS	"kB"     
        ACCESS read-write
        STATUS mandatory
        DESCRIPTION
                "Set burst length when storm control open on the interface. ."
        ::= { rcSwitchConfig 8 } 


    rcStpEnable OBJECT-TYPE
        SYNTAX  EnableVar
        ACCESS read-write
        STATUS mandatory
        DESCRIPTION
             "The enabled/disabled status of STP for the bridge entity."
        DEFVAL  { 1 }  
        ::= { rcSwitchConfig 9 }  
        
	rcSvlEnable OBJECT-TYPE
        SYNTAX  EnableVar
        ACCESS read-write
        STATUS mandatory
        DESCRIPTION
             "share vlan mode enable or disable"
        DEFVAL  { disable }  
        ::= { rcSwitchConfig 10 }  
        
	rcGarpEnable OBJECT-TYPE
        SYNTAX  EnableVar
        ACCESS read-write
        STATUS mandatory
        DESCRIPTION
             "GARP enable or disable"
        DEFVAL  { disable }  
        ::= { rcSwitchConfig 11 }    
        
    rcLacpEnable OBJECT-TYPE
        SYNTAX  EnableVar
        ACCESS read-write
        STATUS mandatory
        DESCRIPTION
             "share vlan mode enable or disable"
        DEFVAL  { disable }  
        ::= { rcSwitchConfig 12 }
              
	rcVlanSpaceNum OBJECT-TYPE 
        SYNTAX  INTEGER (0..4093)         
        ACCESS read-write
        STATUS obsolete
        DESCRIPTION
             "The system supports at most rcVlanSpaceSize vlans, 
             so the vlan ID increases at rcVlanSpaceSize step over."
        DEFVAL  { 0 }  
        ::= { rcSwitchConfig 13 }
                  
	rcPvidSpaceNum OBJECT-TYPE 
        SYNTAX  INTEGER (0..4093)         
        ACCESS read-write
        STATUS obsolete         
        DESCRIPTION
             "The system supports at most rcPvidSpaceSize vlans, 
             so the vlan ID increases at rcPvidSpaceSize step over."
        DEFVAL  { 0 }  
        ::= { rcSwitchConfig 14 }
      
	rcLoopbackDetectInterval   OBJECT-TYPE
        SYNTAX  INTEGER (1..65535)  
        UNITS "second"
        MAX-ACCESS  read-write
        STATUS      current
        DESCRIPTION
            "Interval of sending loopback-detect packet."
        ::= { rcSwitchConfig 15 }
          
	rcArpAgingTime   OBJECT-TYPE
        SYNTAX Integer32 (0..2147483647)  
        UNITS "second"              
        MAX-ACCESS read-write
        STATUS deprecated
        DESCRIPTION  "arp timeout"  
        DEFVAL { 1200 }     
        ::= { rcSwitchConfig 16 }
      
	rcBpduTransPorts   OBJECT-TYPE
        SYNTAX      PortList
        MAX-ACCESS  read-write
        STATUS      current
        DESCRIPTION
            "The ports translating BPDU packets."
        ::= { rcSwitchConfig 17 }  
        
	rcDot1xTransPorts   OBJECT-TYPE
        SYNTAX      PortList
        MAX-ACCESS  read-write
        STATUS      current
        DESCRIPTION
            "The ports translating Dot1x packets."
        ::= { rcSwitchConfig 18 }                                   
          
	rcLacpTransPorts   OBJECT-TYPE
        SYNTAX      PortList
        MAX-ACCESS  read-write
        STATUS      current
        DESCRIPTION
            "The ports translating Lacp packets."
        ::= { rcSwitchConfig 19 } 
         
	rcGarpTransPorts   OBJECT-TYPE
        SYNTAX      PortList
        MAX-ACCESS  read-write
        STATUS      current
        DESCRIPTION
            "The ports translating Garp packets."
        ::= { rcSwitchConfig 20 } 
           
	rcGmrpTransPorts   OBJECT-TYPE
        SYNTAX      PortList
        MAX-ACCESS  read-write
        STATUS      current
        DESCRIPTION
            "The ports translating Gmrp packets."
        ::= { rcSwitchConfig 21 } 
           
	rcGvrpTransPorts   OBJECT-TYPE
        SYNTAX      PortList
        MAX-ACCESS  read-write
        STATUS      current
        DESCRIPTION
            "The ports translating Gvrp packets."
        ::= { rcSwitchConfig 22 } 

	rcIpRouting	OBJECT-TYPE
        SYNTAX INTEGER {
        	startIpRouting (1),
        	stopIpRouting(2)
        }
        MAX-ACCESS read-write
        STATUS current
        DESCRIPTION
            "start or stop system routing function .
            this is a commnd MIB variable ."
        ::= { rcSwitchConfig 23 }
        
	rcStaticRouteDistance OBJECT-TYPE
        SYNTAX Integer32 (0..255)
        MAX-ACCESS read-write
        STATUS current
        DESCRIPTION
            "system static route distance value .
            this is a commnd MIB variable ."
        ::= { rcSwitchConfig 24 }   
        
    rcFastRoute OBJECT-TYPE
        SYNTAX  TruthValue
        MAX-ACCESS read-write
        STATUS current
        DESCRIPTION
            "true for fast route and false for normal route ."
        ::= { rcSwitchConfig 25 }                                               
                                      
    rcDlfForwardingEnable OBJECT-TYPE
        SYNTAX  EnableVar
        MAX-ACCESS read-write
        STATUS mandatory
        DESCRIPTION
            "whether forwarding DLF packets ."
        ::= { rcSwitchConfig 26 }      
                                                            
    rcLoopbackDetectVlan OBJECT-TYPE
        SYNTAX  Integer32 (1..4094)
        MAX-ACCESS read-write
        STATUS mandatory
        DESCRIPTION
            "loopback-detection packet belongs to which VLAN."
        ::= { rcSwitchConfig 27 }      
                                              
    rcLoopbackDetectDestAddr OBJECT-TYPE
        SYNTAX  MacAddress
        MAX-ACCESS read-write
        STATUS mandatory
        DESCRIPTION
            "destination MAC address of loopback-detection packet."
        ::= { rcSwitchConfig 28 }
                                                
    rcMaxAllowedFrameLength OBJECT-TYPE
        SYNTAX  INTEGER (1500..65535)
        MAX-ACCESS read-write
        STATUS mandatory         
        DESCRIPTION
            "the maximum packet size for the switch."   
        DEFVAL {1522}
        ::= { rcSwitchConfig 29 }                     
                                                                    
    rcSvlDefaultVlan OBJECT-TYPE
        SYNTAX  Integer32 (1..4094)
        MAX-ACCESS read-write
        STATUS mandatory
        DESCRIPTION
            "default vlan which the mac address is also learned to."   
        DEFVAL {1}
        ::= { rcSwitchConfig 30 }

    rcTelnetMaxSessions OBJECT-TYPE
        SYNTAX  Integer32 (0..5)
        MAX-ACCESS read-write
        STATUS current
        DESCRIPTION
            "Max sessions device telnet server permits. '0' indicates that 
            device won't permits any telnet connect."   
        DEFVAL {5}
        ::= { rcSwitchConfig 31 }
        
    rcTelnetAcceptPorts OBJECT-TYPE
        SYNTAX  PortList
        MAX-ACCESS read-write
        STATUS current
        DESCRIPTION
            "Ports that access telnet connect request to telnet server 
            on device."   
        ::= { rcSwitchConfig 32 }
        
    rcVlanMacLearning OBJECT-TYPE
        SYNTAX  Vlanset
        MAX-ACCESS read-write
        STATUS current
        DESCRIPTION
            "Enable or disable source MAC address learning on VLAN."   
        ::= { rcSwitchConfig 33 }
        
    rcConsoleEnable OBJECT-TYPE
        SYNTAX  EnableVar
        MAX-ACCESS read-write
        STATUS current
        DESCRIPTION
            "Enable or disable console connect."
        ::= { rcSwitchConfig 34 }
    
    rcStormControlOperpps OBJECT-TYPE
        SYNTAX  INTEGER  (1..262143)
        UNITS	"pps"      
        ACCESS read-only
        STATUS mandatory
        DESCRIPTION
                " The actual limit number for storm control on the interface ."    
        ::= { rcSwitchConfig 35 }
                                             
    rcStormControlOperbps OBJECT-TYPE
        SYNTAX  INTEGER  (0..1073741823)
        UNITS	"bps"      
        ACCESS read-only
        STATUS mandatory
        DESCRIPTION
                " The actual limit number for storm control on the interface ."    
        ::= { rcSwitchConfig 36 }
        
     rcOperMaxAllowedFrameLength OBJECT-TYPE
        SYNTAX  INTEGER (1500..65535)
        MAX-ACCESS read-only
        STATUS mandatory         
        DESCRIPTION
            "The actual maximum packet size for the switch."   
        DEFVAL {1522}
        ::= { rcSwitchConfig 37 }                     
   
        
    rcTrapBindipEnable    OBJECT-TYPE
        SYNTAX  EnableVar
        MAX-ACCESS read-write
        STATUS current
        DESCRIPTION
            "Enable or disable rapBindip.DEFVAL  { disable } "         
        ::= { rcSwitchConfig 38 }    
    
              
--rcPortInfoConfig  
  
    rcPortTable OBJECT-TYPE
        SYNTAX SEQUENCE OF RcPortEntry
        MAX-ACCESS not-accessible
        STATUS current
        DESCRIPTION
            "A table of switch port and associated properties."
        ::= { rcPortInfoConfig 1 }

    rcPortEntry OBJECT-TYPE
        SYNTAX RcPortEntry
        MAX-ACCESS not-accessible
        STATUS current
        DESCRIPTION
            "Table entry for switch port control and status information."
        INDEX { rcPortIndex }
        ::= { rcPortTable 1 }
                      
    RcPortEntry ::= SEQUENCE {
        rcPortIndex                		Integer32,
        rcPortType 						INTEGER,
        rcSlotTableIndex                INTEGER,
        rcSlotPortIndex                 INTEGER,
        rcPortAdminStatus               INTEGER,
        rcPortOperStatus                INTEGER,
        rcPortDuplexSpeedSet      		INTEGER,
        rcPortDuplexSpeedGet      		INTEGER,
        rcPortFlowControlEnable    		EnableVar,
        rcPortMacLearningEnable    		EnableVar,
        rcPortMacThreshold         		INTEGER,
        rcPortStormControlBcastEnable	EnableVar,
        rcPortStormControlMcastEnable   EnableVar,
        rcPortStormControlDlfEnable	  	EnableVar,
        rcPortStormControlBurst			INTEGER, 
        rcPortStormControlLimit	  		INTEGER,
        rcPortStormControlLimitRatio	INTEGER,
        rcPortDefaultPriority	  		INTEGER,
        rcPortLoopbackDetectEnable		EnableVar,
        rcPortLoopbackDetectSrcPort		INTEGER,	
        rcPortProtected		  			EnableVar,
        rcPortFlowControlRecvEnable    	EnableVar,
        rcPortFlowControlSendEnable    	EnableVar,
        rcPortFlowControlRecvStatus    	EnableVar,
        rcPortFlowControlSendStatus    	EnableVar,
        rcPortLoopbackDetectDownTime   	INTEGER,
        rcPortMediaAttachType			INTEGER,
        rcPortMediaAttachCapability		INTEGER,
        rcPortMDIXMode                  INTEGER,
        rcPortMDIXStatus                INTEGER,
        rcportDiscPKts                  Counter32,
        rcPortMacThresholdVlan		    INTEGER, 
        rcPortPhysicalStatus            INTEGER,  
        rcPortLinkUpDelayTime           INTEGER 

        
     }      
     
   	rcPortIndex OBJECT-TYPE
        SYNTAX Integer32 
        MAX-ACCESS read-only
        STATUS current
        DESCRIPTION
            "An index based 1 that uniquely identifies a system interface."
        ::= { rcPortEntry 1 }     
        
    rcPortType OBJECT-TYPE
        SYNTAX INTEGER{
        		inexistence(0),
        		fx-DulMode-1000M(1), 
        		tx-1000M(2), 
        		fx-SigMode-1000M(3), 
        		fx-DulMode-100M(4), 
        		fx-SigMode-100M(5), 
        		tx-100M(6),
        		px-1000M(7)
        } 
        MAX-ACCESS read-only
        STATUS current
        DESCRIPTION
            "port type,same as slot type."
        ::= { rcPortEntry 2 }
                  
    rcSlotTableIndex OBJECT-TYPE
        SYNTAX INTEGER 
        MAX-ACCESS read-only
        STATUS current
        DESCRIPTION
            "the index of slot which this port is in."
        ::= { rcPortEntry 3 }
          
    rcSlotPortIndex OBJECT-TYPE
        SYNTAX INTEGER 
        MAX-ACCESS read-only
        STATUS current
        DESCRIPTION
            "index of this port in the slot"
        ::= { rcPortEntry 4 }
        
	rcPortAdminStatus OBJECT-TYPE
        SYNTAX INTEGER {
             up(1), 
             down(2)
        }
        MAX-ACCESS read-write
        STATUS current
        DESCRIPTION
            "The desired state of the interface."
         DEFVAL  { up }
        ::= { rcPortEntry 5 }
        
    rcPortOperStatus OBJECT-TYPE
        SYNTAX INTEGER {
             up(1), 
             down(2)
        }
        MAX-ACCESS read-only
        STATUS current
        DESCRIPTION
            "The current operational state of the interface."
        ::= { rcPortEntry 6 }   
        
    rcPortDuplexSpeedSet OBJECT-TYPE
        SYNTAX INTEGER {
             autonegotiate(1),
             half-10(2),
             full-10(3),
             half-100(4),
             full-100(5), 
             half-1000(6),
             full-1000(7)
        }
        MAX-ACCESS read-write
        STATUS current
        DESCRIPTION
            "The desired speed and duplex for this interface. If the selected
            control is not possible on the interface, a value of illegal(99)
            is returned.  If the port type does NOT support the default
            of autonegotiate(1), then the application initializes the
            port to a valid value (e.g., 1000full(6)).  Note that not all
            controls are possible for all interfaces.  For example, only
            full-1000(6) is available for Gigabit Ethernet interfaces."
        DEFVAL  { autonegotiate }
        ::= { rcPortEntry 7 }

    rcPortDuplexSpeedGet OBJECT-TYPE
        SYNTAX INTEGER {
             unknown(1),
             half-10(2),
             full-10(3),
             half-100(4),
             full-100(5), 
             half-1000(6),
             full-1000(7),
             illegal(99)
        }
        MAX-ACCESS read-only
        STATUS current
        DESCRIPTION
            "The actual speed and duplex for this interface.  If the
            interface is not configured for an acceptable value, a value of
            illegal(99) is returned.  A value of unknown(1) is returned when
            the 'rcPortLink' indicates down(2) for this interface." 
        ::= { rcPortEntry 8 } 
        
    rcPortFlowControlEnable OBJECT-TYPE
        SYNTAX  EnableVar        
        ACCESS read-write
        STATUS mandatory
        DESCRIPTION
                " Set the flow control on the interface to enable(1) or disable(2)."
        DEFVAL  { disable }
        ::= { rcPortEntry 9 }
        
    rcPortMacLearningEnable OBJECT-TYPE
        SYNTAX  EnableVar
        ACCESS read-write
        STATUS mandatory
        DESCRIPTION
                "Set the learning ability on the interface to enable(1) or disable(2)."
        DEFVAL  { enable }         
        ::= { rcPortEntry 10 }
            
    rcPortMacThreshold OBJECT-TYPE
        SYNTAX  INTEGER 
        ACCESS read-write
        STATUS mandatory
        DESCRIPTION
                "The Mac limit number on the interface or interface-vlan."
        ::= { rcPortEntry 11 }
                            
    rcPortStormControlBcastEnable OBJECT-TYPE
        SYNTAX  EnableVar
        ACCESS read-write
        STATUS mandatory
        DESCRIPTION
                "Set the broadcast storm control on the interface to enable(1) or disable(2)." 
        DEFVAL  { disable }
        ::= { rcPortEntry 12 }       
                                  
    rcPortStormControlMcastEnable OBJECT-TYPE
        SYNTAX  EnableVar
        ACCESS read-write
        STATUS mandatory
        DESCRIPTION
                "Set the multicast storm control on the interface to enable(1) or disable(2)." 
        DEFVAL  { disable }
        ::= { rcPortEntry 13 } 

                          
    rcPortStormControlDlfEnable OBJECT-TYPE
        SYNTAX  EnableVar
        ACCESS read-write
        STATUS mandatory
        DESCRIPTION
                "Set the DLF storm control on the interface to enable(1) or disable(2)." 
        DEFVAL  { disable }
        ::= { rcPortEntry 14 } 
             
    rcPortStormControlBurst OBJECT-TYPE
        SYNTAX  INTEGER (0..512)   
        UNITS	"kB"     
        ACCESS read-write
        STATUS mandatory
        DESCRIPTION
                "Set burst length when storm control open on the interface. ."
        ::= { rcPortEntry 15 } 
                           
    rcPortStormControlLimit OBJECT-TYPE
        SYNTAX  INTEGER (0..2621430)     
        UNITS	"pps"   
        ACCESS read-write
        STATUS mandatory
        DESCRIPTION
                "The limit number for storm control on this port . "         
        ::= { rcPortEntry 16 }
        
    rcPortStormControlLimitRatio OBJECT-TYPE
        SYNTAX  INTEGER (1..100)    
        UNITS	"percent"    
        ACCESS read-write
        STATUS mandatory
        DESCRIPTION
                "storm control limit ratio on this port"
        ::= { rcPortEntry 17 } 
     
    rcPortDefaultPriority OBJECT-TYPE
        SYNTAX  INTEGER (1..8)
        ACCESS read-write
        STATUS mandatory
        DESCRIPTION
                "The received untaged frames are forwarded to a proper queue according to
                 this default priority."
        ::= { rcPortEntry 18 }   
	
	rcPortLoopbackDetectEnable OBJECT-TYPE
        SYNTAX EnableVar
        MAX-ACCESS read-write
        STATUS current
        DESCRIPTION
            "Loopback detect of this port is on or off."
        ::= { rcPortEntry 19 }         
	
	rcPortLoopbackDetectSrcPort OBJECT-TYPE
        SYNTAX INTEGER 
        MAX-ACCESS read-only
        STATUS current
        DESCRIPTION
            "The source port(it sends loopback-detect packets) makes of loop with
            loopback port."
        ::= { rcPortEntry 20 }

   	rcPortProtected OBJECT-TYPE
        SYNTAX  EnableVar
        ACCESS read-write
        STATUS mandatory
        DESCRIPTION
                "Traffic between protected port group members are blocked. "
        DEFVAL  { disable }
        ::= { rcPortEntry 21 }   
    
    rcPortFlowControlRecvEnable OBJECT-TYPE
        SYNTAX  EnableVar        
        ACCESS read-write
        STATUS mandatory
        DESCRIPTION
                " Set the flow control on receive direction of the interface 
                to enable(1) or disable(2)."
        DEFVAL  { disable }
        ::= { rcPortEntry 22 }

    rcPortFlowControlSendEnable OBJECT-TYPE
        SYNTAX  EnableVar        
        ACCESS read-write
        STATUS mandatory
        DESCRIPTION
                " Set the flow control on sender direction of the interface 
                to enable(1) or disable(2)."
        DEFVAL  { disable }
        ::= { rcPortEntry 23 }
         
    rcPortFlowControlRecvStatus OBJECT-TYPE
        SYNTAX  EnableVar        
        ACCESS read-only
        STATUS mandatory
        DESCRIPTION
                " The flow control status on receive direction of the interface 
                to enable(1) or disable(2)."
        DEFVAL  { disable }
        ::= { rcPortEntry 24 }

    rcPortFlowControlSendStatus OBJECT-TYPE
        SYNTAX  EnableVar        
        ACCESS read-only
        STATUS mandatory
        DESCRIPTION
                " The flow control status on sender direction of the interface 
                to enable(1) or disable(2)."
        DEFVAL  { disable }
        ::= { rcPortEntry 25 }
         
    rcPortLoopbackDetectDownTime OBJECT-TYPE
        SYNTAX  INTEGER (0..65535)        
        ACCESS read-write
        STATUS mandatory
        DESCRIPTION
                " time of loopback port shutdown."
        ::= { rcPortEntry 26 }
                           
    rcPortMediaAttachType OBJECT-TYPE
        SYNTAX INTEGER{
        		copper(1), 
        		fiber(2),
        		card(3), 
        		sfp(4), 
        		combo-sfp(5), 
        		combo-copper(6)
        } 
        MAX-ACCESS read-only
        STATUS current
        DESCRIPTION
            "media attachment type of this Ether like interface."
        ::= { rcPortEntry 27 }
                
    rcPortMediaAttachCapability OBJECT-TYPE
        SYNTAX INTEGER{
        		inexistence(0),
        		copper-1000M(1), 
        		copper-100M(2), 
        		fiber-1000M(3), 
        		fiber-100M(4),
        		unlimited(5)
        } 
        MAX-ACCESS read-only
        STATUS current
        DESCRIPTION
            "Medium type and capability of media attachment units. It is different with 
            rcPortType which identifys the capability of the Ether like interface."
        ::= { rcPortEntry 28 }
        
    rcPortMDIXMode   OBJECT-TYPE
    	SYNTAX INTEGER{
        		normal(1), 
        		xover(2),
        		auto(3)
        } 
        MAX-ACCESS read-write
        STATUS current
        DESCRIPTION
            "Automatic MDI Crossover mode of a port/PHY"
        DEFVAL  { auto }
        ::= { rcPortEntry 29 }
        
    rcPortMDIXStatus   OBJECT-TYPE
    	SYNTAX INTEGER{
        		normal(1), 
        		xover(2)
        } 
        MAX-ACCESS read-write
        STATUS current
        DESCRIPTION
            "Automatic MDI Crossover mode of a port/PHY"
        DEFVAL  { auto }
        ::= { rcPortEntry 30 }    
        
    rcportDiscPKts  OBJECT-TYPE
        SYNTAX  Counter32 
        MAX-ACCESS read-only
        STATUS current
        DESCRIPTION
            "The number of packets which were the difference between 
            the total number of packets received on the interface and 
            all packets transmitted out of the interface "
        ::= { rcPortEntry 31 }
        
    rcPortMacThresholdVlan OBJECT-TYPE
        SYNTAX  INTEGER (1..4095)
        ACCESS read-write
        STATUS mandatory
        DESCRIPTION
                "when the Mac limits mac-thredshold on the interface-vlan, 
                it indicates the VlanId;when the mac limits mac-thredshold on interface, 
                its value is 4095."
        ::= { rcPortEntry 32 } 
        
      rcPortPhysicalStatus OBJECT-TYPE
        SYNTAX INTEGER {
             up(1), 
             down(2)
        }
        ACCESS read-write
        STATUS mandatory
        DESCRIPTION
                "The current physical state of the interface."
        ::= { rcPortEntry 33 }  
        
      rcPortLinkUpDelayTime OBJECT-TYPE
        SYNTAX  INTEGER (0..60)
        ACCESS read-write
        STATUS mandatory
        DESCRIPTION
                "The port link delay time."
        ::= { rcPortEntry 34 }

--
--Combo port property
-- 

    rcComboPortTable OBJECT-TYPE
        SYNTAX SEQUENCE OF RcComboPortEntry
        MAX-ACCESS not-accessible
        STATUS current
        DESCRIPTION
            "A table of Combo port and associated properties."
        ::= { rcPortInfoConfig 2 }

    rcComboPortEntry OBJECT-TYPE
        SYNTAX RcComboPortEntry
        MAX-ACCESS not-accessible
        STATUS current
        DESCRIPTION
            "Table entry for Combo port status information."
        INDEX { rcComboIndex, rcComboPortIndex }
        ::= { rcComboPortTable 1 }
                      
    RcComboPortEntry ::= SEQUENCE {
        rcComboIndex           		INTEGER,
        rcComboPortIndex			INTEGER,
        rcComboPortType 			INTEGER,
		rcComboPortMediaAttachType	INTEGER,
		rcComboPortActiveStatus		INTEGER,
		rcComboPortMediaAttachCapability   INTEGER 
     }      
     
   	rcComboIndex OBJECT-TYPE
        SYNTAX INTEGER 
        MAX-ACCESS not-accessible
        STATUS current
        DESCRIPTION
            "An index based 1 that uniquely identifies a Ether like interface."
        ::= { rcComboPortEntry 1 }     
                  
   	rcComboPortIndex OBJECT-TYPE
        SYNTAX INTEGER 
        MAX-ACCESS not-accessible
        STATUS current
        DESCRIPTION
            "An index for media attachment on Combo that 'rcComboIndex' uniquely identifies
            a Ether like interface."
        ::= { rcComboPortEntry 2 }     

    rcComboPortType OBJECT-TYPE
        SYNTAX INTEGER{
        		inexistence(0),
        		fx-DulMode-1000M(1), 
        		tx-1000M(2), 
        		fx-SigMode-1000M(3), 
        		fx-DulMode-100M(4), 
        		fx-SigMode-100M(5), 
        		tx-100M(6)
        } 
        MAX-ACCESS read-only
        STATUS current
        DESCRIPTION
            "port type identfies capability of Ether like interface."
        ::= { rcComboPortEntry 3 }
                               
    rcComboPortMediaAttachType OBJECT-TYPE
        SYNTAX INTEGER{
        		sfp(1), 
        		copper(2)
        } 
        MAX-ACCESS read-only
        STATUS current
        DESCRIPTION
            "media attachment type of Combo port."
        ::= { rcComboPortEntry 4 }
                                   
    rcComboPortActiveStatus OBJECT-TYPE
        SYNTAX INTEGER{
        		active(1), 
        		inactive(2)
        } 
        MAX-ACCESS read-only
        STATUS current
        DESCRIPTION
            "used to identify whether this Combo port currently be in the active state."
        ::= { rcComboPortEntry 5 }      
                                        
    rcComboPortMediaAttachCapability OBJECT-TYPE
        SYNTAX INTEGER{
        		inexistence(0),
        		copper-1000M(1), 
        		copper-100M(2), 
        		fiber-1000M(3), 
        		fiber-100M(4)
        } 
        MAX-ACCESS read-only
        STATUS current
        DESCRIPTION
            "Medium type and capability of media attachment units.  It is different with 
            rcComboPortType which identifys the capability of the Ether like interface"
        ::= { rcComboPortEntry 6 }          

--
--port storm control
-- 
    rcPortStormControlTable OBJECT-TYPE
        SYNTAX SEQUENCE OF RcPortStormControlEntry
        MAX-ACCESS not-accessible
        STATUS current
        DESCRIPTION
            "A table of ports' storm control properties."
        ::= { rcPortInfoConfig 3 }  
        
    rcPortStormControlEntry OBJECT-TYPE
        SYNTAX RcPortStormControlEntry
        MAX-ACCESS not-accessible
        STATUS current
        DESCRIPTION
            "Table entry for ports' storm control information."
        INDEX {rcPortStormControlPortIndex ,  
               rcPortStormControlPktType}
        ::= { rcPortStormControlTable 1 }
                      
    RcPortStormControlEntry ::= SEQUENCE {
        rcPortStormControlPortIndex         INTEGER,
        rcPortStormControlPktType			INTEGER,
        rcPortStormControlUnit 			    INTEGER,
		rcPortStormControlMaxValue	    INTEGER 
       } 
     
    rcPortStormControlPortIndex OBJECT-TYPE
        SYNTAX INTEGER 
        MAX-ACCESS not-accessible
        STATUS current
        DESCRIPTION
            "An index based 1 that uniquely identifies a Ether like interface."
        ::= { rcPortStormControlEntry 1 }     
    
    rcPortStormControlPktType OBJECT-TYPE
        SYNTAX INTEGER {broadcast(1),multicast(2),dlf(3)}
        MAX-ACCESS not-accessible
        STATUS current
        DESCRIPTION
            "An index that uniquely identifies packet type for storm control."
        ::= { rcPortStormControlEntry 2 }       
       
    rcPortStormControlUnit OBJECT-TYPE
        SYNTAX INTEGER {pps(1),bps(2)} 
        MAX-ACCESS read-write
        STATUS current
        DESCRIPTION
            "unit of value for storm control."
        ::= { rcPortStormControlEntry 3 } 
       
    rcPortStormControlMaxValue OBJECT-TYPE 
    	SYNTAX INTEGER  
    	MAX-ACCESS read-write
        STATUS current
        DESCRIPTION
            "Max value for storm control."
        ::= { rcPortStormControlEntry 4 } 
        
rcLoopbackLinkUpTrap NOTIFICATION-TYPE
           OBJECTS { rcPortIndex }
           STATUS  current
           DESCRIPTION
               "A linkDown trap signifies that the port identified by rcPortIndex
               change to link up state from link down."
       ::= { rcLoopbackTrap 1 }

	rcLoopbackLinkDownTrap NOTIFICATION-TYPE
           OBJECTS { rcPortIndex, rcPortLoopbackDetectSrcPort,rcPortLoopbackDetectDownTime  }
           STATUS  current
           DESCRIPTION
               "A linkDown trap signifies that the port identified by rcPortIndex
               change to link down state from link up."
       ::= { rcLoopbackTrap 2 }
  
--
-- insert or remove connector trap
--        
    rcPortConnectorInsertTrap NOTIFICATION-TYPE
           OBJECTS { rcPortIndex, rcPortType, rcPortMediaAttachType, rcPortMediaAttachCapability }
           STATUS  current
           DESCRIPTION
               "To notify NMS that connector has been inserted. If 'rcPortMediaAttachType'
               is 'combo' NMS need check 'rcComboPortTable' for deciding which combo port
               is inserted."
       ::= { rcPorConnectorChangeTrap 1 }

	rcPortConnectorRemoveTrap NOTIFICATION-TYPE
           OBJECTS { rcPortIndex, rcPortType, rcPortMediaAttachType, rcPortMediaAttachCapability}
           STATUS  current
           DESCRIPTION
               "To notify NMS that connector has been removed. If 'rcPortMediaAttachType'
               is 'combo' NMS need check 'rcComboPortTable' for deciding which combo port
               is removed."
       ::= { rcPorConnectorChangeTrap 2 }   
       
       
   -- Port to USP mapping table
   rcUspPortToUspMappingTable  OBJECT-TYPE
       SYNTAX     SEQUENCE OF RcUspPortToUspMappingEntry
       MAX-ACCESS  not-accessible
       STATUS      current
       DESCRIPTION
           "The table describes how the port map to the USP."
       ::= { rcPortMappingInfoConfig 1 }
       
   rcUspPortToUspMappingEntry OBJECT-TYPE
       SYNTAX      RcUspPortToUspMappingEntry
       MAX-ACCESS  not-accessible
       STATUS      current
       DESCRIPTION 
           "Defines an entry in the rcUspPortToUspMappingTable.The index is
           rcPortIndex,while is unique in raisecom private mib."
       INDEX   { 
                 rcPortIndex
               }
       ::= { rcUspPortToUspMappingTable 1 }

   RcUspPortToUspMappingEntry ::=
       SEQUENCE {  
       rcUspPortToUspMappingUnitIndex      INTEGER,
       rcUspPortToUspMappingSlotIndex      INTEGER,
       rcUspPortToUspMappingPortIndex      INTEGER
       }  
       
   rcUspPortToUspMappingUnitIndex   OBJECT-TYPE
       SYNTAX     INTEGER
       MAX-ACCESS  read-only
       STATUS      current
       DESCRIPTION
           "The unit index which port is mapped to."
       ::= { rcUspPortToUspMappingEntry 1 } 
       
   rcUspPortToUspMappingSlotIndex    OBJECT-TYPE
       SYNTAX     INTEGER
       MAX-ACCESS  read-only
       STATUS      current
       DESCRIPTION
           "The slot index which port is mapped to."
       ::= { rcUspPortToUspMappingEntry 2 }
       
   rcUspPortToUspMappingPortIndex   OBJECT-TYPE
       SYNTAX     INTEGER
       MAX-ACCESS  read-only
       STATUS      current
       DESCRIPTION
           "The port index which port is mapped to."
       ::= { rcUspPortToUspMappingEntry 3 }             
 
    -- USP to port mapping table
   rcUspUspToPortMappingTable  OBJECT-TYPE
       SYNTAX     SEQUENCE OF RcUspUspToPortMappingEntry
       MAX-ACCESS  not-accessible
       STATUS      current
       DESCRIPTION
           "The table describes how the USP map to the port."
       ::= { rcPortMappingInfoConfig 2 }
       
   rcUspUspToPortMappingEntry OBJECT-TYPE
       SYNTAX      RcUspUspToPortMappingEntry
       MAX-ACCESS  not-accessible
       STATUS      current
       DESCRIPTION 
           "Defines an entry in the rcUspUspToPortMappingTable.The indexes are
           rcUspUspToPortMappingUnitIndex,rcUspUspToPortMappingSlotIndex and rcUspUspToPortMappingPortIndex."
       INDEX   { 
                 rcUspUspToPortMappingUnitIndex,
                 rcUspUspToPortMappingSlotIndex,
                 rcUspUspToPortMappingPortIndex
               }
       ::= { rcUspUspToPortMappingTable 1 }

   RcUspUspToPortMappingEntry ::=
       SEQUENCE {  
       rcUspUspToPortMappingUnitIndex      INTEGER,
       rcUspUspToPortMappingSlotIndex      INTEGER,
       rcUspUspToPortMappingPortIndex      INTEGER,
       rcUspPortIndex                      INTEGER
       }  

   rcUspUspToPortMappingUnitIndex   OBJECT-TYPE
       SYNTAX     INTEGER
       MAX-ACCESS  not-accessible
       STATUS      current
       DESCRIPTION
           "The unit index which is mapped to the port."
       ::= { rcUspUspToPortMappingEntry 1 }
              
   rcUspUspToPortMappingSlotIndex   OBJECT-TYPE
       SYNTAX     INTEGER
       MAX-ACCESS  not-accessible
       STATUS      current
       DESCRIPTION
           "The slot index which is mapped to the port."
       ::= { rcUspUspToPortMappingEntry 2 }
       
   rcUspUspToPortMappingPortIndex   OBJECT-TYPE
       SYNTAX     INTEGER
       MAX-ACCESS  not-accessible
       STATUS      current
       DESCRIPTION
           "The port index which is mapped to the port."
       ::= { rcUspUspToPortMappingEntry 3 }
       
   rcUspPortIndex   OBJECT-TYPE
       SYNTAX     INTEGER
       MAX-ACCESS  read-only
       STATUS      current
       DESCRIPTION
           "The port index which the USP is mapped to."
       ::= { rcUspUspToPortMappingEntry 4 }
       
    -- Simple Object Definitions
   rcUspUnitNum   OBJECT-TYPE
       SYNTAX      INTEGER
       MAX-ACCESS  read-only
       STATUS      current
       DESCRIPTION
          "The total unit number."
       DEFVAL { 0 }
       ::= { rcPortMappingInfoConfig 3 }
       
   -- USP unit info table
   rcUspUnitTable  OBJECT-TYPE
       SYNTAX     SEQUENCE OF RcUspUnitEntry
       MAX-ACCESS  not-accessible
       STATUS      current
       DESCRIPTION
           "The table describes the detail of unit."
       ::= { rcPortMappingInfoConfig 4 }
       
   rcUspUnitEntry OBJECT-TYPE
       SYNTAX      RcUspUnitEntry
       MAX-ACCESS  not-accessible
       STATUS      current
       DESCRIPTION 
           "Defines an entry in the rcUspUnitTable.The index is rcUspUnitIndex."
       INDEX   { 
                 rcUspUnitIndex 
               }
       ::= { rcUspUnitTable 1 }

   RcUspUnitEntry ::=
       SEQUENCE {  
       rcUspUnitIndex                      INTEGER,
       rcUspUnitSlotNum                    INTEGER,
       rcUspUnitPortNum                    INTEGER
       }  
       
   rcUspUnitIndex   OBJECT-TYPE
       SYNTAX     INTEGER
       MAX-ACCESS  not-accessible
       STATUS      current
       DESCRIPTION
           "The port index which the USP is mapped to."
       ::= { rcUspUnitEntry 1 } 
       
   rcUspUnitSlotNum   OBJECT-TYPE
       SYNTAX     INTEGER
       MAX-ACCESS  read-only
       STATUS      current
       DESCRIPTION
           "The total slot num which the corresponding unit has."
       ::= { rcUspUnitEntry 2 }
       
   rcUspUnitPortNum   OBJECT-TYPE
       SYNTAX     INTEGER
       MAX-ACCESS  read-only
       STATUS      current
       DESCRIPTION
           "The total port num which the corresponding unit has."
       ::= { rcUspUnitEntry 3 }
       
   -- USP slot info table
   rcUspSlotTable  OBJECT-TYPE
       SYNTAX     SEQUENCE OF RcUspSlotEntry
       MAX-ACCESS  not-accessible
       STATUS      current
       DESCRIPTION
           "The table describes the detail of slot."
       ::= { rcPortMappingInfoConfig 5 }
       
   rcUspSlotEntry OBJECT-TYPE
       SYNTAX      RcUspSlotEntry
       MAX-ACCESS  not-accessible
       STATUS      current
       DESCRIPTION 
           "Defines an entry in the rcUspSlotTable.The indexes are rcUspSlotUnitIndex and rcUspSlotSlotIndex."
       INDEX   { 
                 rcUspSlotUnitIndex,
                 rcUspSlotSlotIndex 
               }
       ::= { rcUspSlotTable 1 }

   RcUspSlotEntry ::=
       SEQUENCE {  
       rcUspSlotUnitIndex                      INTEGER,
       rcUspSlotSlotIndex                      INTEGER,
       rcUspSlotSlotType                       INTEGER,
       rcUspSlotRightSubcardType               INTEGER,
       rcUspSlotActualSubcardType              INTEGER,
       rcUspSlotSerial                         OCTET STRING,
       rcUspSlotHardVersion                    OCTET STRING,
       rcUspSlotSoftwareVersion                OCTET STRING,
       rcUspSlotPortStart                      INTEGER,
       rcUspSlotPortNum                        INTEGER, 
       rcUspSlotSlotState                      INTEGER
              }  
       
   rcUspSlotUnitIndex   OBJECT-TYPE
       SYNTAX     INTEGER
       MAX-ACCESS  not-accessible
       STATUS      current
       DESCRIPTION
           "The unit index which a slot belongs to."
       ::= { rcUspSlotEntry 1 } 
       
    rcUspSlotSlotIndex   OBJECT-TYPE
       SYNTAX     INTEGER
       MAX-ACCESS  not-accessible
       STATUS      current
       DESCRIPTION
           "The slot index."
       ::= { rcUspSlotEntry 2 }  
       
    rcUspSlotSlotType   OBJECT-TYPE
       SYNTAX     INTEGER {
        		other(1),
        		manage(2), 
        		manage-backup(3), 
        		power(4), 
        		fan(5),
        		monite(6),
        		fixed(7),
                gigabit-ethenet(8),
                tdm-clock(9),  
                pon(10)
        }
       MAX-ACCESS  read-only
       STATUS      current
       DESCRIPTION
           "The slot type."
       ::= { rcUspSlotEntry 3 }
       
    rcUspSlotRightSubcardType   OBJECT-TYPE
       SYNTAX   INTEGER
       MAX-ACCESS  read-only
       STATUS      current
       DESCRIPTION
           "The type of subcard which is suitable to the slot."
       ::= { rcUspSlotEntry 4 } 
       
   rcUspSlotActualSubcardType   OBJECT-TYPE
       SYNTAX   INTEGER
       MAX-ACCESS  read-only
       STATUS      current
       DESCRIPTION
           "The type of subcard which is inserted to the slot."
       ::= { rcUspSlotEntry 5 }
       
    rcUspSlotSerial   OBJECT-TYPE
       SYNTAX     OCTET STRING
       MAX-ACCESS  read-only
       STATUS      current
       DESCRIPTION
           "The serial number of slot."
       DEFVAL { "--" }
       ::= { rcUspSlotEntry 6 }
       
    rcUspSlotHardVersion   OBJECT-TYPE
       SYNTAX     OCTET STRING
       MAX-ACCESS  read-only
       STATUS      current
       DESCRIPTION
           "The hard version of slot."
       DEFVAL { "--" }
       ::= { rcUspSlotEntry 7 }
       
    rcUspSlotSoftwareVersion   OBJECT-TYPE
       SYNTAX     OCTET STRING
       MAX-ACCESS  read-only
       STATUS      current
       DESCRIPTION
           "The soft version of slot."
       DEFVAL { "--" }
       ::= { rcUspSlotEntry 8 }
       
    rcUspSlotPortStart   OBJECT-TYPE
       SYNTAX     INTEGER
       MAX-ACCESS  read-only
       STATUS      current
       DESCRIPTION
           "The global port index this slot starts from."
       ::= { rcUspSlotEntry 9 }
       
    rcUspSlotPortNum   OBJECT-TYPE
       SYNTAX     INTEGER
       MAX-ACCESS  read-only
       STATUS      current
       DESCRIPTION
           "The number of ports this slot has."
       ::= { rcUspSlotEntry 10 }     
       
    rcUspSlotSlotState   OBJECT-TYPE
       SYNTAX     INTEGER {
        		active(1),
        		empty(2)
        }
       MAX-ACCESS  read-only
       STATUS      current
       DESCRIPTION
           "The slot State."
       ::= { rcUspSlotEntry 11 }   
       
   -- IF to USP mapping table
   rcUspIfToUspMappingTable  OBJECT-TYPE
       SYNTAX     SEQUENCE OF RcUspIfToUspMappingEntry
       MAX-ACCESS  not-accessible
       STATUS      current
       DESCRIPTION
           "The table describes how the IF map to the USP."
       ::= { rcPortMappingInfoConfig 6 }
       
   rcUspIfToUspMappingEntry OBJECT-TYPE
       SYNTAX      RcUspIfToUspMappingEntry
       MAX-ACCESS  not-accessible
       STATUS      current
       DESCRIPTION 
           "Defines an entry in the rcUspIfToUspMappingTable.The index is
           ifIndex,while is unique in raisecom private mib."
       INDEX   { 
                 ifIndex
               }
       ::= { rcUspIfToUspMappingTable 1 }

   RcUspIfToUspMappingEntry ::=
       SEQUENCE {  
       rcUspIfToUspMappingUnitIndex      INTEGER,
       rcUspIfToUspMappingSlotIndex      INTEGER,
       rcUspIfToUspMappingPortIndex      INTEGER,
	   rcUspIfType                       INTEGER,
	   rcUspIfState                      INTEGER
       }  
       
   rcUspIfToUspMappingUnitIndex   OBJECT-TYPE
       SYNTAX     INTEGER
       MAX-ACCESS  read-only
       STATUS      current
       DESCRIPTION
           "The unit index which IF is mapped to."
       ::= { rcUspIfToUspMappingEntry 1 } 
       
   rcUspIfToUspMappingSlotIndex    OBJECT-TYPE
       SYNTAX     INTEGER
       MAX-ACCESS  read-only
       STATUS      current
       DESCRIPTION
           "The slot index which IF is mapped to."
       ::= { rcUspIfToUspMappingEntry 2 }
       
   rcUspIfToUspMappingPortIndex   OBJECT-TYPE
       SYNTAX     INTEGER
       MAX-ACCESS  read-only
       STATUS      current
       DESCRIPTION
           "The port index which IF is mapped to."
       ::= { rcUspIfToUspMappingEntry 3 }             

   rcUspIfType   OBJECT-TYPE
       SYNTAX     INTEGER
        {
       		none(0),  
       		port(1),
       		line(2), 
       		client(3), 
       		tdm(4), 
       		ethernet(5),
       		fastethernet(6),
       		gigaethernet(7),
			tengigabitethernet(8),
			aggregator (9), 
			ip (10),
			loopback(11),
			outband(12),
			max(13)
        }
       MAX-ACCESS  read-only
       STATUS      current
       DESCRIPTION
           "The IF type which IF is mapped to."
       ::= { rcUspIfToUspMappingEntry 4 }  
   
   rcUspIfState   OBJECT-TYPE
       SYNTAX     INTEGER {
        		active(1),
        		empty(2)
        }
       MAX-ACCESS  read-only
       STATUS      current
       DESCRIPTION
           "The IF State."
       ::= { rcUspIfToUspMappingEntry 5 } 
	      
    -- USP to port mapping table
   rcUspUspToIfMappingTable  OBJECT-TYPE
       SYNTAX     SEQUENCE OF RcUspUspToIfMappingEntry
       MAX-ACCESS  not-accessible
       STATUS      current
       DESCRIPTION
           "The table describes how the USP map to the IF."
       ::= { rcPortMappingInfoConfig 7 }
       
   rcUspUspToIfMappingEntry OBJECT-TYPE
       SYNTAX      RcUspUspToIfMappingEntry
       MAX-ACCESS  not-accessible
       STATUS      current
       DESCRIPTION 
           "Defines an entry in the rcUspUspToIfMappingTable.The indexes are
           rcUspUspToIfMappingUnitIndex,rcUspUspToIfMappingSlotIndex,rcUspUspToIfMappingPortIndex and rcUspIfTypeIndex."
       INDEX   { 
                 rcUspUspToIfMappingUnitIndex,
                 rcUspUspToIfMappingSlotIndex,
                 rcUspUspToIfMappingPortIndex,
				 rcUspIfTypeIndex				 
               }
       ::= { rcUspUspToIfMappingTable 1 }

   RcUspUspToIfMappingEntry ::=
       SEQUENCE {  
       rcUspUspToIfMappingUnitIndex      INTEGER,
       rcUspUspToIfMappingSlotIndex      INTEGER,
       rcUspUspToIfMappingPortIndex      INTEGER,
	   rcUspIfTypeIndex                          INTEGER,
       rcUspIfIndex                      INTEGER
       }  

   rcUspUspToIfMappingUnitIndex   OBJECT-TYPE
       SYNTAX     INTEGER
       MAX-ACCESS  not-accessible
       STATUS      current
       DESCRIPTION
           "The unit index which is mapped to the IF."
       ::= { rcUspUspToIfMappingEntry 1 }
              
   rcUspUspToIfMappingSlotIndex   OBJECT-TYPE
       SYNTAX     INTEGER
       MAX-ACCESS  not-accessible
       STATUS      current
       DESCRIPTION
           "The slot index which is mapped to the IF."
       ::= { rcUspUspToIfMappingEntry 2 }
       
   rcUspUspToIfMappingPortIndex   OBJECT-TYPE
       SYNTAX     INTEGER
       MAX-ACCESS  not-accessible
       STATUS      current
       DESCRIPTION
           "The port index which is mapped to the IF."
       ::= { rcUspUspToIfMappingEntry 3 }
	   
   rcUspIfTypeIndex   OBJECT-TYPE
       SYNTAX     INTEGER
        {
       		none(0),  
       		port(1),
       		line(2), 
       		client(3), 
       		tdm(4), 
       		ethernet(5),
       		fastethernet(6),
       		gigaethernet(7),
			tengigabitethernet(8),
			aggregator (9), 
			ip (10),
			loopback(11),
			outband(12),
			max(13)
        }
       MAX-ACCESS  not-accessible
       STATUS      current
       DESCRIPTION
           "The port type which is mapped to the IF."
       ::= { rcUspUspToIfMappingEntry 4 }
	   
   rcUspIfIndex   OBJECT-TYPE
       SYNTAX     INTEGER
       MAX-ACCESS  read-only
       STATUS      current
       DESCRIPTION
           "The If Index which is mapped to the IF."
       ::= { rcUspUspToIfMappingEntry 5 }       
--
-- END of ROSE-SYSINFO-MIB                
--

END
