OMNI-gx2RFA1000-MIB DEFINITIONS ::= BEGIN

    IMPORTS

	IpAddress, TimeTicks, Counter            
					      FROM RFC1155-SMI
	OBJECT-TYPE                     
					      FROM RFC-1212
	DisplayString        
					      FROM RFC1213-MIB
	TRAP-TYPE                       
					      FROM RFC-1215
	gx2Rfa1000
					      FROM GX2HFC-MIB

	trapIdentifier,trapNetworkElemModelNumber,
	trapNetworkElemSerialNum, trapPerceivedSeverity,
	trapNetworkElemOperState, trapNetworkElemAlarmStatus,
	trapNetworkElemAdminState, trapNetworkElemAvailStatus,
	trapText, trapNETrapLastTrapTimeStamp, trapChangedObjectId,
	trapChangedValueInteger, trapChangedValueDisplayString
					      FROM NLSBBN-TRAPS-MIB;



	       -- This MIB module uses the extended OBJECT-TYPE macro as
	       -- defined in RFC1212 and the TRAP-TYPE macro as defined
	       -- in RFC 1215.

		   --REVISION	"1" JAN 14, 2004
		   --DESCRIPTION
		   --			Initial release


		--    OMNISTAR RF Amplifier Module  MIB MODULE

	-- This MIB module defines information for management of HFC networks
		-- 
		-- The MIB module assumes that all generic (static) network element
		-- information is defined in a different module such as the HFC module
		-- The MIB consists of two groups:
		-- the device type descriptor subgroup and 
		-- gx2Rfa1000 Network Elements subgroup.
		-- The device type descriptor subgroup is used to define 
		-- parameters specific to gx2Rfa1000 device type.
		-- These parameters are common across all network elements
		-- from gx2Rfa1000 device type.
		--
		-- The gx2Rfa1000 Network Elements subgroup is
		-- a list of gx2Rfa1000 type elements in the
		-- current network topology with nominal
		-- and current parameter values for the
		-- individual network elements; the individual
		-- network elements are identified by  
		-- index from hfcCommonTable.
		-- That implies what hfcCommonTableIndex and
		-- gx2Rfa1000TableIndex are equal for each individual
		-- network element.
		-- This table is an extension of the hfcCommonTable
		-- for all elements of gx2Rfa1000 type.
		--
		-- Both groups are mandatory for management of gx2Rfa1000 devices.

-- ****************************************************************************
		--
		-- All floating point numbers will be represented by an IEEE 32 Bit number.
		-- Conversion of this number must be done on the user interface to view the 
		-- actual floating point number. 
		--

		Float ::= Counter  -- UNSIGNED (32 BITS) 

-- ****************************************************************************

		-- gx2Rfa1000 Device Descriptor subgroup.

		-- The device type descriptor subgroup is used to define 
		-- parameters specific to gx2Rfa1000 device type.
		-- These parameters are common across all network elements
		-- from gx2Rfa1000 device type.


		gx2Rfa1000Descriptor OBJECT IDENTIFIER ::= {gx2Rfa1000 1}



--*****************************************************************************
		--              gx2Rfa1000 Table
		
		-- The individual network elements indentified by  
		-- index from hfcCommonTable.
		-- That implies what hfcCommonTableIndex and
		-- gx2Rfa1000TableIndex are equal for each individual
		-- nettwork element.
		-- This table should be used as an extension of the hfcCommonTable
		-- for all elements of gx2Rfa1000 type.


	       gx2Rfa1000AnalogTable                    OBJECT-TYPE
			 SYNTAX             SEQUENCE OF Gx2Rfa1000AnalogEntry
			 ACCESS             not-accessible
			 STATUS             mandatory
			 DESCRIPTION
			 "This table contains gx2Rfa1000 specific parameters with
			  nominal and current values."
			 ::= { gx2Rfa1000 2 }


	       gx2Rfa1000AnalogEntry               OBJECT-TYPE
			 SYNTAX             Gx2Rfa1000AnalogEntry
			 ACCESS             not-accessible
			 STATUS             mandatory
			 DESCRIPTION
			 "This list contains digital product class and the
			  associated RF channel parameters and descriptions."
			 INDEX { rfagx2Rfa1000AnalogTableIndex }
			 ::= { gx2Rfa1000AnalogTable  1}

--*************************************************************************
	       gx2Rfa1000DigitalTable                    OBJECT-TYPE
			 SYNTAX             SEQUENCE OF Gx2Rfa1000DigitalEntry
			 ACCESS             not-accessible
			 STATUS             mandatory
			 DESCRIPTION
			 "This table contains gx2Rfa1000 specific parameters with
			  nominal and current values."
			 ::= { gx2Rfa1000 3 }

	       gx2Rfa1000DigitalEntry               OBJECT-TYPE
			 SYNTAX             Gx2Rfa1000DigitalEntry
			 ACCESS             not-accessible
			 STATUS             mandatory
			 DESCRIPTION
			 "This list contains digital product class and the
			  associated RF channel parameters and descriptions."
			 INDEX { rfagx2Rfa1000DigitalTableIndex }
			 ::= { gx2Rfa1000DigitalTable  2}

--*************************************************************************
	       gx2Rfa1000StatusTable                    OBJECT-TYPE
			 SYNTAX             SEQUENCE OF Gx2Rfa1000StatusEntry
			 ACCESS             not-accessible
			 STATUS             mandatory
			 DESCRIPTION
			 "This table contains gx2Rfa1000 specific parameters with
			  nominal and current values."
			 ::= { gx2Rfa1000 4 }

	       gx2Rfa1000StatusEntry               OBJECT-TYPE
			 SYNTAX             Gx2Rfa1000StatusEntry
			 ACCESS             not-accessible
			 STATUS             mandatory
			 DESCRIPTION
			 "This list contains digital product class and the
			  associated RF channel parameters and descriptions."
			 INDEX { rfagx2Rfa1000StatusTableIndex }
			 ::= { gx2Rfa1000StatusTable  3}

--*************************************************************************
	       gx2Rfa1000FactoryTable                    OBJECT-TYPE
			 SYNTAX             SEQUENCE OF Gx2Rfa1000FactoryEntry
			 ACCESS             not-accessible
			 STATUS             mandatory
			 DESCRIPTION
			 "This table contains gx2Rfa1000 specific parameters with
			  nominal and current values."
			 ::= { gx2Rfa1000 5 }

	       gx2Rfa1000FactoryEntry               OBJECT-TYPE
			 SYNTAX             Gx2Rfa1000FactoryEntry
			 ACCESS             not-accessible
			 STATUS             mandatory
			 DESCRIPTION
			 "This list contains digital product class and the
			  associated RF channel parameters and descriptions."
			 INDEX { rfagx2Rfa1000FactoryTableIndex }
			 ::= { gx2Rfa1000FactoryTable  4}

--***********************************************************************

	       gx2Rfa1000HoldTimeTable                    OBJECT-TYPE
			 SYNTAX             SEQUENCE OF Gx2Rfa1000HoldTimeEntry
			 ACCESS             not-accessible
			 STATUS             mandatory
			 DESCRIPTION
			 "This table contains gx2Rfa1000 specific parameters with
			  nominal and current values."
			 ::= { gx2Rfa1000 6 }

	       gx2Rfa1000HoldTimeEntry               OBJECT-TYPE
			 SYNTAX             Gx2Rfa1000HoldTimeEntry
			 ACCESS             not-accessible
			 STATUS             mandatory
			 DESCRIPTION
			 "This list contains digital product class and the
			  associated RF channel parameters and descriptions."
			 INDEX { gx2Rfa1000HoldTimeTableIndex, gx2Rfa1000HoldTimeSpecIndex }
			 ::= { gx2Rfa1000HoldTimeTable  5}

--***********************************************************************

	     Gx2Rfa1000AnalogEntry    ::= SEQUENCE  
	    {
		rfagx2Rfa1000AnalogTableIndex         INTEGER,   
		
		--           Analog Parameters

		rfalabelModTemp			DisplayString (SIZE (0..80)),
		rfauomModTemp			DisplayString (SIZE (0..80)),
		rfamajorHighModTemp		Float, 
		rfamajorLowModTemp		Float, 
		rfaminorHighModTemp		Float,
		rfaminorLowModTemp		Float, 
		rfacurrentValueModTemp		Float, 
		rfastateFlagModTemp		INTEGER,
		rfaminValueModTemp		Float,
		rfamaxValueModTemp		Float,
		rfaalarmStateModTemp		INTEGER,

		rfalabelFanCurrent		DisplayString (SIZE (0..80)),
		rfauomFanCurrent			DisplayString (SIZE (0..80)),
		rfamajorHighFanCurrent		Float, 
		rfamajorLowFanCurrent		Float, 
		rfaminorHighFanCurrent		Float,
		rfaminorLowFanCurrent		Float, 
		rfacurrentValueFanCurrent	Float, 
		rfastateFlagFanCurrent		INTEGER,
		rfaminValueFanCurrent		Float,
		rfamaxValueFanCurrent 		Float,
		rfaalarmStateFanCurrent		INTEGER,

		rfalabel12Volt			DisplayString (SIZE (0..80)),
		rfauom12Volt			DisplayString (SIZE (0..80)),
		rfamajorHigh12Volt		Float, 
		rfamajorLow12Volt			Float, 
		rfaminorHigh12Volt		Float,
		rfaminorLow12Volt			Float, 
		rfacurrentValue12Volt		Float, 
		rfastateFlag12Volt		INTEGER,
		rfaminValue12Volt			Float,
		rfamaxValue12Volt			Float,
		rfaalarmState12Volt		INTEGER
		}

		-- ****************  Digital Parameters ***********************
      Gx2Rfa1000DigitalEntry   ::= SEQUENCE  
      {

		rfagx2Rfa1000DigitalTableIndex         INTEGER,   
		rfalabelSlopeSetting 		DisplayString (SIZE (0..80)),
		rfavalueSlopeSetting		INTEGER,
		rfaenumSlopeSetting		DisplayString (SIZE (0..80)),
		rfastateFlagSlopeSetting      	INTEGER,

		rfalabelAttnSetting		DisplayString (SIZE (0..80)),
		rfavalueAttnSetting		INTEGER,
		rfaenumAttnSetting		DisplayString (SIZE (0..80)),
		rfastateFlagAttnSetting      	INTEGER,

		rfalabelFactoryDefault		DisplayString (SIZE (0..80)),
		rfavalueFactoryDefault		INTEGER,
		rfaenumFactoryDefault		DisplayString (SIZE (0..80)),
		rfastateFlagFactoryDefault   	INTEGER
		}

		-- ****************  Status Parameters ************************************
      Gx2Rfa1000StatusEntry    ::= SEQUENCE  
      {

		rfagx2Rfa1000StatusTableIndex         INTEGER,   
		rfalabelBoot				DisplayString (SIZE (0..80)),
		rfavalueBoot				INTEGER,
		rfastateflagBoot				INTEGER,
		
		rfalabelFlash				DisplayString (SIZE (0..80)),
		rfavalueFlash				INTEGER,
		rfastateflagFlash				INTEGER,

		rfalabelFactoryDataCRC 			DisplayString (SIZE (0..80)),
		rfavalueFactoryDataCRC			INTEGER,
		rfastateflagFactoryDataCRC		INTEGER,

		rfalabelAlarmDataCRC 			DisplayString (SIZE (0..80)),
		rfavalueAlarmDataCRC			INTEGER,
		rfastateflagAlarmDataCRC		INTEGER,

		rfalabelSlopeCalDataCRC		DisplayString (SIZE (0..80)),
		rfavalueSlopeCalDataCRC		INTEGER,
		rfastateflagSlopeCalDataCRC	INTEGER,

		rfalabelAttnCalDataCRC		DisplayString (SIZE (0..80)),
		rfavalueAttnCalDataCRC		INTEGER,
		rfastateflagAttnCalDataCRC		INTEGER

		}
		

		-- ****************  Factory Parameters *************************************
      Gx2Rfa1000FactoryEntry    ::= SEQUENCE  
      {
		rfagx2Rfa1000FactoryTableIndex         INTEGER,   
		rfabootControlByte  	INTEGER,
		rfabootStatusByte   	INTEGER,
		rfabank0CRC    			INTEGER,
		rfabank1CRC    			INTEGER,
		rfaprgEEPROMByte    	INTEGER,
		rfafactoryCRC    		INTEGER,
		rfacalculateCRC    		INTEGER,
		rfahourMeter    		INTEGER,
		rfaflashPrgCntA    		INTEGER,
		rfaflashPrgCntB    		INTEGER,
		rfafwRev0	    		DisplayString (SIZE (0..80)),
		rfafwRev1	    		DisplayString (SIZE (0..80))

		}


		-- ****************  Hold Time Parameters *************************************
	    Gx2Rfa1000HoldTimeEntry    ::= SEQUENCE  
	    {
		gx2Rfa1000HoldTimeTableIndex        INTEGER,
		gx2Rfa1000HoldTimeSpecIndex         INTEGER,   
		gx2Rfa1000HoldTimeData  			 INTEGER
		}

            -- ************** Analog Parameters ****************************
		rfagx2Rfa1000AnalogTableIndex              OBJECT-TYPE
			   SYNTAX           INTEGER (1..2147483647)
			   ACCESS           read-only
			   STATUS           mandatory
			   DESCRIPTION
			   "The value of this object identifies the network
			    element. This index is equal to the
			    hfcCommonTableIndex for the same element."
			   ::= { gx2Rfa1000AnalogEntry 1}

-- New Parameter

		rfalabelModTemp              OBJECT-TYPE
			   SYNTAX           DisplayString (SIZE (0..80))
			   ACCESS           read-only
			   STATUS           optional
			   DESCRIPTION
			   "The value of this object provides the label of the
			    Module Temperature Analog parameter."
			   ::= { gx2Rfa1000AnalogEntry 2}

		rfauomModTemp                OBJECT-TYPE
			   SYNTAX           DisplayString (SIZE (0..80))
			   ACCESS           read-only
			   STATUS           optional
			   DESCRIPTION
			   "The value of this object provides the Unit of Measure of the
			    Module Temperature Analog parameter. The unit of measure for 
			    this parameter is Degrees C"
			   ::= { gx2Rfa1000AnalogEntry 3}

		rfamajorHighModTemp          OBJECT-TYPE
			   SYNTAX           Float 
			   ACCESS           read-only
			   STATUS           mandatory
			   DESCRIPTION
			   "The value of this object provides the Major High alarm value
			   of the Module Temperature Analog parameter. This value is a floating 
			   point number that is represented as an IEEE 32 bit number."
			   ::= { gx2Rfa1000AnalogEntry 4}


		rfamajorLowModTemp           OBJECT-TYPE
			   SYNTAX           Float 
			   ACCESS           read-only
			   STATUS           mandatory
			   DESCRIPTION
			   "The value of this object provides the Major Low alarm value
			          of the Module Temperature Analog parameter. "
			   ::= { gx2Rfa1000AnalogEntry 5}

		rfaminorHighModTemp          OBJECT-TYPE
			   SYNTAX           Float
			   ACCESS           read-only
			   STATUS           mandatory
			   DESCRIPTION
			   "The value of this object provides the Minor High alarm value
			          of the Module Temperature Analog parameter."
			   ::= { gx2Rfa1000AnalogEntry 6}

		rfaminorLowModTemp           OBJECT-TYPE
			   SYNTAX           Float 
			   ACCESS           read-only
			   STATUS           mandatory
			   DESCRIPTION
			   "The value of this object provides the Minor Low alarm value
			          of the Module Temperature Analog parameter. "
			   ::= { gx2Rfa1000AnalogEntry 7}

		rfacurrentValueModTemp       OBJECT-TYPE
			   SYNTAX           Float 
			   ACCESS           read-only
			   STATUS           mandatory
			   DESCRIPTION
			   "The value of this object provides the Current value
			          of the Module Temperature Analog parameter. "
			   ::= { gx2Rfa1000AnalogEntry 8}

		rfastateFlagModTemp          OBJECT-TYPE
			   SYNTAX           INTEGER
								{
								hidden(1),
								read-only(2),
								updateable(3)
								}
			   ACCESS           read-only
			   STATUS           mandatory
			   DESCRIPTION
			   "The value of this object provides the state
			    of the Module Temperature Analog parameter. (1-hidden	
			          2-read-only, 3-updateable)."
			   ::= { gx2Rfa1000AnalogEntry 9}

		rfaminValueModTemp           OBJECT-TYPE
			   SYNTAX           Float
			   ACCESS           read-only
			   STATUS           mandatory
			   DESCRIPTION
			   "The value of this object provides the minimum value
			          of the Module Temperature Analog parameter. "
			   ::= { gx2Rfa1000AnalogEntry 10}

		rfamaxValueModTemp           OBJECT-TYPE
			   SYNTAX           Float
			   ACCESS           read-only
			   STATUS           mandatory
			   DESCRIPTION
			   "The value of this object provides the maximum value
			          of the Module Temperature Analog parameter. "
			   ::= { gx2Rfa1000AnalogEntry 11}

		rfaalarmStateModTemp         OBJECT-TYPE
			   SYNTAX           INTEGER
									{
									noAlarm(1),
									majorLowAlarm(2),
									minorLowAlarm(3),
									minorHighAlarm(4),
									majorHighAlarm(5),
									informational(6)
									}
			   ACCESS           read-only
			   STATUS           mandatory
			   DESCRIPTION
			   "The value of this object provides the curent alarm state of
			    the Module Temperature Analog parameter."
			   ::= { gx2Rfa1000AnalogEntry 12}

-- New Parameter

		rfalabelFanCurrent           OBJECT-TYPE
			   SYNTAX           DisplayString (SIZE (0..80))
			   ACCESS           read-only
			   STATUS           optional
			   DESCRIPTION
			   "The value of this object provides the label of the
			    Fan Current Analog parameter."
			   ::= { gx2Rfa1000AnalogEntry 13}

		rfauomFanCurrent             OBJECT-TYPE
			   SYNTAX           DisplayString (SIZE (0..80))
			   ACCESS           read-only
			   STATUS           optional
			   DESCRIPTION
			   "The value of this object provides the Unit of Measure of the
			    Fan Current Analog parameter. The unit of measure for 
			    this parameter is mA"
			   ::= { gx2Rfa1000AnalogEntry 14}

		rfamajorHighFanCurrent       OBJECT-TYPE
			   SYNTAX           Float 
			   ACCESS           read-only
			   STATUS           mandatory
			   DESCRIPTION
			   "The value of this object provides the Major High alarm value
			          of the Fan Current Analog parameter."
			   ::= { gx2Rfa1000AnalogEntry 15}


		rfamajorLowFanCurrent        OBJECT-TYPE
			   SYNTAX           Float 
			   ACCESS           read-only
			   STATUS           mandatory
			   DESCRIPTION
			   "The value of this object provides the Major Low alarm value
			          of the Fan Current Analog parameter. "
			   ::= { gx2Rfa1000AnalogEntry 16}

		rfaminorHighFanCurrent       OBJECT-TYPE
			   SYNTAX           Float
			   ACCESS           read-only
			   STATUS           obsolete
			   DESCRIPTION
			   "The value of this object provides the Minor High alarm value
			          of the Fan Current Analog parameter. This object is not 
			          used by this module and always returns invalid float 
			          value of 0xFFFFFFFF . This object is kept here for persistence"
			   ::= { gx2Rfa1000AnalogEntry 17}

		rfaminorLowFanCurrent        OBJECT-TYPE
			   SYNTAX           Float 
			   ACCESS           read-only
			   STATUS           obsolete
			   DESCRIPTION
			   "The value of this object provides the Minor Low alarm value
			          of the Fan Current Analog parameter. This object is not 
			          used by this module and always returns invalid float 
			          value of 0xFFFFFFFF . This object is kept here for persistence"
			   ::= { gx2Rfa1000AnalogEntry 18}

		rfacurrentValueFanCurrent    OBJECT-TYPE
			   SYNTAX           Float 
			   ACCESS           read-only
			   STATUS           mandatory
			   DESCRIPTION
			   "The value of this object provides the Current value
			          of the Fan Current Analog parameter. "
			   ::= { gx2Rfa1000AnalogEntry 19}

		rfastateFlagFanCurrent       OBJECT-TYPE
			   SYNTAX           INTEGER
								{
								hidden(1),
								read-only(2),
								updateable(3)
								}

			   ACCESS           read-only
			   STATUS           mandatory
			   DESCRIPTION
			   "The value of this object provides the state
			    of the Fan Current Analog parameter. (1-hidden	
			          2-read-only, 3-updateable)."
			   ::= { gx2Rfa1000AnalogEntry 20}

		rfaminValueFanCurrent        OBJECT-TYPE
			   SYNTAX           Float
			   ACCESS           read-only
			   STATUS           mandatory
			   DESCRIPTION
			   "The value of this object provides the minimum value
			          of the Fan Current Analog parameter. "
			   ::= { gx2Rfa1000AnalogEntry 21}

		rfamaxValueFanCurrent        OBJECT-TYPE
			   SYNTAX           Float
			   ACCESS           read-only
			   STATUS           mandatory
			   DESCRIPTION
			   "The value of this object provides the maximum value
			          of the Fan Current Analog parameter. "
			   ::= { gx2Rfa1000AnalogEntry 22}

		rfaalarmStateFanCurrent      OBJECT-TYPE
			   SYNTAX           INTEGER
									{
									noAlarm(1),
									majorLowAlarm(2),
									minorLowAlarm(3),
									minorHighAlarm(4),
									majorHighAlarm(5),
									informational(6)
									}
			   ACCESS           read-only
			   STATUS           mandatory
			   DESCRIPTION
			   "The value of this object provides the curent alarm state of
			    the Fan Current Analog parameter."
			   ::= { gx2Rfa1000AnalogEntry 23}
-- New Parameter

		rfalabel12Volt               OBJECT-TYPE
			   SYNTAX           DisplayString (SIZE (0..80))
			   ACCESS           read-only
			   STATUS           optional
			   DESCRIPTION
			   "The value of this object provides the label of the
			    12v Current Analog parameter."
			   ::= { gx2Rfa1000AnalogEntry 24}

		rfauom12Volt                 OBJECT-TYPE
			   SYNTAX           DisplayString (SIZE (0..80))
			   ACCESS           read-only
			   STATUS           optional
			   DESCRIPTION
			   "The value of this object provides the Unit of Measure of the
			    12v Current Analog parameter. The unit of measure for 
			    this parameter is mA"
			   ::= { gx2Rfa1000AnalogEntry 25}

		rfamajorHigh12Volt           OBJECT-TYPE
			   SYNTAX           Float 
			   ACCESS           read-only
			   STATUS           mandatory
			   DESCRIPTION
			   "The value of this object provides the Major High alarm value
			          of the 12 Volt Current Analog parameter. "
			   ::= { gx2Rfa1000AnalogEntry 26}


		rfamajorLow12Volt            OBJECT-TYPE
			   SYNTAX           Float 
			   ACCESS           read-only
			   STATUS           mandatory
			   DESCRIPTION
			   "The value of this object provides the Major Low alarm value
			          of the 12 Volt Current Analog parameter. "
			   ::= { gx2Rfa1000AnalogEntry 27}

		rfaminorHigh12Volt           OBJECT-TYPE
			   SYNTAX           Float
			   ACCESS           read-only
			   STATUS           mandatory
			   DESCRIPTION
			   "The value of this object provides the Minor High alarm value
			          of the 12 Volt Current Analog parameter. "
			   ::= { gx2Rfa1000AnalogEntry 28}

		rfaminorLow12Volt            OBJECT-TYPE
			   SYNTAX           Float 
			   ACCESS           read-only
			   STATUS           mandatory
			   DESCRIPTION
			   "The value of this object provides the Minor Low alarm value
			          of the 12 Volt Current Analog parameter. "
			   ::= { gx2Rfa1000AnalogEntry 29}

		rfacurrentValue12Volt        OBJECT-TYPE
			   SYNTAX           Float 
			   ACCESS           read-only
			   STATUS           mandatory
			   DESCRIPTION
			   "The value of this object provides the Current value
			          of the 12 Volt Current Analog parameter. "
			   ::= { gx2Rfa1000AnalogEntry 30}

		rfastateFlag12Volt           OBJECT-TYPE
			   SYNTAX           INTEGER
								{
								hidden(1),
								read-only(2),
								updateable(3)
								}
			   ACCESS           read-only
			   STATUS           mandatory
			   DESCRIPTION
			   "The value of this object provides the state
			    of the 12v Current Analog parameter. (1-hidden	
			          2-read-only, 3-updateable)."
			   ::= { gx2Rfa1000AnalogEntry 31}

		rfaminValue12Volt            OBJECT-TYPE
			   SYNTAX           Float
			   ACCESS           read-only
			   STATUS           mandatory
			   DESCRIPTION
			   "The value of this object provides the minimum value
			          of the 12 Volt Current Analog parameter. "
			   ::= { gx2Rfa1000AnalogEntry 32}

		rfamaxValue12Volt            OBJECT-TYPE
			   SYNTAX           Float
			   ACCESS           read-only
			   STATUS           mandatory
			   DESCRIPTION
			   "The value of this object provides the maximum value
			          of the 12 Volt Current Analog parameter. "
			   ::= { gx2Rfa1000AnalogEntry 33}

		rfaalarmState12Volt          OBJECT-TYPE
			   SYNTAX           INTEGER
									{
									noAlarm(1),
									majorLowAlarm(2),
									minorLowAlarm(3),
									minorHighAlarm(4),
									majorHighAlarm(5),
									informational(6)
									}
			   ACCESS           read-only
			   STATUS           mandatory
			   DESCRIPTION
			   "The value of this object provides the curent alarm state of
			    the 12v Current Analog parameter."
			   ::= { gx2Rfa1000AnalogEntry 34}

-- ************************ Digital parameters **********************************
		rfagx2Rfa1000DigitalTableIndex              OBJECT-TYPE
			   SYNTAX           INTEGER (1..2147483647)
			   ACCESS           read-only
			   STATUS           mandatory
			   DESCRIPTION
			   "The value of this object identifies the network
			    element. This index is equal to the
			    hfcCommonTableIndex for the same element."
			   ::= { gx2Rfa1000DigitalEntry 1}

-- New parameter
		rfalabelSlopeSetting	          	OBJECT-TYPE
			   SYNTAX         	DisplayString (SIZE (0..80))         
			   ACCESS           	read-only
			   STATUS           	optional
			   DESCRIPTION
			   "The value of this object provides the label of the
			    RX1000's AttnSetting  Digital parameter."
			   ::= { gx2Rfa1000DigitalEntry 2}

		rfaenumSlopeSetting	          	OBJECT-TYPE
			   SYNTAX         	DisplayString (SIZE (0..80))         
			   ACCESS           	read-only
			   STATUS           	optional
			   DESCRIPTION
			   "The value of this object represents the Enumeration values
			    possible for the Digital parameter. Each Enumerated values is
			    separated by a common. The first value has a enumerated value of 0."
			   ::= { gx2Rfa1000DigitalEntry 3}

		rfavalueSlopeSetting	            OBJECT-TYPE
			   SYNTAX       		INTEGER
									{
									db1point0(1),
									db1point5(2),
									db2point0(3),
									db2point5(4),
									db3point0(5),
									db3point5(6),
									db4point0(7)
									}
			   ACCESS           	read-write
			   STATUS           	mandatory
			   DESCRIPTION
			   "The value of this object is the current value of the parameter. It is an integer 
                      value from 1 to 7. Each increment represents 1/2 dB of slope from 1 to 4 dB. 
			    Where 1 = 1db and 7 = 4db"
			   ::= { gx2Rfa1000DigitalEntry 4}

		rfastateFlagSlopeSetting	    	OBJECT-TYPE
			   SYNTAX         	INTEGER
								{
								hidden(1),
								read-only(2),
								updateable(3)
								}
			   ACCESS           	read-only
			   STATUS           	mandatory
			   DESCRIPTION
			   "The value of this object provides the state
			    of the the parameter. (1-hidden	
			          2-read-only, 3-updateable)."
			   ::= { gx2Rfa1000DigitalEntry 5}
-- New parameter
		rfalabelAttnSetting	          	OBJECT-TYPE
			   SYNTAX         	DisplayString (SIZE (0..80))         
			   ACCESS           	read-only
			   STATUS           	optional
			   DESCRIPTION
			   "The value of this object provides the label of the
			    RX1000's AttnSetting  Digital parameter."
			   ::= { gx2Rfa1000DigitalEntry 6}

		rfaenumAttnSetting	          	OBJECT-TYPE
			   SYNTAX         	DisplayString (SIZE (0..80))         
			   ACCESS           	read-only
			   STATUS           	optional
			   DESCRIPTION
			   "The value of this object represents the Enumeration values
			    possible for the Digital parameter. Each Enumerated values is
			    separated by a common. The first value has a enumerated value of 0."
			   ::= { gx2Rfa1000DigitalEntry 7}

		rfavalueAttnSetting	            OBJECT-TYPE
			   SYNTAX       		INTEGER
                                    {
									db0point00(1),
									db0point25(2),
									db0point50(3),
									db0point75(4),
									db1point00(5),
									db1point25(6),
									db1point50(7),
									db1point75(8),
									db2point00(9),
									db2point25(10),
									db2point50(11),
									db2point75(12),
									db3point00(13),
									db3point25(14),
									db3point50(15),
									db3point75(16),
									db4point00(17),
									db4point25(18),
									db4point50(19),
									db4point75(20),
									db5point00(21)
									}
			   ACCESS           	read-write
			   STATUS           	mandatory
			   DESCRIPTION
			   "The value of this object is the current value of the parameter. It is an integer 
                      value from 1to 21 Each increment represents 1/4 dB of attenuation from 0 to 5 dB. 
			    Where 1 = 0db and 21 = 5db"
			   ::= { gx2Rfa1000DigitalEntry 8}

		rfastateFlagAttnSetting	    	OBJECT-TYPE
			   SYNTAX         	INTEGER
								{
								hidden(1),
								read-only(2),
								updateable(3)
								}
			   ACCESS           	read-only
			   STATUS           	mandatory
			   DESCRIPTION
			   "The value of this object provides the state
			    of the the parameter. (1-hidden	
			          2-read-only, 3-updateable)."
			   ::= { gx2Rfa1000DigitalEntry 9}
-- New parameter
		rfalabelFactoryDefault           OBJECT-TYPE
			   SYNTAX       		DisplayString (SIZE (0..80))         
			   ACCESS           	read-only
			   STATUS           	optional
			   DESCRIPTION
			   "The value of this object provides the label of the
			    Factory Default Reset  Digital parameter."
			   ::= { gx2Rfa1000DigitalEntry 10}

		rfaenumFactoryDefault          	OBJECT-TYPE
			   SYNTAX       		DisplayString (SIZE (0..80))         
			   ACCESS           	read-only
			   STATUS           	optional
			   DESCRIPTION
			   "The value of this object represents the Enumeration values
			    possible for the Digital parameter. Each Enumerated values is
			    separated by a common. The first value has a enumerated value of 1."
			   ::= { gx2Rfa1000DigitalEntry 11}

		rfavalueFactoryDefault         	OBJECT-TYPE
			   SYNTAX       		INTEGER
					    		{
							off(1),
							on(2)
					    		}
			   ACCESS           	read-write
			   STATUS           	mandatory
			   DESCRIPTION
			   "The value of this object is the current value of the parameter.This parameter
			   will always read off(1)"
			   ::= { gx2Rfa1000DigitalEntry 12}

		rfastateFlagFactoryDefault     	OBJECT-TYPE
			   SYNTAX       		INTEGER
								{
								hidden(1),
								read-only(2),
								updateable(3)
								}
			   ACCESS           	read-only
			   STATUS           	mandatory
			   DESCRIPTION
			   "The value of this object provides the state
			    of the the parameter. (1-hidden	
			          2-read-only, 3-updateable)."
			   ::= { gx2Rfa1000DigitalEntry 13}


		--*********** STATUS *****************
		rfagx2Rfa1000StatusTableIndex              OBJECT-TYPE
			   SYNTAX           INTEGER (1..2147483647)
			   ACCESS           read-only
			   STATUS           mandatory
			   DESCRIPTION
			   "The value of this object identifies the network
			    element. This index is equal to the
			    hfcCommonTableIndex for the same element."
			   ::= { gx2Rfa1000StatusEntry 1}

--New Parameter
		rfalabelBoot               	OBJECT-TYPE
			   SYNTAX       		DisplayString (SIZE (0..80))         
			   ACCESS           	read-only
			   STATUS           	optional
			   DESCRIPTION
			   "The value of this object provides the label of the
			    Boot Status  Status parameter."
			   ::= { gx2Rfa1000StatusEntry 2}

		rfavalueBoot              		OBJECT-TYPE
			   SYNTAX       		INTEGER
									{
									ok(1),
									undetermined(2),
									warning(3),
									minor(4),
									major(5),
									critical(6)
									}
			   ACCESS           	read-only
			   STATUS           	mandatory
			   DESCRIPTION
			   "The value of this object provides the current state of
			    the parameter (1-ok, 2-undetermined
			    3-warning, 4-minor, 5-major, 6-critical)."
			   ::= { gx2Rfa1000StatusEntry 3}

		rfastateflagBoot     	OBJECT-TYPE
			   SYNTAX       		INTEGER
								{
								hidden(1),
								read-only(2),
								updateable(3)
								}
			   ACCESS           	read-only
			   STATUS           	mandatory
			   DESCRIPTION
			   "The value of this object provides the state
			    of the the parameter. (1-hidden	
			          2-read-only, 3-updateable)."
			   ::= { gx2Rfa1000StatusEntry  4}


--New Parameter
		rfalabelFlash               	OBJECT-TYPE
			   SYNTAX       		DisplayString (SIZE (0..80))         
			   ACCESS           	read-only
			   STATUS           	optional
			   DESCRIPTION
			   "The value of this object provides the label of the
			    Flash Status  Status parameter."
			   ::= { gx2Rfa1000StatusEntry 5}

		rfavalueFlash              	OBJECT-TYPE
			   SYNTAX       		INTEGER
									{
									ok(1),
									undetermined(2),
									warning(3),
									minor(4),
									major(5),
									critical(6)
									}
			   ACCESS           	read-only
			   STATUS           	mandatory
			   DESCRIPTION
			   "The value of this object provides the current state of
			    the parameter (1-ok, 2-undetermined
			    3-warning, 4-minor, 5-major, 6-critical)."
			   ::= { gx2Rfa1000StatusEntry 6}

		rfastateflagFlash     	OBJECT-TYPE
			   SYNTAX       		INTEGER
								{
								hidden(1),
								read-only(2),
								updateable(3)
								}
			   ACCESS           	read-only
			   STATUS           	mandatory
			   DESCRIPTION
			   "The value of this object provides the state
			    of the the parameter. (1-hidden	
			          2-read-only, 3-updateable)."
			   ::= { gx2Rfa1000StatusEntry 7}


--New Parameter
		rfalabelFactoryDataCRC           OBJECT-TYPE
			   SYNTAX       		DisplayString (SIZE (0..80))         
			   ACCESS           	read-only
			   STATUS           	optional
			   DESCRIPTION
			   "The value of this object provides the label of the
			    Factory Data CRC Status parameter."
			   ::= { gx2Rfa1000StatusEntry 8}

		rfavalueFactoryDataCRC          	OBJECT-TYPE
			   SYNTAX       		INTEGER
									{
									ok(1),
									undetermined(2),
									warning(3),
									minor(4),
									major(5),
									critical(6)
									}
			   ACCESS           	read-only
			   STATUS           	mandatory
			   DESCRIPTION
			   "The value of this object provides the current state of
			    the parameter (1-ok, 2-undetermined
			    3-warning, 4-minor, 5-major, 6-critical)."
			   ::= { gx2Rfa1000StatusEntry 9}

		rfastateflagFactoryDataCRC     	OBJECT-TYPE
			   SYNTAX       		INTEGER
								{
								hidden(1),
								read-only(2),
								updateable(3)
								}
			   ACCESS           	read-only
			   STATUS           	mandatory
			   DESCRIPTION
			   "The value of this object provides the state
			    of the the parameter. (1-hidden	
			          2-read-only, 3-updateable)."
			   ::= { gx2Rfa1000StatusEntry 10}


--New Parameter
		rfalabelAlarmDataCRC             OBJECT-TYPE
			   SYNTAX       		DisplayString (SIZE (0..80))         
			   ACCESS           	read-only
			   STATUS           	optional
			   DESCRIPTION
			   "The value of this object provides the label of the
			    Alarm Data CRC Status parameter."
			   ::= { gx2Rfa1000StatusEntry 11}

		rfavalueAlarmDataCRC           	OBJECT-TYPE
			   SYNTAX       		INTEGER
									{
									ok(1),
									undetermined(2),
									warning(3),
									minor(4),
									major(5),
									critical(6)
									}
			   ACCESS           	read-only
			   STATUS           	mandatory
			   DESCRIPTION
			   "The value of this object provides the current state of
			    the parameter (1-ok, 2-undetermined
			    3-warning, 4-minor, 5-major, 6-critical)."
			   ::= { gx2Rfa1000StatusEntry 12}

		rfastateflagAlarmDataCRC     	OBJECT-TYPE
			   SYNTAX       		INTEGER
								{
								hidden(1),
								read-only(2),
								updateable(3)
								}
			   ACCESS           	read-only
			   STATUS           	mandatory
			   DESCRIPTION
			   "The value of this object provides the state
			    of the the parameter. (1-hidden	
			          2-read-only, 3-updateable)."
			   ::= { gx2Rfa1000StatusEntry 13}


--New Parameter
		rfalabelSlopeCalDataCRC       OBJECT-TYPE
			   SYNTAX       		DisplayString (SIZE (0..80))         
			   ACCESS           	read-only
			   STATUS           	optional
			   DESCRIPTION
			   "The value of this object provides the label of the
			    Calibration Data CRC Status parameter."
			   ::= { gx2Rfa1000StatusEntry 14}

		rfavalueSlopeCalDataCRC      	OBJECT-TYPE
			   SYNTAX       		INTEGER
									{
									ok(1),
									undetermined(2),
									warning(3),
									minor(4),
									major(5),
									critical(6)
									}
			   ACCESS           	read-only
			   STATUS           	mandatory
			   DESCRIPTION
			   "The value of this object provides the current state of
			    the parameter (1-ok, 2-undetermined
			    3-warning, 4-minor, 5-major, 6-critical)."
			   ::= { gx2Rfa1000StatusEntry 15}

		rfastateflagSlopeCalDataCRC     	OBJECT-TYPE
			   SYNTAX       		INTEGER
								{
								hidden(1),
								read-only(2),
								updateable(3)
								}
			   ACCESS           	read-only
			   STATUS           	mandatory
			   DESCRIPTION
			   "The value of this object provides the state
			    of the the parameter. (1-hidden	
			          2-read-only, 3-updateable)."
			   ::= { gx2Rfa1000StatusEntry 16}


--New Parameter
		rfalabelAttnCalDataCRC       OBJECT-TYPE
			   SYNTAX       		DisplayString (SIZE (0..80))         
			   ACCESS           	read-only
			   STATUS           	optional
			   DESCRIPTION
			   "The value of this object provides the label of the
			    Factor Cal Setting CRC Status parameter."
			   ::= { gx2Rfa1000StatusEntry 17}

		rfavalueAttnCalDataCRC      	OBJECT-TYPE
			   SYNTAX       		INTEGER
									{
									ok(1),
									undetermined(2),
									warning(3),
									minor(4),
									major(5),
									critical(6)
									}
			   ACCESS           	read-only
			   STATUS           	mandatory
			   DESCRIPTION
			   "The value of this object provides the current state of
			    the parameter (1-ok, 2-undetermined
			    3-warning, 4-minor, 5-major, 6-critical)."
			   ::= { gx2Rfa1000StatusEntry 18}

		rfastateflagAttnCalDataCRC    	OBJECT-TYPE
			   SYNTAX       		INTEGER
								{
								hidden(1),
								read-only(2),
								updateable(3)
								}
			   ACCESS           	read-only
			   STATUS           	mandatory
			   DESCRIPTION
			   "The value of this object provides the state
			    of the the parameter. (1-hidden	
			          2-read-only, 3-updateable)."
			   ::= { gx2Rfa1000StatusEntry 19}


            -- ************ FACTORY DATA ****************
		rfagx2Rfa1000FactoryTableIndex              OBJECT-TYPE
			   SYNTAX           INTEGER (1..2147483647)
			   ACCESS           read-only
			   STATUS           mandatory
			   DESCRIPTION
			   "The value of this object identifies the network
			    element. This index is equal to the
			    hfcCommonTableIndex for the same element."
			   ::= { gx2Rfa1000FactoryEntry 1}

		rfabootControlByte          	OBJECT-TYPE
			   SYNTAX       		INTEGER
			   ACCESS           	read-only
			   STATUS           	mandatory
			   DESCRIPTION
			   "The value of this object indicates which bank the firmware
			    is currently being boot from."
			   ::= { gx2Rfa1000FactoryEntry 2}

		rfabootStatusByte          	OBJECT-TYPE
			   SYNTAX       		INTEGER
			   ACCESS           	read-only
			   STATUS           	mandatory
			   DESCRIPTION
			   "This object indicates the status of the last boot"
			   ::= { gx2Rfa1000FactoryEntry 3}

		rfabank0CRC          		OBJECT-TYPE
			   SYNTAX       		INTEGER
			   ACCESS           	read-only
			   STATUS           	mandatory
			   DESCRIPTION
			   "This object provides the CRC code of bank 0."
			   ::= { gx2Rfa1000FactoryEntry 4}

		rfabank1CRC          		OBJECT-TYPE
			   SYNTAX       		INTEGER
			   ACCESS           	read-only
			   STATUS           	mandatory
			   DESCRIPTION
			   "This object provides the CRC code of bank 1."
			   ::= { gx2Rfa1000FactoryEntry 5}

		rfaprgEEPROMByte          		OBJECT-TYPE
			   SYNTAX       		INTEGER
			   ACCESS           	read-only
			   STATUS           	mandatory
			   DESCRIPTION
			   "This object indicates if the EEPROM has been programmed"
			   ::= { gx2Rfa1000FactoryEntry 6}

		rfafactoryCRC          		OBJECT-TYPE
			   SYNTAX       		INTEGER
			   ACCESS           	read-only
			   STATUS           	mandatory
			   DESCRIPTION
			   "This object provides the CRC code for the Factory data."
			   ::= { gx2Rfa1000FactoryEntry 7}

		rfacalculateCRC          		OBJECT-TYPE
			   SYNTAX       		INTEGER
					    		{
                                          factory(1),
							calibration(2),
							alarmdata(3),
							calSetting(4)
					    		}
			   ACCESS           	read-only
			   STATUS           	obsolete
			   DESCRIPTION
			   "This object indicates which of the Emnums will have the CRC calculated."
			   ::= { gx2Rfa1000FactoryEntry 8}

		rfahourMeter          		OBJECT-TYPE
			   SYNTAX       		INTEGER
			   ACCESS           	read-only
			   STATUS           	mandatory
			   DESCRIPTION
			   "This object provides the hour meter reading of the module."
			   ::= { gx2Rfa1000FactoryEntry 9}

		rfaflashPrgCntA          		OBJECT-TYPE
			   SYNTAX       		INTEGER
			   ACCESS           	read-only
			   STATUS           	mandatory
			   DESCRIPTION
			   "This object provides the number of times the flash has been 
                      programmed on side A."
			   ::= { gx2Rfa1000FactoryEntry 10}

		rfaflashPrgCntB          		OBJECT-TYPE
			   SYNTAX       		INTEGER
			   ACCESS           	read-only
			   STATUS           	mandatory
			   DESCRIPTION
			   "This object provides the number of times the flash has been 
                      programmed on side B."
			   ::= { gx2Rfa1000FactoryEntry 11}

		rfafwRev0     		     		OBJECT-TYPE
			   SYNTAX       		DisplayString (SIZE (0..80))
			   ACCESS           	read-only
			   STATUS           	mandatory
			   DESCRIPTION
			   "This object provides the Revision of the firmware stores in bank 0."
			   ::= { gx2Rfa1000FactoryEntry 12}

		rfafwRev1     		     		OBJECT-TYPE
			   SYNTAX       		DisplayString (SIZE (0..80))
			   ACCESS           	read-only
			   STATUS           	mandatory
			   DESCRIPTION
			   "This object provides the Revision of the firmware stores in bank 1."
			   ::= { gx2Rfa1000FactoryEntry 13}


            -- ************ Hold Time DATA ****************
		gx2Rfa1000HoldTimeTableIndex              OBJECT-TYPE
			   SYNTAX           INTEGER (1..4294967295)
			   ACCESS           read-only
			   STATUS           mandatory
			   DESCRIPTION
			   "The value of this object is the index of the data object."
			   ::= { gx2Rfa1000HoldTimeEntry 1}

		gx2Rfa1000HoldTimeSpecIndex              OBJECT-TYPE
			   SYNTAX           INTEGER (1..4294967295)
			   ACCESS           read-only
			   STATUS           mandatory
			   DESCRIPTION
			   "The value of this object identifies the index of the alarm object to be modified."
			   ::= { gx2Rfa1000HoldTimeEntry 2}

		gx2Rfa1000HoldTimeData          	OBJECT-TYPE
			   SYNTAX       		INTEGER
			   ACCESS           	read-write
			   STATUS           	mandatory
			   DESCRIPTION
			   "The value of this object provides access to the hold timers used 
			   to suppress nose on analog objects. This object is a 32 bit object. 
			   Validation data is entered into bytes zero and one of the object. 
			   Bytes three and four are used to entering the hold time for the 
			   specified alarm object. The Hold timer data ranges from 0 to 1300 seconds.
			   The index of this object corresponds to the alarm object to be modified. 
			   Alarm Hold timers correspond to the index of this object as follows:  
			   Index 1 = xxx, index 2 = xxxx, Index 3 = xxxx, 
			   The hold time is represented in seconds."
			   ::= { gx2Rfa1000HoldTimeEntry 3}

-- ****************************************************************
--
-- TRAP DEFINITIONS
--
--
-- Every trap generated by an HFC agents will include first 9 identical
-- fields. If particular variable is not supported in
-- particular TRAP-TYPE then default value will be returned.
--
-- DESCRIPTION will include explanation of use of generic
-- variables (trapAdditionalInfo******.)  If no
-- DESCRIPTION is given then generic variables will contain
-- default values.
--
-- *****************************************************************
-- **************************************************************************
--                              RFA1000 Module traps
-- **************************************************************************
   trapRFA1000ConfigChangeInteger TRAP-TYPE
       ENTERPRISE gx2Rfa1000
       VARIABLES
	       {       
		trapIdentifier,
		trapNetworkElemModelNumber,
		trapNetworkElemSerialNum,
		trapPerceivedSeverity,
		trapNetworkElemOperState,
		trapNetworkElemAlarmStatus,  
		trapNetworkElemAdminState,
		trapNetworkElemAvailStatus,
		trapText,
		trapChangedObjectId,
		trapChangedValueInteger,
		trapNETrapLastTrapTimeStamp
	       }
       DESCRIPTION
	"This trap is issued if configuration of a single variable
	 with integer type was changed (via ANY interface).  
	 TrapChangedValueInteger variable may contain current reading
	 of that variable.
	 trapPerceivedSeverity - 'indeterminate'"
  ::= 1

   trapRFA1000ConfigChangeDisplayString TRAP-TYPE
       ENTERPRISE gx2Rfa1000
       VARIABLES
	       {       
		trapIdentifier,
		trapNetworkElemModelNumber,
		trapNetworkElemSerialNum,
		trapPerceivedSeverity,
		trapNetworkElemOperState,
		trapNetworkElemAlarmStatus,  
		trapNetworkElemAdminState,
		trapNetworkElemAvailStatus,
		trapText,
		trapChangedObjectId,
		trapChangedValueDisplayString,
		trapNETrapLastTrapTimeStamp
	       }
       DESCRIPTION
	"This trap is issued if configuration of a single variable
	 with DispalayString type was changed (via ANY interface).  
	 TrapChangedValueDisplayString variable may contain current reading
	 of that variable.
	 trapPerceivedSeverity - 'indeterminate'"
  ::= 2
  
  trapRFA1000ModuleTemperatureAlarm TRAP-TYPE
	ENTERPRISE gx2Rfa1000
	VARIABLES
		{       
		 trapIdentifier,
		 trapNetworkElemModelNumber,
		 trapNetworkElemSerialNum,
		 trapPerceivedSeverity,
		 trapNetworkElemOperState,
		 trapNetworkElemAlarmStatus,  
		 trapNetworkElemAdminState,
		 trapNetworkElemAvailStatus,
		 trapText,
		 trapChangedObjectId,
		 trapChangedValueInteger,
		 trapNETrapLastTrapTimeStamp
		}
	DESCRIPTION
	"This trap is issued when the RFA1000 Module's Temperature goes out of range."
  ::= 3

  trapRFA1000FanCurrentAlarm TRAP-TYPE
	ENTERPRISE gx2Rfa1000
	VARIABLES
		{       
		 trapIdentifier,
		 trapNetworkElemModelNumber,
		 trapNetworkElemSerialNum,
		 trapPerceivedSeverity,
		 trapNetworkElemOperState,
		 trapNetworkElemAlarmStatus,  
		 trapNetworkElemAdminState,
		 trapNetworkElemAvailStatus,
		 trapText,
		 trapChangedObjectId,
		 trapChangedValueInteger,
		 trapNETrapLastTrapTimeStamp
		}
	DESCRIPTION
	"This trap is issued when the RFA1000 Module's Fan Currrent parameter 
	 goes out of range."
  ::= 4

  trapRFA1000Plus12CurrentAlarm TRAP-TYPE
	ENTERPRISE gx2Rfa1000
	VARIABLES
		{       
		 trapIdentifier,
		 trapNetworkElemModelNumber,
		 trapNetworkElemSerialNum,
		 trapPerceivedSeverity,
		 trapNetworkElemOperState,
		 trapNetworkElemAlarmStatus,  
		 trapNetworkElemAdminState,
		 trapNetworkElemAvailStatus,
		 trapText,
		 trapChangedObjectId,
		 trapChangedValueInteger,
		 trapNETrapLastTrapTimeStamp
		}
	DESCRIPTION
	"This trap is issued when the RFA1000 Module's positive 12 volt current parameter 
	 goes out of range."
  ::= 5

  trapRFA1000Boot0Alarm TRAP-TYPE
	ENTERPRISE gx2Rfa1000
	VARIABLES
		{       
		 trapIdentifier,
		 trapNetworkElemModelNumber,
		 trapNetworkElemSerialNum,
		 trapPerceivedSeverity,
		 trapNetworkElemOperState,
		 trapNetworkElemAlarmStatus,  
		 trapNetworkElemAdminState,
		 trapNetworkElemAvailStatus,
		 trapText,
		 trapChangedObjectId,
		 trapChangedValueInteger,
		 trapNETrapLastTrapTimeStamp
		}
	DESCRIPTION
	"This trap is issued when the RFA1000 Module's Bank 0 Boot sequence has detected an error."
  ::= 6

  trapRFA1000Boot1Alarm TRAP-TYPE
	ENTERPRISE gx2Rfa1000
	VARIABLES
		{       
		 trapIdentifier,
		 trapNetworkElemModelNumber,
		 trapNetworkElemSerialNum,
		 trapPerceivedSeverity,
		 trapNetworkElemOperState,
		 trapNetworkElemAlarmStatus,  
		 trapNetworkElemAdminState,
		 trapNetworkElemAvailStatus,
		 trapText,
		 trapChangedObjectId,
		 trapChangedValueInteger,
		 trapNETrapLastTrapTimeStamp
		}
	DESCRIPTION
	"This trap is issued when the RFA1000 Module's Bank 1 Boot sequence has detected an error."
  ::= 7

  trapRFA1000FlashAlarm TRAP-TYPE
	ENTERPRISE gx2Rfa1000
	VARIABLES
		{       
		 trapIdentifier,
		 trapNetworkElemModelNumber,
		 trapNetworkElemSerialNum,
		 trapPerceivedSeverity,
		 trapNetworkElemOperState,
		 trapNetworkElemAlarmStatus,  
		 trapNetworkElemAdminState,
		 trapNetworkElemAvailStatus,
		 trapText,
		 trapChangedObjectId,
		 trapChangedValueInteger,
		 trapNETrapLastTrapTimeStamp
		}
	DESCRIPTION
	"This trap is issued when the RFA1000 Module's boot or flash programming sequence has 
       detected a Flash error."
  ::= 8

  trapRFA1000AlarmDataCRCAlarm TRAP-TYPE
	ENTERPRISE gx2Rfa1000
	VARIABLES
		{       
		 trapIdentifier,
		 trapNetworkElemModelNumber,
		 trapNetworkElemSerialNum,
		 trapPerceivedSeverity,
		 trapNetworkElemOperState,
		 trapNetworkElemAlarmStatus,  
		 trapNetworkElemAdminState,
		 trapNetworkElemAvailStatus,
		 trapText,
		 trapChangedObjectId,
		 trapChangedValueInteger,
		 trapNETrapLastTrapTimeStamp
		}
      DESCRIPTION
      "This trap is issued when the RFA1000 Module detects an error calculating the alarm limit CRC."
  ::= 9

  trapRFA1000FactoryDataCRCAlarm TRAP-TYPE
	ENTERPRISE gx2Rfa1000
	VARIABLES
		{       
		 trapIdentifier,
		 trapNetworkElemModelNumber,
		 trapNetworkElemSerialNum,
		 trapPerceivedSeverity,
		 trapNetworkElemOperState,
		 trapNetworkElemAlarmStatus,  
		 trapNetworkElemAdminState,
		 trapNetworkElemAvailStatus,
		 trapText,
		 trapChangedObjectId,
		 trapChangedValueInteger,
		 trapNETrapLastTrapTimeStamp
		}
      DESCRIPTION
      "This trap is issued when the RFA1000 Module detects an error calculating the Factory data CRC."
  ::= 10

  trapRFA1000SlopeCalDataCRCAlarm TRAP-TYPE
	ENTERPRISE gx2Rfa1000
	VARIABLES
		{       
		 trapIdentifier,
		 trapNetworkElemModelNumber,
		 trapNetworkElemSerialNum,
		 trapPerceivedSeverity,
		 trapNetworkElemOperState,
		 trapNetworkElemAlarmStatus,  
		 trapNetworkElemAdminState,
		 trapNetworkElemAvailStatus,
		 trapText,
		 trapChangedObjectId,
		 trapChangedValueInteger,
		 trapNETrapLastTrapTimeStamp
		}
      DESCRIPTION
      "This trap is issued when the RFA1000 Module detects an error calculating the Slope Calibration data CRC."
  ::= 11

  trapRFA1000AttnCalDataCRCAlarm TRAP-TYPE
	ENTERPRISE gx2Rfa1000
	VARIABLES
		{       
		 trapIdentifier,
		 trapNetworkElemModelNumber,
		 trapNetworkElemSerialNum,
		 trapPerceivedSeverity,
		 trapNetworkElemOperState,
		 trapNetworkElemAlarmStatus,  
		 trapNetworkElemAdminState,
		 trapNetworkElemAvailStatus,
		 trapText,
		 trapChangedObjectId,
		 trapChangedValueInteger,
		 trapNETrapLastTrapTimeStamp
		}
      DESCRIPTION
      "This trap is issued when the RFA1000 Module detects an Attenuation Calibration Data CRC alarm."
  ::= 12

    trapRFA1000ResetFacDefault TRAP-TYPE
	ENTERPRISE gx2Rfa1000
	VARIABLES
		{       
		 trapIdentifier,
		 trapNetworkElemModelNumber,
		 trapNetworkElemSerialNum,
		 trapPerceivedSeverity,
		 trapNetworkElemOperState,
		 trapNetworkElemAlarmStatus,  
		 trapNetworkElemAdminState,
		 trapNetworkElemAvailStatus,
		 trapText,
		 trapChangedObjectId,
		 trapChangedValueInteger,
		 trapNETrapLastTrapTimeStamp
		}
      DESCRIPTION
      "This trap is issued when the RFA1000 resets to factory defaults"
  ::= 13

  END
