VERILINK-ENTERPRISE-NCMQUAD-MIB


	-- Created:  Muralidhar.S in 1995.
	-- set up MIB-wide defaults
	-- all functions can use %n for object name and
	-- %t for object type, %p for parent name,
	-- %d for name of default-bearing node and %% for %

	  DEFINITIONS ::= BEGIN

     --  This MIB module uses the extended OBJECT-TYPE macro as
     --  defined in RFC 1212.
     --  This MIB module uses the TRAP-TYPE macro as
     --  defined in RFC 1215.
     --  enterprises{iso(1).org(3).dod(6).intrnet(1).pvt(4).entrprs(1).
     --                                                    vlnk(321).as2000(1).x }
	  
	  IMPORTS OBJECT-TYPE, enterprises, Gauge FROM RFC1155-SMI;


	     verilink         OBJECT IDENTIFIER ::= { enterprises 321 }
             as2000           OBJECT IDENTIFIER ::= { verilink 1 }
	     ncm-quad         OBJECT IDENTIFIER ::= { as2000 3009 }


     -- The consists of tables:
     --    Configuration
     --    Current
     --    Interval
     --    Total
     --    Fdl
     --    Sync

     -- the NCM QUAD Configuration Table


	 ncmquadConfigTable OBJECT-TYPE
	     SYNTAX  SEQUENCE OF NcmCSUConfigEntry
	     ACCESS  not-accessible
	     STATUS  mandatory
DESCRIPTION ""
        --DEFAULT test-function    quad_test
        --DEFAULT next-function    quad_next
	    ::= { ncm-quad 11000 }


	 ncmquadConfigEntry OBJECT-TYPE
	     SYNTAX  NcmCSUConfigEntry
	     ACCESS  not-accessible
	     STATUS  mandatory
	     DESCRIPTION
		"An entry in the QUAD Configuration table."
	    INDEX   { ncmquadLineIndex }
	    ::= { ncmquadConfigTable 1 }

     NcmCSUConfigEntry ::=
	 SEQUENCE {
	     ncmquadLineIndex
		 INTEGER,
	     ncmquadIfIndex
		 INTEGER,
	     ncmquadEndId
		 INTEGER,
	     ncmquadPort
		 INTEGER,
	     ncmquadLineType
		 INTEGER,
	     ncmquadLineCoding
		 INTEGER,
	     ncmquadFDL
		 INTEGER,
	     ncmquadDensityPattern
		 INTEGER,
	     ncmquadNetworkLineBuildOut
		 INTEGER,
	     ncmquadNetworkLoopConfig
		 INTEGER,
	     ncmquadLineStatus
		 INTEGER,
	     ncmquadLoopbackConfig
		 INTEGER,
	     ncmquadSendCode
		 INTEGER,
	     ncmquadResetPerfReg
		 INTEGER,
	     ncmquadValidIntervals
		 INTEGER,
	     ncmquadTimeElapsed
		 INTEGER,
	     ncmquadResetT1Error
		INTEGER

	 }

	 ncmquadLineIndex OBJECT-TYPE
	     SYNTAX  INTEGER (1..'7fffffff'h)
	     ACCESS  read-only
	     STATUS  mandatory
	     DESCRIPTION
		"This object is the identifier of a  Inter-
		face on a managed device.  If there is an ifEn-
		try that is directly associated with  this  and
		only  this  DS1  interface,  it should have the
		same value as ifIndex.   Otherwise,  the  value
		exceeds  ifNumber,  and  is a unique identifier
		following this rule: inside  interfaces  (e.g.,
		equipment  side)  with even numbers and outside
		interfaces  (e.g.,  network   side)   with   odd
		numbers."
	    ::= { ncmquadConfigEntry 1 }


	 ncmquadIfIndex OBJECT-TYPE
	     SYNTAX  INTEGER (1..'7fffffff'h)
	     ACCESS  read-only
	     STATUS  mandatory
	     DESCRIPTION
		"This value for this object  is  equal  to  the
		value  of  ifIndex from the Interfaces table of
		MIB II (RFC 1213)."
	    ::= { ncmquadConfigEntry 2 }


	 ncmquadEndId  OBJECT-TYPE
	     SYNTAX  INTEGER {
			near-End(0),
			far-End(1)
		     }
	     ACCESS  read-only
	     STATUS  mandatory
	     DESCRIPTION
		"This value for this object indicates which
		 end of the equipment it is configuring."
	    ::= { ncmquadConfigEntry 3 }

	 ncmquadPort  OBJECT-TYPE
	     SYNTAX  INTEGER {
			 disabled(1),
			 enabled(2)
		     }
	     ACCESS  read-write
	     STATUS  mandatory
	     DESCRIPTION
		"This variable indicates Whether the port is in
		 service or out of service"
	     ::= { ncmquadConfigEntry 4 }


	 ncmquadLineType OBJECT-TYPE
	     SYNTAX  INTEGER {
			 other(1),
			 eSF(2),
			 d4(3)
		     }
	     ACCESS  read-write
	     STATUS  mandatory
	     DESCRIPTION
		"This variable indicates  the  variety  of
		Line  implementing  this  circuit.  The type of
		circuit affects the number of bits  per  second
		that  the circuit can reasonably carry, as well
		as the interpretation of the  usage  and  error
		statistics.  The values, in sequence, describe:

		TITLE:        SPECIFICATION:
		ESF       Extended SuperFrame DS1
		D4        AT&T D4 format DS1"
	     ::= { ncmquadConfigEntry 5 }

	 ncmquadLineCoding OBJECT-TYPE
	     SYNTAX  INTEGER {
			 other(6),
			 b8ZS (2),
			 aMI (5)
		     }
	     ACCESS  read-write
	     STATUS  mandatory
	     DESCRIPTION
		"This variable describes the  variety  of  Zero
		Code  Suppression  used  on  the link, which in
		turn affects a number of its characteristics.

		B8ZS refers to the use of a specified  pat-
		tern  of  normal  bits  and  bipolar violations
		which are used to replace a sequence  of  eight
		zero bits.

		AMI refers to a mode wherein no  zero  code
		suppression  is  present  and the line encoding
		does not solve the problem directly.   In  this
		application, the higher layer must provide data
		which meets or exceeds the  pulse  density  re-
		quirements, such as inverting HDLC data."
	    ::= { ncmquadConfigEntry 6 }

	 ncmquadFDL OBJECT-TYPE
	     SYNTAX  INTEGER {
             disabled(0),
             enabled(1)
		     }
	     ACCESS  read-write
	     STATUS  mandatory
	     DESCRIPTION
          "The variable specifies the Disable/Enable of the ncmfdl State."
	    ::= { ncmquadConfigEntry 7 }

	ncmquadDensityPattern OBJECT-TYPE
	    SYNTAX  INTEGER {
			d80Zeros(1),
			d15Zeros(2),
			d12d5c80Zero(3),
			tR-62411(4),
			other(5),
			disabled(6)
		    }
	    ACCESS  read-write
	    STATUS  mandatory
	    DESCRIPTION
		"This variable indicates what type of density network is being sent
		on the port or line by the device. The values mean :
		'Disabled' refers to no network ones density exist.
		'D80Zeros' refers to send a request for network one's density
		of 80 zeroes density pattern.
		'D15Zeros' refers to send a request for network one's density
		of 15 zeroes density pattern.
		'D12d5c80Zero'refers to send a request for 12.5% and 80
		zeroes network one's density pattern.
		'TR_62411' refers to sending a request for TR6241
		network density pattern.
		'Other' refers to sending a network's density pattern
		other than those described by this object[pvt]**."
	   ::= { ncmquadConfigEntry 8 }

	ncmquadNetworkLineBuildOut OBJECT-TYPE
	    SYNTAX INTEGER {
			bldLn-0db(1),
			bldLnNeg7d5db(2),
			bldLnNeg15db(3),
			bldLnNeg22d5(4)
		    }
	    ACCESS  read-write
	    STATUS  mandatory
	    DESCRIPTION
		"This variable indicates the db rate at which the line or port using,
		i.e., is 0 , -7.5db, -15db or -22.5db.[pvt]"
	    ::= { ncmquadConfigEntry 9 }

	 ncmquadNetworkLoopConfig OBJECT-TYPE
	     SYNTAX  INTEGER {
			disabled(1),
			enabled(2)
		}
	     ACCESS  read-write
	     STATUS  mandatory
	     DESCRIPTION
		" This variable represents whether the device can be
		configured throught the network for loopback. Here
		values mean :
		Disabled: This device cannot be loopbacked throught
			 network.
		Enabled: This device can be loopbacked throught the
			 network."
	    ::= { ncmquadConfigEntry 10 }


	 ncmquadLineStatus OBJECT-TYPE
	     SYNTAX  INTEGER {
			 noAlarms(1),
			 alarms(2)
		     }
	     ACCESS  read-only
	     STATUS  mandatory
	     DESCRIPTION
		"This variable indicates the Line Status of the
		interface.   It contains loopback, failure, re-
		ceived 'alarm'  and transmitted 'alarm'  infor-
		mation.

	      NoAlarms
		  This variables indicates their is no alarms on
		this port or this line.

	      Alarms
		  This variables indicates their is alarms on
		line with any of the following bit map :
		The ncmquadLineStatus is a bit  map  represented  as  a  sum,
		therefore, it can represent multiple failures (alarms) and
		a LoopbackState simultaneously.
		If the ncmquadLoopbackState bit is set, the loopback  in  ef-
		fect can be determined from the ncmquadLoopbackConfig object.
		The various bit positions are:
		  0     Reserved
		  1     quadCRC6error         (1 = yes, 0 = no)
		  2     Reserved
		  3     FramingSlip          (1 = yes, 0 = no)
		  4     quadRAI               (1 = yes, 0 = no)
		  5     quadLOF               LOF (1 = yes, 0 = no)
		  6     quadAIS               AIS (1 = yes, 0 = no)
		  7     quadLOS               LOS (1 = yes, 0 = no)
		  8~15  ReservedForOtherFailure "

	 ::= { ncmquadConfigEntry 11 }

	 ncmquadLoopbackConfig OBJECT-TYPE
	     SYNTAX  INTEGER {
			 noLoop(1),
			 quadActPayloadLoop(2),
			 quadDeactPayloadLoop(9),
			 quadActLineLoop(3),
			 quadDeactLineLoop(10),
			 quadActLocalLoopbk(5),
			 quadDeactLocalLoopbk(11),
                         quadActLLBBOP(7),
			 quadDeactLLBBOP(13),
                         quadActPLBBOP(8),
			 quadDeactPLBBOP(14)
		     }
	     ACCESS  read-write
	     STATUS  mandatory
	     DESCRIPTION
		"This variable represents the  loopback  confi-
		guration of the DS1 interface.  Agents support-
		ing read/write access should return badValue in
		response to a requested loopback state that the
		interface does not support.  The values mean:
		quadNoLoop
		     Not in the loopback state.  A device  that
		     is not capable of performing a loopback on
		     the interface shall always return this  as
		     it's value.

		quadPayloadLoop
		     The received signal at this  interface  is
		     looped  through  the device. Typically the
		     received signal is  looped  back  for  re-
		     transmission  after  it has passed through
		     the device's framing function.

		quadLineLoop
		     The received signal at this interface does
		     not  go  through the device (minimum pene-
		     tration) but is looped back out.

		quadLocalLoopbk
		     This variable indicates whether the
		     local loopback is enabled or disabled on
		     the port or line by the device.

		quadOtherLoop
		     Loopbacks that are not defined here."
	    ::= { ncmquadConfigEntry 12 }

	 ncmquadSendCode OBJECT-TYPE
	     SYNTAX  INTEGER {
			 noCode(1),
			 qRSS(5),
			 three-in-24type(7),
			 other(8)
		     }
	     ACCESS  read-write
	     STATUS  mandatory
	     DESCRIPTION
		"This variable indicates what type of  code  is
		being sent across the DS1 interface by the dev-
		ice.  The values mean:

		NoCode
		     sending looped or normal data

		QRSS
		     sending a Quasi-Random Signal  (QRSS)  test
		     pattern

		3in24type
		     sending a fixed test pattern of 3 bits set
		     in 24

		Other
		     sending a test pattern  other  than  those
		     described by this object"
	    ::= { ncmquadConfigEntry 13 }

         ncmquadResetPerfReg OBJECT-TYPE
	     SYNTAX  INTEGER {
			 yes(1),
			 no(2)
		     }
             ACCESS  read-write
             STATUS  mandatory
             DESCRIPTION
                "Reset Performance Monitoring registers."
            ::= { ncmquadConfigEntry 14}

         ncmquadValidIntervals OBJECT-TYPE
             SYNTAX  INTEGER (0..96)
             ACCESS  read-only
             STATUS  mandatory
             DESCRIPTION
                "The number of  previous  intervals  for  which
                valid data was collected.  The value will be 96
                unless the interface was brought on-line within
                the last 24 hours, in which case the value will
                be the number of complete 15  minute  intervals
                the since interface has been online."
            ::= { ncmquadConfigEntry 15}

         ncmquadTimeElapsed OBJECT-TYPE
             SYNTAX  INTEGER (0..899)
             ACCESS  read-only
             STATUS  mandatory
             DESCRIPTION
                "The number of seconds that have elapsed  since
                the  beginning of the current error-measurement
                period."
            ::= { ncmquadConfigEntry 16 }


	ncmquadResetT1Error OBJECT-TYPE
	      SYNTAX  INTEGER {
			 no(0),
			 yes(1)
				}
              ACCESS  read-write
              STATUS  mandatory
              DESCRIPTION
                "This variable indicates the option for reseting the 
		 T1 error counters."
            ::= { ncmquadConfigEntry 17 }



     -- the  Loss Current Table

     -- The loss current table contains various statistics of loss signals being
     -- collected for the current 15 minute interval.

     -- "The Loss Current table."
	 ncmquadLossCurrentTable OBJECT-TYPE
	     SYNTAX  SEQUENCE OF NcmCsuLossCurrentEntry
	     ACCESS  not-accessible
	     STATUS  mandatory
DESCRIPTION ""
        --DEFAULT test-function    quad_test
        --DEFAULT next-function    quad_next
	    ::= { ncm-quad 11001 }


	 ncmquadLCurrentEntry OBJECT-TYPE
	     SYNTAX  NcmCsuLossCurrentEntry
	     ACCESS  not-accessible
	     STATUS  mandatory
	     DESCRIPTION
		"An entry in the Loss Current table."
	    INDEX   { ncmquadLCurrentIndex }
	    ::= { ncmquadLossCurrentTable 1 }

     NcmCsuLossCurrentEntry ::=
	 SEQUENCE {
	     ncmquadLCurrentIndex
		 INTEGER,
	     ncmquadCurrentEndId
		 INTEGER,
	     ncmquadLCurrentASs
		 Gauge,
	     ncmquadLCurrentLOSs
		 Gauge,
	     ncmquadLCurrentAISs
		 Gauge,
	     ncmquadLCurrentLOFs
		 Gauge,
	     ncmquadLCurrentOFs
		 Gauge,
	     ncmquadLCurrentESs
		 Gauge,
	     ncmquadLCurrentSESs
		 Gauge,
	     ncmquadLCurrentSEFs
		 Gauge,
	     ncmquadLCurrentUASs
		 Gauge,
	     ncmquadLCurrentBESs
		 Gauge,
	     ncmquadLCurrentESAs
		 Gauge,
	     ncmquadLCurrentSASs
		 Gauge,
	     ncmquadLCurrentCSSs
                 Gauge,
	     ncmquadLCurrentLOFCs
                 Gauge
	 }

	 ncmquadLCurrentIndex OBJECT-TYPE
	     SYNTAX  INTEGER (1..'7fffffff'h)
	     ACCESS  read-only
	     STATUS  mandatory
	     DESCRIPTION
		"The index value which uniquely identifies  the
		interface  to which this entry is applicable.
		The interface identified by a  particular
		value  of  this  index is the same interface as
		identified by the same value as a ncmquadLineIndex
		object instance."
	    ::= { ncmquadLCurrentEntry 1 }

	 ncmquadCurrentEndId  OBJECT-TYPE
	     SYNTAX  INTEGER {
			near-End(0),
			far-End(1)
		     }
	     ACCESS  read-only
	     STATUS  mandatory
	     DESCRIPTION
		"This value for this object indicates which
		 end of the equipment it is acessing."
	    ::= { ncmquadLCurrentEntry 2 }

	 ncmquadLCurrentASs OBJECT-TYPE
	     SYNTAX  Gauge
	     ACCESS  read-only
	     STATUS  mandatory
	     DESCRIPTION
		"The number of Availabe Seconds, encountered  by
		a DS1 interface in the current 15 minute inter-
		val.
             Remark:  Available Seconds does not support for QUAD 2164."  		

	    ::= { ncmquadLCurrentEntry 3 }


	 ncmquadLCurrentLOSs OBJECT-TYPE
	     SYNTAX  Gauge
	     ACCESS  read-only
	     STATUS  mandatory
	     DESCRIPTION
		"The number of Loss Of Signal Seconds encoun-
		tered  by  a  DS1  interface  in the current 15
		minute interval."
	    ::= { ncmquadLCurrentEntry 4 }


	 ncmquadLCurrentAISs OBJECT-TYPE
	     SYNTAX  Gauge
	     ACCESS  read-only
	     STATUS  mandatory
	     DESCRIPTION
		"The number of Alarm indication Signal Seconds
		encountered  by  a DS1 interface in the current
		15 minute interval."
	    ::= { ncmquadLCurrentEntry 5 }


	 ncmquadLCurrentLOFs OBJECT-TYPE
	     SYNTAX  Gauge
	     ACCESS  read-only
	     STATUS  mandatory
	     DESCRIPTION
		"The number of Loss of Frame Seconds  encountered
		by a DS1 interface in the current 15 minute in-
		terval."
	    ::= { ncmquadLCurrentEntry 6 }

	 ncmquadLCurrentOFs OBJECT-TYPE
	     SYNTAX  Gauge
	     ACCESS  read-only
	     STATUS  mandatory
	     DESCRIPTION
		"The number of Out of Frame Seconds  encountered
		by a DS1 interface in the current 15 minute in-
		terval."
	    ::= { ncmquadLCurrentEntry 7 }

	 ncmquadLCurrentESs OBJECT-TYPE
	     SYNTAX  Gauge
	     ACCESS  read-only
	     STATUS  mandatory
	     DESCRIPTION
		"The number of Errored Seconds  encountered
		by a DS1 interface in the current 15 minute in-
		terval."
	    ::= { ncmquadLCurrentEntry 8 }

	 ncmquadLCurrentSESs OBJECT-TYPE
	     SYNTAX  Gauge
	     ACCESS  read-only
	     STATUS  mandatory
	     DESCRIPTION
		"The number of Severely Errored Seconds  encountered
		by a DS1 interface in the current 15 minute in-
		terval."
	    ::= { ncmquadLCurrentEntry 9 }

	 ncmquadLCurrentSEFs OBJECT-TYPE
	     SYNTAX  Gauge
	     ACCESS  read-only
	     STATUS  mandatory
	     DESCRIPTION
		"The number of Severely Errored Framing Seconds  encountered
		by a DS1 interface in the current 15 minute in-
		terval."
	    ::= { ncmquadLCurrentEntry 10 }

	 ncmquadLCurrentUASs OBJECT-TYPE
	     SYNTAX  Gauge
	     ACCESS  read-only
	     STATUS  mandatory
	     DESCRIPTION
		"The number of Out of Unavailable Seconds  encountered
		by a DS1 interface in the current 15 minute in-
		terval."
	    ::= { ncmquadLCurrentEntry 11 }

	 ncmquadLCurrentBESs OBJECT-TYPE
	     SYNTAX  Gauge
	     ACCESS  read-only
	     STATUS  mandatory
	     DESCRIPTION
		"The number of Bursty Errored Seconds  encountered
		by a DS1 interface in the current 15 minute in-
		terval."
	    ::= { ncmquadLCurrentEntry 12 }


	ncmquadLCurrentESAs OBJECT-TYPE
	     SYNTAX  Gauge
	     ACCESS  read-only
	     STATUS  mandatory
	     DESCRIPTION
		"The number of ESAs  encountered
		by a DS1 interface in the current 15 minute in-
		terval."
	    ::= { ncmquadLCurrentEntry 13 }

	ncmquadLCurrentSASs OBJECT-TYPE
	     SYNTAX  Gauge
	     ACCESS  read-only
	     STATUS  mandatory
	     DESCRIPTION
		"The number of SASs  encountered
		by a DS1 interface in the current 15 minute in-
		terval."
	    ::= { ncmquadLCurrentEntry 14 }

	ncmquadLCurrentCSSs OBJECT-TYPE
	     SYNTAX  Gauge
	     ACCESS  read-only
	     STATUS  mandatory
	     DESCRIPTION
		"The number of CSSs  encountered
		by a DS1 interface in the current 15 minute in-
		terval."
	    ::= { ncmquadLCurrentEntry 15 }

	ncmquadLCurrentLOFCs OBJECT-TYPE
	     SYNTAX  Gauge
	     ACCESS  read-only
	     STATUS  mandatory
	     DESCRIPTION
		"The number of LOFCs  encountered
		by a DS1 interface in the current 15 minute in-
		terval."
	    ::= { ncmquadLCurrentEntry 16 }



     -- The Loss Interval Table contains various statistics
     -- collected by each DS1 Interface over the previous 24 hours of
     -- operation.  The past 24 hours are broken into 96 completed
     -- 15 minute intervals.

     -- "The Loss Interval table."
	 ncmquadLossIntervalTable OBJECT-TYPE
	     SYNTAX  SEQUENCE OF NcmCsuLossIntervalEntry
	     ACCESS  not-accessible
	     STATUS  mandatory
DESCRIPTION ""
        --DEFAULT test-function    quad_interval_test
        --DEFAULT next-function    quad_interval_next
	    ::= { ncm-quad 11002 }


	 ncmquadLIntervalEntry OBJECT-TYPE
	     SYNTAX  NcmCsuLossIntervalEntry
	     ACCESS  not-accessible
	     STATUS  mandatory
	     DESCRIPTION
		"An entry in the Loss Interval table."
	    INDEX   { ncmquadLIntervalIndex }
	    ::= { ncmquadLossIntervalTable 1 }

     NcmCsuLossIntervalEntry ::=
	 SEQUENCE {
	     ncmquadLIntervalIndex
		 INTEGER,
	     ncmquadLIntervalEndId
		 INTEGER,
	     ncmquadLIntervalNumber
		 INTEGER,
	     ncmquadLIntervalASs
		 Gauge,
	     ncmquadLIntervalLOSs
		 Gauge,
	     ncmquadLIntervalAISs
		 Gauge,
	     ncmquadLIntervalLOFs
		 Gauge,
	     ncmquadLIntervalOFs
		 Gauge,
	     ncmquadLIntervalESs
		 Gauge,
	     ncmquadLIntervalSESs
		 Gauge,
	     ncmquadLIntervalSEFs
		 Gauge,
	     ncmquadLIntervalUASs
		 Gauge,
	     ncmquadLIntervalBESs
		 Gauge,
             ncmquadLIntervalESAs
		 Gauge,
	     ncmquadLIntervalSASs
		 Gauge,
	     ncmquadLIntervalCSSs
		 Gauge,
	     ncmquadLIntervalLOFCs
		 Gauge

	     
	 }

	 ncmquadLIntervalIndex OBJECT-TYPE
	     SYNTAX  INTEGER (1..'7fffffff'h)
	     ACCESS  read-only
	     STATUS  mandatory
	     DESCRIPTION
		"The index value which uniquely identifies  the
		DS1  interface  to which this entry is applica-
		ble.  The interface identified by a  particular
		value  of  this  index is the same interface as
		identified by the same value as a ncmquadLineIndex
		object instance."
	    ::= { ncmquadLIntervalEntry 1 }


	 ncmquadLIntervalEndId  OBJECT-TYPE
	     SYNTAX  INTEGER {
			near-End(0),
			far-End(1)
		     }
	     ACCESS  read-only
	     STATUS  mandatory
	     DESCRIPTION
		"This value for this object indicates which
		 end of the equipment it is accessing."
	    ::= { ncmquadLIntervalEntry 2 }

	 ncmquadLIntervalNumber OBJECT-TYPE
	     SYNTAX  INTEGER (1..96)
	     ACCESS  read-only
	     STATUS  mandatory
	     DESCRIPTION
		"A number between 1 and 96, where 1 is the most
		recently completed 15 minute interval and 96 is
		the least recently completed 15 minutes  inter-
		val   (assuming   that  all  96  intervals  are
		valid)."
	    ::= { ncmquadLIntervalEntry 3 }

	 ncmquadLIntervalASs OBJECT-TYPE
	     SYNTAX  Gauge
	     ACCESS  read-only
	     STATUS  mandatory
	     DESCRIPTION
		"The number of Available Seconds encountered by a
		DS1  interface in one of the previous 96, indi-
		vidual 15 minute, intervals.
		Remark:  Available Seconds does not support for QUAD 2164."
	    ::= { ncmquadLIntervalEntry 4 }


	 ncmquadLIntervalLOSs OBJECT-TYPE
	     SYNTAX  Gauge
	     ACCESS  read-only
	     STATUS  mandatory
	     DESCRIPTION
		"The number of Loss of Signal Seconds encoun-
		tered by a DS1 interface in one of the previous
		96, individual 15 minute, intervals."
	    ::= { ncmquadLIntervalEntry 5 }


	 ncmquadLIntervalAISs OBJECT-TYPE
	     SYNTAX  Gauge
	     ACCESS  read-only
	     STATUS  mandatory
	     DESCRIPTION
		"The number of Alarm Indication Signal Seconds
		encountered  by  a  DS1 interface in one of the
		previous 96, individual 15 minute, intervals."
	    ::= { ncmquadLIntervalEntry 6 }


	 ncmquadLIntervalLOFs OBJECT-TYPE
	     SYNTAX  Gauge
	     ACCESS  read-only
	     STATUS  mandatory
	     DESCRIPTION
		"The number of Loss Of Frame Seconds  encountered
		by  a  DS1 interface in one of the previous 96,
		individual 15 minute, intervals."
	    ::= { ncmquadLIntervalEntry 7 }


	 ncmquadLIntervalOFs OBJECT-TYPE
	     SYNTAX  Gauge
	     ACCESS  read-only
	     STATUS  mandatory
	     DESCRIPTION
		"The number of Out Of Frame Seconds  encoun-
		tered by a DS1 interface in one of the previous
		96, individual 15 minute, intervals."
	    ::= { ncmquadLIntervalEntry 8 }

	 ncmquadLIntervalESs OBJECT-TYPE
	     SYNTAX  Gauge
	     ACCESS  read-only
	     STATUS  mandatory
	     DESCRIPTION
		"The number of Error Seconds  encoun-
		tered by a DS1 interface in one of the previous
		96, individual 15 minute, intervals."
	    ::= { ncmquadLIntervalEntry 9 }

	 ncmquadLIntervalSESs OBJECT-TYPE
	     SYNTAX  Gauge
	     ACCESS  read-only
	     STATUS  mandatory
	     DESCRIPTION
		"The number of Severe Error Seconds  encoun-
		tered by a DS1 interface in one of the previous
		96, individual 15 minute, intervals."
	    ::= { ncmquadLIntervalEntry 10 }

	 ncmquadLIntervalSEFs OBJECT-TYPE
	     SYNTAX  Gauge
	     ACCESS  read-only
	     STATUS  mandatory
	     DESCRIPTION
		"The number of Severly Errored Frame Seconds  encoun-
		tered by a DS1 interface in one of the previous
		96, individual 15 minute, intervals."
	    ::= { ncmquadLIntervalEntry 11 }

	 ncmquadLIntervalUASs OBJECT-TYPE
	     SYNTAX  Gauge
	     ACCESS  read-only
	     STATUS  mandatory
	     DESCRIPTION
		"The number of Unavailable Seconds  encoun-
		tered by a DS1 interface in one of the previous
		96, individual 15 minute, intervals."
	    ::= { ncmquadLIntervalEntry 12 }

	 ncmquadLIntervalBESs OBJECT-TYPE
	     SYNTAX  Gauge
	     ACCESS  read-only
	     STATUS  mandatory
	     DESCRIPTION
		"The number of Bursty Error Seconds  encoun-
		tered by a DS1 interface in one of the previous
		96, individual 15 minute, intervals."
	    ::= { ncmquadLIntervalEntry 13 }

	 ncmquadLIntervalESAs OBJECT-TYPE
	     SYNTAX  Gauge
	     ACCESS  read-only
	     STATUS  mandatory
	     DESCRIPTION
		"The number of ESAs Seconds  encoun-
		tered by a DS1 interface in one of the previous
		96, individual 15 minute, intervals."
	    ::= { ncmquadLIntervalEntry 14 }

	 ncmquadLIntervalSASs OBJECT-TYPE
	     SYNTAX  Gauge
	     ACCESS  read-only
	     STATUS  mandatory
	     DESCRIPTION
		"The number of SASs  encoun-
		tered by a DS1 interface in one of the previous
		96, individual 15 minute, intervals."
	    ::= { ncmquadLIntervalEntry 15 }

	 ncmquadLIntervalCSSs OBJECT-TYPE
	     SYNTAX  Gauge
	     ACCESS  read-only
	     STATUS  mandatory
	     DESCRIPTION
		"The number of CSSs  encoun-
		tered by a DS1 interface in one of the previous
		96, individual 15 minute, intervals."
	    ::= { ncmquadLIntervalEntry 16 }

	 ncmquadLIntervalLOFCs OBJECT-TYPE
	     SYNTAX  Gauge
	     ACCESS  read-only
	     STATUS  mandatory
	     DESCRIPTION
		"The number of LOFCs  encoun-
		tered by a DS1 interface in one of the previous
		96, individual 15 minute, intervals."
	    ::= { ncmquadLIntervalEntry 17 }

     -- The Total Loss Table contains the cumulative sum of the
     -- various statistics for the 24 hour period preceding the
     -- current interval.

     -- "The Loss Total table.  24 hour interval."
	 ncmquadLossTotalTable OBJECT-TYPE
	     SYNTAX  SEQUENCE OF NcmCsuLossTotalEntry
	     ACCESS  not-accessible
	     STATUS  mandatory
DESCRIPTION ""
        --DEFAULT test-function    quad_test
        --DEFAULT next-function    quad_next
	    ::= { ncm-quad 11003 }


	 ncmquadLTotalEntry OBJECT-TYPE
	     SYNTAX  NcmCsuLossTotalEntry
	     ACCESS  not-accessible
	     STATUS  mandatory
	     DESCRIPTION
		"An entry in the DS1 Total Loss table."
	    INDEX   { ncmquadLTotalIndex }
	    ::= { ncmquadLossTotalTable 1 }

     NcmCsuLossTotalEntry ::=
	 SEQUENCE {
	     ncmquadLTotalIndex
		 INTEGER,
	     ncmquadTotalEndId
		 INTEGER,
	     ncmquadLTotalASs
		 Gauge,
	     ncmquadLTotalLOSs
		 Gauge,
	     ncmquadLTotalAISs
		 Gauge,
	     ncmquadLTotalLOFs
		 Gauge,
	     ncmquadLTotalOFs
		 Gauge,
	     ncmquadLTotalESs
		 Gauge,
	     ncmquadLTotalSESs
		 Gauge,
	     ncmquadLTotalSEFs
		 Gauge,
	     ncmquadLTotalUASs
		 Gauge,
	     ncmquadLTotalBESs
		 Gauge,
             ncmquadLTotalESAs
		 Gauge,
	     ncmquadLTotalSASs
		 Gauge,
	     ncmquadLTotalCSSs
		 Gauge,
	     ncmquadLTotalLOFCs
		 Gauge

             
	 }

	 ncmquadLTotalIndex OBJECT-TYPE
	     SYNTAX  INTEGER (1..'7fffffff'h)
	     ACCESS  read-only
	     STATUS  mandatory
	     DESCRIPTION
		"The index value which uniquely identifies  the
		DS1  interface  to which this entry is applica-
		ble.  The interface identified by a  particular
		value  of  this  index is the same interface as
		identified by the same value as a ncmquadLineIndex
		object instance."
	    ::= { ncmquadLTotalEntry 1 }

	 ncmquadTotalEndId  OBJECT-TYPE
	     SYNTAX  INTEGER {
			near-End(0),
			far-End(1)
		     }
	     ACCESS  read-only
	     STATUS  mandatory
	     DESCRIPTION
		"This value for this object indicates which
		 end of the equipment it is accessing."
	    ::= { ncmquadLTotalEntry 2 }

	 ncmquadLTotalASs OBJECT-TYPE
	     SYNTAX  Gauge
	     ACCESS  read-only
	     STATUS  mandatory
	     DESCRIPTION
		"The number of Available Seconds encountered by a
		DS1 interface in the previous 24 hour interval.
		 Remark:  Available Seconds does not support for QUAD 2164."
	    ::= { ncmquadLTotalEntry 3 }


	 ncmquadLTotalLOSs OBJECT-TYPE
	     SYNTAX  Gauge
	     ACCESS  read-only
	     STATUS  mandatory
	     DESCRIPTION
		"The number of Loss Of Signal Seconds encoun-
		tered  by  a  DS1  interface in the previous 24
		hour interval."
	    ::= { ncmquadLTotalEntry 4 }


	 ncmquadLTotalAISs OBJECT-TYPE
	     SYNTAX  Gauge
	     ACCESS  read-only
	     STATUS  mandatory
	     DESCRIPTION
		"The number of Alarm Indication Signal Seconds
		encountered  by a DS1 interface in the previous
		24 hour interval."
	    ::= { ncmquadLTotalEntry 5 }


	 ncmquadLTotalLOFs OBJECT-TYPE
	     SYNTAX  Gauge
	     ACCESS  read-only
	     STATUS  mandatory
	     DESCRIPTION
		"The number of Loss Of Frame Seconds  encountered
		by  a DS1 interface in the previous 24 hour in-
		terval."
	    ::= { ncmquadLTotalEntry 6 }


	 ncmquadLTotalOFs OBJECT-TYPE
	     SYNTAX  Gauge
	     ACCESS  read-only
	     STATUS  mandatory
	     DESCRIPTION
		"The number of Controlled Slip Seconds  encoun-
		tered  by  a  DS1  interface in the previous 24
		hour interval."
	    ::= { ncmquadLTotalEntry 7 }

	ncmquadLTotalESs OBJECT-TYPE
	     SYNTAX  Gauge
	     ACCESS  read-only
	     STATUS  mandatory
	     DESCRIPTION
		"The number of Errored Seconds  encoun-
		tered  by  a  DS1  interface in the previous 24
		hour interval."
	    ::= { ncmquadLTotalEntry 8 }

	ncmquadLTotalSESs OBJECT-TYPE
	     SYNTAX  Gauge
	     ACCESS  read-only
	     STATUS  mandatory
	     DESCRIPTION
		"The number of Severly Errored Seconds  encoun-
		tered  by  a  DS1  interface in the previous 24
		hour interval."
	    ::= { ncmquadLTotalEntry 9 }

	ncmquadLTotalSEFs OBJECT-TYPE
	     SYNTAX  Gauge
	     ACCESS  read-only
	     STATUS  mandatory
	     DESCRIPTION
		"The number of Severly Errored Frame Seconds  encoun-
		tered  by  a  DS1  interface in the previous 24
		hour interval."
	    ::= { ncmquadLTotalEntry 10 }

	ncmquadLTotalUASs OBJECT-TYPE
	     SYNTAX  Gauge
	     ACCESS  read-only
	     STATUS  mandatory
	     DESCRIPTION
		"The number of Unavailable Seconds  encoun-
		tered  by  a  DS1  interface in the previous 24
		hour interval."
	    ::= { ncmquadLTotalEntry 11 }

	ncmquadLTotalBESs OBJECT-TYPE
	     SYNTAX  Gauge
	     ACCESS  read-only
	     STATUS  mandatory
	     DESCRIPTION
		"The number of Bursty Errored Seconds  encoun-
		tered  by  a  DS1  interface in the previous 24
		hour interval."
	    ::= { ncmquadLTotalEntry 12 }

	ncmquadLTotalESAs OBJECT-TYPE
	     SYNTAX  Gauge
	     ACCESS  read-only
	     STATUS  mandatory
	     DESCRIPTION
		"The number of ESAs Seconds  encoun-
		tered  by  a  DS1  interface in the previous 24
		hour interval."
	    ::= { ncmquadLTotalEntry 13 }

	ncmquadLTotalSASs OBJECT-TYPE
	     SYNTAX  Gauge
	     ACCESS  read-only
	     STATUS  mandatory
	     DESCRIPTION
		"The number of  SASs encoun-
		tered  by  a  DS1  interface in the previous 24
		hour interval."
	    ::= { ncmquadLTotalEntry 14 }

	ncmquadLTotalCSSs OBJECT-TYPE
	     SYNTAX  Gauge
	     ACCESS  read-only
	     STATUS  mandatory
	     DESCRIPTION
		"The number of CSSs Seconds  encoun-
		tered  by  a  DS1  interface in the previous 24
		hour interval."
	    ::= { ncmquadLTotalEntry 15 }

	ncmquadLTotalLOFCs OBJECT-TYPE
	     SYNTAX  Gauge
	     ACCESS  read-only
	     STATUS  mandatory
	     DESCRIPTION
		"The number of LOFCs Seconds  encoun-
		tered  by  a  DS1  interface in the previous 24
		hour interval."
	    ::= { ncmquadLTotalEntry 16 }


	-- the NCM Advanced T1 Port Configuration Table

	ncmadvancedT1ConfigTable OBJECT-TYPE
	SYNTAX  SEQUENCE OF NcmAdvancedT1ConfigEntry
	ACCESS  not-accessible
	STATUS  mandatory
	DESCRIPTION
	"The ncmadvanced T1 Configuration table."
        --DEFAULT test-function    quad_test
        --DEFAULT next-function    quad_next
	 ::= { ncm-quad 11004 }


	ncmadvancedT1ConfigEntry OBJECT-TYPE
	SYNTAX  NcmAdvancedT1ConfigEntry
	ACCESS  not-accessible
	STATUS  mandatory
	DESCRIPTION
	"An entry in the ncmadvanced T1 Configuration table."
	 INDEX   { ncmadvancedT1LineIndex }
	 ::= { ncmadvancedT1ConfigTable 1 }


	NcmAdvancedT1ConfigEntry ::=
	 SEQUENCE {
	     ncmadvancedT1LineIndex
		 INTEGER,
	     ncmportIdentifier
		 INTEGER,
	     ncmfdlMode
		 INTEGER,
	     ncmfdlStandard
		INTEGER,
	     ncmfdlPerformanceReport
		INTEGER,
             ncmfdlLBEnableDisable
                INTEGER,
             ncmfdlLLBT1BOPMsg
                INTEGER,
             ncmfdlPLBT1BOPMsg
                INTEGER,
	     ncmfdlIdlePattern
		INTEGER,
	     ncmfdlMonitoringCsuType
		INTEGER
		}



	ncmadvancedT1LineIndex OBJECT-TYPE
	SYNTAX  INTEGER (1..'7fffffff'h)
	ACCESS  read-only
	STATUS  mandatory
	DESCRIPTION
	"The index value which uniquely identifies  the
	 interface  to which this entry is applicable."

	::= { ncmadvancedT1ConfigEntry 1 }


	ncmportIdentifier OBJECT-TYPE
	SYNTAX INTEGER {

		       port-1(0),
		       port-2(1),
		       port-3(2),
		       port-4(3)

	       }
	  ACCESS read-write
	  STATUS mandatory
	  DESCRIPTION
	  "The variable specifies the port identifier and port_3 and
	  port_4 are for Quad T1 only."

	::= { ncmadvancedT1ConfigEntry 2 }


	ncmfdlMode OBJECT-TYPE
	SYNTAX INTEGER {

		       terminated(0),
		       pass(1)

	       }
	  ACCESS read-write
	  STATUS mandatory
	  DESCRIPTION
	  "The variable specifies the ncmfdl mode which is bit 0 of  ncmfdl
	  Parameter1."

	::= { ncmadvancedT1ConfigEntry 3 }

	ncmfdlStandard OBJECT-TYPE
	SYNTAX INTEGER {

		       reserved(0),
		       type-54016(4),
		       type-T1-403(8),
		       type-both(12)

	       }
	  ACCESS read-write
	  STATUS mandatory
	  DESCRIPTION
	  "The variable specifies the ncmfdl standard which is bits 1
	  and bit 2 of ncmfdl Parameter1."

	::= { ncmadvancedT1ConfigEntry 4 }

	ncmfdlPerformanceReport OBJECT-TYPE
	SYNTAX INTEGER {

		       disable(0),
		       user(32),
		       telco(64)


	       }
	  ACCESS read-write
	  STATUS mandatory
	  DESCRIPTION
	  "The variable specifies the ncmfdl standard which is bits 3
	  and bit 4 of ncmfdl Parameter1."

	::= { ncmadvancedT1ConfigEntry 5 }


          ncmfdlLBEnableDisable OBJECT-TYPE
          SYNTAX INTEGER {

                       disabled(0),
                       enabled(1)

	       }
	  ACCESS read-write
	  STATUS mandatory
	  DESCRIPTION
          "The variable specifies the Disable/Enable of the ncmfdl Loopback
           which is bit 0 of the ncmfdl_loop"

           ::= { ncmadvancedT1ConfigEntry 6 }


          ncmfdlLLBT1BOPMsg OBJECT-TYPE
          SYNTAX INTEGER {

                       disabled(0),
                       enabled(2)

	       }
	  ACCESS read-write
	  STATUS mandatory
	  DESCRIPTION
          "The variable specifies the Disable/Enable of the send/receive of
           the LLB T1.403 BOP Messages. It is the bit 1 of the ncmfdl_loop"

           ::= { ncmadvancedT1ConfigEntry 7 }


          ncmfdlPLBT1BOPMsg OBJECT-TYPE
          SYNTAX INTEGER {

                       disabled(0),
                       enabled(4)

	       }
	  ACCESS read-write
	  STATUS mandatory
	  DESCRIPTION
          "The variable specifies the Disable/Enable of the send/receive of
           the PLB T1.403 BOP Messages. It is the bit 2 of the ncmfdl_loop"

           ::= { ncmadvancedT1ConfigEntry 8 }


	ncmfdlIdlePattern OBJECT-TYPE
	SYNTAX INTEGER {

		       all-ones(0),
		       flags(1)

	       }
	  ACCESS read-write
	  STATUS mandatory
	  DESCRIPTION
	  "The variable specifies the ncmfdl idle pattern which is bit 0 of ncmfdl
	  Parameter2."

	::= { ncmadvancedT1ConfigEntry 9 }


	ncmfdlMonitoringCsuType OBJECT-TYPE
	SYNTAX INTEGER {

		       polling(0),
		       no-polling(4),
		       unsolicited-messages(8)


	       }
	  ACCESS read-write
	  STATUS mandatory
	  DESCRIPTION
	  "The variable specifies the ncmfdl standard which is bits 1
	  and bit 2 of ncmfdl Parameter2."

	::= { ncmadvancedT1ConfigEntry 10 }


     -- the QUAD Sync Time  Table


	 ncmquadSyncTable OBJECT-TYPE
	     SYNTAX  SEQUENCE OF NcmCSUSyncEntry
	     ACCESS  not-accessible
	     STATUS  mandatory
DESCRIPTION ""
                --DEFAULT test-function    quad_test
        	--DEFAULT next-function    sync_next
	    ::= { ncm-quad 11005 }


	 ncmquadSyncEntry OBJECT-TYPE
	     SYNTAX  NcmCSUSyncEntry
	     ACCESS  not-accessible
	     STATUS  mandatory
	     DESCRIPTION
		"An entry in the QUAD Sync Time table."
	    INDEX   { ncmquadLineIndex }
	    ::= { ncmquadSyncTable 1 }

     NcmCSUSyncEntry ::=
	 SEQUENCE {
	     ncmquadSyncIndex
		 INTEGER,
	     ncmquadSyncEndId
		 INTEGER,
	     ncmquadClkSyncSource
		 INTEGER,
	     ncmquadClkCardPrim
		 INTEGER,
	     ncmquadClkSyncPrimary
		 INTEGER,
	     ncmquadAutoRestorePrim
		 INTEGER,
	     ncmquadClkCardAlt1
		 INTEGER,
	     ncmquadClkSyncAlt1
		 INTEGER,
	     ncmquadAutoRestore1
		 INTEGER,
	     ncmquadClkCardAlt2
		 INTEGER,
	     ncmquadClkSyncAlt2
		 INTEGER,
	     ncmquadAutoRestore2
		 INTEGER

	}
	ncmquadSyncIndex OBJECT-TYPE
	     SYNTAX  INTEGER (1..'7fffffff'h)
	     ACCESS  read-only
	     STATUS  mandatory
	     DESCRIPTION
		"This object is the identifier of a  Inter-
		face on a managed device.  If there is an ifEn-
		try that is directly associated with  this  and
		only  this  DS1  interface,  it should have the
		same value as ifIndex.   Otherwise,  the  value
		exceeds  ifNumber,  and  is a unique identifier
		following this rule: inside  interfaces  (e.g.,
		equipment  side)  with even numbers and outside
		interfaces  (e.g.,  network   side)   with   odd
		numbers."
	    ::= { ncmquadSyncEntry 1 }


	 ncmquadSyncEndId  OBJECT-TYPE
	     SYNTAX  INTEGER {
			near-End(0),
			far-End(1)
		     }
	     ACCESS  read-only
	     STATUS  mandatory
	     DESCRIPTION
		"This value for this object indicates which
		 end of the equipment it is configuring."
	    ::= { ncmquadSyncEntry 2 }

	ncmquadClkSyncSource OBJECT-TYPE
	    SYNTAX INTEGER {
			primary(0),
			alt-1(1),
			alt-2(2)
		    }
	    ACCESS  read-only
	    STATUS  mandatory
	    DESCRIPTION
		"This variable indicates Current Clk Source Active i.e.,
		 primary, Alt_1 or Alt_2 source."
	    ::= { ncmquadSyncEntry 3 }

	ncmquadClkCardPrim OBJECT-TYPE
             SYNTAX  INTEGER {
			c-1(0),
			c-2(1),
			c-3(2),
			c-4(3),
			c-5(4),
			c-6(5),
			c-7(6),
			c-8(7),
			c-9(8),
			c-10(9),
			c-11(10),
			c-12(11),
			c-13(12)
		   }
             ACCESS  read-write
             STATUS  mandatory
             DESCRIPTION
		" This variable indicates the primary clock source from which
		  card of the that shelf. "
	    ::= { ncmquadSyncEntry 4 }

	ncmquadClkSyncPrimary OBJECT-TYPE
	    SYNTAX INTEGER {
			internal(0),
			external(1),
			masterNet1(2),
			masterNet2(3),
			masterNet3(4),
			masterNet4(5)
		    }
	    ACCESS  read-write
	    STATUS  mandatory
	    DESCRIPTION
		"This variable indicates the Clock source internal, external or
		network port. Setting Auto restore one can have auto restore 
		Capability."
	    ::= { ncmquadSyncEntry 5 }


	ncmquadAutoRestorePrim OBJECT-TYPE
	    SYNTAX INTEGER {
			disable(0),
			enable(1)
		    }
	    ACCESS  read-write
	    STATUS  mandatory
	    DESCRIPTION
		"This variable indicates the Clock source auto restore or not for 
		Internal, external or network clocks." 
	    ::= { ncmquadSyncEntry 6 }

        ncmquadClkCardAlt1 OBJECT-TYPE
             SYNTAX INTEGER { 
                        c-1(0),
                        c-2(1),
                        c-3(2),
                        c-4(3),
                        c-5(4),
                        c-6(5),
                        c-7(6),
                        c-8(7),
                        c-9(8),
                        c-10(9),
                        c-11(10),
                        c-12(11),
                        c-13(12)
		   }
             ACCESS  read-write
             STATUS  mandatory
             DESCRIPTION
		" This variable indicates the primary clock source from which
		  card of the that shelf. "
	    ::= { ncmquadSyncEntry 7 }

	ncmquadClkSyncAlt1 OBJECT-TYPE
	    SYNTAX INTEGER {
			internal(0),
			external(1),
			masterNet1(2),
			masterNet2(3),
			masterNet3(4),
			masterNet4(5)
		    }
	    ACCESS  read-write
	    STATUS  mandatory
	    DESCRIPTION
		"This variable indicates the Clock source internal, external or
		network port. Setting Auto restore one can have auto restore 
		Capability."
	    ::= { ncmquadSyncEntry 8 }


	ncmquadAutoRestore1 OBJECT-TYPE
	    SYNTAX INTEGER {
			disable(0),
			enable(1)
		    }
	    ACCESS  read-write
	    STATUS  mandatory
	    DESCRIPTION
		"This variable indicates the Clock source auto restore or not for 
		Internal, external or network clocks." 
	    ::= { ncmquadSyncEntry 9 }

	 ncmquadClkCardAlt2 OBJECT-TYPE
             SYNTAX INTEGER { 
                        c-1(0),
                        c-2(1),
                        c-3(2),
                        c-4(3),
                        c-5(4),
                        c-6(5),
                        c-7(6),
                        c-8(7),
                        c-9(8),
                        c-10(9),
                        c-11(10),
                        c-12(11),
                        c-13(12)
		   }
             ACCESS  read-write
             STATUS  mandatory
             DESCRIPTION
		" This variable indicates the primary clock source from which
		  card of the that shelf. "
	    ::= { ncmquadSyncEntry 10 }

	ncmquadClkSyncAlt2 OBJECT-TYPE
	    SYNTAX INTEGER {
			internal(0),
			external(1),
			masterNet1(2),
			masterNet2(3),
			masterNet3(4),
			masterNet4(5)
		    }
	    ACCESS  read-write
	    STATUS  mandatory
	    DESCRIPTION
		"This variable indicates the Clock source internal, external or
		network port. Setting Auto restore one can have auto restore 
		Capability."
	    ::= { ncmquadSyncEntry 11 }

	ncmquadAutoRestore2 OBJECT-TYPE
	    SYNTAX INTEGER {
			disable(0),
			enable(1)
		    }
	    ACCESS  read-write
	    STATUS  mandatory
	    DESCRIPTION
		"This variable indicates the Clock source auto restore or not for 
		Internal, external or network clocks." 
	    ::= { ncmquadSyncEntry 12 }

     END
