-- ============================================================================
-- Copyright (C) 2012 by  HUAWEI TECHNOLOGIES. All rights reserved.
-- Description:  The MIB module defines the MIB objects of the two layer IPDSLAM 
--               configuration that based on port.
--               The port configuration includes configuring and querying all 
--               types of physical and service virtual ports. 
-- Reference:  
-- Version: V1.23
-- ============================================================================
    HUAWEI-IPDSLAML2PPORTCONFIG-MIB DEFINITIONS ::= BEGIN
        IMPORTS 
            hwConfigChangeIP
                    FROM HUAWEI-DEVICE-MIB
            ifIndex            
                    FROM IF-MIB            
            OBJECT-TYPE, MODULE-IDENTITY, Integer32, NOTIFICATION-TYPE        
                    FROM SNMPv2-SMI           
            huaweiUtility            
                    FROM HUAWEI-MIB                            
            TruthValue, RowStatus, MacAddress, TEXTUAL-CONVENTION, DisplayString            
                    FROM SNMPv2-TC;

        hwIpDslamL2pPortConfig MODULE-IDENTITY    
            LAST-UPDATED "2012071900000Z"
            ORGANIZATION "Huawei Technologies Co.,Ltd."
            CONTACT-INFO 
                "Huawei Industrial Base
                 Bantian, Longgang
                 Shenzhen 518129
                 People's Republic of China 
                 Website: http://www.huawei.com
                 Email: support@huawei.com
                "
            DESCRIPTION 
                "The MIB module defines the MIB objects of the two layer IPDSLAM 
                 configuration that based on port.
                 The port configuration includes configuring and querying all 
                 types of physical and service virtual ports."
            
            --  Revision history
            REVISION     "2012071900000Z" 
            DESCRIPTION  "V1.23, Changed pitpForbidForwarding to pitpPermitForwarding, changed option82ForbidForwarding to option82PermitForwarding.
			              Modified the description of pitpForbidForwarding and option82ForbidForwarding."
			
            REVISION     "2011091300000Z" 
            DESCRIPTION  "V1.22, modified the status of hwIpDslamL2pSrvFlowConfigRowStatus."

            REVISION     "2010120100000Z" 
            DESCRIPTION  "V1.21, added hwIpDslamL2pVlanCtrlVmacIPoESubStatus, hwIpDslamL2pVlanCtrlVmacPPPoESubStatus,
                          hwIpDslamL2pVlanCtrlVmacPPPoASubStatus and hwIpDslamL2pVlanCtrlPppoaMacMode."

            REVISION     "2010111000000Z" 
            DESCRIPTION  "V1.20, modified description."
            
            REVISION     "201008160000Z" 
            DESCRIPTION  "V1.19, added hwIpDslamL2pSrvFlowConfigValueStr, hwIpDslamL2pSrvFlowConfigChangeTrap."
            
            REVISION     "201007210000Z" 
            DESCRIPTION  "V1.18, modified the description of this MIB module.
                          Modified the description of hwIpDslamL2pSrvFlowConfigObject."
            
            REVISION     "201007020000Z" 
            DESCRIPTION  "V1.17, modified the description of hwIpDslamL2pPortConfigSecondIndex, the value range changed.
                          Modified MIB file name from HUAWEI-IPDSLAM-L2PPORTCONFIG-MIB to HUAWEI-IPDSLAML2PPORTCONFIG-MIB."
            
            REVISION     "201006100000Z" 
            DESCRIPTION  "V1.16, modified the description of hwIpDslamL2pPortConfigSecondIndex and hwIpDslamL2pPortConfigThirdIndex."
            
            REVISION     "201004220000Z" 
            DESCRIPTION  "V1.15, modified description."
                        
            REVISION     "201003220000Z" 
            DESCRIPTION  "V1.14, corrected expression."
            
            REVISION     "201003030000Z" 
            DESCRIPTION  "V1.13, addad enum value ipoeSmacMaxIpCount(7), and add mib-node hwIpDslamL2pVlanCtrlVmacStatus,modify multi-mac to multiMac,modify single-mac to singleMac."

            REVISION     "201001041100Z" 
            DESCRIPTION  "V1.12, modified datatype, such as INTEGER to Integer32.Modify for VLAN ctrl table."
                                 
            REVISION     "200912251030Z" 
            DESCRIPTION  "V1.10, extended the value of the hwIpDslamL2pSrvFlowConfigObject 
                          with ipoe-smac-max-ip-count(7)in the hwIpDslamL2pSrvFlowConfigTable."
                            
            REVISION     "200910190000Z" 
            DESCRIPTION  "V1.09, added hwIpDslamL2pVlanCtrlVmacStatus in hwIpDslamL2pVlanCtrlTable 
                          to support configugering vmac switch of the vlan separately."
                
            REVISION     "200606310000Z" 
            DESCRIPTION  "V1.00, Initial version."
                
            ::= { huaweiUtility 109}                            
        
        hwIpDslamL2pPortConfigTable OBJECT-TYPE
            SYNTAX      SEQUENCE OF HwIpDslamL2pPortConfigEntry
            MAX-ACCESS  not-accessible
            STATUS      current
            DESCRIPTION
                "Used for setting and querying the configuration based on port.
                 The indexes of this table are hwIpDslamL2pPortConfigIfIndex, hwIpDslamL2pPortConfigSecondIndex, 
                 hwIpDslamL2pPortConfigThirdIndex, and hwIpDslamL2pPortConfigObject.
                "
            ::= { hwIpDslamL2pPortConfig 1 }                      
        
        hwIpDslamL2pPortConfigEntry OBJECT-TYPE
            SYNTAX HwIpDslamL2pPortConfigEntry
            MAX-ACCESS not-accessible
            STATUS current
            DESCRIPTION
                "Used for setting and querying the configuration based on port.
                 The indexes of this entry are hwIpDslamL2pPortConfigIfIndex, hwIpDslamL2pPortConfigSecondIndex, 
                 hwIpDslamL2pPortConfigThirdIndex, and hwIpDslamL2pPortConfigObject.
                "
            INDEX 
                { 
                hwIpDslamL2pPortConfigIfIndex, 
                hwIpDslamL2pPortConfigSecondIndex, 
                hwIpDslamL2pPortConfigThirdIndex, 
                hwIpDslamL2pPortConfigObject 
                }
            ::= { hwIpDslamL2pPortConfigTable 1 }            
        
        HwIpDslamL2pPortConfigEntry ::=
            SEQUENCE 
                { 
                hwIpDslamL2pPortConfigIfIndex
                    Integer32,
                hwIpDslamL2pPortConfigSecondIndex
                    Integer32,
                hwIpDslamL2pPortConfigThirdIndex
                    Integer32,                                    
                hwIpDslamL2pPortConfigObject
                    INTEGER,
                hwIpDslamL2pPortConfigType
                    INTEGER,
                hwIpDslamL2pPortConfigValue
                    DisplayString,
                hwIpDslamL2pPortConfigRowStatus
                    RowStatus                                    
                }

        hwIpDslamL2pPortConfigIfIndex OBJECT-TYPE
            SYNTAX Integer32 
            MAX-ACCESS not-accessible
            STATUS current
            DESCRIPTION
                "The same as the ifIndex in Huawei MIB. 
                 To set or query hwIpDslamL2pPortConfigTable, you need to input the value of 
                 hwIpDslamL2pPortConfigIfIndex on the NMS.
                "                 
            ::= { hwIpDslamL2pPortConfigEntry 1 }

        hwIpDslamL2pPortConfigSecondIndex OBJECT-TYPE
            SYNTAX Integer32 
            MAX-ACCESS not-accessible
            STATUS current
            DESCRIPTION
                "An invalid value needs to be input for this leaf for the ADSL, SHDSL, VDSL2, 
                 and OPFA boards. The invalid value is defined as 65535. For GPON boards, 
                 in the xPON distributed mode, the configuration granularity of L2 enhanced services 
                 based on physical port is GEM port. In this case, this leaf is used to indicate the 
                 GEM port ID and the value range is 128-3999.
                 In the xPON (EPON and GPON) profile mode, this leaf is used to indicate the ONT ID.
                "
            ::= { hwIpDslamL2pPortConfigEntry 2 }

        hwIpDslamL2pPortConfigThirdIndex OBJECT-TYPE
            SYNTAX Integer32 
            MAX-ACCESS not-accessible
            STATUS current
            DESCRIPTION
                "In the xPON profile mode, the configuration granularity of L2 services based on physical 
                 port is GEM index and the value range is 0-1023.
                 For the ADSL, SHDSL, VDSL2, OPFA, and EPON boards, an invalid value needs to be input for this leaf.
                 The invalid value is defined as -1. 
                 For GPON boards, this leaf takes effect only in the xPON profile mode. 
                 In this case, this leaf is used to indicate the GEM index of a GPON port. 
                 In other modes, an invalid value needs to be input for this leaf.
                "                     
            ::= { hwIpDslamL2pPortConfigEntry 3 }

        hwIpDslamL2pPortConfigObject OBJECT-TYPE
            SYNTAX INTEGER
                {    
                pppoeSessionCount(1),
                pitp(2),
                dhcpOption82(3)
                }                                
            MAX-ACCESS not-accessible
            STATUS current
            DESCRIPTION
                "Indicates the configured object.
                 Options: 
                 1. pppoeSessionCount(1) -indicates the configured object is pppoeSessionCount
                 2. pitp(2)              -indicates the configured object is pitp
                 3. dhcpOption82(3)      -indicates the configured object is dhcpOption82
                "
            ::= { hwIpDslamL2pPortConfigEntry 4 }

        hwIpDslamL2pPortConfigType OBJECT-TYPE
            SYNTAX INTEGER
                {
                integer(1),
                string(2)
                }
            MAX-ACCESS read-write
            STATUS current
            DESCRIPTION
                "Indicates the value type of the configured object.
                 Options:
                 1. integer(1) -integer type
                 2. string(2)  -string type
                 Currently, only integer(1) is supported.
                "
            ::= { hwIpDslamL2pPortConfigEntry 5 }

        hwIpDslamL2pPortConfigValue OBJECT-TYPE
            SYNTAX DisplayString 
            MAX-ACCESS read-write
            STATUS current
            DESCRIPTION
                "Indicates the value of the configured object. Because some configured objects
                 must be of the integer type while others may be of the character string type, 
                 the values of the configured objects must be input as a character string when 
                 the objects are configured through this leaf. The length of the character string 
                 is 0-255 characters.
                 When hwIpDslamL2pPortConfigObject is set to pppoeSessionCount(1), 
                 the input range is (1..8) and the default value is 8.
                 When hwIpDslamL2pPortConfigObject is set to pitp(2), the input range is (1..2), 
                 where 1 indicates enabled and 2 indicates disabled. The default value is 1.
                 When hwIpDslamL2pPortConfigObject is set to dhcpOption82(3), the input range is (1..2), 
                 where 1 indicates enabled and 2 indicates disabled. The default value is 1.
                "
            ::= { hwIpDslamL2pPortConfigEntry 6 }

        hwIpDslamL2pPortConfigRowStatus OBJECT-TYPE
            SYNTAX       RowStatus
            MAX-ACCESS read-create
            STATUS current
            DESCRIPTION
                "This leaf must be set and issued if the configured object is the character string type. 
                 Options: 
                 1. active(1)      -indicates query operation
                 2. createAndgo(4) -indicates setting operation
                 3. destroy(6)     -indicates destroying operation
                 Currently, configured objects support only the integer type so this leaf can be ignored.
                "
            DEFVAL { active }                    
            ::= { hwIpDslamL2pPortConfigEntry 7 }                                               

        hwIpDslamL2pSrvFlowConfigTable OBJECT-TYPE
            SYNTAX      SEQUENCE OF HwIpDslamL2pSrvFlowConfigEntry
            MAX-ACCESS  not-accessible
            STATUS      current
            DESCRIPTION
                "Used for setting and querying the status of L2 enhanced features based on service port. 
                 The indexes of this table are hwIpDslamL2pSrvFlowConfigIndex and hwIpDslamL2pSrvFlowConfigObject.
                "
            ::= { hwIpDslamL2pPortConfig 2 }                      
        
        hwIpDslamL2pSrvFlowConfigEntry OBJECT-TYPE
            SYNTAX HwIpDslamL2pSrvFlowConfigEntry
            MAX-ACCESS not-accessible
            STATUS current
            DESCRIPTION
                "Used for setting and querying the status of L2 enhanced features based on service port. 
                 The indexes of this entry are hwIpDslamL2pSrvFlowConfigIndex and hwIpDslamL2pSrvFlowConfigObject.
                "
            INDEX { hwIpDslamL2pSrvFlowConfigIndex, hwIpDslamL2pSrvFlowConfigObject }
            ::= { hwIpDslamL2pSrvFlowConfigTable 1 }            
        
        HwIpDslamL2pSrvFlowConfigEntry ::=
            SEQUENCE 
                { 
                hwIpDslamL2pSrvFlowConfigIndex
                    Integer32,                                
                hwIpDslamL2pSrvFlowConfigObject
                    INTEGER,
                hwIpDslamL2pSrvFlowConfigType
                    INTEGER,
                hwIpDslamL2pSrvFlowConfigValue
                    DisplayString,
                hwIpDslamL2pSrvFlowConfigRowStatus
                    RowStatus                                        
                }

         hwIpDslamL2pSrvFlowConfigIndex OBJECT-TYPE
             SYNTAX Integer32 
             MAX-ACCESS not-accessible
             STATUS current
             DESCRIPTION
                 "The meaning and value of this leaf are the same as those of hwExtSrvFlowIndex in Huawei's MIB hwExtSrvFlowTable.
                 "
             ::= { hwIpDslamL2pSrvFlowConfigEntry 1 }

        hwIpDslamL2pSrvFlowConfigObject OBJECT-TYPE
            SYNTAX INTEGER
                {    
                macSpoofingMacCount(1),
                maxSessionCount(2),
                pitp(3),
                dhcpOption82(4),
                pitpPermitForwarding(5),
                option82PermitForwarding(6),
                ipoeSmacMaxIpCount(7)
                }                
            MAX-ACCESS not-accessible
            STATUS current
            DESCRIPTION
                "Indicates the configured object.
                 Options:
                 1. macSpoofingMacCount(1)      -indicates the maximum number of MAC addresses that can 
                                                 be bound to each service port for the anti-MAC spoofing 
                                                 feature.
                 2. maxSessionCount(2)          -indicates the maximum number of sessions that can be created 
                                                 on each service port for the PPPoE SMAC service. This option 
                                                 is supported by only the GPON service port.
                 3. pitp(3)                     -Enables/Disables PITP on a service port.
                 4. dhcpOption82(4)             -Enables/Disables DHCP Option82 on a service port.
                 5. pitpPermitForwarding(5)     -allow the user-side packet to carry PITP information. 
                                                 This function is enabled or disabled based on service port.
                 6. option82PermitForwarding(6) -allow the user-side packet to carry DHCP Option82 
                                                 information. This function is enabled or disabled based 
                                                 on service port.
                 7. ipoeSmacMaxIpCount(7)       -indicates the maximum number of IP addresses permitted by each 
                                                 service port in the IPoE SMAC mode.
                "
            ::= { hwIpDslamL2pSrvFlowConfigEntry 2 }

        hwIpDslamL2pSrvFlowConfigType OBJECT-TYPE
            SYNTAX INTEGER
            {
                integer(1),
                string(2)
            }                                
            MAX-ACCESS read-write
            STATUS current
            DESCRIPTION
                "Indicates the type of the configured object.
                 Options:
                 1. integer(1) -integer type
                 2. string(2)  -string type
                 Currently, only integer(1) is supported.
                "
            ::= { hwIpDslamL2pSrvFlowConfigEntry 3 }                                            

        hwIpDslamL2pSrvFlowConfigValue OBJECT-TYPE
            SYNTAX DisplayString 
            MAX-ACCESS read-write
            STATUS current
            DESCRIPTION
                "Indicates the value of the configured object. Because some configured objects must 
                 be of the integer type while others may be of the character string type, the values 
                 of the configured objects must be input as a character string when the objects are 
                 configured through this leaf. The length of the character string is 0-255 characters.
                 
                 When hwIpDslamL2pSrvFlowConfigObject is set to macSpoofingMacCount(1), the input range 
                 is {0..8} and the default value is 8.
                 
                 When hwIpDslamL2pSrvFlowConfigObject is set to maxSessionCount(2), the input range is 
                 {1..8} and the default value is 8.

                 When hwIpDslamL2pSrvFlowConfigObject is set to pitp(3), the input range is {1..2}, where 
                 1 indicates enabled and 2 indicates disabled. The default value is 1.
                 
                 When hwIpDslamL2pSrvFlowConfigObject is set to dhcpOption82(4), the input range is {1..2}, 
                 where 1 indicates enabled and 2 indicates disabled. The default value is 1.
                 
                 When hwIpDslamL2pSrvFlowConfigObject is set to pitpForbidForwarding(5), the input range is 
                 {1..2}, where 1 indicates enabled and 2 indicates disabled. The default value is 1.
                 
                 When hwIpDslamL2pSrvFlowConfigObject is set to option82ForbidForwarding(6), the input range 
                 is {1..2}, where 1 indicates enabled and 2 indicates disabled. The default value is 1.

                 When hwIpDslamL2pSrvFlowConfigObject is set to ipoeSmacMaxIpCount(7), the input range is 
                 {1..8} and the default value is 8.
                "
            ::= { hwIpDslamL2pSrvFlowConfigEntry 4 }

        hwIpDslamL2pSrvFlowConfigRowStatus OBJECT-TYPE
            SYNTAX       RowStatus
            MAX-ACCESS read-create
            STATUS obsolete
            DESCRIPTION
                "Indicates the row status. This leaf must be set and issued together with the 
                 configured object if the configured object is of the character string type. 
                 This leaf must not be set or issued together with the configured object if 
                 the configured object is of the integer type. For example, configured objects 
                 max-session-count and ipoe-smac-max-ip-count are of the integer type, so the 
                 row status must not be set or issued together with the configured objects in 
                 relevant operations.
                 During the configuration of a character string type configured object, you need 
                 to set the row status to createAndGo(4) and perform the set operation.
                 Perform the get operation to query the value of a character string type 
                 configured object. The queried value of the row status is always active(1).
                 Options: 
                 1. active(1)      -indicates query operation
                 2. createAndgo(4) -indicates setting operation
                 3. destroy(6)     -indicates destroying operation
                "
            DEFVAL { active }                    
            ::= { hwIpDslamL2pSrvFlowConfigEntry 5 }                    

        hwIpDslamL2pVlanCtrlTable OBJECT-TYPE
            SYNTAX      SEQUENCE OF HwIpDslamL2pVlanCtrlEntry
            MAX-ACCESS  not-accessible
            STATUS      current
            DESCRIPTION
                "Used for setting and querying the status of L2 protocol features based on VLAN. 
                 The index of this table is hwIpDslamL2pVlanCtrlIndex.
                "
            ::= { hwIpDslamL2pPortConfig 3 }                      
        
        hwIpDslamL2pVlanCtrlEntry OBJECT-TYPE
            SYNTAX HwIpDslamL2pVlanCtrlEntry
            MAX-ACCESS not-accessible
            STATUS current
            DESCRIPTION
                "Used for setting and querying the status of L2 protocol features based on VLAN. 
                 The index of this entry is hwIpDslamL2pVlanCtrlIndex.
                "
            INDEX { hwIpDslamL2pVlanCtrlIndex }
            ::= { hwIpDslamL2pVlanCtrlTable 1 }            
        
        HwIpDslamL2pVlanCtrlEntry ::=
            SEQUENCE 
                { 
                hwIpDslamL2pVlanCtrlIndex
                    Integer32,                                
                hwIpDslamL2pVlanCtrlMacSpoofing
                    INTEGER,
                hwIpDslamL2pVlanCtrlPppoeMacMode
                    INTEGER,    
                hwIpDslamL2pVlanCtrlDhcpBroadcastControl
                    INTEGER,
                hwIpDslamL2pVlanCtrlVmacStatus
                    INTEGER,                            
                hwIpDslamL2pVlanCtrlVmacIpoeSubStatus
                    INTEGER,                            
                hwIpDslamL2pVlanCtrlVmacPppoeSubStatus
                    INTEGER,                            
                hwIpDslamL2pVlanCtrlVmacPppoaSubStatus
                    INTEGER,                            
                hwIpDslamL2pVlanCtrlPppoaMacMode
                    INTEGER
                }

        hwIpDslamL2pVlanCtrlIndex OBJECT-TYPE
            SYNTAX Integer32  (1..4095)
            MAX-ACCESS not-accessible
            STATUS current
            DESCRIPTION                     
                "Used as the index for the VLAN-based feature control and is issued 
                 together with various leaves corresponding to the features to be 
                 configured. 
                 Range: 1-4095
                "
            ::= { hwIpDslamL2pVlanCtrlEntry 1 }

        hwIpDslamL2pVlanCtrlMacSpoofing OBJECT-TYPE
            SYNTAX INTEGER
                {    
                disable(1),
                enable(2)
                }                
            MAX-ACCESS read-write
            STATUS current
            DESCRIPTION
                "Used for setting or querying the anti-MAC-spoofing status of the VLAN. 
                 Options: 
                 1. disable(1) -indicates the anti-MAC-spoofing switch of the VLAN is off
                 2. enable(2)  -indicates the anti-MAC-spoofing switch of the VLAN is on
                 Default: disable(1)
                "
            ::= { hwIpDslamL2pVlanCtrlEntry 2 }

        hwIpDslamL2pVlanCtrlPppoeMacMode OBJECT-TYPE
            SYNTAX INTEGER
                {    
                multiMac(1),
                singleMac(2)
                }                                        
            MAX-ACCESS read-write
            STATUS current
            DESCRIPTION
                "Indicates the MAC address mode of a PPPoE user.
                 Options:
                 1. multiMac(1)  -indicates multiple MAC address mode of PPPoE user
                 2. singleMac(2) -indicates single MAC address mode of PPPoE user
                 Default: multiMac(1)
                "
            ::= {hwIpDslamL2pVlanCtrlEntry 3 }
                 
        hwIpDslamL2pVlanCtrlDhcpBroadcastControl OBJECT-TYPE
            SYNTAX INTEGER
                {    
                disable(1),
                enable(2)
                }                
            MAX-ACCESS read-write
            STATUS current
            DESCRIPTION
                "The status of DhcpBroadcastControl switch.
                 Options:
                 1. disable(1) -indicates the DhcpBroadcastControl switch is off
                 2. enable(2)  -indicates the DhcpBroadcastControl switch is on
                "
            ::= { hwIpDslamL2pVlanCtrlEntry 4 }
        
        hwIpDslamL2pVlanCtrlVmacStatus OBJECT-TYPE
            SYNTAX INTEGER
                {	
                disable(1),
                enable(2)
                }				
            MAX-ACCESS read-write
            STATUS current
            DESCRIPTION
                "Identifies the VMAC status of the specified VLAN, which is used for setting the VMAC status of the specified VLAN. 
                 Options:
                 1. disable(1) -indicates the VMAC switch of the VLAN is off
                 2. enable(2)  -indicates the VMAC switch of the VLAN is on
                 Default: disable(1)
                "
            ::= { hwIpDslamL2pVlanCtrlEntry 5 }
		
        hwIpDslamL2pVlanCtrlVmacIpoeSubStatus OBJECT-TYPE
            SYNTAX INTEGER
                {	
                disable(1),
                enable(2)
                }				
            MAX-ACCESS read-write
            STATUS current
            DESCRIPTION
                "Identifies the IPoE VMAC status of the specified VLAN, which is used for setting the IPoE VMAC status of the specified VLAN. 
                 Options:
                 1. disable(1) -indicates the IPoE VMAC switch of the VLAN is off
                 2. enable(2)  -indicates the IPoE VMAC switch of the VLAN is on
                 Default: disable(1)
                "
            ::= { hwIpDslamL2pVlanCtrlEntry 6 }
		
        hwIpDslamL2pVlanCtrlVmacPppoeSubStatus OBJECT-TYPE
            SYNTAX INTEGER
                {	
                disable(1),
                enable(2)
                }				
            MAX-ACCESS read-write
            STATUS current
            DESCRIPTION
                "Identifies the PPPoE VMAC status of the specified VLAN, which is used for setting the PPPoE VMAC status of the specified VLAN. 
                 Options:
                 1. disable(1) -indicates the PPPoE VMAC switch of the VLAN is off
                 2. enable(2)  -indicates the PPPoE VMAC switch of the VLAN is on
                 Default: disable(1)
                "
            ::= { hwIpDslamL2pVlanCtrlEntry 7 }
		
        hwIpDslamL2pVlanCtrlVmacPppoaSubStatus OBJECT-TYPE
            SYNTAX INTEGER
                {	
                disable(1),
                enable(2)
                }				
            MAX-ACCESS read-write
            STATUS current
            DESCRIPTION
                "Identifies the PPPoA VMAC status of the specified VLAN, which is used for setting the PPPoA VMAC status of the specified VLAN. 
                 Options:
                 1. disable(1) -indicates the PPPoA VMAC switch of the VLAN is off
                 2. enable(2)  -indicates the PPPoA VMAC switch of the VLAN is on
                 Default: disable(1)
                "
            ::= { hwIpDslamL2pVlanCtrlEntry 8 }
		
        hwIpDslamL2pVlanCtrlPppoaMacMode OBJECT-TYPE
            SYNTAX INTEGER
                {	
                multiMac(1),
                singleMac(2)
                }				
            MAX-ACCESS read-write
            STATUS current
            DESCRIPTION
                "Indicates the MAC address mode of a PPPoA user.
                 Options:
                 1. multiMac(1)  -indicates multiple MAC address mode of PPPoA user
                 2. singleMac(2) -indicates single MAC address mode of PPPoA user
                 Default: multiMac(1)
                "
            ::= { hwIpDslamL2pVlanCtrlEntry 9 }
		
         hwIpDslamL2pTrapsVbOids OBJECT IDENTIFIER ::= { hwIpDslamL2pPortConfig 4 }
		
         hwIpDslamL2pSrvFlowConfigValueStr OBJECT-TYPE
                SYNTAX OCTET STRING (SIZE (0..254))
                MAX-ACCESS accessible-for-notify
                STATUS current
                DESCRIPTION
                     "Indicates the value of the configured object."
                ::= { hwIpDslamL2pTrapsVbOids 1 }
		
         hwIpDslamL2pTraps OBJECT IDENTIFIER ::= { hwIpDslamL2pPortConfig 5 }
		
         hwIpDslamL2pAlarmTraps OBJECT IDENTIFIER ::= { hwIpDslamL2pTraps 1 }
		
         hwIpDslamL2pCommonTraps OBJECT IDENTIFIER ::= { hwIpDslamL2pTraps 2 }
		
         hwIpDslamL2pCommonTrapsPrefix OBJECT IDENTIFIER ::= { hwIpDslamL2pCommonTraps 0 }
		
         hwIpDslamL2pSrvFlowConfigChangeTrap NOTIFICATION-TYPE
                OBJECTS  
                { 
                hwConfigChangeIP, 
                hwIpDslamL2pSrvFlowConfigIndex, 
                hwIpDslamL2pSrvFlowConfigObject,
                hwIpDslamL2pSrvFlowConfigType,
                hwIpDslamL2pSrvFlowConfigValue,
                hwIpDslamL2pSrvFlowConfigValueStr 
                }
                STATUS current
                DESCRIPTION 
                     "The SNMP trap that is generated when service port config change."
                ::= { hwIpDslamL2pCommonTrapsPrefix 1 }

    END
