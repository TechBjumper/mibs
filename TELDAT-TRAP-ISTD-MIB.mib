-- file automatically created


TELDAT-TRAP-ISTD-MIB DEFINITIONS ::= BEGIN


IMPORTS
	MODULE-IDENTITY,OBJECT-TYPE,OBJECT-IDENTITY,NOTIFICATION-TYPE,Integer32,IpAddress
		FROM SNMPv2-SMI
	DisplayString
		FROM SNMPv2-TC
	telEventTraps
		FROM TELDAT-MIB;


istdTrapsMIB MODULE-IDENTITY
    LAST-UPDATED "201401200930Z"
    ORGANIZATION "Teldat, S.A."
    CONTACT-INFO 
        "Teldat, S.A.
        Customer Service

        Postal: Parque Tecnologico de Madrid
                Tres Cantos 28760
                Madrid, SPAIN

        Tel.: +34 918 076 565

        http://www.teldat.com"
    DESCRIPTION
        "This Module Information Base file is defined for managing received
        SNMP notifications generated by the ISTD event subsystem."
    REVISION "201401200930Z"
    DESCRIPTION "Initial implementation"
        ::= { telEventTraps 212 }


istdEventsGroup	OBJECT IDENTIFIER	::= { istdTrapsMIB 1 }

istdNotifications	OBJECT IDENTIFIER	::= { istdTrapsMIB 2 }
istdNotificationsPrefix	OBJECT IDENTIFIER	::= { istdNotifications 0 }

istdEventObjects1 OBJECT-IDENTITY
    STATUS current
    DESCRIPTION
        "Event ISTD.1
        An error has been detected and reported."
    ::= { istdEventsGroup 1 }

istd1-error-message OBJECT-TYPE
    SYNTAX DisplayString
    MAX-ACCESS accessible-for-notify
    STATUS current
    DESCRIPTION
        "Parameter 'error-message' in event ISTD.1"
    ::= { istdEventObjects1 1 }

istdEventObjects2 OBJECT-IDENTITY
    STATUS current
    DESCRIPTION
        "Event ISTD.2
        Data has been received from UDP."
    ::= { istdEventsGroup 2 }

istd2-size OBJECT-TYPE
    SYNTAX Integer32
    MAX-ACCESS accessible-for-notify
    STATUS current
    DESCRIPTION
        "Parameter 'size' in event ISTD.2"
    ::= { istdEventObjects2 1 }

istdEventObjects3 OBJECT-IDENTITY
    STATUS current
    DESCRIPTION
        "Event ISTD.3
        Data has been sent to UDP."
    ::= { istdEventsGroup 3 }

istd3-size OBJECT-TYPE
    SYNTAX Integer32
    MAX-ACCESS accessible-for-notify
    STATUS current
    DESCRIPTION
        "Parameter 'size' in event ISTD.3"
    ::= { istdEventObjects3 1 }

istdEventObjects4 OBJECT-IDENTITY
    STATUS current
    DESCRIPTION
        "Event ISTD.4
        A valid protocol frame has been received from the indicated address"
    ::= { istdEventsGroup 4 }

istd4-frame-type OBJECT-TYPE
    SYNTAX DisplayString
    MAX-ACCESS accessible-for-notify
    STATUS current
    DESCRIPTION
        "Parameter 'frame-type' in event ISTD.4"
    ::= { istdEventObjects4 1 }

istd4-source-ip-address OBJECT-TYPE
    SYNTAX IpAddress
    MAX-ACCESS accessible-for-notify
    STATUS current
    DESCRIPTION
        "Parameter 'source-ip-address' in event ISTD.4"
    ::= { istdEventObjects4 2 }

istdEventObjects5 OBJECT-IDENTITY
    STATUS current
    DESCRIPTION
        "Event ISTD.5
        An unknown protocol frame has been received from the indicated address"
    ::= { istdEventsGroup 5 }

istd5-source-ip-address OBJECT-TYPE
    SYNTAX IpAddress
    MAX-ACCESS accessible-for-notify
    STATUS current
    DESCRIPTION
        "Parameter 'source-ip-address' in event ISTD.5"
    ::= { istdEventObjects5 1 }

istdEventObjects6 OBJECT-IDENTITY
    STATUS current
    DESCRIPTION
        "Event ISTD.6
        An unsupported protocol frame has been received from the indicated address"
    ::= { istdEventsGroup 6 }

istd6-frame-opcode OBJECT-TYPE
    SYNTAX Integer32
    MAX-ACCESS accessible-for-notify
    STATUS current
    DESCRIPTION
        "Parameter 'frame-opcode' in event ISTD.6"
    ::= { istdEventObjects6 1 }

istd6-source-ip-address OBJECT-TYPE
    SYNTAX IpAddress
    MAX-ACCESS accessible-for-notify
    STATUS current
    DESCRIPTION
        "Parameter 'source-ip-address' in event ISTD.6"
    ::= { istdEventObjects6 2 }

istdEventObjects7 OBJECT-IDENTITY
    STATUS current
    DESCRIPTION
        "Event ISTD.7
        A valid protocol frame has been sent"
    ::= { istdEventsGroup 7 }

istd7-frame-type OBJECT-TYPE
    SYNTAX DisplayString
    MAX-ACCESS accessible-for-notify
    STATUS current
    DESCRIPTION
        "Parameter 'frame-type' in event ISTD.7"
    ::= { istdEventObjects7 1 }

istdEventObjects10 OBJECT-IDENTITY
    STATUS current
    DESCRIPTION
        "Event ISTD.10
        Report general trace information"
    ::= { istdEventsGroup 10 }

istd10-str OBJECT-TYPE
    SYNTAX DisplayString
    MAX-ACCESS accessible-for-notify
    STATUS current
    DESCRIPTION
        "Parameter 'str' in event ISTD.10"
    ::= { istdEventObjects10 1 }


istdNotification1 NOTIFICATION-TYPE
    OBJECTS { 
              istd1-error-message 
            }
    STATUS current
    DESCRIPTION
        "Notification of Event ISTD.1

        Message: 'ERROR: $1'

        Parameters list:
              $1: istd1-error-message

        An error has been detected and reported."
    ::= { istdNotificationsPrefix 1 }

istdNotification2 NOTIFICATION-TYPE
    OBJECTS { 
              istd2-size 
            }
    STATUS current
    DESCRIPTION
        "Notification of Event ISTD.2

        Message: 'Data received from UDP. Size: $1'

        Parameters list:
              $1: istd2-size

        Data has been received from UDP."
    ::= { istdNotificationsPrefix 2 }

istdNotification3 NOTIFICATION-TYPE
    OBJECTS { 
              istd3-size 
            }
    STATUS current
    DESCRIPTION
        "Notification of Event ISTD.3

        Message: 'Data sent to UDP. Size: $1'

        Parameters list:
              $1: istd3-size

        Data has been sent to UDP."
    ::= { istdNotificationsPrefix 3 }

istdNotification4 NOTIFICATION-TYPE
    OBJECTS { 
              istd4-frame-type, 
              istd4-source-ip-address 
            }
    STATUS current
    DESCRIPTION
        "Notification of Event ISTD.4

        Message: 'Frame of type $1 received from $2'

        Parameters list:
              $1: istd4-frame-type
              $2: istd4-source-ip-address

        A valid protocol frame has been received from the indicated address"
    ::= { istdNotificationsPrefix 4 }

istdNotification5 NOTIFICATION-TYPE
    OBJECTS { 
              istd5-source-ip-address 
            }
    STATUS current
    DESCRIPTION
        "Notification of Event ISTD.5

        Message: 'Unknown frame received from $1'

        Parameters list:
              $1: istd5-source-ip-address

        An unknown protocol frame has been received from the indicated address"
    ::= { istdNotificationsPrefix 5 }

istdNotification6 NOTIFICATION-TYPE
    OBJECTS { 
              istd6-frame-opcode, 
              istd6-source-ip-address 
            }
    STATUS current
    DESCRIPTION
        "Notification of Event ISTD.6

        Message: 'Unsupported frame type $1 received from $2'

        Parameters list:
              $1: istd6-frame-opcode
              $2: istd6-source-ip-address

        An unsupported protocol frame has been received from the indicated address"
    ::= { istdNotificationsPrefix 6 }

istdNotification7 NOTIFICATION-TYPE
    OBJECTS { 
              istd7-frame-type 
            }
    STATUS current
    DESCRIPTION
        "Notification of Event ISTD.7

        Message: 'Frame of type $1 sent'

        Parameters list:
              $1: istd7-frame-type

        A valid protocol frame has been sent"
    ::= { istdNotificationsPrefix 7 }

istdNotification8 NOTIFICATION-TYPE
    STATUS current
    DESCRIPTION
        "Notification of Event ISTD.8

        Message: 'Discovery timeout'

        Supervisor has not answered to the discover frame in the timeout interval"
    ::= { istdNotificationsPrefix 8 }

istdNotification9 NOTIFICATION-TYPE
    STATUS current
    DESCRIPTION
        "Notification of Event ISTD.9

        Message: 'Supervisor timeout'

        Supervisor has not queried any data in the supervisor timeout interval.
        Supervisor Discovery process is started"
    ::= { istdNotificationsPrefix 9 }

istdNotification10 NOTIFICATION-TYPE
    OBJECTS { 
              istd10-str 
            }
    STATUS current
    DESCRIPTION
        "Notification of Event ISTD.10

        Message: '$1'

        Parameters list:
              $1: istd10-str

        Report general trace information"
    ::= { istdNotificationsPrefix 10 }


END
