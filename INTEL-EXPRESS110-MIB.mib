INTEL-EXPRESS110-MIB DEFINITIONS ::= BEGIN
-- MIB Version = V3.0

IMPORTS
Counter, IpAddress, TimeTicks, Gauge    FROM RFC1155-SMI
hub-products                            FROM Intel-Common-MIB
DisplayString, PhysAddress              FROM RFC1213-MIB
TRAP-TYPE                               FROM RFC-1215
OBJECT-TYPE                             FROM RFC-1212;

express110        OBJECT IDENTIFIER ::= { hub-products    1 }

hubNumberofStackedChassis   OBJECT-TYPE
    SYNTAX    INTEGER
    ACCESS    read-only
    STATUS    mandatory
    DESCRIPTION
          "Displays the total number of chassis in the stack. "
    ::= { express110    1 }

hubDescriptionString   OBJECT-TYPE
    SYNTAX    OCTET STRING (SIZE (5..33))
    ACCESS    read-only
    STATUS    mandatory
    DESCRIPTION
          "Bitfield used by SNMP application. "
    ::= { express110    2 }

hubStackReset   OBJECT-TYPE
    SYNTAX    INTEGER  {
                  reset(1),
                  notreset(2)
                }
    ACCESS    read-write
    STATUS    mandatory
    DESCRIPTION
          "Resets all modules in all of the chassis in the stack.  "
    ::= { express110    3 }

hubLCDModeVariable   OBJECT-TYPE
    SYNTAX    INTEGER  {
                sysName(1),
                sysLocation(2),
                sysContact(3),
                traps(4),
                utilization(5),
                ipaddress(6),
                lcdSleepText(7),
                notSupported(8)
                }
    ACCESS    read-write
    STATUS    mandatory
    DESCRIPTION
          "Sets the type of information displayed on the Management
           Module's LCD when in Sleep Mode. sysContact, sysLocation, 
           and sysName are user-definable. Traps shows the most current 
           SNMP trap message generated. Utilization shows the percentage 
           of bandwidth used in each segment in the stack. Ipaddress
           shows the currently assigned Management Module IP address.
           Sleep text shows user-definable text set with the
           hubLCDSleepText object. "
    ::= { express110    4 }

hubLCDSleepText   OBJECT-TYPE
    SYNTAX    DisplayString (SIZE (32))
    ACCESS    read-write
    STATUS    mandatory
    DESCRIPTION
          "Sets user-defined text to be displayed by the LCD when in
           Sleep Mode. For example, you may want the name and phone number 
           of a contact person to display on the LCD panel.
           This object is only applicable to 200 series stackable hubs."
    ::= { express110    5 }

hubLCDSleepTime   OBJECT-TYPE
    SYNTAX    INTEGER (0 .. 255)
    ACCESS    read-write
    STATUS    mandatory
    DESCRIPTION
          "Sets the number of minutes before the LCD goes into Sleep
           Mode. If an LCD button isn't pressed for the time 
           specified, the LCD goes into Sleep Mode and displays
           the information set by hubLCDModeVariable. To disable 
           this feature, set the time to 0.
           This object is only applicable to 200 series stackable hubs."
    ::= { express110    6 }

hubRFC1516Segment   OBJECT-TYPE
    SYNTAX    INTEGER  {
                segment1(1),
                segment2(2),
                allsegments(3)
                }
    ACCESS    read-write
    STATUS    mandatory
    DESCRIPTION
          "Sets which segment the standard repeater MIB (RFC1516)
           returns counters for. The standard repeater MIB doesn't
           support two segments at the same time."
    ::= { express110    7 }

chassisConfigTable   OBJECT-TYPE
    SYNTAX    SEQUENCE OF ChassisConfigEntry
    ACCESS    not-accessible
    STATUS    mandatory
    DESCRIPTION
          "Configuration information at the chassis level."
    ::= { express110    8 }

chassisConfigEntry   OBJECT-TYPE
    SYNTAX    ChassisConfigEntry
    ACCESS    not-accessible
    STATUS    mandatory
    DESCRIPTION
          "A table entry, containing configuration information
           about a single chassis."
    INDEX    {  chassisConfigTableIndex  }
    ::= { chassisConfigTable    1 }

ChassisConfigEntry ::=
    SEQUENCE {
        chassisConfigTableIndex
            INTEGER,
        chassisSegmentMode
            INTEGER,
        chassisReset
            INTEGER,
        chassisRPSState   
            INTEGER,
        chassisIsolate
            INTEGER
    }
    
chassisConfigTableIndex   OBJECT-TYPE
    SYNTAX    INTEGER
    ACCESS    read-only
    STATUS    mandatory
    DESCRIPTION
          "Chassis number in the stack. This object refers to the 
           number in the example below.

           Example: chassisConfigTableIndex.1 
           This example refers to chassis 1 of the stack. 
           The chassis at the top of the stack is number 1. "
    ::= { chassisConfigEntry    1 }

chassisSegmentMode   OBJECT-TYPE
    SYNTAX    INTEGER  {
                        segment1(1),
                        segment2(2),
                        auto(3),
                        mixed(4)
                       }
    ACCESS    read-write
    STATUS    mandatory
    DESCRIPTION
          "Sets/reports the repeater segment the chassis ports participate in.
           For chassis which do not support port speed autosensing, only
           'segment1' or 'segment2' can be set. For stacks with both segments
           set to the same speed, setting a chassis to 'auto' causes linked
           ports to participate in segment2. The 'mixed' value is read-only and
           indicates that ports within the chassis do not share the same
           segment mode. Setting chassis ports via this object does not prevent
           ports from being set independently."
    ::= { chassisConfigEntry    2 }

chassisReset   OBJECT-TYPE
    SYNTAX    INTEGER  {
                reset(1),
                notreset(2)
                }
    ACCESS    read-write
    STATUS    mandatory
    DESCRIPTION
          "Resets all modules in the selected chassis. "
    ::= { chassisConfigEntry    3 }

chassisRPSState   OBJECT-TYPE
    SYNTAX    INTEGER  {
                        notPresent(1),
                        standby(2),
                        active(3),
                        notSupported(4)
                       }
    ACCESS    read-only
    STATUS    mandatory
    DESCRIPTION
          "The state of the optional Redundant Power Supply connected
           to the chassis. standby means the RPS is actively backing up
           the chassis. active means the chassis power supply has failed
           and the RPS is powering the chassis. "
    ::= { chassisConfigEntry    4 }


chassisIsolate   OBJECT-TYPE
    SYNTAX    INTEGER  {
                        isolate(1),
                        unisolate(2),
                        notSupported(3)
                       }
    ACCESS    read-write
    STATUS    mandatory
    DESCRIPTION
          "The isolated or unisolates the hub from the backplane channel."
    ::= { chassisConfigEntry    5 }


moduleConfigStatusTable   OBJECT-TYPE
    SYNTAX    SEQUENCE OF ModuleConfigStatusEntry
    ACCESS    not-accessible
    STATUS    mandatory
    DESCRIPTION
          "Configuration and status information at the module level."
    ::= { express110    9 }

moduleConfigStatusEntry   OBJECT-TYPE
    SYNTAX    ModuleConfigStatusEntry
    ACCESS    not-accessible
    STATUS    mandatory
    DESCRIPTION
          "A table entry, containing configuration and status
           information about a single module."
    INDEX    {  moduleChassisIndex, moduleIndex  }
    ::= { moduleConfigStatusTable    1 }

ModuleConfigStatusEntry ::=
    SEQUENCE {
        moduleChassisIndex
            INTEGER,
        moduleIndex
            INTEGER,
        moduleType
            INTEGER,
        moduleUserAssignedType
            DisplayString,
        moduleUserAssignedNumber
            DisplayString,
        moduleUserAssignedName
            DisplayString,
        moduleSizeofROM
            INTEGER,
        moduleSizeofRAM
            INTEGER,
        moduleHWDescription
            DisplayString,
        moduleAgentSWVersion
            DisplayString,
        moduleBootSWVersion
            DisplayString,
        moduleManufacturingInfo
            DisplayString,
        moduleTotalPortCount
            INTEGER,
        moduleExternalPortCount
            INTEGER,
        moduleSegmentLockout
            INTEGER,
        moduleLEDInfo
            OCTET STRING,
        moduleLastErrorID
            INTEGER,
        moduleMediaDevicesReset
            INTEGER,
        moduleImageFileSource
            IpAddress,
        moduleImageFileName
            DisplayString,
        moduleImageDownloadControl
            INTEGER,
        moduleImageDownloadStatus
            INTEGER,
        moduleOperationalStatus
            INTEGER,
        moduleUptime
            TimeTicks,
        moduleReset
            INTEGER,
        moduleAllPortLEDInfo
            OCTET STRING,
        moduleAllPortAdminStatus
            OCTET STRING,
        moduleAllPortOperStatus
            OCTET STRING,
        moduleAllPortSpeed
            OCTET STRING,
        moduleAllPortSpeedInfo
            OCTET STRING,
        moduleSegmentMode
            INTEGER,
        moduleAllPortLinkPartnerInfo
            OCTET STRING,
        moduleAllPortCounterReset
            INTEGER,
        moduleAllPortTimeSinceLinkChange
            OCTET STRING,
        modulePersistentMemoryReset
            INTEGER
    }
    
moduleChassisIndex   OBJECT-TYPE
    SYNTAX    INTEGER
    ACCESS    read-only
    STATUS    mandatory
    DESCRIPTION
          "Chassis number in the stack. This object refers to the first
           number in the example below.

           Example: moduleChassisIndex.1.1
           The first number is the chassis (hub) and the second number is the
           module in the chassis. This example refers to module 1 in hub 1
           (which is the hub at the top of the stack). Base ports on the hub
           are always module 1. 
           The left expansion slot (when facing the hub) is module 2 and the
           right expansion slot is module 3.  "
    ::= { moduleConfigStatusEntry    1 }

moduleIndex   OBJECT-TYPE
    SYNTAX    INTEGER
    ACCESS    read-only
    STATUS    mandatory
    DESCRIPTION
          "Module number in the chassis. This object refers to the second
           number in the example below.

           Example: moduleChassisIndex.1.1
           The first number is the chassis (hub) and the second number is the
           module in the chassis. This example refers to module 1 in hub 1
           (which is the hub at the top of the stack). Base ports on the hub
           are always module 1. 
           The left expansion slot (when facing the hub) is module 2 and the 
           right expansion slot is module 3. "
    ::= { moduleConfigStatusEntry    2 }

moduleType   OBJECT-TYPE
    SYNTAX    INTEGER  {
                none(1),
                hubTXports12(2),
                hubTXports24(3),
                reserved4(4),
                management(5),
                bridge(6),
                managementWithRMON(7),
                reserved8(8),
                hubcrTXports12(9),
                hubcrTXports24(10),
                hubppTXports12(11),
                hubppTXports24(12),
                express330TXports16(13),
                express330TXports24(14),
                fxUplink(15),
                txUplink(16)
                }
    ACCESS    read-only
    STATUS    mandatory
    DESCRIPTION
          "The module type. The base ports of a 12- or
           24-port hub are considered modules. For example,
           hubTXports12 are ports 1-12 on a 12-port hub.
           bridge is an externally inserted bridge and refers to
           the Ethernet Module or the Fiber Module. management
           is the Management Module (also called the SNMP agent).
           None means no module is installed. "
    ::= { moduleConfigStatusEntry    3 }

moduleUserAssignedType   OBJECT-TYPE
    SYNTAX    DisplayString (SIZE (24))
    ACCESS    read-write
    STATUS    mandatory
    DESCRIPTION
          "User-definable information about the type of the module.
           Manufacturer assigns a default value. "
    ::= { moduleConfigStatusEntry    4 }

moduleUserAssignedNumber   OBJECT-TYPE
    SYNTAX    DisplayString (SIZE (24))
    ACCESS    read-write
    STATUS    mandatory
    DESCRIPTION
          "User-definable information about the module.
           Blank by default. "
    ::= { moduleConfigStatusEntry    5 }

moduleUserAssignedName   OBJECT-TYPE
    SYNTAX    DisplayString (SIZE (24))
    ACCESS    read-write
    STATUS    mandatory
    DESCRIPTION
          "User-definable information about the module.
           Blank by default. "
    ::= { moduleConfigStatusEntry    6 }

moduleSizeofROM   OBJECT-TYPE
    SYNTAX    INTEGER
    ACCESS    read-only
    STATUS    mandatory
    DESCRIPTION
          "Displays the module's ROM size.  "
    ::= { moduleConfigStatusEntry    7 }

moduleSizeofRAM   OBJECT-TYPE
    SYNTAX    INTEGER
    ACCESS    read-only
    STATUS    mandatory
    DESCRIPTION
          "Displays the module's RAM size.  "
    ::= { moduleConfigStatusEntry    8 }

moduleHWDescription   OBJECT-TYPE
    SYNTAX    DisplayString (SIZE (24))
    ACCESS    read-only
    STATUS    mandatory
    DESCRIPTION
          "Displays the CPU type and flash capacity.  "
    ::= { moduleConfigStatusEntry    9 }

moduleAgentSWVersion   OBJECT-TYPE
    SYNTAX    DisplayString (SIZE (24))
    ACCESS    read-only
    STATUS    mandatory
    DESCRIPTION
          "Displays the module's agent software version.  Each module has
           software which contributes to the SNMP agent's functionality.
           The Management Module version is the SNMP agent's version."
    ::= { moduleConfigStatusEntry    10 }

moduleBootSWVersion   OBJECT-TYPE
    SYNTAX    DisplayString (SIZE (24))
    ACCESS    read-only
    STATUS    mandatory
    DESCRIPTION
          "Displays the module's boot software version.  "
    ::= { moduleConfigStatusEntry    11 }

moduleManufacturingInfo   OBJECT-TYPE
    SYNTAX    DisplayString (SIZE (24))
    ACCESS    read-only
    STATUS    mandatory
    DESCRIPTION
          "Displays the manufacturer-assigned hardware description. "
    ::= { moduleConfigStatusEntry    12 }

moduleTotalPortCount   OBJECT-TYPE
    SYNTAX    INTEGER
    ACCESS    read-only
    STATUS    mandatory
    DESCRIPTION
          "Displays the total number of ports in the module. This
           can be:
           14 = a 12-port hub 
                (12 base ports plus 2 expansion modules)
           16 = a 12-port hub with an internal bridge
                (14, as described for a 12-port hub,
                plus 2 internal bridge ports)
           24 = a 24-port hub 
           26 = a 24-port hub with an internal bridge
           1 or 2 for an expansion module (module dependent). "
    ::= { moduleConfigStatusEntry    13 }

moduleExternalPortCount   OBJECT-TYPE
    SYNTAX    INTEGER
    ACCESS    read-only
    STATUS    mandatory
    DESCRIPTION
          "Number of external ports in the module.  "
    ::= { moduleConfigStatusEntry    14 }

moduleSegmentLockout   OBJECT-TYPE
    SYNTAX    INTEGER  {
                yButtonyMgmt(1),
                nButtonyMgmt(2),
                yButtonnMgmt(3),
                nButtonnMgmt(4)
                }
    ACCESS    read-write
    STATUS    mandatory
    DESCRIPTION
          "Prevents the hub speed from being changed by either
           a management station and/or the Change speed button
           on the front of a hub. 
           Only nButtonnMgmt is valid for expansion modules.
           Only nButtonnMgmt or nButtonyMgmt is valid for hubs which
           do not have speed change buttons."
    ::= { moduleConfigStatusEntry    15 }

moduleLEDInfo   OBJECT-TYPE
    SYNTAX    OCTET STRING (SIZE (4))
    ACCESS    read-only
    STATUS    mandatory
    DESCRIPTION
          "Bitfield used by SNMP application. "
    ::= { moduleConfigStatusEntry    16 }

moduleLastErrorID   OBJECT-TYPE
    SYNTAX    INTEGER  
    ACCESS    read-write
    STATUS    mandatory
    DESCRIPTION
          "Bitfield used by SNMP application. "
    ::= { moduleConfigStatusEntry    17 }

moduleMediaDevicesReset   OBJECT-TYPE
    SYNTAX    INTEGER  {
                reset(1),
                notreset(2),
                notSupported(3)
                }
    ACCESS    read-write
    STATUS    mandatory
    DESCRIPTION
          "Performs a physical layer reset of the module. Use this
           reset if ports lock-up on an individual hub. "
    ::= { moduleConfigStatusEntry    18 }

moduleImageFileSource   OBJECT-TYPE
    SYNTAX    IpAddress
    ACCESS    read-write
    STATUS    mandatory
    DESCRIPTION
          "Sets the IP address of the device that transfers the
           image file to the module. The image filename is 
           specified by the moduleImageFileName object. The
           moduleImageDownloadControl object starts and stops
           the download process. "
    ::= { moduleConfigStatusEntry    19 }

moduleImageFileName   OBJECT-TYPE
    SYNTAX    DisplayString (SIZE (128))
    ACCESS    read-write
    STATUS    mandatory
    DESCRIPTION
          "Sets the image filename contained on the device 
           specified by the moduleImageFileSource object. 
           The moduleImageDownloadControl object starts 
           and stops the download process to the module.
           e300agentImageUpdateCtrl must be set to enabled
           before starting the download process."
    ::= { moduleConfigStatusEntry    20 }

moduleImageDownloadControl   OBJECT-TYPE
    SYNTAX    INTEGER  {
                start(1),
                stop(2),
                notSupported(3)
                }
    ACCESS    read-write
    STATUS    mandatory
    DESCRIPTION
          "Starts and stops the image file download process to
           the module. Use the moduleImageFileSource to set the 
           IP address of the device that contains image file. 
           Use the moduleImageFileName object to set the image filename.  "
    ::= { moduleConfigStatusEntry    21 }

moduleImageDownloadStatus   OBJECT-TYPE
    SYNTAX    INTEGER  {
                started(1),
                stopping(2),
                completed(3),
                error(4),
                notSupported(5)
                }
    ACCESS    read-only
    STATUS    mandatory
    DESCRIPTION
          "Displays the Management Module's image file download status.
           If error appears, use the moduleImageFileSource, moduleImageFileName, 
           and moduleImageDownloadControl objects to configure and download
           the image file to the module.  Do not reset the module until the
           status has changed to completed. "
    ::= { moduleConfigStatusEntry    22 }

moduleOperationalStatus   OBJECT-TYPE
    SYNTAX    INTEGER  {
                operational(1),
                notoperational(2),
                notpresent(3)
                }
    ACCESS    read-only
    STATUS    mandatory
    DESCRIPTION
          "Current operational state of the module.  "
    ::= { moduleConfigStatusEntry    23 }

moduleUptime   OBJECT-TYPE
    SYNTAX    TimeTicks
    ACCESS    read-only
    STATUS    mandatory
    DESCRIPTION
          "Time since the module was last reset.  "
    ::= { moduleConfigStatusEntry    24 }

moduleReset   OBJECT-TYPE
    SYNTAX    INTEGER  {
                reset(1),
                notreset(2),
                notSupported(3)
                }
    ACCESS    read-write
    STATUS    mandatory
    DESCRIPTION
          "Resets the module. "
    ::= { moduleConfigStatusEntry    25 }

moduleAllPortLEDInfo   OBJECT-TYPE
    SYNTAX    OCTET STRING
    ACCESS    read-only
    STATUS    mandatory
    DESCRIPTION
          "Bitfield used by SNMP application. "
    ::= { moduleConfigStatusEntry    26 }

moduleAllPortAdminStatus   OBJECT-TYPE
    SYNTAX    OCTET STRING
    ACCESS    read-write
    STATUS    mandatory
    DESCRIPTION
          "Bitfield used by SNMP application. "
    ::= { moduleConfigStatusEntry    27 }

moduleAllPortOperStatus   OBJECT-TYPE
    SYNTAX    OCTET STRING
    ACCESS    read-only
    STATUS    mandatory
    DESCRIPTION
          "Bitfield used by SNMP application. "
    ::= { moduleConfigStatusEntry    28 }

moduleAllPortSpeed   OBJECT-TYPE
    SYNTAX    OCTET STRING
    ACCESS    read-only
    STATUS    mandatory
    DESCRIPTION
          "Bitfield used by SNMP application. "
    ::= { moduleConfigStatusEntry    29 }

moduleAllPortSpeedInfo   OBJECT-TYPE
    SYNTAX    OCTET STRING
    ACCESS    read-only
    STATUS    mandatory
    DESCRIPTION
          "Bitfield used by SNMP application. "
    ::= { moduleConfigStatusEntry    30 }

moduleSegmentMode   OBJECT-TYPE
    SYNTAX    INTEGER  {
                        segment1(1),
                        segment2(2),
                        auto(3),
                        mixed(4)
                       }
    ACCESS    read-write
    STATUS    mandatory
    DESCRIPTION
          "Sets/reports the repeater segment the module ports participate in.
           For modules which do not support automatic port speed selection,
           only 'segment1' or 'segment2' may be set. 
           The 'mixed' value is read-only and indicates that ports
           within the module do not share the same segment mode.
           Setting module ports via this object does not prevent ports
           from being set independently."
    ::= { moduleConfigStatusEntry    31 }

moduleAllPortLinkPartnerInfo   OBJECT-TYPE
    SYNTAX    OCTET STRING
    ACCESS    read-only
    STATUS    mandatory
    DESCRIPTION
          "Bitfield used by SNMP application. "
    ::= { moduleConfigStatusEntry    32 }

moduleAllPortCounterReset   OBJECT-TYPE
    SYNTAX    INTEGER  {
                reset(1),
                notreset(2)
                }
    ACCESS    read-write
    STATUS    mandatory
    DESCRIPTION
          "Resets all the port counters in the module to zero. This includes 
           all traffic statistics (packet count, etc.) and error counts. "
    ::= { moduleConfigStatusEntry    33 }

moduleAllPortTimeSinceLinkChange   OBJECT-TYPE
    SYNTAX    OCTET STRING
    ACCESS    read-only
    STATUS    mandatory
    DESCRIPTION
          "Bitfield used by SNMP application. "
    ::= { moduleConfigStatusEntry    34 }

modulePersistentMemoryReset   OBJECT-TYPE
    SYNTAX    INTEGER  {
                reset(1),
                notreset(2),
                notSupported(3)
                }
    ACCESS    read-write
    STATUS    mandatory
    DESCRIPTION
          "Reset contents of persistent memory objects to factory
           defaults. Persistent memory object are settings that are
           saved even after the module is reset or power-cycled.  "
    ::= { moduleConfigStatusEntry    35 }

portConfigTable   OBJECT-TYPE
    SYNTAX    SEQUENCE OF PortConfigEntry
    ACCESS    not-accessible
    STATUS    mandatory
    DESCRIPTION
          "Configuration information at the Port level."
    ::= { express110    10 }

portConfigEntry   OBJECT-TYPE
    SYNTAX    PortConfigEntry
    ACCESS    not-accessible
    STATUS    mandatory
    DESCRIPTION
          "A table entry, containing configuration information
           about a single port."
    INDEX    { portChassisIndex,
               portModuleIndex,
               portIndex  }
    ::= { portConfigTable    1 }

PortConfigEntry ::=
    SEQUENCE {
        portChassisIndex
            INTEGER,
        portModuleIndex
            INTEGER,
        portIndex
            INTEGER,
        portType
            INTEGER,
        portAdminStatus
            INTEGER,
        portOperStatus
            INTEGER,
        portJabber
            INTEGER,
        portLinkPartnerInfo
            OCTET STRING,
        portLEDInfo
            OCTET STRING,
        portTimeSinceLastLinkChange
            TimeTicks,
        portAllCountersReset
            INTEGER,
        portReset
            INTEGER,
        portLastErrorID
            INTEGER,
        portSegmentAdminMode   
            INTEGER, 
        portSegmentOperStatus   
            INTEGER,  
        portLinkSpeed
            INTEGER,
        portSecureAdminMode
            INTEGER,
        portSecureMAC
            OCTET STRING,
        portLinkTestState
            INTEGER,
        portLinkTestStatusTrapCtrl
            INTEGER,
        portSpeedStatusTrapCtrl
            INTEGER,
        portPolarityStatus
            INTEGER
    }
portChassisIndex   OBJECT-TYPE
    SYNTAX    INTEGER
    ACCESS    read-only
    STATUS    mandatory
    DESCRIPTION
          "Chassis number in stack. This object refers to the first
           number in the example below.

           Example: portChassisIndex.1.1.9
           The first number is the chassis. The second number is the module 
           in the chassis. The third number is the port in the module. This 
           example refers to port 9 in module 1 in hub 1 (which is the hub at the 
           top of the stack). Base ports on the hub are always module 1. The 
           left expansion slot (when facing the hub) is module 2 and the right 
           expansion slot is module 3. "

    ::= { portConfigEntry    1 }

portModuleIndex   OBJECT-TYPE
    SYNTAX    INTEGER
    ACCESS    read-only
    STATUS    mandatory
    DESCRIPTION
          "Module number in the chassis. This object refers to the second
           number in the example below.

           Example: portModuleIndex.1.1.9
           The first number is the chassis. The second number is the module 
           in the chassis. The third number is the port in the module. This 
           example refers to port 9 in module 1 in hub 1 (which is the hub at 
           the top of the stack). Base ports on the hub are always module 1. 
           The left expansion slot (when facing the hub) is module 2 and the
           right expansion slot is module 3. "
    ::= { portConfigEntry    2 }

portIndex   OBJECT-TYPE
    SYNTAX    INTEGER
    ACCESS    read-only
    STATUS    mandatory
    DESCRIPTION
          "Port number in the module. This object refers to the third
           number in the example below.

           Example: portChassisIndex 1.1.9
           The first number is the chassis. The second number is the module 
           in the chassis. The third number is the port in the module. This 
           example refers to port 9 in module 1 in hub 1 (which is the hub at 
           the top of the stack). Base ports on the hub are always module 1. 
           The left expansion slot (when facing the hub) is module 2 and the 
           right expansion slot is module 3. "
    ::= { portConfigEntry    3 }

portType   OBJECT-TYPE
    SYNTAX    INTEGER  {
                twistedPairHalfDuplex(1),
                twistedPairFullDuplex(2),
                fiberMultimode(3),
                fiberSinglemode(4),
                internalHalfDuplex(5)
                }
    ACCESS    read-only
    STATUS    mandatory
    DESCRIPTION
          "Displays the selected port's capabilities. internalHalfDuplex
           is the expansion module's internal connection to a port in the hub."
    ::= { portConfigEntry    4 }

portAdminStatus   OBJECT-TYPE
    SYNTAX    INTEGER  {
                enable(1),
                disable(2)
                }
    ACCESS    read-write
    STATUS    mandatory
    DESCRIPTION
          "Enables or disables the selected port. Disabled ports
           will not be able to establish a link to a device.
           Disabled ports remain disabled until re-enabled."
    ::= { portConfigEntry    5 }

portOperStatus   OBJECT-TYPE
    SYNTAX    INTEGER  {
                operational(1),
                notoperational(2),
                notpresent(3),
                violated(4)
                }
    ACCESS    read-only
    STATUS    mandatory
    DESCRIPTION
          "Displays the current link status of the port. 
           Operational means a port has established a link to a device. 
           Notoperational means the port does not have a link established. 
               It does not mean there is a problem with the port. 
           Notpresent may mean that an Intel Cascade Cable was removed from 
               a hub or that the cable is faulty.
           Violated means that this port was disabled by a security violation.
               Port security is enabled/disabled with the portSecureAdminMode
               object.  A violated port can be re-enabled with the
               portAdminStatus object."
    ::= { portConfigEntry    6 }

portJabber   OBJECT-TYPE
    SYNTAX    INTEGER  {
                ok(1),
                failure(2)
                }
    ACCESS    read-only
    STATUS    mandatory
    DESCRIPTION
          "Jabber state of the port. Failure means the device attached to
           the port caused the hub's jabber lock-up protection to turn on. 
           Check the device attached to the port. "
    ::= { portConfigEntry    7 }

portLinkPartnerInfo   OBJECT-TYPE
    SYNTAX    OCTET STRING (SIZE (2))
    ACCESS    read-only
    STATUS    mandatory
    DESCRIPTION
          "Bitfield used by SNMP application. "
    ::= { portConfigEntry    8 }

portLEDInfo   OBJECT-TYPE
    SYNTAX    OCTET STRING (SIZE (1))
    ACCESS    read-only
    STATUS    mandatory
    DESCRIPTION
          "Bitfield used by SNMP application. "
    ::= { portConfigEntry    9 }

portTimeSinceLastLinkChange   OBJECT-TYPE
    SYNTAX    TimeTicks
    ACCESS    read-only
    STATUS    mandatory
    DESCRIPTION
          "Time since the last link status change. "
    ::= { portConfigEntry    10 }

portAllCountersReset   OBJECT-TYPE
    SYNTAX    INTEGER  {
                reset(1),
                notreset(2)
                }
    ACCESS    read-write
    STATUS    mandatory
    DESCRIPTION
          "Resets all counters for ports to zero. This includes all 
           traffic statistics (packet count, etc.) and error counts. "
    ::= { portConfigEntry    11 }

portReset   OBJECT-TYPE
    SYNTAX    INTEGER  {
                reset(1),
                notreset(2),
                notSupported(3)
                }
    ACCESS    read-write
    STATUS    mandatory
    DESCRIPTION
          "Reset the port at the media level.  "
    ::= { portConfigEntry    12 }

portLastErrorID   OBJECT-TYPE
    SYNTAX    INTEGER  {
                noError(1),
                badPhy(2),
                polarity(3),
                wrongSpeedLP(4),
                jabberSeen(5),
                partition(6),
                reserved1(7),
                reserved2(8)
                }
    ACCESS    read-only
    STATUS    mandatory
    DESCRIPTION
          "Type of last error that occurred on the port since the last
           link status change. badPhy is a hardware problem with the hub
           port. polarity means there's a cabling problem between the hub
           and the attached device. wrongSpeedLP means the device attached
           to the port is operating at the wrong speed. jabberSeen means
           you may have a faulty device attached to the port. partition
           means the port was automatically partitioned at least once. "
    ::= { portConfigEntry    13 }

portSegmentAdminMode   OBJECT-TYPE
    SYNTAX    INTEGER  {
                        segment1(1),
                        segment2(2),
                        auto(3)
                       }
    ACCESS    read-write
    STATUS    mandatory
    DESCRIPTION
          "For ports that have the ability to be set independent of
           the hub or module they reside in, this object allows setting the
           port to 'segment1', 'segment2', or 'auto'."
    ::= { portConfigEntry    14 }

portSegmentOperStatus   OBJECT-TYPE
    SYNTAX    INTEGER  {
                        segment1(1),
                        segment2(2),
                        none(3)
                       }
    ACCESS    read-only
    STATUS    mandatory
    DESCRIPTION
          "Reports the port's segment assignment.  
          'none' indicates the port has a portSegmentAdminMode of 'auto' 
           and has not negotiated a link speed setting with a device."
    ::= { portConfigEntry    15 }

portLinkSpeed   OBJECT-TYPE
    SYNTAX    INTEGER  {
                        none(1),
                        mb10(2),
                        mb100(3)
                       }
    ACCESS    read-only
    STATUS    mandatory
    DESCRIPTION
          "The operational speed of this port when linked.  Ports which do not
           have a link report 'none'."
    ::= { portConfigEntry    16 }

portSecureAdminMode   OBJECT-TYPE
    SYNTAX    INTEGER  {
                        portSecurityOff(1),
                        portSecurityOn(2)
                       }
    ACCESS    read-write
    STATUS    mandatory
    DESCRIPTION
          "Causes a port to be administratively disabled if an 
           un-authorized MAC address is detected as having transmitted 
           a frame into this hub port.  A trap is also generated when
           an unauthorized source MAC address is detected.

           An unauthorized source MAC addresss is defined as follows:

           If a portSecureMAC is specified, any frame received from
           this port which does not originate from the specified 
           portSecureMAC is unauthorized.

           If no portSecureMAC is specified, the first source MAC address
           detected on this port is the authorized MAC.  Any frame 
           originating on this port with a different MAC address from 
           the first MAC address detected is unauthorized.
           
           Older Management modules (those which do not support RMON) will not
           allow enabling of port security due to hardware limitations."
    ::= { portConfigEntry    17 }

portSecureMAC   OBJECT-TYPE
    SYNTAX    OCTET STRING (SIZE (6))
    ACCESS    read-write
    STATUS    mandatory
    DESCRIPTION
          "Specifies the authorized MAC address for this port if
          portSecureAdminMode is set to portSecurityOn."  
    ::= { portConfigEntry    18 }

portLinkTestState   OBJECT-TYPE
    SYNTAX  INTEGER     {
            enable(1),
            disable(2),
            notSupported(3)
                        }
    ACCESS  read-write
    STATUS  mandatory
    DESCRIPTION
    "The current setting of link test function for the port. When disable,
    a port will no longer be disconnected due to link fail. When enable,
    the port will only remain connected to the network so long as link pulses
    are being received."
    ::= { portConfigEntry 19 }

portLinkTestStatusTrapCtrl OBJECT-TYPE
    SYNTAX  INTEGER {
            enable(1),
            disable(2),
            notSupported(3)
    }
    ACCESS  read-write
    STATUS  mandatory
    DESCRIPTION
    "This object indicates whether a trap should be generated
    when the link state changes."
    ::= { portConfigEntry 20 }

portSpeedStatusTrapCtrl OBJECT-TYPE
    SYNTAX  INTEGER {
            enable(1),
            disable(2),
            notSupported(3)
    }
    ACCESS  read-write
    STATUS  mandatory
    DESCRIPTION
    "This object indicates whether a trap should be generated
    when the speed status changes."
    ::= { portConfigEntry 21 }


portPolarityStatus OBJECT-TYPE
    SYNTAX  INTEGER {
            normal(1),
            reversed(2),
            unknown(3)
    }
    ACCESS  read-only
    STATUS  mandatory
    DESCRIPTION
    "The current polarity status of this port."
    ::= { portConfigEntry 22 }


rptrSegmentConfigTable   OBJECT-TYPE
    SYNTAX    SEQUENCE OF RptrSegmentConfigEntry
    ACCESS    not-accessible
    STATUS    mandatory
    DESCRIPTION
          "Repeater configuration information at the segment level. "
    ::= { express110    11 }

rptrSegmentConfigEntry   OBJECT-TYPE
    SYNTAX    RptrSegmentConfigEntry
    ACCESS    not-accessible
    STATUS    mandatory
    DESCRIPTION
          "A table entry, containing repeater configuration information
           about a single segment. "
    INDEX    {  rptrSegmentConfigIndex  }
        ::= { rptrSegmentConfigTable    1 }

RptrSegmentConfigEntry ::=
    SEQUENCE {
        rptrSegmentConfigIndex
            INTEGER,
        rptrSegmentOperationalStatus
            INTEGER,
        rptrSegmentZeroCounters
            INTEGER,
        rptrSegmentReset
            INTEGER,
        rptrSegmentResetMedia
            INTEGER,
        rptrSegmentPartitionThreshold
            INTEGER,
        rptrSegmentNonDisruptTest
            INTEGER,
        rptrSegmentUtilizationTrapThreshold
            Gauge,
        rptrSegmentCollisionTrapThreshold
            Counter,
        rptrSegmentUtilizationTrapPeriod
            INTEGER,
        rptrSegmentCollisionTrapPeriod
            INTEGER,
        rptrSegmentSpeed
            INTEGER
    }
    
rptrSegmentConfigIndex   OBJECT-TYPE
    SYNTAX    INTEGER  {
                        segment1(1),
                        segment2(2)
                       }
    ACCESS    read-only
    STATUS    mandatory
    DESCRIPTION
          "Index into this table is rptrSegmentConfigIndex. Any
           configuration changes apply to all repeater ports
           participating in the segment.

           If a stack does not have any ports at the selected speed, 
           the OperationalStatus of this segment will be NotPresent."
    ::= { rptrSegmentConfigEntry    1 }

rptrSegmentOperationalStatus   OBJECT-TYPE
    SYNTAX    INTEGER  {
                other(1),
                ok(2),
                rptrFailure(3),
                groupFailure(4),
                portFailure(5),
                generalFailure(6),
                holdInReset(7)
                }
    ACCESS    read-only
    STATUS    mandatory
    DESCRIPTION
          "Displays the operational status of the segment. "
    ::= { rptrSegmentConfigEntry    2 }

rptrSegmentZeroCounters   OBJECT-TYPE
    SYNTAX    INTEGER  {
                reset(1),
                notreset(2)
                }
    ACCESS    read-write
    STATUS    mandatory
    DESCRIPTION
          "Resets all repeater per-port counters of the repeater modules 
           in the segment. The read value is always notreset.  "
    ::= { rptrSegmentConfigEntry    3 }

rptrSegmentReset   OBJECT-TYPE
    SYNTAX    INTEGER  {
                reset(1),
                notreset(2),
                notSupported(3)
                }
    ACCESS    read-write
    STATUS    mandatory
    DESCRIPTION
          "Performs a cold-reset of all repeater modules in the segment.
          
           (RFC2108 rptrInfoReset) "
    ::= { rptrSegmentConfigEntry    4 }

rptrSegmentResetMedia   OBJECT-TYPE
    SYNTAX    INTEGER  {
                reset(1),
                notreset(2),
                notSupported(3)
                }
    ACCESS    read-write
    STATUS    mandatory
    DESCRIPTION
          "Performs a media layer reset of all repeater modules in the segment. "
    ::= { rptrSegmentConfigEntry    5 }

rptrSegmentPartitionThreshold   OBJECT-TYPE
    SYNTAX    INTEGER  {
                collisions64(1),
                collisions128(2),
                collisions32(3)
                }
    ACCESS    read-write
    STATUS    mandatory
    DESCRIPTION
          "The number of consecutive collisions that will cause
           a port to autopartition. Note that this sets the value 
           for all repeaters in the segment.  "
    ::= { rptrSegmentConfigEntry    6 }

rptrSegmentNonDisruptTest   OBJECT-TYPE
    SYNTAX    INTEGER  {
                noSelfTest(1),
                selfTest(2),
                notSupported(3)
                }
    ACCESS    read-write
    STATUS    mandatory
    DESCRIPTION
          "Performs a self-test of all repeater modules in the segment. "
    ::= { rptrSegmentConfigEntry    7 }

rptrSegmentUtilizationTrapThreshold   OBJECT-TYPE
    SYNTAX    Gauge
    ACCESS    read-write
    STATUS    mandatory
    DESCRIPTION
          "If the utilization rate exceeds this value, a trap is sent.
           Use 0 to disable. This trap is based on the utilization
           rate over the last rptrSegmentUtilizationTrapPeriod.  "
    ::= { rptrSegmentConfigEntry    8 }

rptrSegmentCollisionTrapThreshold   OBJECT-TYPE
    SYNTAX    Counter
    ACCESS    read-write
    STATUS    mandatory
    DESCRIPTION
          "If the number of collisions exceeds this value, a trap
           is sent. Use 0 to disable.  This trap is based on the
           number of collision in the last rptrSegmentCollisionTrapPeriod.  "
    ::= { rptrSegmentConfigEntry    9 }

rptrSegmentUtilizationTrapPeriod   OBJECT-TYPE
    SYNTAX    INTEGER (0..60)
    ACCESS    read-write
    STATUS    mandatory
    DESCRIPTION
          "Time period (in minutes) that segment utilization must
           exceed the trap threshold value to generate a trap."
    ::= { rptrSegmentConfigEntry    10 }

rptrSegmentCollisionTrapPeriod   OBJECT-TYPE
    SYNTAX    INTEGER (0..60)
    ACCESS    read-write
    STATUS    mandatory
    DESCRIPTION
          "Time period (in minutes) that segment collisions must
           exceed the trap threshold value to generate a trap."
    ::= { rptrSegmentConfigEntry    11 }

rptrSegmentSpeed   OBJECT-TYPE
    SYNTAX    INTEGER {
                        mb10(1),
                        mb100(2)
                      }
    ACCESS    read-only
    STATUS    mandatory
    DESCRIPTION
          "The speed of the ports within the segment."
    ::= { rptrSegmentConfigEntry    12 }


rptrSegmentStatTable   OBJECT-TYPE
    SYNTAX    SEQUENCE OF RptrSegmentStatEntry
    ACCESS    not-accessible
    STATUS    mandatory
    DESCRIPTION
          "Repeater status information at the segment level. "
    ::= { express110    12 }

rptrSegmentStatEntry   OBJECT-TYPE
    SYNTAX    RptrSegmentStatEntry
    ACCESS    not-accessible
    STATUS    mandatory
    DESCRIPTION
          "A table entry, containing repeater status information
           about a single repeater. "
    INDEX    {  rptrSegmentStatIndex  }
        ::= { rptrSegmentStatTable    1 }

RptrSegmentStatEntry ::=
    SEQUENCE {
        rptrSegmentStatIndex
            INTEGER,
        rptrSegmentTotalFrames
            Counter,
        rptrSegmentTotalOctets
            Counter,
        rptrSegmentTotalErrors
            Counter,
        rptrSegmentTotalCollisions
            Counter,
        rptrSegmentPartitionedPorts
            Gauge,
        rptrSegmentHealthText
            DisplayString,
        rptrSegmentUtilization
            Gauge
    }
    
rptrSegmentStatIndex   OBJECT-TYPE
    SYNTAX    INTEGER  {
                 segment1(1),
                 segment2(2)
                 }
    ACCESS    read-only
    STATUS    mandatory
    DESCRIPTION
          "Selects the 10Mbps or 100Mbps segment.  "
    ::= { rptrSegmentStatEntry    1 }

rptrSegmentTotalFrames   OBJECT-TYPE
    SYNTAX    Counter
    ACCESS    read-only
    STATUS    mandatory
    DESCRIPTION
          "The number of frames detected without errors. Includes unicast, 
           broadcast, and multicast frames. Does not include frames received 
           with frames too long, runt, FCS, or alignment errors.

           (RFC2108 rptrMonitorGroupTotalFrames for all groups in
           this segment.) "
    ::= { rptrSegmentStatEntry    2 }

rptrSegmentTotalOctets   OBJECT-TYPE
    SYNTAX    Counter
    ACCESS    read-only
    STATUS    mandatory
    DESCRIPTION
          "The number of octets (bytes) contained in frames received that had no
           errors. This includes octets in unicast, broadcast, and multicast 
           frames. 
           It also includes octets after the start frame delimiter up to FCS but
           not including FCS octets.

           (RFC2108 rptrMonitorGroupTotalOctets for all groups in this segment.)"
    ::= { rptrSegmentStatEntry    3 }

rptrSegmentTotalErrors   OBJECT-TYPE
    SYNTAX    Counter
    ACCESS    read-only
    STATUS    mandatory
    DESCRIPTION
          "The total number of errors detected. Total errors include FCS errors,
           alignment errors, frame too long, short events, late events, very 
           long event, and rate mismatch errors.

           (RFC2108 rptrMonitorGroupTotalErrors for all groups in this segment.)"
    ::= { rptrSegmentStatEntry    4 }

rptrSegmentTotalCollisions   OBJECT-TYPE
    SYNTAX    Counter
    ACCESS    read-only
    STATUS    mandatory
    DESCRIPTION
          "Sum of all collisions in this segment.
          
           (RFC2108 rptrMonTxCollisions) "
    ::= { rptrSegmentStatEntry    5 }

rptrSegmentPartitionedPorts   OBJECT-TYPE
    SYNTAX    Gauge
    ACCESS    read-only
    STATUS    mandatory
    DESCRIPTION
          "Total number of present and enabled, but autopartitioned ports.
          
           (RFC2108 rptrInfoPartitionedPorts) "
    ::= { rptrSegmentStatEntry    6 }

rptrSegmentHealthText   OBJECT-TYPE
    SYNTAX    DisplayString
    ACCESS    read-only
    STATUS    mandatory
    DESCRIPTION
          "Description of current health of all repeaters in the segment.
         
           (RFC2108 rptrHealthText) "
    ::= { rptrSegmentStatEntry    7 }

rptrSegmentUtilization   OBJECT-TYPE
    SYNTAX    Gauge
    ACCESS    read-only
    STATUS    mandatory
    DESCRIPTION
          "The utilization rate over the last one second."
    ::= { rptrSegmentStatEntry    8 }

rptrModuleStatTable   OBJECT-TYPE
    SYNTAX    SEQUENCE OF RptrModuleStatEntry
    ACCESS    not-accessible
    STATUS    mandatory
    DESCRIPTION
          "***** Deprecated and replaced by rptrChassisSegmentStatTable *****
           
           Repeater status information at the Module level. "
    ::= { express110    13 }

rptrModuleStatEntry   OBJECT-TYPE
    SYNTAX    RptrModuleStatEntry
    ACCESS    not-accessible
    STATUS    mandatory
    DESCRIPTION
          "***** Deprecated and replaced by rptrChassisSegmentStatEntry *****
           
           A table entry, containing repeater status information
           about a single module. "
    INDEX    {  rptrModuleIndex  }
        ::= { rptrModuleStatTable    1 }

RptrModuleStatEntry ::=
    SEQUENCE {
        rptrModuleIndex
            INTEGER,
        rptrModuleTotalFrames
            Counter,
        rptrModuleTotalOctets
            Counter,
        rptrModuleTotalErrors
            Counter,
        rptrModuleFCSErrors
            Counter,
        rptrModuleAlignmentErrors
            Counter,
        rptrModuleFrameTooLongs
            Counter,
        rptrModuleShortEvents
            Counter,
        rptrModuleRunts
            Counter,
        rptrModuleCollisions
            Counter,
        rptrModuleLateEvents
            Counter,
        rptrModuleVeryLongEvents
            Counter,
        rptrModuleDataRateMismatches
            Counter,
        rptrModuleAutoPartitions
            Counter
    }
    
rptrModuleIndex   OBJECT-TYPE
    SYNTAX    INTEGER
    ACCESS    read-only
    STATUS    mandatory
    DESCRIPTION
          "***** Deprecated and replaced by rptrChassisSegmentIndex *****
           
           This index is the chassis number in the stack.
           The chassis at the top of the stack is number 1.  "
    ::= { rptrModuleStatEntry    1 }

rptrModuleTotalFrames   OBJECT-TYPE
    SYNTAX    Counter
    ACCESS    read-only
    STATUS    mandatory
    DESCRIPTION
          "***** Deprecated and replaced by rptrChassisSegmentTotalFrames *****
           
           The number of frames detected without errors. Includes unicast, 
           broadcast, and multicast frames. Does not include frames received 
           with frames too long, runt, FCS, or alignment errors. This is the 
           sum of all valid received frames for all ports in this repeater 
           module.

           (RFC2108 rptrMonitorGroupTotalFrames) "
    ::= { rptrModuleStatEntry    2 }

rptrModuleTotalOctets   OBJECT-TYPE
    SYNTAX    Counter
    ACCESS    read-only
    STATUS    mandatory
    DESCRIPTION
          "***** Deprecated and replaced by rptrChassisSegmentTotalOctets *****
           
           The number of octets (bytes) contained in frames received that had no
           errors. This includes octets in unicast, broadcast, and multicast 
           frames. 
           It also includes octets after the start frame delimiter up to FCS 
           but not including FCS octets. This is the sum of all valid received
           octets for all ports in this repeater module.

           (RFC2108 rptrMonitorGroupTotalOctets) "
    ::= { rptrModuleStatEntry    3 }

rptrModuleTotalErrors   OBJECT-TYPE
    SYNTAX    Counter
    ACCESS    read-only
    STATUS    mandatory
    DESCRIPTION
          "***** Deprecated and replaced by rptrChassisSegmentTotalErrors *****
           
           The total number of errors detected. Total errors include FCS errors,
           alignment errors, frame too long, short events, late events, very 
           long event, and rate mismatch errors. This is the sum of all errors
           for all ports in this repeater module.

           (RFC2108 rptrMonitorGroupTotalErrors) "
    ::= { rptrModuleStatEntry    4 }

rptrModuleFCSErrors   OBJECT-TYPE
    SYNTAX    Counter
    ACCESS    read-only
    STATUS    mandatory
    DESCRIPTION
          "***** Deprecated and replaced by rptrChassisSegmentFCSErrors *****
           
           The number of frames detected that are free of partial octets 
           and do not pass the FCS check. Usually caused by adapter underrun 
           (when the adapter can't get enough bus bandwidth). FCS errors do 
           not necessarily indicate that data has been lost.  "
    ::= { rptrModuleStatEntry    5 }

rptrModuleAlignmentErrors   OBJECT-TYPE
    SYNTAX    Counter
    ACCESS    read-only
    STATUS    mandatory
    DESCRIPTION
          "***** Deprecated and replaced by rptrChassisSegmentAlignmentErrors *****
           
           The number of frames detected that contain partial octets and do not 
           pass the FCS check.  "
    ::= { rptrModuleStatEntry    6 }

rptrModuleFrameTooLongs   OBJECT-TYPE
    SYNTAX    Counter
    ACCESS    read-only
    STATUS    mandatory
    DESCRIPTION
          "***** Deprecated and replaced by rptrChassisSegmentFrameTooLongs *****
           
           The number of frames detected that exceed the maximum permitted 
           frame size. "
    ::= { rptrModuleStatEntry    7 }

rptrModuleShortEvents   OBJECT-TYPE
    SYNTAX    Counter
    ACCESS    read-only
    STATUS    mandatory
    DESCRIPTION
          "***** Deprecated and replaced by rptrChassisSegmentShortEvents *****
           
           The number of fragments detected with ActivityDuration less than
           ShortEventMaxTime (greater than 74 bit times and less than 82 bit
           times). Usually indicates a network topology problem. "
    ::= { rptrModuleStatEntry    8 }

rptrModuleRunts   OBJECT-TYPE
    SYNTAX    Counter
    ACCESS    read-only
    STATUS    mandatory
    DESCRIPTION
          "***** Deprecated and replaced by rptrChassisSegmentRunts *****
           
           The number of frames detected that are less than the minimum
           permitted frame size of 64 octets but have a good FCS. Runts usually
           indicate collision fragments, a normal network event. "
    ::= { rptrModuleStatEntry    9 }

rptrModuleCollisions   OBJECT-TYPE
    SYNTAX    Counter
    ACCESS    read-only
    STATUS    mandatory
    DESCRIPTION
          "***** Deprecated and replaced by rptrChassisSegmentCollisions *****
           
           Sum of all collisions for all ports in this repeater module.  "
    ::= { rptrModuleStatEntry    10 }

rptrModuleLateEvents   OBJECT-TYPE
    SYNTAX    Counter
    ACCESS    read-only
    STATUS    mandatory
    DESCRIPTION
          "***** Deprecated and replaced by rptrChassisSegmentLateEvents *****
           
           The number of collisions detected after the allowable detection 
           period. 
           Usually indicates a network topology problem, such as daisy-chaining
           class I 100Mbps hubs with UTP cable or a network diameter that is 
           too wide. "
    ::= { rptrModuleStatEntry    11 }

rptrModuleVeryLongEvents   OBJECT-TYPE
    SYNTAX    Counter
    ACCESS    read-only
    STATUS    mandatory
    DESCRIPTION
          "***** Deprecated and replaced by rptrChassisSegmentVeryLongEvents *****
           
           The number of times MAU jabber lockup protection (MJLP) was detected
           due to transmission of data that exceeded 5 msec in duration 
           (octet count greater than maxFrameSize). Can indicate a faulty 
           device or port. "
    ::= { rptrModuleStatEntry    12 }

rptrModuleDataRateMismatches   OBJECT-TYPE
    SYNTAX    Counter
    ACCESS    read-only
    STATUS    mandatory
    DESCRIPTION
          "***** Deprecated and replaced by rptrChassisSegmentDataRateMismatches *****
           
           A count of the occurrences of out-of-specification bit rates. 
           This indicates the number of times the FIFO buffer overruns or 
           underruns due to transmission rate errors. This could indicate 
           an incorrect FIFO setting on a network adapter or a faulty adapter. "
    ::= { rptrModuleStatEntry    13 }

rptrModuleAutoPartitions   OBJECT-TYPE
    SYNTAX    Counter
    ACCESS    read-only
    STATUS    mandatory
    DESCRIPTION
          "***** Deprecated and replaced by rptrChassisSegmentAutoPartitions *****
           
           The number of times this port was automatically partitioned. This 
           condition occurs when too many consecutive collisions are detected
           on the port. These collisions are due to excessive traffic on the 
           segment, a malfunctioning port, or a malfunctioning adapter that
           is jabbering. "
    ::= { rptrModuleStatEntry    14 }

rptrPortStatTable   OBJECT-TYPE
    SYNTAX    SEQUENCE OF RptrPortStatEntry
    ACCESS    not-accessible
    STATUS    mandatory
    DESCRIPTION
          "Repeater status information at the port level."
    ::= { express110    14 }

rptrPortStatEntry   OBJECT-TYPE
    SYNTAX    RptrPortStatEntry
    ACCESS    not-accessible
    STATUS    mandatory
    DESCRIPTION
          "A table entry, containing repeater status information
           about a single port."
    INDEX    { rptrPortChassisIndex,
               rptrPortIndex  }
    ::= { rptrPortStatTable    1 }

RptrPortStatEntry ::=
    SEQUENCE {
        rptrPortChassisIndex
            INTEGER,
        rptrPortIndex
            INTEGER,
        rptrPortPartitionState
            INTEGER,
        rptrPortReadableFrames
            Counter,
        rptrPortReadableOctets
            Counter,
        rptrPortFcsErrors
            Counter,
        rptrPortAlignmentErrors
            Counter,
        rptrPortFrameTooLongs
            Counter,
        rptrPortShortEvents
            Counter,
        rptrPortRunts
            Counter,
        rptrPortCollisions
            Counter,
        rptrPortLateEvents
            Counter,
        rptrPortVeryLongEvents
            Counter,
        rptrPortDataRateMismatches
            Counter,
        rptrPortAutoPartitions
            Counter,
        rptrPortTotalErrors
            Counter,
        rptrPortLastMACAddress
            DisplayString,
        rptrPortNumberofMACAddressChanges
            Counter,
        rptrPortSymbolErrors
            Counter
    }
    
rptrPortChassisIndex   OBJECT-TYPE
    SYNTAX    INTEGER
    ACCESS    read-only
    STATUS    mandatory
    DESCRIPTION
          "Chassis number in stack. The chassis at the top is number 1. "
    ::= { rptrPortStatEntry    1 }

rptrPortIndex   OBJECT-TYPE
    SYNTAX    INTEGER
    ACCESS    read-only
    STATUS    mandatory
    DESCRIPTION
          "Port number in the module.  "
    ::= { rptrPortStatEntry    2 }

rptrPortPartitionState   OBJECT-TYPE
    SYNTAX    INTEGER  {
                autoPartition(1),
                notAutoPartition(2)
                }
    ACCESS    read-only
    STATUS    mandatory
    DESCRIPTION
          "Indicates a port's current autopartitioned state.

           (RFC2108 rptrPortAutoPartitionState) "
    ::= { rptrPortStatEntry    3 }

rptrPortReadableFrames   OBJECT-TYPE
    SYNTAX    Counter
    ACCESS    read-only
    STATUS    mandatory
    DESCRIPTION
          "The number of frames detected without errors. Includes unicast, 
           broadcast, and multicast frames. Does not include frames received 
           with frames too long, runt, FCS, or alignment errors.

           (RFC2108 rptrMonitorPortReadableFrames) "
    ::= { rptrPortStatEntry    4 }

rptrPortReadableOctets   OBJECT-TYPE
    SYNTAX    Counter
    ACCESS    read-only
    STATUS    mandatory
    DESCRIPTION
          "The number of octets (bytes) contained in frames received that had no
           errors. This includes octets in unicast, broadcast, and multicast 
           frames. It also includes octets after the start frame delimiter up
           to FCS but not including FCS octets.
          
          (RFC2108 rptrMonitorPortReadableOctets) "
    ::= { rptrPortStatEntry    5 }

rptrPortFcsErrors   OBJECT-TYPE
    SYNTAX    Counter
    ACCESS    read-only
    STATUS    mandatory
    DESCRIPTION
          "The number of frames detected that are free of partial octets 
           and do not pass the FCS check. Usually caused by adapter underrun 
           (when the adapter can't get enough bus bandwidth). FCS errors do 
           not necessarily indicate that data has been lost.  

           (RFC2108 rptrMonitorPortFCSErrors) "
    ::= { rptrPortStatEntry    6 }

rptrPortAlignmentErrors   OBJECT-TYPE
    SYNTAX    Counter
    ACCESS    read-only
    STATUS    mandatory
    DESCRIPTION
          "The number of frames detected that contain partial octets and do not 
           pass the FCS check.  

           (RFC2108 rptrMonitorPortAlignmentErrors) "
    ::= { rptrPortStatEntry    7 }

rptrPortFrameTooLongs   OBJECT-TYPE
    SYNTAX    Counter
    ACCESS    read-only
    STATUS    mandatory
    DESCRIPTION
          "The number of frames detected that exceed the maximum permitted 
           frame size of 1518 octets.

           (RFC2108 rptrMonitorPortFrameTooLongs) "
    ::= { rptrPortStatEntry    8 }

rptrPortShortEvents   OBJECT-TYPE
    SYNTAX    Counter
    ACCESS    read-only
    STATUS    mandatory
    DESCRIPTION
          "The number of fragments detected with ActivityDuration less than 
           ShortEventMaxTime (greater than 74 bit times and less than 82 bit
           times). Usually indicates a network topology problem.

           (RFC2108 rptrMonitorPortShortEvents) "
    ::= { rptrPortStatEntry    9 }

rptrPortRunts   OBJECT-TYPE
    SYNTAX    Counter
    ACCESS    read-only
    STATUS    mandatory
    DESCRIPTION
          "The number of frames detected that are less than the minimum
           permitted frame size of 64 octets but have a good FCS. Runts
           usually indicate collision fragments, a normal network event. 

           (RFC2108 rptrMonitorPortRunts) "
    ::= { rptrPortStatEntry    10 }

rptrPortCollisions   OBJECT-TYPE
    SYNTAX    Counter
    ACCESS    read-only
    STATUS    mandatory
    DESCRIPTION
          "The number of collisions detected on a port.

           (RFC2108 rptrMonitorPortCollisions) "
    ::= { rptrPortStatEntry    11 }

rptrPortLateEvents   OBJECT-TYPE
    SYNTAX    Counter
    ACCESS    read-only
    STATUS    mandatory
    DESCRIPTION
          "The number of collisions detected after the allowable detection 
           period. 
           Usually indicates a network topology problem, such as daisy-chaining
           Class I 100Mbps hubs with UTP cable or a network diameter that is
           too wide.

           (RFC2108 rptrMonitorPortLateEvents) "
    ::= { rptrPortStatEntry    12 }

rptrPortVeryLongEvents   OBJECT-TYPE
    SYNTAX    Counter
    ACCESS    read-only
    STATUS    mandatory
    DESCRIPTION
          "The number of times MAU jabber lockup protection (MJLP) was detected
           due to transmission of data that exceeded 5 msec in duration 
           (octet count greater than maxFramSize). Can indicate a faulty device
           or port. 

           (RFC2108 rptrMonitorPortVeryLongEvents) "
    ::= { rptrPortStatEntry    13 }

rptrPortDataRateMismatches   OBJECT-TYPE
    SYNTAX    Counter
    ACCESS    read-only
    STATUS    mandatory
    DESCRIPTION
          "A count of the occurrences of out-of-specification bit rates. 
           This indicates the number of times the FIFO buffer overruns or 
           underruns due to transmission rate errors. This could indicate 
           an incorrect FIFO setting on a network adapter or a faulty adapter. 

           (RFC2108 rptrMonitorPortDataRateMismatches) "
    ::= { rptrPortStatEntry    14 }

rptrPortAutoPartitions   OBJECT-TYPE
    SYNTAX    Counter
    ACCESS    read-only
    STATUS    mandatory
    DESCRIPTION
          "The number of times this port was automatically partitioned. This
           condition occurs when 64 consecutive collisions are detected on the 
           port. These collisions are due to excessive traffic on the segment, 
           a malfunctioning port, or a malfunctioning adapter that is jabbering. 

           (RFC2108 rptrMonitorPortAutoPartitions) "
    ::= { rptrPortStatEntry    15 }

rptrPortTotalErrors   OBJECT-TYPE
    SYNTAX    Counter
    ACCESS    read-only
    STATUS    mandatory
    DESCRIPTION
          "The total number of errors detected. Total errors include FCS errors,
           alignment errors, frame too long, short events, late events, very 
           long event, rate mismatch, and symbol errors.

           (RFC2108 rptrMonitorPortTotalErrors) "
    ::= { rptrPortStatEntry    16 }

rptrPortLastMACAddress   OBJECT-TYPE
    SYNTAX    DisplayString
    ACCESS    read-only
    STATUS    mandatory
    DESCRIPTION
          "The source address of the last readable frame received
           by this port. If no frames have been received on this
           port, the length of the returned DisplayString is zero.

           (RFC2108 rptrAddrTrackNewLastSrcAddress) "
    ::= { rptrPortStatEntry    17 }

rptrPortNumberofMACAddressChanges   OBJECT-TYPE
    SYNTAX    Counter
    ACCESS    read-only
    STATUS    mandatory
    DESCRIPTION
          "The number of times that the value of rptrPortLastMACAddress has 
           changed.
           The typical value for this port is 1, meaning the value of
           rptrPortLastMACAddress changed from all zeros to a MAC address.
           A high number of changes indicates a port connected to a switch or 
           bridge.

           (RFC2108 rptrAddrTrackSourceAddrChanges) "
    ::= { rptrPortStatEntry    18 }

rptrPortSymbolErrors   OBJECT-TYPE
    SYNTAX    Counter
    ACCESS    read-only
    STATUS    mandatory
    DESCRIPTION
          "This counter is incremented by one each time a
           valid length packet was received at the port and
           there was at least one occurrence of an invalid
           data symbol. This can increment only once per valid
           carrier event. A collision presence at any port of
           the repeater containing port N will not cause this
           attribute to increment. "
    ::= { rptrPortStatEntry    19 }

rptrChassisSegmentStatTable   OBJECT-TYPE
    SYNTAX    SEQUENCE OF RptrChassisSegmentStatEntry
    ACCESS    not-accessible
    STATUS    mandatory
    DESCRIPTION
          "Repeater status information by segment at the chassis level. "
    ::= { express110    15 }

rptrChassisSegmentStatEntry   OBJECT-TYPE
    SYNTAX    RptrChassisSegmentStatEntry
    ACCESS    not-accessible
    STATUS    mandatory
    DESCRIPTION
          "A table entry, containing repeater status information
           about a single chassis and segment. "
    INDEX    {  rptrChassisIndex, rptrChassisSegmentIndex  }
        ::= { rptrChassisSegmentStatTable    1 }

RptrChassisSegmentStatEntry ::=
    SEQUENCE {
        rptrChassisIndex
            INTEGER,
        rptrChassisSegmentIndex
            INTEGER,
        rptrChassisSegmentTotalFrames
            Counter,
        rptrChassisSegmentTotalOctets
            Counter,
        rptrChassisSegmentTotalErrors
            Counter,
        rptrChassisSegmentFCSErrors
            Counter,
        rptrChassisSegmentAlignmentErrors
            Counter,
        rptrChassisSegmentFrameTooLongs
            Counter,
        rptrChassisSegmentShortEvents
            Counter,
        rptrChassisSegmentRunts
            Counter,
        rptrChassisSegmentCollisions
            Counter,
        rptrChassisSegmentLateEvents
            Counter,
        rptrChassisSegmentVeryLongEvents
            Counter,
        rptrChassisSegmentDataRateMismatches
            Counter,
        rptrChassisSegmentAutoPartitions
            Counter,
        rptrChassisSegmentSymbolErrors
            Counter
    }
    
rptrChassisIndex   OBJECT-TYPE
    SYNTAX    INTEGER
    ACCESS    read-only
    STATUS    mandatory
    DESCRIPTION
          "This index is the chassis number in the stack.
           The chassis at the top of the stack is number 1.  "
    ::= { rptrChassisSegmentStatEntry    1 }

rptrChassisSegmentIndex   OBJECT-TYPE
    SYNTAX    INTEGER
    ACCESS    read-only
    STATUS    mandatory
    DESCRIPTION
          "This index is the segment number in the stack."
    ::= { rptrChassisSegmentStatEntry    2 }

rptrChassisSegmentTotalFrames   OBJECT-TYPE
    SYNTAX    Counter
    ACCESS    read-only
    STATUS    mandatory
    DESCRIPTION
          "The number of frames detected without errors. Includes unicast, 
           broadcast, and multicast frames. Does not include frames received 
           with frames too long, runt, FCS, or alignment errors. This is the 
           sum of all valid received frames for all ports in this repeater 
           module.

           (RFC2108 rptrMonitorGroupTotalFrames) "
    ::= { rptrChassisSegmentStatEntry    3 }

rptrChassisSegmentTotalOctets   OBJECT-TYPE
    SYNTAX    Counter
    ACCESS    read-only
    STATUS    mandatory
    DESCRIPTION
          "The number of octets (bytes) contained in frames received that had no
           errors. This includes octets in unicast, broadcast, and multicast 
           frames. 
           It also includes octets after the start frame delimiter up to FCS 
           but not including FCS octets. This is the sum of all valid received
           octets for all ports in this repeater module.

           (RFC2108 rptrMonitorGroupTotalOctets) "
    ::= { rptrChassisSegmentStatEntry    4 }

rptrChassisSegmentTotalErrors   OBJECT-TYPE
    SYNTAX    Counter
    ACCESS    read-only
    STATUS    mandatory
    DESCRIPTION
          "The total number of errors detected. Total errors include FCS errors,
           alignment errors, frame too long, short events, late events, very 
           long event, and rate mismatch errors. This is the sum of all errors
           for all ports in this repeater module.

           (RFC2108 rptrMonitorGroupTotalErrors) "
    ::= { rptrChassisSegmentStatEntry    5 }

rptrChassisSegmentFCSErrors   OBJECT-TYPE
    SYNTAX    Counter
    ACCESS    read-only
    STATUS    mandatory
    DESCRIPTION
          "The number of frames detected that are free of partial octets 
           and do not pass the FCS check. Usually caused by adapter underrun 
           (when the adapter can't get enough bus bandwidth). FCS errors do 
           not necessarily indicate that data has been lost.  "
    ::= { rptrChassisSegmentStatEntry    6 }

rptrChassisSegmentAlignmentErrors   OBJECT-TYPE
    SYNTAX    Counter
    ACCESS    read-only
    STATUS    mandatory
    DESCRIPTION
          "The number of frames detected that contain partial octets and do not 
           pass the FCS check.  "
    ::= { rptrChassisSegmentStatEntry    7 }

rptrChassisSegmentFrameTooLongs   OBJECT-TYPE
    SYNTAX    Counter
    ACCESS    read-only
    STATUS    mandatory
    DESCRIPTION
          "The number of frames detected that exceed the maximum permitted 
           frame size. "
    ::= { rptrChassisSegmentStatEntry    8 }

rptrChassisSegmentShortEvents   OBJECT-TYPE
    SYNTAX    Counter
    ACCESS    read-only
    STATUS    mandatory
    DESCRIPTION
          "The number of fragments detected with ActivityDuration less than
           ShortEventMaxTime (greater than 74 bit times and less than 82 bit
           times). Usually indicates a network topology problem. "
    ::= { rptrChassisSegmentStatEntry    9 }

rptrChassisSegmentRunts   OBJECT-TYPE
    SYNTAX    Counter
    ACCESS    read-only
    STATUS    mandatory
    DESCRIPTION
          "The number of frames detected that are less than the minimum
           permitted frame size of 64 octets but have a good FCS. Runts usually
           indicate collision fragments, a normal network event. "
    ::= { rptrChassisSegmentStatEntry    10 }

rptrChassisSegmentCollisions   OBJECT-TYPE
    SYNTAX    Counter
    ACCESS    read-only
    STATUS    mandatory
    DESCRIPTION
          "Sum of all collisions for all ports in this repeater module.  "
    ::= { rptrChassisSegmentStatEntry    11 }

rptrChassisSegmentLateEvents   OBJECT-TYPE
    SYNTAX    Counter
    ACCESS    read-only
    STATUS    mandatory
    DESCRIPTION
          "The number of collisions detected after the allowable detection 
           period. 
           Usually indicates a network topology problem, such as daisy-chaining
           class I 100Mbps hubs with UTP cable or a network diameter that is 
           too wide. "
    ::= { rptrChassisSegmentStatEntry    12 }

rptrChassisSegmentVeryLongEvents   OBJECT-TYPE
    SYNTAX    Counter
    ACCESS    read-only
    STATUS    mandatory
    DESCRIPTION
          "The number of times MAU jabber lockup protection (MJLP) was detected
           due to transmission of data that exceeded 5 msec in duration 
           (octet count greater than maxFrameSize). Can indicate a faulty 
           device or port. "
    ::= { rptrChassisSegmentStatEntry    13 }

rptrChassisSegmentDataRateMismatches   OBJECT-TYPE
    SYNTAX    Counter
    ACCESS    read-only
    STATUS    mandatory
    DESCRIPTION
          "A count of the occurrences of out-of-specification bit rates. 
           This indicates the number of times the FIFO buffer overruns or 
           underruns due to transmission rate errors. This could indicate 
           an incorrect FIFO setting on a network adapter or a faulty adapter. "
    ::= { rptrChassisSegmentStatEntry    14 }

rptrChassisSegmentAutoPartitions   OBJECT-TYPE
    SYNTAX    Counter
    ACCESS    read-only
    STATUS    mandatory
    DESCRIPTION
          "The number of times this port was automatically partitioned. This 
           condition occurs when too many consecutive collisions are detected
           on the port. These collisions are due to excessive traffic on the 
           segment, a malfunctioning port, or a malfunctioning adapter that
           is jabbering. "
    ::= { rptrChassisSegmentStatEntry    15 }

rptrChassisSegmentSymbolErrors   OBJECT-TYPE
    SYNTAX    Counter
    ACCESS    read-only
    STATUS    mandatory
    DESCRIPTION
          "This counter is incremented by one when a valid
           length packet was received at the port and
           there was at least one occurrence of an invalid
           data symbol. This can increment only once per valid
           carrier event. A collision presence at any port of
           the repeater containing port N will not cause this
           attribute to increment. "
    ::= { rptrChassisSegmentStatEntry    16 }

tBrdgAdminTable   OBJECT-TYPE
    SYNTAX    SEQUENCE OF TBrdgAdminEntry
    ACCESS    not-accessible
    STATUS    mandatory
    DESCRIPTION
          "Embedded transparent bridge administration."
    ::= { express110    16 }

tBrdgAdminEntry   OBJECT-TYPE
    SYNTAX    TBrdgAdminEntry
    ACCESS    not-accessible
    STATUS    mandatory
    DESCRIPTION
          "A table entry, containing administration information 
           for a single embedded transparent bridge span."
    INDEX    { tBrdgAdminSpanIndex }
    ::= { tBrdgAdminTable    1 }

TBrdgAdminEntry ::=
    SEQUENCE {
        tBrdgAdminSpanIndex 
            INTEGER,
        tBrdgAdminState 
            INTEGER,
        tBrdgReset
            INTEGER,
        tBrdgThrshld
            INTEGER,
        tBrdgPeriod
            INTEGER,
        tBrdgLockout
            INTEGER,
        tBrdgHubId
            INTEGER,
        tBrdgSegments
            OCTET STRING
    }
    
tBrdgAdminSpanIndex   OBJECT-TYPE
    SYNTAX    INTEGER
    ACCESS    read-only
    STATUS    mandatory
    DESCRIPTION
          "Embedded transparent bridge span number.  
           A bridge span consists of one or more embedded transparent bridges
           forwarding packets between two segments."
    ::= { tBrdgAdminEntry    1 }

tBrdgAdminState OBJECT-TYPE
    SYNTAX    INTEGER  {
                enable(1),
                disable(2)
                }
    ACCESS    read-write
    STATUS    mandatory
    DESCRIPTION
          "The state of the embedded transparent bridging span.
           enable  - Allows packets to be forwarded by embedded bridging
                     to the peer segment.
           disable - Prevents packets from being forwarded by embedded 
                     bridging to the peer segment."
    ::= { tBrdgAdminEntry 2 }

tBrdgReset OBJECT-TYPE
    SYNTAX    INTEGER  {
                reset(1),
                resetCounters(2),
                notreset(3),
                notSupported(4)
                }
    ACCESS    read-write
    STATUS    mandatory
    DESCRIPTION
          "'reset' resets all enabled transparent bridges in the span.
           'resetCounters' clears all transparent bridge statistics."
    ::= { tBrdgAdminEntry 3 }

tBrdgThrshld OBJECT-TYPE
    SYNTAX    INTEGER 
    ACCESS    read-write
    STATUS    mandatory
    DESCRIPTION
          "If the number of times the transparent bridge indicates buffer full
           exceeds this value, a trap is generated.  Use 0 to disable.  
           This trap is based on the number of tBrdgBufferFullCount in the last 
           tBrdgPeriod.  "
    ::= { tBrdgAdminEntry 4 }

tBrdgPeriod OBJECT-TYPE
    SYNTAX    INTEGER 
    ACCESS    read-write
    STATUS    mandatory
    DESCRIPTION
          "Time period (in minutes) that the transparent bridge buffer full
           count must exceed the trap threshold value in order to generate 
           a trap."
    ::= { tBrdgAdminEntry 5 }

tBrdgLockout   OBJECT-TYPE
    SYNTAX    INTEGER  {
                        yButtonyMgmt(1),
                        nButtonyMgmt(2),
                        yButtonnMgmt(3),
                        nButtonnMgmt(4)
                       }
    ACCESS    read-write
    STATUS    mandatory
    DESCRIPTION
          "Prevents embedded transparent bridging from being enabled or
           disabled via a button on the front of a hub or by the local
           management console interface."
    ::= { tBrdgAdminEntry 6 }

tBrdgHubId   OBJECT-TYPE
    SYNTAX    INTEGER 
    ACCESS    read-only
    STATUS    mandatory
    DESCRIPTION
          "chassisConfigTableIndex of the chassis containing the primary
           internal bridge for the span.  
           All internal bridge statistics are reported as ports 101 and 102 
           within this hub chassis."
    ::= { tBrdgAdminEntry 7 }

tBrdgSegments   OBJECT-TYPE
    SYNTAX    OCTET STRING
    ACCESS    read-only
    STATUS    mandatory
    DESCRIPTION
          "Embedded transparent bridge span segments.
           This is a list of segments (1 per byte) in this bridge span."
    ::= { tBrdgAdminEntry 8 }

tBrdgStatsTable   OBJECT-TYPE
    SYNTAX    SEQUENCE OF TBrdgStatsEntry
    ACCESS    not-accessible
    STATUS    mandatory
    DESCRIPTION
          "Embedded transparent bridge statistics."
    ::= { express110    17 }

tBrdgStatsEntry   OBJECT-TYPE
    SYNTAX    TBrdgStatsEntry
    ACCESS    not-accessible
    STATUS    mandatory
    DESCRIPTION
          "A table entry, containing statistics for a single
           embedded transparent bridge span domain."
    INDEX    { tBrdgStatsSpan, tBrdgStatsSegment }
    ::= { tBrdgStatsTable    1 }

TBrdgStatsEntry ::=
    SEQUENCE {
        tBrdgStatsSpan
            INTEGER,
        tBrdgStatsSegment
            INTEGER,
        tBrdgUtilIn
            INTEGER,
        tBrdgUtilOut
            INTEGER,
        tBrdgBufferFullCount
            INTEGER
    }
    
tBrdgStatsSpan   OBJECT-TYPE
    SYNTAX    INTEGER
    ACCESS    read-only
    STATUS    mandatory
    DESCRIPTION
          "Embedded transparent bridge span number.  
           A bridge span consists of one or more embedded transparent bridges
           forwarding packets between two segments."
    ::= { tBrdgStatsEntry 1 }

tBrdgStatsSegment   OBJECT-TYPE
    SYNTAX    INTEGER
    ACCESS    read-only
    STATUS    mandatory
    DESCRIPTION
          "Embedded transparent bridge statistics segment.
           This index specifies which segment is associated with the
           transparent bridge statistics."
    ::= { tBrdgStatsEntry 2 }

tBrdgUtilIn OBJECT-TYPE
    SYNTAX    INTEGER 
    ACCESS    read-only
    STATUS    mandatory
    DESCRIPTION
          "The percentage of this segment's traffic that was bridged from 
           the peer segment during the previous second."
    ::= { tBrdgStatsEntry 3 }

tBrdgUtilOut OBJECT-TYPE
    SYNTAX    INTEGER 
    ACCESS    read-only
    STATUS    mandatory
    DESCRIPTION
          "The percentage of this segment's traffic which was bridged to 
           the peer segment during the previous second."
    ::= { tBrdgStatsEntry 4 }

tBrdgBufferFullCount OBJECT-TYPE
    SYNTAX    INTEGER 
    ACCESS    read-only
    STATUS    mandatory
    DESCRIPTION
          "The number of times internal buffer capacity was exceeded
           while bridging frames out of this segment."
    ::= { tBrdgStatsEntry 5 }

stackConfigExtensions   OBJECT IDENTIFIER ::= { express110    18 }

stackClearPortSecurity   OBJECT-TYPE
    SYNTAX    INTEGER  { clear(1) }
    ACCESS    write-only
    STATUS    mandatory
    DESCRIPTION
          "Clears all active and persistent port security settings."
    ::= { stackConfigExtensions 1 }


express-snmp-agents     OBJECT IDENTIFIER ::= { express110    19 }

e300agentConfiguration    OBJECT IDENTIFIER ::= { express-snmp-agents 1 }

e300agentVendorName   OBJECT-TYPE
    SYNTAX    DisplayString (SIZE (128))
    ACCESS    read-only
    STATUS    mandatory
    DESCRIPTION
          "Displays the SNMP agent's manufacturer name.  "
    ::= { e300agentConfiguration    1 }

e300agentProductName   OBJECT-TYPE
    SYNTAX    DisplayString (SIZE (128))
    ACCESS    read-only
    STATUS    mandatory
    DESCRIPTION
          "Displays the product name that contains the SNMP agent.  "
    ::= { e300agentConfiguration    2 }

e300agentChassisIndex   OBJECT-TYPE
    SYNTAX    INTEGER
    ACCESS    read-only
    STATUS    mandatory
    DESCRIPTION
          "Displays which chassis contains the SNMP agent's module.  "
    ::= { e300agentConfiguration    3 }

e300agentModuleIndex   OBJECT-TYPE
    SYNTAX    INTEGER
    ACCESS    read-only
    STATUS    mandatory
    DESCRIPTION
          "Displays which module in the chassis is the SNMP agent's
           module. The chassis number is in the object agentChassisIndex. "
    ::= { e300agentConfiguration    4 }

e300mibversion   OBJECT-TYPE
    SYNTAX    DisplayString (SIZE (8))
    ACCESS    read-only
    STATUS    mandatory
    DESCRIPTION
          "Displays the version of the MIB supported by the SNMP agent.  "
    ::= { e300agentConfiguration    5 }

e300resetAgent   OBJECT-TYPE
    SYNTAX    INTEGER  {
                reset(1),
                notreset(2)
                }
    ACCESS    read-write
    STATUS    mandatory
    DESCRIPTION
          "Performs a cold reset of the SNMP agent. If a new IP configuration
           was set, it will be used after the reset.  "
    ::= { e300agentConfiguration    6 }


e300agentRole OBJECT-TYPE
    SYNTAX  INTEGER {
            other(1),
            primaryAgent(2),
            backupAgent(3)
                        }
    ACCESS  read-only
    STATUS  mandatory
    DESCRIPTION
    "The current role of this agent within this hub stack."
    ::= { e300agentConfiguration 7 }

e300agentIpBootServerAddr OBJECT-TYPE
    SYNTAX  IpAddress
    ACCESS  read-write
    STATUS  mandatory
    DESCRIPTION
    "The IP Address of Boot Server."
    ::= {  e300agentConfiguration 8 }

e300agentIpUnauthAddr OBJECT-TYPE
    SYNTAX  IpAddress
    ACCESS  read-only
    STATUS  mandatory
    DESCRIPTION
    "The IP address of an unauthorized SNMP packet."
    ::= { e300agentConfiguration 9 }

e300agentIpUnauthComm OBJECT-TYPE
    SYNTAX  DisplayString (SIZE (0..20))
    ACCESS  read-only
    STATUS  mandatory
    DESCRIPTION
    "The community string of an unauthorized SNMP packet."
    ::= { e300agentConfiguration 10 }

e300agentIpLastBootServerAddr OBJECT-TYPE
    SYNTAX  IpAddress
    ACCESS  read-only
    STATUS  mandatory
    DESCRIPTION
    "The last IP address used as Boot server IP address."
    ::= {  e300agentConfiguration 11 }

e300agentIpLastIpAddr OBJECT-TYPE
    SYNTAX  IpAddress
    ACCESS  read-only
    STATUS  mandatory
    DESCRIPTION
    "The last IP address used as the agent system IP address."
    ::= {  e300agentConfiguration 12 }

e300ipConfiguration        OBJECT IDENTIFIER ::= { express-snmp-agents 2 }

e300ipAddressMethodInUse   OBJECT-TYPE
    SYNTAX    INTEGER  {
                fixed(1),
                bootp(2)
                }
    ACCESS    read-only
    STATUS    mandatory
    DESCRIPTION
          "Displays how the IP address in use was determined. 
           For example, fixed means the IP address was assigned by the
           user and stored within the Management Module. BOOTP means the
           SNMP agent used a BOOTP server to get its IP configuration. "
    ::= { e300ipConfiguration    1 }

e300ipAddressInUse   OBJECT-TYPE
    SYNTAX    IpAddress
    ACCESS    read-only
    STATUS    mandatory
    DESCRIPTION
          "Displays the IP address currently in use.  "
    ::= { e300ipConfiguration    2 }

e300gatewayorRouterAddrInUse   OBJECT-TYPE
    SYNTAX    IpAddress
    ACCESS    read-only
    STATUS    mandatory
    DESCRIPTION
          "Displays the default gateway address currently in use. 
           This is the device that routes to a different network. 
           Usually a router or a routing server.  "
    ::= { e300ipConfiguration    3 }

e300networkMaskInUse   OBJECT-TYPE
    SYNTAX    IpAddress
    ACCESS    read-only
    STATUS    mandatory
    DESCRIPTION
          "Displays the network (subnet) mask currently in use. This
           must match the masks of other devices on the same network.  "
    ::= { e300ipConfiguration    4 }

e300broadcastAddressInUse   OBJECT-TYPE
    SYNTAX    IpAddress
    ACCESS    read-only
    STATUS    mandatory
    DESCRIPTION
          "Displays the broadcast address currently in use. "
    ::= { e300ipConfiguration    5 }

e300ipAddressMethodNextReset   OBJECT-TYPE
    SYNTAX    INTEGER  {
                fixed(1),
                bootp(2)
                }
    ACCESS    read-write
    STATUS    mandatory
    DESCRIPTION
          "Displays how the IP address will be determined after the 
           SNMP agent is reset. For example, fixed means the IP address 
           will be determined locally. BOOTP means the SNMP agent will 
           search for a BOOTP server to get its IP configuration. "
    ::= { e300ipConfiguration    6 }

e300ipAddressNextReset   OBJECT-TYPE
    SYNTAX    IpAddress
    ACCESS    read-write
    STATUS    mandatory
    DESCRIPTION
          "Displays the IP address the SNMP agent will use the next
           time it is reset.  "
    ::= { e300ipConfiguration    7 }

e300gatewayorRouterAddrNextReset   OBJECT-TYPE
    SYNTAX    IpAddress
    ACCESS    read-write
    STATUS    mandatory
    DESCRIPTION
          "Displays the default gateway the SNMP agent will use the next
           time it is reset. "
    ::= { e300ipConfiguration    8 }

e300networkMaskNextReset   OBJECT-TYPE
    SYNTAX    IpAddress
    ACCESS    read-write
    STATUS    mandatory
    DESCRIPTION
          "Displays the netmask (subnet mask) the SNMP agent will use the next 
           time it is reset. "
    ::= { e300ipConfiguration    9 }

e300snmpConfiguration        OBJECT IDENTIFIER ::= { express-snmp-agents 3 }

e300snmpReadCommunityString   OBJECT-TYPE
    SYNTAX    DisplayString (SIZE (0..32))
    ACCESS    write-only
    STATUS    mandatory
    DESCRIPTION
          "Sets the password for reads from the SNMP agent's MIB.  "
    ::= { e300snmpConfiguration    1 }

e300snmpWriteCommunityString   OBJECT-TYPE
    SYNTAX    DisplayString (SIZE (0..32))
    ACCESS    write-only
    STATUS    mandatory
    DESCRIPTION
          "Sets the password for writes to the SNMP agent's MIB.  "
    ::= { e300snmpConfiguration    2 }

e300snmpTrapReceiverMAX   OBJECT-TYPE
    SYNTAX    INTEGER
    ACCESS    read-only
    STATUS    mandatory
    DESCRIPTION
          "Displays the maximum number of trap receiving stations.  "
    ::= { e300snmpConfiguration    3 }

e300snmpTrapReceiverNumber   OBJECT-TYPE
    SYNTAX    INTEGER
    ACCESS    read-only
    STATUS    mandatory
    DESCRIPTION
          "Displays the current number of trap receiving stations. "
    ::= { e300snmpConfiguration    4 }

e300snmpTrapAddressTable   OBJECT-TYPE
    SYNTAX    SEQUENCE OF E300SnmpTrapAddressEntry
    ACCESS    not-accessible
    STATUS    mandatory
    DESCRIPTION
          "Contains information on individual trap receiving stations. "
    ::= { e300snmpConfiguration    5 }

e300snmpTrapAddressEntry   OBJECT-TYPE
    SYNTAX    E300SnmpTrapAddressEntry
    ACCESS    not-accessible
    STATUS    mandatory
    DESCRIPTION
          "An entry in the table, containing information on an individual
           trap receiving station. "
    INDEX    {  e300trapAddrIndex  }
        ::= { e300snmpTrapAddressTable    1 }

E300SnmpTrapAddressEntry ::=
    SEQUENCE {
        e300trapAddrIndex
            INTEGER,
        e300trapIPAddr
            IpAddress,
        e300trapCommunityString
            DisplayString,
        e300trapStatus
            INTEGER
    }
e300trapAddrIndex   OBJECT-TYPE
    SYNTAX    INTEGER
    ACCESS    read-only
    STATUS    mandatory
    DESCRIPTION
          "Displays the index number of the trap receiving station.  "
    ::= { e300snmpTrapAddressEntry    1 }

e300trapIPAddr   OBJECT-TYPE
    SYNTAX    IpAddress
    ACCESS    read-write
    STATUS    mandatory
    DESCRIPTION
          "Sets the IP address for a trap receiving station.  "
    ::= { e300snmpTrapAddressEntry    2 }

e300trapCommunityString   OBJECT-TYPE
    SYNTAX    DisplayString (SIZE (0..32))
    ACCESS    read-write
    STATUS    mandatory
    DESCRIPTION
          "Sets the password for sending traps from the SNMP agent
           to the SNMP application on the trap receiving station. "
    ::= { e300snmpTrapAddressEntry    3 }

e300trapStatus   OBJECT-TYPE
    SYNTAX    INTEGER  {
                active(1),
                ignore(2)
                }
    ACCESS    read-write
    STATUS    mandatory
    DESCRIPTION
          "Displays whether traps should be sent to this station (active)
           or whether traps should not be sent to this station (ignore). "
    ::= { e300snmpTrapAddressEntry    4 }


e300agentExtConfiguration        OBJECT IDENTIFIER ::= { express-snmp-agents 4 }

e300agentSwUpdateMode OBJECT-TYPE
    SYNTAX  INTEGER {
            other(1),
            network-load(2),
            out-of-band-load(3)
    }
    ACCESS  read-write
    STATUS
    mandatory
    DESCRIPTION
    "The download media used by the system to download the runtime firmware."
    ::= { e300agentExtConfiguration 1 }

e300agentConfigUpdateCtrl OBJECT-TYPE
    SYNTAX  INTEGER {
            enable(1),
            disable(2)
            }
    ACCESS  read-write
    STATUS  mandatory
    DESCRIPTION
    "Current status of configuration file download control. The setting
    is effective the next time you reset or power on the hub."
    ::= { e300agentExtConfiguration 2 }

e300agentConfigFilename OBJECT-TYPE
    SYNTAX  DisplayString  (SIZE (0..64))
    ACCESS  read-write
    STATUS  mandatory
    DESCRIPTION
    "The name of the configuration file to be downloaded from the BootP or TFTP
    server when agentConfigUpdateCtrl is enabled."
    ::= { e300agentExtConfiguration 3 }

e300agentImageUpdateCtrl OBJECT-TYPE
    SYNTAX  INTEGER {
            enable(1),
            disable(2)
            }
    ACCESS  read-write
    STATUS  mandatory
    DESCRIPTION
    "Current status of firmware image download control. The setting
    is effective the next time you reset or power on the hub."
    ::= { e300agentExtConfiguration 4 }

e300agentImageFilename OBJECT-TYPE
    SYNTAX  DisplayString  (SIZE (0..64))
    ACCESS  read-write
    STATUS  mandatory
    DESCRIPTION
    "The name of the image file to be downloaded from the TFTP server when
    agentImageUpdateCtrl is enabled."
    ::= { e300agentExtConfiguration 5 }


e300agentRs232PortConfig OBJECT-TYPE
    SYNTAX  INTEGER {
            other(1),
            console(2),
            out-of-band(3)
    }
    ACCESS  read-write
    STATUS  mandatory
    DESCRIPTION
    "The current setting of RS-232C port.
    The RS-232C port can be configured as the console port or
        used for out-of-band connection."
    ::= { e300agentExtConfiguration 6 }

e300agentOutOfBandBaudRateConfig OBJECT-TYPE
    SYNTAX  INTEGER {
            other(1),
            baudRate-1200 (2),
            baudRate-2400 (3),
            baudRate-9600 (4),
            baudRate-19200(5)
    }
    ACCESS  read-write
    STATUS  mandatory
    DESCRIPTION
    "The baud rate setting for out of band connection.
    The baud rate for the console interface is always 9600."
    ::= { e300agentExtConfiguration 7 }


e300slipConfiguration    OBJECT IDENTIFIER ::= { express-snmp-agents 5 }

e300slipAddressInUse   OBJECT-TYPE
    SYNTAX    IpAddress
    ACCESS    read-only
    STATUS    mandatory
    DESCRIPTION
          "Displays the IP address currently in use.  "
    ::= { e300slipConfiguration    1 }

e300slipGatewayorRouterAddrInUse   OBJECT-TYPE
    SYNTAX    IpAddress
    ACCESS    read-only
    STATUS    mandatory
    DESCRIPTION
          "Displays the default gateway address currently in use. 
           This is the device that routes to a different network. 
           Usually a router or a routing server.  "
    ::= { e300slipConfiguration    2 }

e300slipNetworkMaskInUse   OBJECT-TYPE
    SYNTAX    IpAddress
    ACCESS    read-only
    STATUS    mandatory
    DESCRIPTION
          "Displays the network (subnet) mask currently in use. This
           must match the masks of other devices on the same network.  "
    ::= { e300slipConfiguration    3 }

e300slipBroadcastAddressInUse   OBJECT-TYPE
    SYNTAX    IpAddress
    ACCESS    read-only
    STATUS    mandatory
    DESCRIPTION
          "Displays the broadcast address currently in use. "
    ::= { e300slipConfiguration    4 }

e300slipAddressNextReset   OBJECT-TYPE
    SYNTAX    IpAddress
    ACCESS    read-write
    STATUS    mandatory
    DESCRIPTION
          "Displays the IP address the SNMP agent will use the next
           time it is reset.  "
    ::= { e300slipConfiguration    5 }

e300slipGatewayorRouterAddrNextReset   OBJECT-TYPE
    SYNTAX    IpAddress
    ACCESS    read-write
    STATUS    mandatory
    DESCRIPTION
          "Displays the default gateway the SNMP agent will use the next
           time it is reset. "
    ::= { e300slipConfiguration    6 }

e300slipNetworkMaskNextReset   OBJECT-TYPE
    SYNTAX    IpAddress
    ACCESS    read-write
    STATUS    mandatory
    DESCRIPTION
          "Displays the netmask (subnet mask) the SNMP agent will use the next 
           time it is reset. "
    ::= { e300slipConfiguration    7 }

e300mgmtBasicInfoTable   OBJECT-TYPE
    SYNTAX    SEQUENCE OF E300mgmtBasicInfoEntry
    ACCESS    not-accessible
    STATUS    mandatory
    DESCRIPTION
          "A list of SNMP agent basic information."
    ::= { express-snmp-agents 6 }

e300mgmtBasicInfoEntry   OBJECT-TYPE
    SYNTAX    E300mgmtBasicInfoEntry
    ACCESS    not-accessible
    STATUS    mandatory
    DESCRIPTION
          "A table entry, containing SNMP agent basic information."
    INDEX    {  e300mgmtChassisIndex  }
    ::= { e300mgmtBasicInfoTable    1 }

E300mgmtBasicInfoEntry ::=
    SEQUENCE {
        e300mgmtChassisIndex
            INTEGER,
        e300mgmtIPAddress
            IpAddress,
        e300mgmtPhysicalAddress
            PhysAddress,
        e300mgmtRole   
            INTEGER
    }
    
e300mgmtChassisIndex   OBJECT-TYPE
    SYNTAX    INTEGER
    ACCESS    read-only
    STATUS    mandatory
    DESCRIPTION
          "Chassis number in the stack which SNMP agent located."
    ::= { e300mgmtBasicInfoEntry    1 }

e300mgmtIPAddress   OBJECT-TYPE
    SYNTAX    IpAddress
    ACCESS    read-only
    STATUS    mandatory
    DESCRIPTION
          "IP address of the SNMP agent."
    ::= { e300mgmtBasicInfoEntry    2 }

e300mgmtPhysicalAddress   OBJECT-TYPE
    SYNTAX    PhysAddress
    ACCESS    read-only
    STATUS    mandatory
    DESCRIPTION
          "Physical address of the SNMP agent."
    ::= { e300mgmtBasicInfoEntry    3 }

e300mgmtRole   OBJECT-TYPE
    SYNTAX  INTEGER {
            other(1),
            primaryAgent(2),
            backupAgent(3)
                        }
    ACCESS  read-only
    STATUS  mandatory
    DESCRIPTION
    "The current role of the SNMP agent within this hub stack."
    ::= { e300mgmtBasicInfoEntry    4 }

-- Trap definitions begin

utilizationThresholdExceeded        TRAP-TYPE
ENTERPRISE        express110
VARIABLES        {  rptrSegmentStatIndex }
DESCRIPTION
          "Utilization rate in last rptrSegmentUtilizationTrapPeriod 
           exceeded rptrSegmentUtilizationTrapThreshold.  "
    ::= 0

collisionThresholdExceeded        TRAP-TYPE
ENTERPRISE        express110
VARIABLES        {  rptrSegmentStatIndex }
DESCRIPTION
          "Collisions in last rptrSegmentCollisionTrapPeriod exceeded 
           rptrSegmentCollisionTrapThreshold.  "
    ::= 1

configurationChange        TRAP-TYPE
ENTERPRISE        express110
VARIABLES        {  hubDescriptionString }
DESCRIPTION
          "A chassis was added to the stack or removed, a chassis
           lost power, a module was reset or powered on, or,
           a repeater module changed speeds.  "
    ::= 2

tBrdgBufferFull      TRAP-TYPE
ENTERPRISE        express110
DESCRIPTION
          "Buffer full rate in last tBrdgPeriod exceeded tBrdgThrshld."
    ::= 3

chassisRPSActive  TRAP-TYPE
ENTERPRISE        express110
VARIABLES        {  chassisConfigTableIndex }
DESCRIPTION
          "The power supply has failed and the optional Redundant Power
           Supply for this chassis has activated."
    ::= 4

portSecurityViolation TRAP-TYPE
ENTERPRISE        express110
VARIABLES        {  chassisConfigTableIndex, portIndex  }
DESCRIPTION
          "An ethernet frame with an unauthorized source MAC address was
           detected on this port and the port has been disabled."
    ::= 5

mgmtSwitchedToBackupMgmt TRAP-TYPE
ENTERPRISE                express110
VARIABLES        {  chassisConfigTableIndex }
DESCRIPTION
          "Primary management module failed and switched to backup module.
                   The value associated is the hub number of the active management module."
    ::= 6

bridgeConfigChangeEvent TRAP-TYPE
ENTERPRISE                express110
VARIABLES                 { tBrdgHubId }
DESCRIPTION
    "The trap is sent whenever a stack's bridge configuration is changed.
         The value associated is the hub number of the active bridge."
    ::= 7

bridgeConfigNoBridgeEvent TRAP-TYPE
ENTERPRISE                express110
DESCRIPTION
    "The trap is sent whenever a stack without a bridge warning"
        ::= 8

portlinkChangeEvent TRAP-TYPE
ENTERPRISE                express110
VARIABLES                 { portChassisIndex, portModuleIndex, portIndex, portType, portOperStatus, portLinkTestStatusTrapCtrl }
DESCRIPTION
    "The trap is sent whenever the link state of a port changes
    from link up to link down or from link down to link up"
        ::= 9

portSpeedChangeEvent TRAP-TYPE
ENTERPRISE                express110
VARIABLES                 { portChassisIndex, portModuleIndex, portIndex, portType, portLinkSpeed, portSpeedStatusTrapCtrl}
DESCRIPTION
    "The trap is sent whenever the speed status of a port changes
     from link up to link down or from link down to link up"
        ::= 10

END
