InocuLAN-Alarm-MIB DEFINITIONS ::= BEGIN

	IMPORTS
		enterprises    FROM RFC1065-SMI
		OBJECT-TYPE    FROM RFC-1212
		TRAP-TYPE      FROM RFC-1215;
		
		cheyenne            OBJECT IDENTIFIER ::= { enterprises 46 }
		inoculan            OBJECT IDENTIFIER ::= { cheyenne 879 }
                inoculanNLMRev      OBJECT IDENTIFIER ::= { inoculan 1 }

-- *************************************************************************
-- InocuLAN (1.3.6.1.4.1.46.879)
-- **************************************************************************
inoculanNLMRevMajor OBJECT-TYPE
	SYNTAX INTEGER (0..65535)
	ACCESS read-only
	STATUS mandatory
	DESCRIPTION
		"The major revision level of the NLM (left of the decimal).
		Used for presence checking."
	::= { inoculanNLMRev 1 }

inoculanNLMRevMinor OBJECT-TYPE
	SYNTAX INTEGER (0..65535)
	ACCESS read-only
	STATUS mandatory
	DESCRIPTION
		"The minor revision level of the NLM (right of the decimal)."
	::= { inoculanNLMRev 2 }

inoculanParmsTrapEnable OBJECT-TYPE
	SYNTAX INTEGER (0..1)
	ACCESS read-write
	STATUS mandatory
	DESCRIPTION
		"Indicates whether agent should or should not send traps."
	::= { inoculan 2 }

inoculanParmsPollTime OBJECT-TYPE
	SYNTAX INTEGER (60..2592000)
	ACCESS read-write
	STATUS mandatory
	DESCRIPTION
		"Seconds between checking for traps."
	::= { inoculan 3 }

inoculanServerName OBJECT-TYPE
                SYNTAX OCTET STRING
                ACCESS read-only
                STATUS mandatory
                DESCRIPTION
                        "NetWare Server Which Generated Error"
                ::= {inoculan 4}        
        
inoculantrapdesc   OBJECT-TYPE
                SYNTAX OCTET STRING
                ACCESS read-only
                STATUS optional
                DESCRIPTION
                        "A description of a specific Cheyenne trap"
                ::= {inoculan 5}        
        
-- *************************************************************************
-- traps
-- **************************************************************************
inoculantrapHigh                TRAP-TYPE       
	        		ENTERPRISE	inoculan
                                VARIABLES       {
                                                inoculanServerName,
                                                inoculantrapdesc
                                                }
        			DESCRIPTION
                                        "InocuLAN Critical Trap."
                                --#TYPE "InocuLAN Critical"
                                --#SUMMARY "%s  InocuLAN: %s "
                                --#ARGUMENTS {0,1}
                                --#SEVERITY CRITICAL
                                --#STATE   DEGRADED     
	        	        ::= 1
inoculantrapMed                 TRAP-TYPE       
	        		ENTERPRISE	inoculan
                                VARIABLES       {
                                                inoculanServerName,
                                                inoculantrapdesc
                                                }
        			DESCRIPTION
                                        "InocuLAN Minor Trap"
                                --#TYPE "InocuLAN Warning"
                                --#SUMMARY "%s  InocuLAN: %s "
                                --#ARGUMENTS {0,1}
                                --#SEVERITY MINOR
                                --#TIMEINDEX 1
                                --#STATE   OPERATIONAL     
	        	        ::= 2
inoculantrapLow                 TRAP-TYPE       
	        		ENTERPRISE	inoculan
                                VARIABLES       {
                                                inoculanServerName,
                                                inoculantrapdesc
                                                }
        			DESCRIPTION
                                        "InocuLAN Informational Trap"
                                --#TYPE "InocuLAN Informational"
                                --#SUMMARY "%s  InocuLAN: %s "
                                --#ARGUMENTS {0,1}
                                --#SEVERITY INFORMATIONAL
                                --#STATE   OPERATIONAL     
	        	        ::= 3
END
