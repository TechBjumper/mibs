--
-- Netscape HTTP Server MIB for SNMP
-- Copyright (C) 1995-1996 Netscape Communications Corporation
--
-- Revision History:
-- 01/12/96 initial version, George Dong (gdong@netscape.com)
-- 04/11/96 added NT specific stats, Andy Hakim (ahakim@netscape.com)
--


NETSCAPE-MIB DEFINITIONS ::= 
BEGIN
        IMPORTS DisplayString
                        FROM RFC1213-MIB
                Counter, IpAddress, TimeTicks, enterprises
                        FROM RFC1155-SMI
                OBJECT-TYPE 
                        FROM RFC-1212;


--                TRAP-TYPE 
--                        FROM RFC1215

        netscape OBJECT IDENTIFIER ::= { enterprises 1450 }

--      
-- each server has a its own subtree and this structure is extensible 
--      
        http OBJECT IDENTIFIER ::= { netscape 1 }

--
-- here is a subtree of http service 
--
        httpEntityInfo OBJECT IDENTIFIER ::= { http 1 }


-- --------------------------------------------------------------------
-- static information on HTTP server
-- --------------------------------------------------------------------
        httpEntityTable         OBJECT-TYPE
                SYNTAX          SEQUENCE OF HttpEntityAttr
                ACCESS                  not-accessible
                STATUS                  mandatory
DESCRIPTION ""
                ::= { httpEntityInfo 1 }

        httpEntityEntry                 OBJECT-TYPE
                SYNTAX          HttpEntityAttr
                ACCESS                  not-accessible
                STATUS                  mandatory
DESCRIPTION ""
                INDEX         { httpEntityPort, httpEntityAddress }
                ::= { httpEntityTable 1 }

        HttpEntityAttr  ::= SEQUENCE {  
                httpEntityDescr                 DisplayString,
                httpEntityId            OBJECT IDENTIFIER,
                httpEntityProtocol      DisplayString,          
                httpEntityVersion       DisplayString,
                httpEntityOrganization  DisplayString,
                httpEntityLocation      DisplayString,
                httpEntityContact       DisplayString,
                httpEntityAddress       IpAddress,
                httpEntityPort          INTEGER,
                httpEntityName          DisplayString,
                httpEntityType          DisplayString,
                httpEntityMethods       DisplayString,
                httpEntityMaxProcess    INTEGER,
                httpEntityMinProcess    INTEGER,
                httpEntityMaxThread     INTEGER,
                httpEntityMinThread     INTEGER
                }       

        httpEntityDescr OBJECT-TYPE
                SYNTAX          DisplayString (SIZE (0..255))
                ACCESS          read-only
                STATUS          mandatory
                DESCRIPTION     
                                "A description of the server."
                ::= { httpEntityEntry 1 }
        
        httpEntityId  OBJECT-TYPE
                SYNTAX          OBJECT IDENTIFIER
                ACCESS          read-only
                STATUS          mandatory
                DESCRIPTION
                                "The enterprise subtree for vendors 
                                 (for example, Netscape's MIB has an 
                                 object identifier of 1.3.6.1.4.1.1450)."
                ::= { httpEntityEntry 2 }

        httpEntityProtocol OBJECT-TYPE
                SYNTAX          DisplayString
                ACCESS          read-only
                STATUS          mandatory
                DESCRIPTION     "The HTTP version number."
                ::= { httpEntityEntry 3 }

        httpEntityVersion OBJECT-TYPE
                SYNTAX          DisplayString
                ACCESS          read-only
                STATUS          mandatory
                DESCRIPTION     "The server software version number."
                ::= { httpEntityEntry 4 }

        httpEntityOrganization OBJECT-TYPE
                SYNTAX          DisplayString (SIZE (0..255))
                ACCESS          read-only
                STATUS          mandatory
                DESCRIPTION     "The organization responsible for the server."
                ::= { httpEntityEntry 5 }

        httpEntityLocation OBJECT-TYPE
                SYNTAX          DisplayString(SIZE(0..255))
                ACCESS          read-only
                STATUS          mandatory
                DESCRIPTION     
                                "Location, (for example, full path for the server)."
                ::= { httpEntityEntry 6 }

        httpEntityContact OBJECT-TYPE
                SYNTAX          DisplayString(SIZE(0..255))
                ACCESS          read-only
                STATUS          mandatory
                DESCRIPTION     
                                "The person(s) responsible for the server and contact information."
                ::= { httpEntityEntry 7 }

        httpEntityAddress OBJECT-TYPE
                SYNTAX          IpAddress
                ACCESS          read-only
                STATUS          mandatory
                DESCRIPTION     
                                "The IP address of the machine the server is running on."
                ::= { httpEntityEntry 8 }

        httpEntityPort OBJECT-TYPE
                SYNTAX          INTEGER         
                ACCESS          read-only
                STATUS          mandatory
                DESCRIPTION     
                                "The port number on which the server is listening."
                ::= { httpEntityEntry 9 }

        httpEntityName OBJECT-TYPE
                SYNTAX          DisplayString
                ACCESS          read-only
                STATUS          mandatory
                DESCRIPTION     
                                "The server's identifier name (for example, server2.a.com)."
                ::= { httpEntityEntry 10 }

        httpEntityType OBJECT-TYPE
                SYNTAX          DisplayString
                ACCESS          read-only
                STATUS          mandatory
                DESCRIPTION
                                "The type of server."
                ::= { httpEntityEntry 11 }

        httpEntityMethods OBJECT-TYPE
                SYNTAX          DisplayString
                ACCESS          read-only
                STATUS          mandatory
                DESCRIPTION     
                                "The methods supported by the server (for example, GET, POST, PUT)."
                ::= { httpEntityEntry 12 }

        httpEntityMaxProcess OBJECT-TYPE
                SYNTAX          INTEGER
                ACCESS          read-only
                STATUS          mandatory
                DESCRIPTION     
                                "The maximum number of active processes on the server.
                                (Not applicable to NT version)"
                ::= { httpEntityEntry 13 }

        httpEntityMinProcess OBJECT-TYPE
                SYNTAX          INTEGER
                ACCESS          read-only
                STATUS          mandatory
                DESCRIPTION     
                                "The minimum number of active processes on the server.
                                (Not applicable to NT version)"
                ::= { httpEntityEntry 14 }

        httpEntityMaxThread OBJECT-TYPE
                SYNTAX          INTEGER
                ACCESS          read-only
                STATUS          mandatory
                DESCRIPTION     
                                "The maximum number of active threads on the server.
                                (Not applicable to NT version)"
                ::= { httpEntityEntry 15 }

        httpEntityMinThread OBJECT-TYPE
                SYNTAX          INTEGER
                ACCESS          read-only
                STATUS          mandatory
                DESCRIPTION     
                                "The minimum number of active threads on the server.
                                (Not applicable to NT version)"
                ::= { httpEntityEntry 16 }

-- --------------------------------------------------------------------
-- statistics on HTTP server
-- --------------------------------------------------------------------
        httpStatisticsTable     OBJECT-TYPE
                SYNTAX          SEQUENCE OF HttpStatisticsAttr
                ACCESS                  not-accessible
                STATUS                  mandatory
DESCRIPTION ""
                ::= { httpEntityInfo 2 }

        httpStatisticsEntry             OBJECT-TYPE
                SYNTAX          HttpStatisticsAttr
                ACCESS                  not-accessible
                STATUS                  mandatory
DESCRIPTION ""
                INDEX         { httpStatisticsPort, httpStatisticsAddress }
                ::= { httpStatisticsTable 1 }

         HttpStatisticsAttr      ::= SEQUENCE {  
                httpStatisticsPort              INTEGER,
                httpStatisticsAddress           IpAddress,
                httpStatisticsStatus            INTEGER,
                httpStatisticsUptime            TimeTicks,
                httpStatisticsNumProcessIdle    INTEGER,
                httpStatisticsNumProcessProc    INTEGER,
                httpStatisticsNumProcessDns     INTEGER,
                httpStatisticsRequests          Counter,
                httpStatisticsRequestError      Counter,
--              httpStatisticsInUnknowns        Counter,
--              httpStatisticsInBytes           Counter,
--              httpStatisticsOutBytes          Counter,
--              httpStatisticsTimeOut           Counter,
                httpStatisticsProcessNum        INTEGER,
                httpStatisticsThreadNum         INTEGER
--              httpStatisticsAuthFail          INTEGER,
--              httpStatisticsServHang          INTEGER
                }       


        httpStatisticsPort OBJECT-TYPE
                SYNTAX          INTEGER         
                ACCESS          read-only
                STATUS          mandatory
                DESCRIPTION
                                "The port number on which this server is listening."
                ::= { httpStatisticsEntry 1 }

        httpStatisticsAddress OBJECT-TYPE
                SYNTAX          IpAddress
                ACCESS          read-only
                STATUS          mandatory
                DESCRIPTION
                                "The IP address to which this server is bound."
                ::= { httpStatisticsEntry 2 }

        httpStatisticsStatus OBJECT-TYPE
                SYNTAX          INTEGER
                ACCESS          read-only
                STATUS          mandatory
                DESCRIPTION     
                                "The status of the server (0 -- up or 1 -- down)."
                ::= { httpStatisticsEntry 3 }

        httpStatisticsUptime  OBJECT-TYPE
                SYNTAX          TimeTicks
                ACCESS          read-only
                STATUS          mandatory
                DESCRIPTION     
                                "The uptime of the server since it was started."
                ::= { httpStatisticsEntry 4 }

        httpStatisticsNumProcessIdle OBJECT-TYPE
                SYNTAX                  INTEGER
                ACCESS          read-only
                STATUS          mandatory
                DESCRIPTION     
                                "The number of server's idle processes.
                                 (Not applicable to NT version)"
                ::= { httpStatisticsEntry 5 }
        
        httpStatisticsNumProcessProc OBJECT-TYPE
                SYNTAX                  INTEGER
                ACCESS          read-only
                STATUS          mandatory
                DESCRIPTION     
                                "The number of server's processes that are processing requests.
                                 (Not applicable to NT version)"
                ::= { httpStatisticsEntry 6 }
        
        httpStatisticsNumProcessDns OBJECT-TYPE
                SYNTAX                  INTEGER
                ACCESS          read-only
                STATUS          mandatory
                DESCRIPTION     
                                "The number of processes resolving host names.
                                 (Not applicable to NT version)"
                ::= { httpStatisticsEntry 7 }
        
        httpStatisticsRequests OBJECT-TYPE
                SYNTAX                  Counter
                ACCESS          read-only
                STATUS          mandatory
                DESCRIPTION     
                                "The total number of requests received/generated."
                ::= { httpStatisticsEntry 8 }

        httpStatisticsRequestError OBJECT-TYPE
                SYNTAX                  Counter
                ACCESS          read-only
                STATUS          mandatory
                DESCRIPTION     
                                "The total number of request errors detected."
                ::= { httpStatisticsEntry 9 }

--      httpStatisticsInUnknowns OBJECT-TYPE
--              SYNTAX                  Counter
--              ACCESS          read-only
--              STATUS          mandatory
--                DESCRIPTION   
--                              "Total unknown messages received/generated."
--              ::= { httpStatisticsEntry 10 }

--      httpStatisticsInBytes OBJECT-TYPE
--              SYNTAX                  Counter
--              ACCESS          read-only
--              STATUS          mandatory
--              DESCRIPTION     
--                              "Total bytes received."
--              ::= { httpStatisticsEntry 11 }

--      httpStatisticsOutBytes OBJECT-TYPE
--              SYNTAX                  Counter
--              ACCESS          read-only
--              STATUS          mandatory
--              DESCRIPTION     
--                              "Total bytes generated."
--              ::= { httpStatisticsEntry 12 }

--      httpStatisticsTimeOut OBJECT-TYPE
--              SYNTAX                  Counter
--              ACCESS          read-only
--              STATUS          mandatory
--              DESCRIPTION     
--                              "Total number of time-outs."
--              ::= { httpStatisticsEntry 13 }

        httpStatisticsProcessNum OBJECT-TYPE
                SYNTAX                  INTEGER
                ACCESS          read-only
                STATUS          mandatory
                DESCRIPTION     
                                "The number of running processes.
                                (Not applicable to NT version)"
                ::= { httpStatisticsEntry 14 }

        httpStatisticsThreadNum OBJECT-TYPE
                SYNTAX                  INTEGER
                ACCESS          read-only
                STATUS          mandatory
                DESCRIPTION     
                                "The number of running threads.
                                (Not currently available on NT version)"
                ::= { httpStatisticsEntry 15 }


--      httpStatisticsAuthFial OBJECT-TYPE
--              SYNTAX                  INTEGER
--              ACCESS          read-only
--              STATUS          mandatory
--              DESCRIPTION     
--                              "Number of authorization failures."
--              ::= { httpStatisticsEntry 16 }

--      httpStatisticsServHang OBJECT-TYPE
--              SYNTAX                  INTEGER
--              ACCESS          read-only
--              STATUS          mandatory
--              DESCRIPTION     
--                              "Server response status:"
--                               1 = response received
--                               0 = no response received
--              ::= { httpStatisticsEntry 17 }

-- --------------------------------------------------------------------
-- statistics on HTTP server (NT specific entries)
-- --------------------------------------------------------------------
        httpNTStatisticsTable   OBJECT-TYPE
                SYNTAX          SEQUENCE OF HttpNTStatisticsAttr
                ACCESS                  not-accessible
                STATUS                  mandatory
DESCRIPTION ""
                ::= { httpEntityInfo 3 }

        httpNTStatisticsEntry   OBJECT-TYPE
                SYNTAX          HttpNTStatisticsAttr
                ACCESS                  not-accessible
                STATUS                  mandatory
DESCRIPTION ""
                INDEX           { httpStatisticsPort, httpStatisticsAddress }
                ::= { httpNTStatisticsTable 1 }

        HttpNTStatisticsAttr    ::= SEQUENCE {  
                        httpStatisticsNumBytes  Counter,
                        httpStatisticsNum2xx    Counter,
                        httpStatisticsNum3xx    Counter,
                        httpStatisticsNum4xx    Counter,
                        httpStatisticsNum5xx    Counter,
                        httpStatisticsNum200    Counter,
                        httpStatisticsNum302    Counter,
                        httpStatisticsNum304    Counter,
                        httpStatisticsNum401    Counter,
                        httpStatisticsNum403    Counter
                }       

        httpStatisticsNumBytes OBJECT-TYPE
                SYNTAX          Counter
                ACCESS          read-only
                STATUS          mandatory
                DESCRIPTION
                                "The total number of bytes sent by the server."
                ::= { httpNTStatisticsEntry 1 }

        httpStatisticsNum2xx    OBJECT-TYPE
                SYNTAX          Counter
                ACCESS          read-only
                STATUS          mandatory
                DESCRIPTION
                                "The number of 200-level status requests handled by the server."
                ::= { httpNTStatisticsEntry 2 }

        httpStatisticsNum3xx    OBJECT-TYPE
                SYNTAX          Counter
                ACCESS          read-only
                STATUS          mandatory
                DESCRIPTION
                                "The number of 300-level status requests handled by the server."
                ::= { httpNTStatisticsEntry 3 }

        httpStatisticsNum4xx    OBJECT-TYPE
                SYNTAX          Counter
                ACCESS          read-only
                STATUS          mandatory
                DESCRIPTION
                                "The number of 400-level status requests handled by the server."
                ::= { httpNTStatisticsEntry 4 }

        httpStatisticsNum5xx    OBJECT-TYPE
                SYNTAX          Counter
                ACCESS          read-only
                STATUS          mandatory
                DESCRIPTION
                                "The number of 500-level status requests handled by the server."
                ::= { httpNTStatisticsEntry 5 }

        httpStatisticsNum200    OBJECT-TYPE
                SYNTAX          Counter
                ACCESS          read-only
                STATUS          mandatory
                DESCRIPTION
                                "The number of 200 (Transfer OK) requests."
                ::= { httpNTStatisticsEntry 6 }

        httpStatisticsNum302    OBJECT-TYPE
                SYNTAX          Counter
                ACCESS          read-only
                STATUS          mandatory
                DESCRIPTION
                                "The number of 302 (Moved Temporarily) requests."
                ::= { httpNTStatisticsEntry 7 }

        httpStatisticsNum304    OBJECT-TYPE
                SYNTAX          Counter
                ACCESS          read-only
                STATUS          mandatory
                DESCRIPTION
                                "The number of 304 (Not Modified) requests."
                ::= { httpNTStatisticsEntry 8 }

        httpStatisticsNum401    OBJECT-TYPE
                SYNTAX          Counter
                ACCESS          read-only
                STATUS          mandatory
                DESCRIPTION
                                "The number of 401 (Unauthorized) requests."
                ::= { httpNTStatisticsEntry 9  }

        httpStatisticsNum403    OBJECT-TYPE
                SYNTAX          Counter
                ACCESS          read-only
                STATUS          mandatory
                DESCRIPTION
                                "The number of 403 (Forbidden) requests."
                ::= { httpNTStatisticsEntry 10 }

--
-- trap
--
--        httpEntityStatChg TRAP-TYPE
--                ENTERPRISE      http
--                VARIABLES       { httpEntityPort, httpEntityAddress }
--                DESCRIPTION     "Indicates that the httpStatisticsStatus
--                                 entity has changed."
--                ::= 100001 
                                

END
