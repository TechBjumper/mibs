-- file automatically created


TELDAT-TRAP-X28-MIB DEFINITIONS ::= BEGIN


IMPORTS
	MODULE-IDENTITY,OBJECT-TYPE,OBJECT-IDENTITY,NOTIFICATION-TYPE,Integer32,IpAddress
		FROM SNMPv2-SMI
	DisplayString
		FROM SNMPv2-TC
	telEventTraps
		FROM TELDAT-MIB;


x28TrapsMIB MODULE-IDENTITY
    LAST-UPDATED "201401200930Z"
    ORGANIZATION "Teldat, S.A."
    CONTACT-INFO 
        "Teldat, S.A.
        Customer Service

        Postal: Parque Tecnologico de Madrid
                Tres Cantos 28760
                Madrid, SPAIN

        Tel.: +34 918 076 565

        http://www.teldat.com"
    DESCRIPTION
        "This Module Information Base file is defined for managing received
        SNMP notifications generated by the X28 event subsystem."
    REVISION "201401200930Z"
    DESCRIPTION "Initial implementation"
        ::= { telEventTraps 200 }


x28EventsGroup	OBJECT IDENTIFIER	::= { x28TrapsMIB 1 }

x28Notifications	OBJECT IDENTIFIER	::= { x28TrapsMIB 2 }
x28NotificationsPrefix	OBJECT IDENTIFIER	::= { x28Notifications 0 }

x28EventObjects1 OBJECT-IDENTITY
    STATUS current
    DESCRIPTION
        "Event X28.1
        Detailed Data send to serial interface."
    ::= { x28EventsGroup 1 }

x281-interface OBJECT-TYPE
    SYNTAX DisplayString
    MAX-ACCESS accessible-for-notify
    STATUS current
    DESCRIPTION
        "Parameter 'interface' in event X28.1"
    ::= { x28EventObjects1 1 }

x281-lenght OBJECT-TYPE
    SYNTAX Integer32
    MAX-ACCESS accessible-for-notify
    STATUS current
    DESCRIPTION
        "Parameter 'lenght' in event X28.1"
    ::= { x28EventObjects1 2 }

x281-state OBJECT-TYPE
    SYNTAX Integer32
    MAX-ACCESS accessible-for-notify
    STATUS current
    DESCRIPTION
        "Parameter 'state' in event X28.1"
    ::= { x28EventObjects1 3 }

x281-hex-data OBJECT-TYPE
    SYNTAX DisplayString
    MAX-ACCESS accessible-for-notify
    STATUS current
    DESCRIPTION
        "Parameter 'hex-data' in event X28.1"
    ::= { x28EventObjects1 4 }

x28EventObjects2 OBJECT-IDENTITY
    STATUS current
    DESCRIPTION
        "Event X28.2
        Detailed Data received from serial interface."
    ::= { x28EventsGroup 2 }

x282-interface OBJECT-TYPE
    SYNTAX DisplayString
    MAX-ACCESS accessible-for-notify
    STATUS current
    DESCRIPTION
        "Parameter 'interface' in event X28.2"
    ::= { x28EventObjects2 1 }

x282-lenght OBJECT-TYPE
    SYNTAX Integer32
    MAX-ACCESS accessible-for-notify
    STATUS current
    DESCRIPTION
        "Parameter 'lenght' in event X28.2"
    ::= { x28EventObjects2 2 }

x282-state OBJECT-TYPE
    SYNTAX Integer32
    MAX-ACCESS accessible-for-notify
    STATUS current
    DESCRIPTION
        "Parameter 'state' in event X28.2"
    ::= { x28EventObjects2 3 }

x282-hex-data OBJECT-TYPE
    SYNTAX DisplayString
    MAX-ACCESS accessible-for-notify
    STATUS current
    DESCRIPTION
        "Parameter 'hex-data' in event X28.2"
    ::= { x28EventObjects2 4 }

x28EventObjects3 OBJECT-IDENTITY
    STATUS current
    DESCRIPTION
        "Event X28.3
        A change ON/OFF has been detected in Serial Control Signal Input."
    ::= { x28EventsGroup 3 }

x283-message-type OBJECT-TYPE
    SYNTAX DisplayString
    MAX-ACCESS accessible-for-notify
    STATUS current
    DESCRIPTION
        "Parameter 'message-type' in event X28.3"
    ::= { x28EventObjects3 1 }

x283-interface OBJECT-TYPE
    SYNTAX DisplayString
    MAX-ACCESS accessible-for-notify
    STATUS current
    DESCRIPTION
        "Parameter 'interface' in event X28.3"
    ::= { x28EventObjects3 2 }

x283-state OBJECT-TYPE
    SYNTAX Integer32
    MAX-ACCESS accessible-for-notify
    STATUS current
    DESCRIPTION
        "Parameter 'state' in event X28.3"
    ::= { x28EventObjects3 3 }

x28EventObjects4 OBJECT-IDENTITY
    STATUS current
    DESCRIPTION
        "Event X28.4
        BREAK signal has been received from serial interface."
    ::= { x28EventsGroup 4 }

x284-interface OBJECT-TYPE
    SYNTAX DisplayString
    MAX-ACCESS accessible-for-notify
    STATUS current
    DESCRIPTION
        "Parameter 'interface' in event X28.4"
    ::= { x28EventObjects4 1 }

x284-state OBJECT-TYPE
    SYNTAX Integer32
    MAX-ACCESS accessible-for-notify
    STATUS current
    DESCRIPTION
        "Parameter 'state' in event X28.4"
    ::= { x28EventObjects4 2 }

x28EventObjects5 OBJECT-IDENTITY
    STATUS current
    DESCRIPTION
        "Event X28.5
        Session not found, when data has been received from serial interface."
    ::= { x28EventsGroup 5 }

x285-interface OBJECT-TYPE
    SYNTAX DisplayString
    MAX-ACCESS accessible-for-notify
    STATUS current
    DESCRIPTION
        "Parameter 'interface' in event X28.5"
    ::= { x28EventObjects5 1 }

x28EventObjects6 OBJECT-IDENTITY
    STATUS current
    DESCRIPTION
        "Event X28.6
        X28 command has been received from serial interface."
    ::= { x28EventsGroup 6 }

x286-rx-cmd OBJECT-TYPE
    SYNTAX DisplayString
    MAX-ACCESS accessible-for-notify
    STATUS current
    DESCRIPTION
        "Parameter 'rx-cmd' in event X28.6"
    ::= { x28EventObjects6 1 }

x286-interface OBJECT-TYPE
    SYNTAX DisplayString
    MAX-ACCESS accessible-for-notify
    STATUS current
    DESCRIPTION
        "Parameter 'interface' in event X28.6"
    ::= { x28EventObjects6 2 }

x286-state OBJECT-TYPE
    SYNTAX Integer32
    MAX-ACCESS accessible-for-notify
    STATUS current
    DESCRIPTION
        "Parameter 'state' in event X28.6"
    ::= { x28EventObjects6 3 }


x28Notification1 NOTIFICATION-TYPE
    OBJECTS { 
              x281-interface, 
              x281-lenght,
              x281-state,
              x281-hex-data 
            }
    STATUS current
    DESCRIPTION
        "Notification of Event X28.1

        Message: 'Data transmitted to serial interface $1 ($2 bytes, st $3):$4'

        Parameters list:
              $1: x281-interface
              $2: x281-lenght
              $3: x281-state
              $4: x281-hex-data

        Detailed Data send to serial interface."
    ::= { x28NotificationsPrefix 1 }

x28Notification2 NOTIFICATION-TYPE
    OBJECTS { 
              x282-interface, 
              x282-lenght,
              x282-state,
              x282-hex-data 
            }
    STATUS current
    DESCRIPTION
        "Notification of Event X28.2

        Message: 'Data received from serial interface $1 ($2 bytes, st $3):$4'

        Parameters list:
              $1: x282-interface
              $2: x282-lenght
              $3: x282-state
              $4: x282-hex-data

        Detailed Data received from serial interface."
    ::= { x28NotificationsPrefix 2 }

x28Notification3 NOTIFICATION-TYPE
    OBJECTS { 
              x283-message-type, 
              x283-interface,
              x283-state 
            }
    STATUS current
    DESCRIPTION
        "Notification of Event X28.3

        Message: 'Serial Control Signal Input change to $1, interface $2 state $3'

        Parameters list:
              $1: x283-message-type
              $2: x283-interface
              $3: x283-state

        A change ON/OFF has been detected in Serial Control Signal Input."
    ::= { x28NotificationsPrefix 3 }

x28Notification4 NOTIFICATION-TYPE
    OBJECTS { 
              x284-interface, 
              x284-state 
            }
    STATUS current
    DESCRIPTION
        "Notification of Event X28.4

        Message: 'Received BREAK signal from ifc $1, state $2'

        Parameters list:
              $1: x284-interface
              $2: x284-state

        BREAK signal has been received from serial interface."
    ::= { x28NotificationsPrefix 4 }

x28Notification5 NOTIFICATION-TYPE
    OBJECTS { 
              x285-interface 
            }
    STATUS current
    DESCRIPTION
        "Notification of Event X28.5

        Message: 'In-Data serial data, session not found ifc $1'

        Parameters list:
              $1: x285-interface

        Session not found, when data has been received from serial interface."
    ::= { x28NotificationsPrefix 5 }

x28Notification6 NOTIFICATION-TYPE
    OBJECTS { 
              x286-rx-cmd, 
              x286-interface,
              x286-state 
            }
    STATUS current
    DESCRIPTION
        "Notification of Event X28.6

        Message: 'Received command $1 from interface $2 state $3'

        Parameters list:
              $1: x286-rx-cmd
              $2: x286-interface
              $3: x286-state

        X28 command has been received from serial interface."
    ::= { x28NotificationsPrefix 6 }


END
