UB-MIB-ASM320 { iso org(3) dod(6) internet(1) 4 1 75 }

DEFINITIONS ::= BEGIN
	IMPORTS
		OBJECT-TYPE, enterprises, Counter, TimeTicks FROM RFC1155-SMI
		DisplayString FROM RFC1158-MIB
		PhysAddress FROM RFC1213-MIB;

ubNode 			OBJECT IDENTIFIER 	::= { enterprises 75 }
ubExperimental 		OBJECT IDENTIFIER	 ::= { ubNode  6 }

UniqueIdentifier						::= INTEGER (1..65535)

asm320Prelim		OBJECT IDENTIFIER	::= { ubExperimental asm320(3)}
ubExtensions			OBJECT IDENTIFIER	::= { ubNode 7 }
ubHm				OBJECT IDENTIFIER	::= { ubExtensions 1 }

hmBasicCapability		OBJECT IDENTIFIER	::= { asm320Prelim 1 }
hmMonitorCapability	OBJECT IDENTIFIER	::= { asm320Prelim 2 }
hmAddrTrackCapability	OBJECT IDENTIFIER 	::= { asm320Prelim 3 }
ubHmBasicCapability	OBJECT IDENTIFIER	::= { ubHm 1 }
ubHmMonitorCapability	OBJECT IDENTIFIER	::= { ubHm 2 }
ubHmAddrTrackCapability	OBJECT IDENTIFIER 	::= { ubHm 3 }

hmBasicHub			OBJECT IDENTIFIER	::= { hmBasicCapability 1 }
hmBasicGroup		OBJECT IDENTIFIER	::= { hmBasicCapability 2 }
hmBasicPort			OBJECT IDENTIFIER	::= { hmBasicCapability 3 }
hmMonitorHub		OBJECT IDENTIFIER	::= { hmMonitorCapability 1 }
hmMonitorPort		OBJECT IDENTIFIER	::= { hmMonitorCapability 2 }
hmAddrTrackPort		OBJECT IDENTIFIER	::= { hmAddrTrackCapability 1 }

ubHmBasicGroup		OBJECT IDENTIFIER	::= { ubHmBasicCapability 1 }
ubHmBasicPort		OBJECT IDENTIFIER	::= { ubHmBasicCapability 2 }
ubHmMonitorGroup	OBJECT IDENTIFIER	::= { ubHmMonitorCapability 1 }
ubHmMonitorPort		OBJECT IDENTIFIER	::= { ubHmMonitorCapability 2 }

-- BASIC CONTROL CAPABILITY
-- Implementation of all variables in this group is mandatory for all managed hubs.
-- BASIC HUB 
-- Row selection: the value of hmBasHubID.
-- The Hub group contains each card in a hub cluster, which is all the cards in an Access/One enclosure that constitute a single repeater.  Examples are multiple ASM320's attached to the Ethernet backplane bus to act as a single repeater (an Ethernet bus Hub Cluster, as well as single ASM320's not attached to the this bus.  
-- Any model of Ethernet concentrator (ASM320, ASM310, ASM300, TEC900, and FEC800) may belong to a hub cluster.  When a card is added to an Ethernet bus hub cluster it retains its Group (card) management data, but resets its Hub management data.
	hmBasicHubTable OBJECT-TYPE
		SYNTAX	SEQUENCE OF HmBasicHubEntry
		ACCESS	not-accessible
		STATUS	mandatory
DESCRIPTION ""
		--@ hmBasHubID
		::= { hmBasicHub 1 }

	hmBasicHubEntry OBJECT-TYPE
		SYNTAX	HmBasicHubEntry
		ACCESS	not-accessible
		STATUS	mandatory
DESCRIPTION ""
		--@ hmBasHubID
		::= { hmBasicHubTable 1 }


	HmBasicHubEntry ::= SEQUENCE {
		hmBasHubID				INTEGER,
		hmBasHubGroupCapacity			INTEGER,
		hmBasHubHealthState			INTEGER,
		hmBasHubHealthText			DisplayString,
		hmBasHubHealthData			OCTET STRING,
		hmBasHubGroupMap			OCTET STRING,
		hmBasHubReset				INTEGER,
		hmBasHubOnlyResetTimeStamp		TimeTicks,
		hmBasHubExecuteSelfTest1Action	INTEGER,
		hmBasHubExecuteSelfTest2Action	INTEGER,
		hmBasHubResourceType			DisplayString,
		hmBasHubManufacturerID			OCTET STRING,
		hmBasHubManufacturerProductID	OCTET STRING,
		hmBasHubManufProductVersion		OCTET STRING
	}
	hmBasHubID OBJECT-TYPE
-- An identifier unique within the hub enclosure of the hub cluster, the set of cards in an Access/One enclosure that constitute a single repeater.  The hmBasHubID of the set of cards that by attachment to the Ethernet bus on the backplane form a single repeater (the Ethernet Bus Cluster) is assigned  the current slot identifier of the supervisor (the value of the supervisor's hmBasGroupID). 
--  Any other Access/One Ethernet concentrator in the hub enclosure has a hmBasHubID that is assigned the value of its hmBasGroupID.
	-- The value of hmBasHubID as well as rows in the hmBasicHubTable are assigned dynamically by the Access/One supervisor as hub clusters are formed, reformed, and deleted.
		SYNTAX	INTEGER (1..11)
		ACCESS	read-only
		STATUS	mandatory
DESCRIPTION ""
		::= { hmBasicHubEntry 1 }

	hmBasHubGroupCapacity OBJECT-TYPE
-- The number of cards that can potentially be contained within a hub cluster.
		SYNTAX	INTEGER (1..10)
		ACCESS	read-only
		STATUS	mandatory
DESCRIPTION ""
		::= { hmBasicHubEntry 2 }

	hmBasHubHealthState OBJECT-TYPE
-- Indicates whether there is a known operational failure or problem in the hub.   The hmBasHubHealthText and hmBasHubHealthData attributes may be consulted for more specific information.
		SYNTAX	INTEGER {
other(1),	-- undefined or unknown
ok(2),	-- no known failures or problems
hubFailure(3),	-- failure affecting all groups
groupFailure(4),	-- failure affecting all ports on one group
portFailure(5),	-- failure of one or more but not all ports in a group
generalFailure(6) -- some other failure or problem not covered above.

		}
		ACCESS	read-only
		STATUS	mandatory
DESCRIPTION ""
		::= { hmBasicHubEntry 3 }

	hmBasHubHealthText OBJECT-TYPE
-- Displayable information concerning the operational health of the hub and its components.  Note that hmBasHubHealthState indicates whether the condition applies to a hub, supervisor, group, or port.  This attribute contains a string that is equivalent to or provides further explanation of the value of hmBasHubHealthState as indicated in the following table:
	--hmBasHubHealthState: string
--1: 'Other'
--2: contains either  'Normal Operation', or the string  that is the value of the object a1imPodDiagnosticMsg.
--3: 'Hub Failure'
--4: 'Group Failure'
--5: 'Port Failure'
--6: contains either 'Control Bus Error' , or 'Temperature Problem'
		SYNTAX	DisplayString (SIZE(0..255))
		ACCESS	read-only
		STATUS	mandatory
DESCRIPTION ""
		::= { hmBasicHubEntry 4 }


	hmBasHubHealthData OBJECT-TYPE
-- Numeric information concerning the operational health of the hub and its components.  Note that hmBasHubHealthState indicates whether the condition applies to a hub, supervisor, group, or port.  This attribute contains some numeric value that is equivalent to or provides further explanation of the value of hmBasHubHealthState as indicated in the following table:
	--hmBasHubHealthState: value (string)
--1: 1 ('Other')
--2: contains either 1 ('Normal Operation'), or 2 (the string  that is the value of the object a1imPodDiagnosticMsg)
--3: 1 ('Hub Failure')
--4: 1 ('Group Failure')
--5: 1 ('Port Failure')
--6:  contains either 1 ('Control Bus Error'), or  2 ('Temperature Problem')
		SYNTAX	OCTET STRING (SIZE(1))
		--@formatg%-0,1:10d
		ACCESS	read-only
		STATUS	mandatory
DESCRIPTION ""
		::= { hmBasicHubEntry 5 }

	hmBasHubGroupMap OBJECT-TYPE
-- A bit string that indicates which enclosure slots are currently occupied by groups from this hub.  The first bit (starting from the left) corresponds to the first relative slot.  A '1' indicates a slot is occupied by a group that is part of this hub.
		SYNTAX	OCTET STRING (SIZE(2))
		--@formatg0x%-02x
		ACCESS	read-only
		STATUS	mandatory
DESCRIPTION ""
		::= { hmBasicHubEntry 6 }


	hmBasHubReset OBJECT-TYPE
-- Setting this object's value to resetting causes a hub to be reset without affecting the management state of the hub.    It also updates hmBasHubOnlyResetTimeStamp.  This action also effectively performs an hmBasHubExecuteSelfTest2Action.
-- This also has the effect of performing the ubHmResetGroup action on each card in this hub cluster.
		SYNTAX	INTEGER {
notResetting(1),		--'Not Resetting'
resetting(2)		--'Resetting'
		}
		ACCESS	read-write
		STATUS	mandatory
DESCRIPTION ""
		::= { hmBasicHubEntry 7 }

	hmBasHubOnlyResetTimeStamp OBJECT-TYPE
-- Records the value of sysUpTime anytime the hub is reset without management data being reset.  The resolution of the time stamp is only required to be 100 milliseconds (which is 10 TimeTicks).
		SYNTAX	TimeTicks
		ACCESS	read-only
		STATUS	mandatory
DESCRIPTION ""
		::= { hmBasicHubEntry 8 }

	hmBasHubExecuteSelfTest1Action OBJECT-TYPE
-- Setting this value to selfTesting requests that the hub perform a non-disruptive self-test. 
		SYNTAX	INTEGER {
notSelfTesting(1),	--'Not Self Testing'
selfTesting(2)		--'Self Testing'
		}
		ACCESS	read-write
		STATUS	mandatory
DESCRIPTION ""
		::= { hmBasicHubEntry 9 }


	hmBasHubExecuteSelfTest2Action OBJECT-TYPE
-- The hub performs a disruptive self-test.  This test does not affect management data and  does not inject packets onto any segment, but packets received during this test may or may not be relayed.  This test at least invokes the functionality of the ubHmExecuteGroupSelfTest2 for each group in this hub cluster.
		SYNTAX	INTEGER	{
notSelfTesting(1),	--'Not Self Testing'
selfTesting(2)		--'Self Testing'
		}
		ACCESS	read-write
		STATUS	mandatory
DESCRIPTION ""
		::= { hmBasicHubEntry 10 }

	hmBasHubResourceType OBJECT-TYPE
-- A constant: 'ResourceTypeID'.
		SYNTAX	DisplayString (SIZE(14))
		ACCESS	read-only
		STATUS	mandatory
DESCRIPTION ""
		::= { hmBasicHubEntry 11 }

	hmBasHubManufacturerID OBJECT-TYPE
-- The Organization Unique Identifier as defined in IEEE 802.1A, Overview and Architecture.  This is the first 24 bits of UB's MAC address identifying UB uniquely worldwide and is a constant equal to 00DD00 in hexadecimal.
		SYNTAX	OCTET STRING (SIZE(3))
		--@formatg%0,1:02x %1,1:02x %2,1:02x
		ACCESS	read-only
		STATUS	mandatory
DESCRIPTION ""
		::= { hmBasicHubEntry 12 }

	hmBasHubManufacturerProductID OBJECT-TYPE
-- For the cluster of concentrators attached to the Ethernet bus to form a single repeater, this is a string of ASCII characters representing the resident supervisor's product identifier (i.e., a name identifying an enumeration of a1gProductType).  Some examples are 'suprv-710' and 'suprv-790'.  For single group hubs not capable of forming a single repeater with at least one other concentrator, this is the same as hmBasGroupManufProductID.
		SYNTAX	OCTET STRING (SIZE(1..10))
		ACCESS	read-only
		STATUS	mandatory
DESCRIPTION ""
		::= { hmBasicHubEntry 13 }


	hmBasHubManufProductVersion OBJECT-TYPE
-- For the cluster of concentrators attached to the Ethernet bus to form a single repeater, this is a string that is unique for a specific hmBasHubManufacturerProductID that identifies a supervisor's hardware, firmware, and software versions.  Each of the first four octets are non-negative integers with values from 0 through 255. 
-- If a version does not apply then the version number is zero.  One is the first applicable version number.  The first octet is the hardware version, the second is the firmware version, and the third and fourth represent the software version.  The fifth and sixth octets are available for any use.
	-- For single group hubs not capable of forming a single repeater with at least one other concentrator, this is the same as hmBasGroupManufProductVersion.
		SYNTAX	OCTET STRING (SIZE(6))
		--@formatgHW %0,1:d FW %1,1:d
		ACCESS	read-only
		STATUS	mandatory
DESCRIPTION ""
		::= { hmBasicHubEntry 14 }


-- BASIC GROUP 

	hmBasicGroupTable OBJECT-TYPE
		SYNTAX	SEQUENCE OF HmBasicGroupEntry
		ACCESS	not-accessible
		STATUS	mandatory
DESCRIPTION ""
		--@ hmBasGroupID
		::= { hmBasicGroup 1 }

	hmBasicGroupEntry OBJECT-TYPE
		SYNTAX	HmBasicGroupEntry
		ACCESS	not-accessible
		STATUS	mandatory
DESCRIPTION ""
		--@ hmBasGroupID
		::= { hmBasicGroupTable 1 }

	HmBasicGroupEntry ::= SEQUENCE {
			hmBasGroupID					INTEGER,
			hmBasGroupManufacturerID			OCTET STRING,
			hmBasGroupManufProductID			OCTET STRING,
			hmBasGroupManufProductVersion		OCTET STRING,
			hmBasGroupNumOfPorts				INTEGER
	}

	hmBasGroupID OBJECT-TYPE
-- The number of the slot containing the card.
		SYNTAX	INTEGER (1..11)
		ACCESS	read-only
		STATUS	mandatory
DESCRIPTION ""
		::= { hmBasicGroupEntry 1 }


	hmBasGroupManufacturerID OBJECT-TYPE
-- The Organization Unique Identifier as defined in IEEE 802.1A, Overview and Architecture.  This is the first 24 bits of UB's MAC address identifying UB uniquely worldwide and is a constant equal to 00DD00 in hexadecimal.
		SYNTAX	OCTET STRING (SIZE(3))
		--@formatg%0,1:02x %1,1:02x %2,1:02x
		ACCESS	read-only
		STATUS	mandatory
DESCRIPTION ""
		::= { hmBasicGroupEntry 2 }

	hmBasGroupManufProductID OBJECT-TYPE
-- A string of ASCII characters  representing the concentrator's product identifier (i.e., a name identifying an enumeration of a1gProductType).  Some examples are 'ecm320-1' and 'ecm-310'.
		SYNTAX	OCTET STRING (SIZE(10))
		ACCESS	read-only
		STATUS	mandatory
DESCRIPTION ""
		::= { hmBasicGroupEntry 3 }

	hmBasGroupManufProductVersion OBJECT-TYPE
-- A string that is unique for a specific hmBasHubManufacturerProductID that identifies a concentrators's hardware, firmware, and software versions.  Each of the first four octets are non-negative integers with values from 0 through 255. 
--  If a version does not apply then the version number is zero.  One is the first applicable version number.  The first octet is the hardware version, the second is the firmware version, and the third and fourth represent the software version.  The fifth and sixth octets are available for any use.
		SYNTAX	OCTET STRING (SIZE(6))
		--@formatgHW %0,1:d FW %1,1:d 
		ACCESS	read-only
		STATUS	mandatory
DESCRIPTION ""
		::= { hmBasicGroupEntry 4 }

	hmBasGroupNumOfPorts OBJECT-TYPE
-- The number of ports in this group (includes the AUI port but not the Ethernet backplane bus 'port'.
		SYNTAX	INTEGER (1..13)
		ACCESS	read-only
		STATUS	mandatory
DESCRIPTION ""
		::= { hmBasicGroupEntry 5 }


-- BASIC GROUP  (UB Extension)

	ubHmBasicGroupTable OBJECT-TYPE
		SYNTAX	SEQUENCE OF UbHmBasicGroupEntry
		ACCESS	not-accessible
		STATUS	mandatory
DESCRIPTION ""
		--@ ubHmBasGroupID
		::= { ubHmBasicGroup 1 }

	ubHmBasicGroupEntry OBJECT-TYPE
		SYNTAX	UbHmBasicGroupEntry
		ACCESS	not-accessible
		STATUS	mandatory
DESCRIPTION ""
		--@ ubHmBasGroupID
		::= { ubHmBasicGroupTable 1 }

	UbHmBasicGroupEntry ::= SEQUENCE {
		ubHmBasGroupID					INTEGER,
		ubHmBasGroupCarrierSenses			INTEGER,
		ubHmBasGroupCustomCounterSlctn		INTEGER,
		ubHmBasGroupElectronicSerialNo		PhysAddress,
		ubHmBasGroupHealthState			INTEGER,
		ubHmBasGroupHealthText			DisplayString,
		ubHmBasGroupHealthData			OCTET STRING
	}

	ubHmBasGroupID OBJECT-TYPE
-- The relative slot number in an enclosure, starting with 1 (as numbered on the enclosure).
		SYNTAX	INTEGER	(1..11)
		ACCESS	read-only
		STATUS	mandatory
DESCRIPTION ""
		::= { ubHmBasicGroupEntry 1 }


	ubHmBasGroupCarrierSenses OBJECT-TYPE
-- The number of times carrier sense was on when sampled every 10 milliseconds.
-- Note that this attribute applies only in tier 1.
		SYNTAX	Counter
		ACCESS	read-only
		STATUS	mandatory
DESCRIPTION ""
		::= { ubHmBasicGroupEntry 2 }

	ubHmBasGroupCustomCounterSlctn OBJECT-TYPE
-- This selects which one of various events on a port will increment the ubHmBasPortCustomCounter associated with that port.  Setting this attribute also sets ubHmBasPortCustomCounter to zero.  Each occurrence of the selected event increments ubHmBasPortCustomCounter.
-- Note that this attribute only applies in tier 1.
--1.  The following values each specify an attribute counter.

-- * Non-collided packets is a composite of ReadableFrames + other frames with various errors not including hmMonHubTransmitCollisions, late collisions.

		SYNTAX	INTEGER {
carrierTooLong(1),	-- 'Carrier Too Long'
elasticityBufferErrors(2),	-- Elasticity Buffer Errors
badBitRates(3),		-- 'Bad Bit Rates'
missingSFD(4),		-- 'Missing SFD'
shortEvents(5),		-- 'Short Events '
nonCollidedPackets(6),	-- 'Non-collided Packets'
autoPartitions(7),    	-- 'Autopartition Count'
badLinkEvents(8),	-- Bad Link Events
transmitCollisions(12),	-- Transmit Collisions
receiveCollisions(13),	-- Receive Collisions
lateCollisions(14),	-- 'Late Collisions'
notApplicable(15)	-- not applicable
		}

		ACCESS	read-write
		STATUS	mandatory
DESCRIPTION ""
		::= { ubHmBasicGroupEntry 3 }

	ubHmBasGroupElectronicSerialNo OBJECT-TYPE
-- A worldwide unique identifier for a concentrator.  This is assigned from the address space of MAC addresses available to UB, and may be the same as a MAC address associated with the concentrator.
		SYNTAX	PhysAddress		(SIZE(6))
		--@formatg%0,1:02x %1,1:02x %2,1:02x %3,1:02x %4,1:02x %5,1:02x
		ACCESS	read-only
		STATUS	mandatory
DESCRIPTION ""
		::= { ubHmBasicGroupEntry 4 }

	ubHmBasGroupHealthState OBJECT-TYPE
-- Indicates whether there is a known operational failure or problem in the card.   The values of hmBasGroupHealthText and hmBasGroupHealthData attributes may be consulted for more specific information.
		SYNTAX	INTEGER {
other(1),	-- undefined or unknown
ok(2),	-- no known failures or problems
groupFailure(3),	-- failure affecting all ports in the group
portFailure(4),	-- failure of one or more but not all ports in a group
generalFailure(5) -- some other failure or problem not covered above.
		}
		ACCESS	read-only
		STATUS	mandatory
DESCRIPTION ""
		::= { ubHmBasicGroupEntry 5 }


	ubHmBasGroupHealthText OBJECT-TYPE
-- Displayable information concerning the operational health of the card and its components.  Note that ubHmBasGroupHealthState indicates whether the condition applies to a  group or port.  This attribute contains a string that is equivalent to or provides further explanation of the value of ubHmBasGroupHealthState as indicated in the following table:
	--ubHmBasGroupHealthState: string
--1: 'Other'
--2: contains either  'Normal Operation', or the string  that is the value of the object a1imPodDiagnosticMsg.
--3: 'Group Failure'
--4 'Port Failure'
--5: contains either 'Control Bus Error' , or 'Temperature Problem'
		SYNTAX	DisplayString (SIZE(0..255))
		ACCESS	read-only
		STATUS	mandatory
DESCRIPTION ""
		::= { ubHmBasicGroupEntry 6}


	ubHmBasGroupHealthData OBJECT-TYPE
-- Numeric information concerning the operational health of the group and its components.  Note that ubHmBasGroupHealthState indicates whether the condition applies to a group or  port.  This attribute contains some numeric value that is equivalent to or provides further explanation of the value of ubHmBasGroupHealthState as indicated in the following table:
	--ubHmBasGroupHealthState: value (string)
--1: 1 ('Other')
--2: contains either 1 ('Normal Operation'), or 2 (the string  that is the value of the object a1imPodDiagnosticMsg)
--3: 1 ('Group Failure')
--4: 1 ('Port Failure')
--5:  contains either 1 ('Control Bus Error'), or 2 ('Temperature Problem')
		SYNTAX	OCTET STRING (SIZE(1))
		--@formatg%-0,1:10d
		ACCESS	read-only
		STATUS	mandatory
DESCRIPTION ""
		::= { ubHmBasicGroupEntry 7 }




-- BASIC PORT 

	hmBasicPortTable OBJECT-TYPE
		SYNTAX	SEQUENCE OF HmBasicPortEntry
		ACCESS	not-accessible
		STATUS	mandatory
DESCRIPTION ""
		--@ hmBasPortGroupID, hmBasPortID
		::= { hmBasicPort 1 }

	hmBasicPortEntry OBJECT-TYPE
		SYNTAX	HmBasicPortEntry
		ACCESS	not-accessible
		STATUS	mandatory
DESCRIPTION ""
		--@ hmBasPortGroupID, hmBasPortID
		::= { hmBasicPortTable 1 }

	HmBasicPortEntry ::= SEQUENCE {
		hmBasPortGroupID			INTEGER,
		hmBasPortID				INTEGER,
		hmBasPortType			INTEGER,
		hmBasPortAdminState		INTEGER,
		hmBasPortAutoPartitionState	INTEGER
	}

	hmBasPortGroupID OBJECT-TYPE
-- The relative slot number in an enclosure, starting with 1.  This value is not greater than hmBasHubGroupCapacity.
		SYNTAX	INTEGER (1..11)
		ACCESS	read-only
		STATUS	mandatory
DESCRIPTION ""
		::= { hmBasicPortEntry 1 }

	hmBasPortID OBJECT-TYPE
-- The relative position of a port within a card starting with 1.  The AUI port identifier is 13.
		SYNTAX	INTEGER (1..13)
		ACCESS	read-only
		STATUS	mandatory
DESCRIPTION ""
		::= { hmBasicPortEntry 2 }

	hmBasPortType OBJECT-TYPE
		SYNTAX	INTEGER {
other(1),			-- 'Undefined':not listed here
repeater(2)			-- '802.3 Repeater':802.3 sec. 9  rptr port
		}
		ACCESS	read-only
		STATUS	mandatory
DESCRIPTION ""
		::= { hmBasicPortEntry 3 }

	hmBasPortAdminState OBJECT-TYPE
-- The administrative state of a port; when the unlocked action is requested, a BEGIN is exerted upon the auto-partion state machine (even if hmBasPortAdminState already has the value 'unlocked'.
		SYNTAX	INTEGER {
other(1),	--'N/A'
locked(2),	--'Locked'
unlocked(3)	--'Unlocked'
		}
		ACCESS	read-write
		STATUS	mandatory
DESCRIPTION ""
		::= { hmBasicPortEntry 4 }

	hmBasPortAutoPartitionState OBJECT-TYPE
-- Indicates whether a port has been automatically partitioned by the hub's auto-partition protection; this happens if a port signals continuous collision or there are greater than 30 consectutive collisions on the port.
		SYNTAX	INTEGER {
other(1),		--'Not Applicable'
notAutoPartitioned(2),	--'Not Auto Partitioned'
autoPartitioned(3)	--'Auto Partitioned'
		}
		ACCESS	read-only
		STATUS	mandatory
DESCRIPTION ""
		::= { hmBasicPortEntry 5 }


-- BASIC PORT  (UB Extension)

	ubHmBasicPortTable OBJECT-TYPE
		SYNTAX	SEQUENCE OF UbHmBasicPortEntry
		ACCESS	not-accessible
		STATUS	mandatory
DESCRIPTION ""
		--@ ubHmBasPortGroupID, ubHmBasPortID
		::= { ubHmBasicPort 1}

	ubHmBasicPortEntry OBJECT-TYPE
		SYNTAX	UbHmBasicPortEntry
		ACCESS	not-accessible
		STATUS	mandatory
DESCRIPTION ""
		--@ ubHmBasPortGroupID, ubHmBasPortID
		::= { ubHmBasicPortTable 1 }

	UbHmBasicPortEntry ::= SEQUENCE {
		ubHmBasPortGroupID				INTEGER,
		ubHmBasPortID					INTEGER,
		ubHmBasPortAutoPartitionType			INTEGER,
		ubHmBasPortCarrierSenses			Counter,
		ubHmBasPortCustomCounter			Counter,
		ubHmBasPortExtendedLengthMedia		INTEGER,
		ubHmBasPortLinkStatus				INTEGER,
		ubHmBasPortLinkTestAdminState		INTEGER,
		ubHmBasPortPolarityReversStat			INTEGER,
		ubHmBasPortInterfaceType			INTEGER
	}

	ubHmBasPortGroupID OBJECT-TYPE
-- The relative slot number in an enclosure, starting with 1.  This value is not greater than hmBasHubGroupCapacity.
		SYNTAX	INTEGER (1..11)
		ACCESS	read-only
		STATUS	mandatory
DESCRIPTION ""
		::= { ubHmBasicPortEntry 1 }


	ubHmBasPortID OBJECT-TYPE
-- The relative position of a port within a card starting with 1.  The AUI port identifier is 13.
		SYNTAX	INTEGER (1..13)
		ACCESS	read-only
		STATUS	mandatory
DESCRIPTION ""
		::= { ubHmBasicPortEntry 2 }

	ubHmBasPortAutoPartitionType OBJECT-TYPE
-- Indicates the reason a port was auto-partitioned: either a continuous collision signal or more than 30 consecutive collisions.
		SYNTAX	INTEGER {
notApplicable(1),			--'N/A'
collisionTooLong(2),			--'Collision Too Long'
tooManyConsecutiveCollisions(3)		--'> 30 Consecutive Collisions'
		}
		ACCESS	read-only
		STATUS	mandatory
DESCRIPTION ""
		::= { ubHmBasicPortEntry 3 }

	ubHmBasPortCarrierSenses OBJECT-TYPE
-- The number of times carrier sense was on when sampled every 10 milliseconds.  
-- Note this attribute applies in tier 1 only.
		SYNTAX	Counter
		ACCESS	read-only
		STATUS	mandatory
DESCRIPTION ""
		::= { ubHmBasicPortEntry 4 }


	ubHmBasPortCustomCounter OBJECT-TYPE
-- A counter that is incremented by one of the following occurences on this port: collision, late collision, carrier too long, bad bit rate, missing SFD, short event, non-collided packet, or auto partition. 
--  The setting of ubHmBasGroupCustomCounterSlctn determines which of these events causes this counter to increment.  See ubHmMonitorPortCollisions, hmMonPortLateCollisions, hmMonPortFramesTooLong, hmMonPortDataRateMismatches, ubHmMonitorPortMissingSFDs, hmMonPortShortEvents, ?, and hmMonPortAutoPartitionCount for a more detailed explanation of each type of respective event.
-- Note this attribute only applies in tier 1.
		SYNTAX	Counter
		ACCESS	read-only
		STATUS	mandatory
DESCRIPTION ""
		::= { ubHmBasicPortEntry 5 }

	ubHmBasPortExtendedLengthMedia OBJECT-TYPE
-- Indicates whether the segment from the (MDI, non-AUI) port is set to normal (as defined by 10BaseT) or extended length.  Note that this does not apply to AUI (external MAU) ports.
		SYNTAX	INTEGER {
notApplicable(1),	--'N/A'
normal(2),		--'Normal Length Media'
extended(3)		--'Extended Length Media'
		}
		ACCESS	read-only
		STATUS	mandatory
DESCRIPTION ""
		::= { ubHmBasicPortEntry 6 }

	ubHmBasPortLinkStatus OBJECT-TYPE
-- The result of the latest link integrity test.  Note that this does not apply to an AUI port.
		SYNTAX	INTEGER {
notApplicable(1),	-- '10BaseT Link Integrity Test OFF'
testFailed(2),		--'10BaseT Link Integrity Test Failed'
testPassed(3)		--'10BaseT Link Integrity Test Passed'
		}
		ACCESS	read-only
		STATUS	mandatory
DESCRIPTION ""
		::= { ubHmBasicPortEntry 7 }


	ubHmBasPortLinkTestAdminState OBJECT-TYPE
-- The administrative state of the 10BaseT link integrity function.  When locked, the port functions like an ASP-300.  Note that this does not apply to an AUI port.
		SYNTAX	INTEGER {
other(1),	--'N/A'
locked(2),	--'Link Integrity Test OFF'
unlocked(3)	--'Link Integrity Test ON'
		}
		ACCESS	read-write
		STATUS	mandatory
DESCRIPTION ""
		::= { ubHmBasicPortEntry 8 }

	ubHmBasPortPolarityReversStat OBJECT-TYPE
-- Indicates if the transmit/receive polarity of the twisted pair port was determined to be incorrect and then automatically corrected.  Note that this does not apply to an AUI port.
		SYNTAX	INTEGER {
other(1),	--'N/A'
normal(2),	--'Polarity Normal'
reversed(3)	--'Polarity Corrected'
		}
		ACCESS	read-only
		STATUS	mandatory
DESCRIPTION ""
		::= { ubHmBasicPortEntry 9 }

	ubHmBasPortInterfaceType OBJECT-TYPE
-- Indicates the type of interface between the (physical) port to the physical medium.
		SYNTAX	INTEGER {
notApplicable(1),	--'N/A'
mDI(2),		--@OVInternal MAU (MDI)
aUI(3)		--@OVExternal MAU (AUI)
		}
		ACCESS	read-only
		STATUS	mandatory
DESCRIPTION ""
		::= { ubHmBasicPortEntry 10 }


-- PERFORMANCE MONITOR CAPABILITY

-- Implementataion of this group is optional, but within the group all elements are mandatory.  If a managed hub implements any part of this group, the entire group shall be implemented.

-- HUB 

	hmMonitorHubTable OBJECT-TYPE
		SYNTAX	SEQUENCE OF HmMonitorHubEntry
		ACCESS	not-accessible
		STATUS	mandatory
DESCRIPTION ""
		--@ hmMonHubID
		::= { hmMonitorHub 1 }

	hmMonitorHubEntry OBJECT-TYPE
		SYNTAX	HmMonitorHubEntry
		ACCESS	not-accessible
		STATUS	mandatory
DESCRIPTION ""
		--@ hmMonHubID
		::= { hmMonitorHubTable 1 }

	HmMonitorHubEntry ::= SEQUENCE {
		hmMonHubID	UniqueIdentifier,
		hmMonHubTransmitCollisions		 Counter
	}

	hmMonHubID OBJECT-TYPE
-- The same as hmBasHubID.
		SYNTAX	INTEGER	(1..11)
		ACCESS	read-only
		STATUS	mandatory
DESCRIPTION ""
		::= { hmMonitorHubEntry 1 }


	hmMonHubTransmitCollisions OBJECT-TYPE
-- See the IEEE 802.3 Hub Management Draft Supplement for a defintion.
-- Note that when a concentrator is removed from a hub cluster this value may decrease and if a concentrator is added to a hub cluster it may increase by more than one unit.  Therefore, it is implemented like a counter, except that it may wrap in either direction and it does not always count in single units.
		SYNTAX	Counter		(0..4294967295)
		ACCESS	read-only
		STATUS	mandatory
DESCRIPTION ""
		::= { hmMonitorHubEntry 2 }


--  MONITOR CAPABILITY 
-- GROUP  (UB Extension)

	ubHmMonitorGroupTable OBJECT-TYPE
		SYNTAX	SEQUENCE OF UbHmMonitorGroupEntry
		ACCESS	not-accessible
		STATUS	mandatory
DESCRIPTION ""
		--@ ubHmMonitorGroupID
		::= { ubHmMonitorGroup 1 }

	ubHmMonitorGroupEntry OBJECT-TYPE
		SYNTAX	UbHmMonitorGroupEntry
		ACCESS	not-accessible
		STATUS	mandatory
DESCRIPTION ""
		--@ ubHmMonitorGroupID
		::= { ubHmMonitorGroupTable 1 }

	UbHmMonitorGroupEntry ::= SEQUENCE {
		ubHmMonitorGroupID				INTEGER,
		ubHmMonGroupCollisionApSlctn		INTEGER,
		ubHmMonGroupCollisions				Counter,
		ubHmMonGroupLateCollisions			Counter,
		ubHmMonGroupTotalOctets			Counter,
		ubHmMonGroupResetDrblUserAttrs		Counter
	}

	ubHmMonitorGroupID OBJECT-TYPE
-- The relative slot number in an enclosure, starting with 1 (as numbered on the enclosure).
		SYNTAX	INTEGER	(1..11)
		ACCESS	read-only
		STATUS	mandatory
DESCRIPTION ""
		::= { ubHmMonitorGroupEntry 1 }


	ubHmMonGroupCollisionApSlctn OBJECT-TYPE
-- Selects for all ports in this group which one of hmMonHubTransmitCollisions, hmMonPortLateCollisions, or hmMonPortAutoPartitionCount will increment.  This applies only to tier 2.  The default is hmMonHubTransmitCollisions.
		SYNTAX	INTEGER {
notApplicable(1),	--'N/A'
collisions(2),		--'Collisions'
lateCollisions(3),		--'Late Collisions'
autoPartitionCount(4)	--'Auto Partition Count'
		}
		ACCESS	read-write
		STATUS	mandatory
DESCRIPTION ""
		::= { ubHmMonitorGroupEntry 2 }

	ubHmMonGroupCollisions OBJECT-TYPE
-- Counts the number of times any port in this group had a transmit collision.  Simultaneous collisions on multiple ports are counted as only one group collision.
-- Note that the total of groupCollisions is not necessarily hmMonHubTransmitCollisions (in the hub).
		SYNTAX	Counter
		ACCESS	read-only
		STATUS	mandatory
DESCRIPTION ""
		::= { ubHmMonitorGroupEntry 3 }

	ubHmMonGroupLateCollisions OBJECT-TYPE
-- Counts the number of times any port in this group had transmit and receive active concurrently but late.  Simultaneous late collisions on multiple ports are counted as only one group late collision.
		SYNTAX	Counter
		ACCESS	read-only
		STATUS	mandatory
DESCRIPTION ""
		::= { ubHmMonitorGroupEntry 4 }

	ubHmMonGroupTotalOctets OBJECT-TYPE
--  
		SYNTAX	Counter
		ACCESS	read-only
		STATUS	mandatory
DESCRIPTION ""
		::= { ubHmMonitorGroupEntry 5 }


	ubHmMonGroupResetDrblUserAttrs OBJECT-TYPE
-- A request to copy the default values stored in durable memory to the User Durable attributes also in durable memory.  The User attributes affected are ubHmBasPortLinkTestAdminState, ubHmBasPortExtendedLengthMedia, hmBasPortAdminState, and a1gEthBusMgmtStatus.
		SYNTAX	INTEGER {
resetComplete(1),	-- 'Reset Complete':reset complete or never requested.
setToDefaults(2)		-- 'Durable Attributes Set to Defaults':reset user durable attributes to default values
		}
		ACCESS	read-write
		STATUS	mandatory
DESCRIPTION ""
		::= { ubHmMonitorGroupEntry 6 }


-- PORT 

	hmMonitorPortTable OBJECT-TYPE
		SYNTAX	SEQUENCE OF HmMonitorPortEntry
		ACCESS	not-accessible
		STATUS	mandatory
DESCRIPTION ""
		--@ hmMonPortGroupID, hmMonPortID
		::= { hmMonitorPort 1 }

	hmMonitorPortEntry OBJECT-TYPE
		SYNTAX	HmMonitorPortEntry
		ACCESS	not-accessible
		STATUS	mandatory
DESCRIPTION ""
		--@ hmMonPortGroupID, hmMonPortID
		::= { hmMonitorPortTable 1 }

	HmMonitorPortEntry ::= SEQUENCE {
		hmMonPortGroupID				INTEGER,
		hmMonPortID					INTEGER,
		hmMonPortReadableFrames			Counter,
		hmMonPortReadableOctets			Counter,
		hmMonPortShortEvents				Counter,
		hmMonPortRunts					Counter,
		hmMonPortFrameCheckSeqErrors		Counter,
		hmMonPortAlignmentErrors			Counter,
		hmMonPortFramesTooLong			Counter,
		hmMonPortAutoPartitionCount			Counter,
		hmMonPortDataRateMismatches			Counter,
		hmMonPortLateCollisions				Counter
	}

	hmMonPortGroupID OBJECT-TYPE
-- The relative slot number in an enclosure, starting with 1.  This value is not greater than hmBasHubGroupCapacity.
		SYNTAX	INTEGER (1..11)
		ACCESS	read-only
		STATUS	mandatory
DESCRIPTION ""
		::= { hmMonitorPortEntry 1 }

	hmMonPortID OBJECT-TYPE
-- The relative position of a port within a card starting with 1.  The AUI port identifier is 13.
		SYNTAX	INTEGER (1..13)
		ACCESS	read-only
		STATUS	mandatory
DESCRIPTION ""
		::= { hmMonitorPortEntry 2 }

	hmMonPortReadableFrames OBJECT-TYPE
-- The number of frames of legal length that have not been corrupted while being received.  It is equal to the sum of frames received ok and those received with only an out of range length error.  It does not include frames received with frame-too-long, or FCS errors, nor frames lost due to internal MAC errors, nor frames that are short events (caused by noise) or hmMonPortRunts (caused by collisions).
		SYNTAX	Counter
		ACCESS	read-only
		STATUS	mandatory
DESCRIPTION ""
		::= { hmMonitorPortEntry 3 }

	hmMonPortReadableOctets OBJECT-TYPE
-- The number of data and padding octets contained in frames counted by hmMonPortReadableFrames.  Note this does not count octets in a frame used in the preamble, the SFD, and the FCS fields of a packet.
		SYNTAX	Counter
		ACCESS	read-only
		STATUS	mandatory
DESCRIPTION ""
		::= { hmMonitorPortEntry 4 }

	hmMonPortShortEvents OBJECT-TYPE
-- A carrier sense event that lasts longer than 0 microseconds but less than or equal to 7.4 microseconds increments this counter.  A carrier sense event that lasts longer than 7.4 but less than 8.2 microseconds increments either this counter or the hmMonPortRunts counter but not both.
		SYNTAX	Counter
		ACCESS	read-only
		STATUS	mandatory
DESCRIPTION ""
		::= { hmMonitorPortEntry 5 }


	hmMonPortRunts OBJECT-TYPE
-- A carrier sense event that lasts longer than 7.4 microseconds but less than 8.2 microseconds increments either the hmMonPortShortEvents counter or this counter but not both.  A carrier sense event that lasts at least 8.2 but not longer than 63.2 microseconds increments this counter. 
--  A carrier sense event that does not result from a collision and that lasts longer than 63.2 but less than 64.0 microseconds increments either this counter or the hmMonPortLateCollisions counter but not both.
		SYNTAX	Counter
		ACCESS	read-only
		STATUS	mandatory
DESCRIPTION ""
		::= { hmMonitorPortEntry 6 }

	hmMonPortFrameCheckSeqErrors OBJECT-TYPE
-- The number of frames that are an integral number of octets and do not pass the FCS check.  
		SYNTAX	Counter
		ACCESS	read-only
		STATUS	mandatory
DESCRIPTION ""
		::= { hmMonitorPortEntry 7 }

	hmMonPortAlignmentErrors OBJECT-TYPE
-- The number of frames received on this port that are not an integral number of octets in length.  This type of error takes precedence over hmMonPortFrameCheckSeqErrors (only the hmMonPortAlignmentErrors counter is incremented).
		SYNTAX	Counter
		ACCESS	read-only
		STATUS	mandatory
DESCRIPTION ""
		::= { hmMonitorPortEntry 8 }

	hmMonPortFramesTooLong OBJECT-TYPE
-- The number of frames received that are greater than 1518 octets.
		SYNTAX	Counter
		ACCESS	read-only
		STATUS	mandatory
DESCRIPTION ""
		::= { hmMonitorPortEntry 9 }


	hmMonPortAutoPartitionCount OBJECT-TYPE
-- The number of times that the repeater has automatically partitioned this port.
		SYNTAX	Counter
		ACCESS	read-only
		STATUS	mandatory
DESCRIPTION ""
		::= { hmMonitorPortEntry 10 }

	hmMonPortDataRateMismatches OBJECT-TYPE
-- The count of times that a packet has been received with the transmission frequency (data rate) detectably out of spec.  This count may, but does not have to, include packets that were still able to be repeated (e.g., by having a sufficiently large fifo).
		SYNTAX	Counter
		ACCESS	read-only
		STATUS	mandatory
DESCRIPTION ""
		::= { hmMonitorPortEntry 11 }

	hmMonPortLateCollisions OBJECT-TYPE
-- The number of times this port detects a collision later than 512 bit times into the transmitted packet; hmMonPortLateCollisions are also counted as ubHmMonitorPortCollisions.
		SYNTAX	Counter
		ACCESS	read-only
		STATUS	mandatory
DESCRIPTION ""
		::= {  hmMonitorPortEntry 12 }


-- PORT  (UB Extension)

	ubHmMonitorPortTable OBJECT-TYPE
		SYNTAX	SEQUENCE OF UbHmMonitorPortEntry
		ACCESS	not-accessible
		STATUS	mandatory
DESCRIPTION ""
		--@ ubHmMonitorPortGroupID, ubHmMonitorPortID
		::= { ubHmMonitorPort 1 }

	ubHmMonitorPortEntry OBJECT-TYPE
		SYNTAX	UbHmMonitorPortEntry
		ACCESS	not-accessible
		STATUS	mandatory
DESCRIPTION ""
		--@ ubHmMonitorPortGroupID, ubHmMonitorPortID
		::= { ubHmMonitorPortTable 1 }

	UbHmMonitorPortEntry ::= SEQUENCE {
		ubHmMonitorPortGroupID			INTEGER,
		ubHmMonitorPortID				INTEGER,
		ubHmMonitorPortBadPackets			Counter,
		ubHmMonitorPortCollisions			Counter,
		ubHmMonitorPortLastErrorSARcvd		PhysAddress,
		ubHmMonitorPortLastRcvdFrmErr		OCTET STRING,
		ubHmMonitorPortMissingSFDs			Counter,
		ubHmMonitorPortOutOfRngLenFlds	Counter,
		ubHmMonitorPortTotalOctets			INTEGER
	}

	ubHmMonitorPortGroupID OBJECT-TYPE
-- The relative slot number in an enclosure, starting with 1.  This value is not greater than hmBasHubGroupCapacity.
		SYNTAX	INTEGER (1..11)
		ACCESS	read-only
		STATUS	mandatory
DESCRIPTION ""
		::= { ubHmMonitorPortEntry 1 }


	ubHmMonitorPortID OBJECT-TYPE
-- The relative position of a port within a card starting with 1.  The AUI port identifier is 13.
		SYNTAX	INTEGER (1..13)
		ACCESS	read-only
		STATUS	mandatory
DESCRIPTION ""
		::= { ubHmMonitorPortEntry 2 }


	ubHmMonitorPortBadPackets OBJECT-TYPE
-- A sum of hmMonPortFrameCheckSeqErrors, hmMonPortFramesTooLong, and hmMonPortAlignmentErrors.
		SYNTAX	Counter
		ACCESS	read-only
		STATUS	mandatory
DESCRIPTION ""
		::= { ubHmMonitorPortEntry 3 }

	ubHmMonitorPortCollisions OBJECT-TYPE
-- The number of times this port had transmit and receive active concurrently.  Note that the sum of all port collisions in a group is not necessarily ubHmMonGroupCollisions.
		SYNTAX	Counter
		ACCESS	read-only
		STATUS	mandatory
DESCRIPTION ""
		::= { ubHmMonitorPortEntry 4 }

	ubHmMonitorPortLastErrorSARcvd OBJECT-TYPE
-- The source MAC address of the last frame received with an error.  See ubHmMonitorPortLastRcvdFrmErr for a list of the types of errors considered.  Note that this address may be corrupted, and hence not the correct MAC address.
		SYNTAX	PhysAddress	(SIZE(6))
		--@formatg%0,1:02x %1,1:02x %2,1:02x %3,1:02x %4,1:02x %5,1:02x
		ACCESS	read-only
		STATUS	mandatory
DESCRIPTION ""
		::= { ubHmMonitorPortEntry 5 }


	ubHmMonitorPortLastRcvdFrmErr OBJECT-TYPE
-- The type of error in the frame whose source address is in ubHmMonitorPortLastErrorSARcvd.  The leftmost bit in the octet string is numbered 1, and successive bits are numbered successively.  The meaning of each bit is as follows:
-- frameTooLong(1),	'Frame Too Long'
-- excessiveJitter(2),	 'Carrier Error'
-- badBitRates(3),	'Bad Bit Rates':elasticity buffer error (FIFO)
-- carrierTooLong(4),	 'Carrier Too Long'
-- alignment(5),		'Alignment Error'
-- fcs(6),		'FCS Error'
-- notApplicable(7)	'N/A'

		SYNTAX	OCTET STRING (SIZE(1))
		ACCESS	read-only
		STATUS	mandatory
DESCRIPTION ""
		::= { ubHmMonitorPortEntry 6 }

	ubHmMonitorPortMissingSFDs OBJECT-TYPE
-- The number of  times this port detects a double-zero before a start frame delimiter.
		SYNTAX	Counter
		ACCESS	read-only
		STATUS	mandatory
DESCRIPTION ""
		::= { ubHmMonitorPortEntry 7 }

	ubHmMonitorPortOutOfRngLenFlds OBJECT-TYPE
-- The number of frames with a length field whose value is greater than the maximum value allowed for LLC frames (1500 or 5DC hex).  This could be used to count Ethernet frames (length fields whose values are 600 hex or greater).  Note these frames will also be counted as hmMonPortReadableFrames.
		SYNTAX	Counter
		ACCESS	read-only
		STATUS	mandatory
DESCRIPTION ""
		::= { ubHmMonitorPortEntry 8 }

	ubHmMonitorPortTotalOctets OBJECT-TYPE
-- The number of hmMonPortReadableOctets plus other octets (not data or padding) in frames counted by hmMonPortReadableFrames.
		SYNTAX	Counter
		ACCESS	read-only
		STATUS	mandatory
DESCRIPTION ""
		::= { ubHmMonitorPortEntry 9 }


-- SQE CAPABILITY

-- Implementataion of this group is optional, but within the group all elements are mandatory.  If a managed hub implements any part of this group, the entire group shall be implemented.



--ADDRESS TRACKING CAPABILITY


-- Implementation of this group is optional, but within the group all elements are mandatory.  If a managed hub implements any part of this group, the entire group shall be implemented.
-- PORT 

	hmAddrTrackPortTable OBJECT-TYPE
		SYNTAX	SEQUENCE OF HmAddrTrackPortEntry
		ACCESS	not-accessible
		STATUS	mandatory
DESCRIPTION ""
		--@ hmAddrTrackPortGroupID, hmAddrTrackPortID
		::= { hmAddrTrackPort 1 }

	hmAddrTrackPortEntry OBJECT-TYPE
		SYNTAX	HmAddrTrackPortEntry
		ACCESS	not-accessible
		STATUS	mandatory
DESCRIPTION ""
		--@ hmAddrTrackPortGroupID, hmAddrTrackPortID
		::= { hmAddrTrackPortTable 1 }

	HmAddrTrackPortEntry ::= SEQUENCE {
		hmAddrTrackPortGroupID					INTEGER,
		hmAddrTrackPortID					INTEGER,
		hmAddrTrackPortLastSrcAddress				PhysAddress,
		hmAddrTrackPortSrcAddrChanges		Counter
	}

	hmAddrTrackPortGroupID OBJECT-TYPE
-- The relative slot number in an enclosure, starting with 1.  This value is not greater than hmBasHubGroupCapacity.

		SYNTAX	INTEGER (1..11)
		ACCESS	read-only
		STATUS	mandatory
DESCRIPTION ""
		::= { hmAddrTrackPortEntry 1 }

	hmAddrTrackPortID OBJECT-TYPE
-- The relative position of a port within a card starting with 1.  The AUI port identifier is 13.
		SYNTAX	INTEGER (1..13)
		ACCESS	read-only
		STATUS	mandatory
DESCRIPTION ""
		::= { hmAddrTrackPortEntry 2 }

	hmAddrTrackPortLastSrcAddress OBJECT-TYPE
	-- The source address of the last readable frame received by this port.
		SYNTAX	PhysAddress	(SIZE(6))
		--@formatg%0,1:02x %1,1:02x %2,1:02x %3,1:02x %4,1:02x %5,1:02x
		ACCESS	read-only
		STATUS	mandatory
DESCRIPTION ""
		::= { hmAddrTrackPortEntry 3 }

	hmAddrTrackPortSrcAddrChanges OBJECT-TYPE
	-- The number of times that the value of hmAddrTrackPortLastSrcAddress has changed.
		SYNTAX	Counter
		ACCESS	read-only
		STATUS	mandatory
DESCRIPTION ""
		::= { hmAddrTrackPortEntry 4 }

END
