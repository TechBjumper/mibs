-- Avaya Aura Session Manager MIB
-- Copyright (c) 2008-2009 by Avaya Inc. All rights reserved. 
-- MIB version 1.0.0 
-- Avaya Compas ID: NA

AV-AURA-SESSION-MANAGER-THIRDPARTY-MIB DEFINITIONS ::= BEGIN

-- Add your MIB specific imports in the below import section.
IMPORTS 
MODULE-IDENTITY, OBJECT-TYPE, NOTIFICATION-TYPE, enterprises
    FROM SNMPv2-SMI
InetAddressIPv6
    FROM INET-ADDRESS-MIB
MODULE-COMPLIANCE, OBJECT-GROUP
    FROM SNMPv2-CONF
SnmpAdminString
    FROM SNMP-FRAMEWORK-MIB
DateAndTime
    FROM SNMPv2-TC;

        
--
-- The following are defined in Avaya Aura Session Manager-MIB
--
avaya              OBJECT IDENTIFIER ::= { enterprises 6889 }
products           OBJECT IDENTIFIER ::= { avaya 1 }
mibs               OBJECT IDENTIFIER ::= { avaya 2 }

avAuraSessMgrProd OBJECT IDENTIFIER ::= { products 36 }
avAuraSessMgrMibs MODULE-IDENTITY
       LAST-UPDATED "201301211353Z" -- 21 January 2013
       ORGANIZATION "Avaya, Inc."
       CONTACT-INFO "Avaya Customer Services

                     Postal: Avaya, Inc.
                             211 Mount Airy Rd
                             Basking Ridge. NJ 07920
                             USA
                             Tel: +1 908 953 6000
                             WWW: http://www.avaya.com"
       DESCRIPTION "This MIB module is for exposing Avaya Aura Session Manager inventory information via SNMP GET."
       
       REVISION 	"201301211353Z" -- 21 January 2013
       DESCRIPTION "MIB Version 1.0.0 - autobuild. Generated via the MIBTOOL."
             
       
       ::= { mibs 36 }

avAuraSessMgrMibNotifications OBJECT IDENTIFIER ::= { avAuraSessMgrMibs 0 }

avAuraSessMgrMibObjects OBJECT IDENTIFIER ::= { avAuraSessMgrMibs 1 }
avAuraSessMgrMibConformance OBJECT IDENTIFIER ::= { avAuraSessMgrMibs 2 }

-- Avaya Aura Session Manager Notifications (avAuraSessMgrMibNotifications) will be added here
-----------------------------------------------------------------------
-- According to RFC 2578 section 8.5, the next to last sub-identifier
-- in the name of any newly defined notification must have the value
-- zero. This is to achieve compatibility with SNMPv1 traps.
------------------------------------------------------------------------
-------------------NOTIFICATION OBJECTS *********************************START
avSessMgrTPBR4 NOTIFICATION-TYPE
	STATUS current
	DESCRIPTION
	"Postgres connection failure(Minor)"
	::= { avAuraSessMgrMibNotifications 521 }

avSessMgrTPBR5 NOTIFICATION-TYPE
	STATUS current
	DESCRIPTION
	"Postgres Integrity/Proctocol Violation(Minor)"
	::= { avAuraSessMgrMibNotifications 523 }

avSessMgrTPBR6 NOTIFICATION-TYPE
	STATUS current
	DESCRIPTION
	"Postgres invalid transaction failure(Minor)"
	::= { avAuraSessMgrMibNotifications 525 }

avSessMgrTPBR7 NOTIFICATION-TYPE
	STATUS current
	DESCRIPTION
	"Postgres insufficient resource failure(Minor)"
	::= { avAuraSessMgrMibNotifications 527 }

avSessMgrTPBR8 NOTIFICATION-TYPE
	STATUS current
	DESCRIPTION
	"Postgres resource issues failure(Minor)"
	::= { avAuraSessMgrMibNotifications 529 }

avSessMgrTPBR9 NOTIFICATION-TYPE
	STATUS current
	DESCRIPTION
	"Postgres IO/Internal errors(Minor)"
	::= { avAuraSessMgrMibNotifications 5211 }

avSessMgrTPBR10 NOTIFICATION-TYPE
	STATUS current
	DESCRIPTION
	"Postgres connection/indexing issues(Minor)"
	::= { avAuraSessMgrMibNotifications 5213 }

avSessMgrTPBR30 NOTIFICATION-TYPE
	STATUS current
	DESCRIPTION
	"Event 2057 Virtual disk degraded(Major)"
	::= { avAuraSessMgrMibNotifications 531 }

avSessMgrTPBR31 NOTIFICATION-TYPE
	STATUS current
	DESCRIPTION
	"Event 2048 Device failed(Major)"
	::= { avAuraSessMgrMibNotifications 533 }

avSessMgrTPBR32 NOTIFICATION-TYPE
	STATUS current
	DESCRIPTION
	"Event 2056/2076 Virtual disk failed(Major)"
	::= { avAuraSessMgrMibNotifications 535 }

avSessMgrTPBR33 NOTIFICATION-TYPE
	STATUS current
	DESCRIPTION
	"Event 2080/2083 Physical disk failed(Major)"
	::= { avAuraSessMgrMibNotifications 537 }

avSessMgrTPBR34 NOTIFICATION-TYPE
	STATUS current
	DESCRIPTION
	"Event 2107 Smart configuration change(Major)"
	::= { avAuraSessMgrMibNotifications 539 }

avSessMgrTPBR35 NOTIFICATION-TYPE
	STATUS current
	DESCRIPTION
	"Event 2163 Rebuild completed with errors(Major)"
	::= { avAuraSessMgrMibNotifications 5311 }

avSessMgrTPBR36 NOTIFICATION-TYPE
	STATUS current
	DESCRIPTION
	"Event 2270/2272/2273 Disk media errors(Major)"
	::= { avAuraSessMgrMibNotifications 5313 }

avSessMgrTPBR37 NOTIFICATION-TYPE
	STATUS current
	DESCRIPTION
	"EventID 2282 Hot spare SMART polling failed(Major)"
	::= { avAuraSessMgrMibNotifications 5315 }

avSessMgrTPBR38 NOTIFICATION-TYPE
	STATUS current
	DESCRIPTION
	"EventID 2307 Bad block table is full. Unable to log block(Major)"
	::= { avAuraSessMgrMibNotifications 5317 }

avSessMgrTPBR39 NOTIFICATION-TYPE
	STATUS current
	DESCRIPTION
	"Event2347/2348/2349 Physical disk rebuild failures(Major)"
	::= { avAuraSessMgrMibNotifications 5319 }

avSessMgrTPBR40 NOTIFICATION-TYPE
	STATUS current
	DESCRIPTION
	"EventID 2350 There was an unrecoverable disk media error during the rebuild(Major)"
	::= { avAuraSessMgrMibNotifications 5321 }

avSessMgrTPBR45 NOTIFICATION-TYPE
	STATUS current
	DESCRIPTION
	"EventID 1354 Power supply detected a failure Sensor location PS [1 or 2](Major)"
	::= { avAuraSessMgrMibNotifications 5323 }

avSessMgrTPBR50 NOTIFICATION-TYPE
	STATUS current
	DESCRIPTION
	"EventIDs 2102/2103 Temperature reading errors(Major)"
	::= { avAuraSessMgrMibNotifications 5325 }

avSessMgrTPBR60 NOTIFICATION-TYPE
	STATUS current
	DESCRIPTION
	"EventID 2169 The controller battery needs to be replaced(Major)"
	::= { avAuraSessMgrMibNotifications 5327 }

avSessMgrTPBR70 NOTIFICATION-TYPE
	STATUS current
	DESCRIPTION
	"EventID 2268 Storage Management has lost communication with the controller(Major)"
	::= { avAuraSessMgrMibNotifications 5329 }

avSessMgrTPBR80 NOTIFICATION-TYPE
	STATUS current
	DESCRIPTION
	"EventID 2289/2299 Multi-bit ECC error / Bad Phy(Major)"
	::= { avAuraSessMgrMibNotifications 5331 }

avSessMgrTPBR90 NOTIFICATION-TYPE
	STATUS current
	DESCRIPTION
	"Event 2320/2321 DIMM Single-bit ECC error.(Major)"
	::= { avAuraSessMgrMibNotifications 5333 }

avSessMgrTPBR100 NOTIFICATION-TYPE
	STATUS current
	DESCRIPTION
	"EventID 2340 The BGI completed with uncorrectable errors(Major)"
	::= { avAuraSessMgrMibNotifications 5335 }

avSessMgrTPBR200 NOTIFICATION-TYPE
	STATUS current
	DESCRIPTION
	"Power Supply sensor Power Unit - Redundancy Lost(Major)"
	::= { avAuraSessMgrMibNotifications 541 }

avSessMgrTPBR201 NOTIFICATION-TYPE
	STATUS current
	DESCRIPTION
	"Power Supply sensor Power Supply [1 or 2] - (Power Supply AC lost | Failure detected) Asserted(Major)"
	::= { avAuraSessMgrMibNotifications 543 }

avSessMgrTPBR210 NOTIFICATION-TYPE
	STATUS current
	DESCRIPTION
	"Drive Slot sensor Drive [0 or 1] - Drive Present Deasserted(Major)"
	::= { avAuraSessMgrMibNotifications 545 }

avSessMgrTPBR211 NOTIFICATION-TYPE
	STATUS current
	DESCRIPTION
	"Drive Slot sensor Drive [0 or 1] - In (Critical | Failed) Array Asserted(Major)"
	::= { avAuraSessMgrMibNotifications 547 }

avSessMgrTPBR212 NOTIFICATION-TYPE
	STATUS current
	DESCRIPTION
	"Drive Slot sensor Drive [0 or 1] - Rebuild Aborted Asserted(Major)"
	::= { avAuraSessMgrMibNotifications 549 }

avSessMgrTPBR213 NOTIFICATION-TYPE
	STATUS current
	DESCRIPTION
	"Drive Slot sensor Drive [0 or 1] - Predictive Failure Asserted(Major)"
	::= { avAuraSessMgrMibNotifications 5411 }

avSessMgrTPBR214 NOTIFICATION-TYPE
	STATUS current
	DESCRIPTION
	"Drive Slot sensor Drive [0 or 1] - Drive Fault Asserted(Major)"
	::= { avAuraSessMgrMibNotifications 5413 }

avSessMgrTPBR220 NOTIFICATION-TYPE
	STATUS current
	DESCRIPTION
	"Ambient Temp Upper Critical going high(Major)"
	::= { avAuraSessMgrMibNotifications 5415 }

avSessMgrTPBR230 NOTIFICATION-TYPE
	STATUS current
	DESCRIPTION
	"Planar (3.3,5,12)V Upper Critical going high(Major)"
	::= { avAuraSessMgrMibNotifications 5417 }

avSessMgrTPBR231 NOTIFICATION-TYPE
	STATUS current
	DESCRIPTION
	"Planar (3.3,5,12)V Lower Critical going low(Major)"
	::= { avAuraSessMgrMibNotifications 5419 }

avSessMgrTPBR232 NOTIFICATION-TYPE
	STATUS current
	DESCRIPTION
	"Planar VBAT Lower Critical going low(Major)"
	::= { avAuraSessMgrMibNotifications 5421 }

avSessMgrTPBR240 NOTIFICATION-TYPE
	STATUS current
	DESCRIPTION
	"Fan Tach Lower Critical going low(Major)"
	::= { avAuraSessMgrMibNotifications 5423 }

avSessMgrTPBR300 NOTIFICATION-TYPE
	STATUS current
	DESCRIPTION
	"Power Supply/Fan/Overheating alarms(Major)"
	::= { avAuraSessMgrMibNotifications 551 }

avSessMgrTPBR301 NOTIFICATION-TYPE
	STATUS current
	DESCRIPTION
	"HP hard drive alarms(Major)"
	::= { avAuraSessMgrMibNotifications 553 }

avSessMgrTPBR302 NOTIFICATION-TYPE
	STATUS current
	DESCRIPTION
	"HP RAID alarms(Major)"
	::= { avAuraSessMgrMibNotifications 555 }

avSessMgrTPBR303 NOTIFICATION-TYPE
	STATUS current
	DESCRIPTION
	"HP Memory alarms(Major)"
	::= { avAuraSessMgrMibNotifications 557 }

avSessMgrTPBR304 NOTIFICATION-TYPE
	STATUS current
	DESCRIPTION
	"RAID Battery alarms(Major)"
	::= { avAuraSessMgrMibNotifications 559 }

avSessMgrTPBR305 NOTIFICATION-TYPE
	STATUS current
	DESCRIPTION
	"RAID Controller alarms(Major)"
	::= { avAuraSessMgrMibNotifications 561 }

-------------------NOTIFICATION OBJECTS*******************************************END
END
