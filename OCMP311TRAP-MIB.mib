OCMP311TRAP-MIB DEFINITIONS ::= BEGIN

    --
    --Hewlett Packard Company
    --MIB Definition for the OpenCall Media Platform traps coming from log2trap

    IMPORTS
    OBJECT-TYPE
        FROM RFC-1212
    TRAP-TYPE
        FROM RFC-1215
    DisplayString
        FROM RFC1213-MIB
    enterprises
        FROM RFC1155-SMI;

--   private OBJECT IDENTIFIER ::= { iso(1) org(3) dod(6) internet(1) 4 }
--   enterprises OBJECT IDENTIFIER ::= { private 1 }

   hp                OBJECT IDENTIFIER ::= { enterprises 11 }
   nm                OBJECT IDENTIFIER ::= { hp 2 }
   inNetElem         OBJECT IDENTIFIER ::= { nm 29 }
   openCall          OBJECT IDENTIFIER ::= { inNetElem 2 }
   openCallTraps     OBJECT IDENTIFIER ::= { openCall 0 }
    
--==========================================================

sourcePlatformEntity OBJECT-TYPE
	SYNTAX DisplayString
	ACCESS read-only
	STATUS mandatory
	DESCRIPTION " This is the source entity that sends the trap, typically this
is a combination of platform and machine name. (ex: oc_platform, nta2225.india.hp.com"
	::= { openCallTraps 1 }

sourceObjectID OBJECT-TYPE
	SYNTAX DisplayString
	ACCESS read-only
	STATUS mandatory
	DESCRIPTION " This identifies the objectID of the instance that sends the trap. (ex: Process Name)"
	::= { openCallTraps 2 }

perceivedSeverity OBJECT-TYPE
	SYNTAX DisplayString
	ACCESS read-only
	STATUS mandatory
	DESCRIPTION " This identifies the severity of the trap. Possible severity are
		Cleared
		Informative
		Warning
		Minor
		Major
		Critical"
	::= { openCallTraps 3 }

alarmText OBJECT-TYPE
	SYNTAX DisplayString
	ACCESS read-only
	STATUS mandatory
	DESCRIPTION " This describes the alarm generating the trap."
	::= { openCallTraps 4 }

probableCause OBJECT-TYPE
	SYNTAX DisplayString
	ACCESS read-only
	STATUS mandatory
	DESCRIPTION " This identifies the probable cause of the trap."
	::= { openCallTraps 5 }

correctiveAction OBJECT-TYPE
	SYNTAX DisplayString
	ACCESS read-only
	STATUS mandatory
	DESCRIPTION " This describes the actions to apply for correcting the
problem that generated this alarm."
	::= { openCallTraps 6 }

timeStamp OBJECT-TYPE
	SYNTAX DisplayString
	ACCESS read-only
	STATUS mandatory
	DESCRIPTION " Time-Stamp recorded in the log generated by this alarm."
	::= { openCallTraps 7 }

-- necessaire de remplacer remplacer HPOC- par hHPOC-
hHPOC-20000006 TRAP-TYPE
	ENTERPRISE openCall
	VARIABLES { sourcePlatformEntity, sourceObjectID, perceivedSeverity, alarmText, probableCause, correctiveAction, timeStamp }
DESCRIPTION "Host [<string>] OCMP [<string>] launched"
	::= 20000006

hHPOC-20000007 TRAP-TYPE
	ENTERPRISE openCall
	VARIABLES { sourcePlatformEntity, sourceObjectID, perceivedSeverity, alarmText, probableCause, correctiveAction, timeStamp }
DESCRIPTION "Host [<string>] OCMP [<string>] down"
	::= 20000007

hHPOC-20000010 TRAP-TYPE
	ENTERPRISE openCall
	VARIABLES { sourcePlatformEntity, sourceObjectID, perceivedSeverity, alarmText, probableCause, correctiveAction, timeStamp }
DESCRIPTION "Host [<string>] OCMP [<string>] aborted [<string>]"
	::= 20000010

hHPOC-20000011 TRAP-TYPE
	ENTERPRISE openCall
	VARIABLES { sourcePlatformEntity, sourceObjectID, perceivedSeverity, alarmText, probableCause, correctiveAction, timeStamp }
DESCRIPTION "Host [<string>] OCMP [<string>] aborted [<string>] "
	::= 20000011

hHPOC-20000017 TRAP-TYPE
        ENTERPRISE openCall
        VARIABLES { sourcePlatformEntity, sourceObjectID, perceivedSeverity, alarmText, probableCause, correctiveAction, timeStamp }
DESCRIPTION " Platform overloaded : no outgoing calls allowed "
        ::= 20000017

hHPOC-20000018 TRAP-TYPE
        ENTERPRISE openCall
        VARIABLES { sourcePlatformEntity, sourceObjectID, perceivedSeverity, alarmText, probableCause, correctiveAction, timeStamp }
DESCRIPTION " Platform return to normal load : outgoing calls are allowed "
        ::= 20000018

hHPOC-20000019 TRAP-TYPE
        ENTERPRISE openCall
        VARIABLES { sourcePlatformEntity, sourceObjectID, perceivedSeverity, alarmText, probableCause, correctiveAction, timeStamp }
DESCRIPTION " Platform overloaded : no incoming calls allowed"
        ::= 20000019

hHPOC-20000020 TRAP-TYPE
        ENTERPRISE openCall
        VARIABLES { sourcePlatformEntity, sourceObjectID, perceivedSeverity, alarmText, probableCause, correctiveAction, timeStamp }
DESCRIPTION " Platform return to normal load : incoming calls are allowed"
        ::= 20000020

hHPOC-201000001 TRAP-TYPE
        ENTERPRISE openCall
        VARIABLES { sourcePlatformEntity, sourceObjectID, perceivedSeverity, alarmText, probableCause, correctiveAction, timeStamp }
DESCRIPTION " Service [<string>] started "
        ::= 20100001

hHPOC-201000002 TRAP-TYPE
        ENTERPRISE openCall
        VARIABLES { sourcePlatformEntity, sourceObjectID, perceivedSeverity, alarmText, probableCause, correctiveAction, timeStamp }
DESCRIPTION " Service [<string>] stopped"
        ::= 20100002

hHPOC-20200005 TRAP-TYPE
	ENTERPRISE openCall
	VARIABLES { sourcePlatformEntity, sourceObjectID, perceivedSeverity, alarmText, probableCause, correctiveAction, timeStamp }
DESCRIPTION "DPC [<string>] not available "
	::= 20200005

hHPOC-20200006 TRAP-TYPE
	ENTERPRISE openCall
	VARIABLES { sourcePlatformEntity, sourceObjectID, perceivedSeverity, alarmText, probableCause, correctiveAction, timeStamp }
DESCRIPTION "DPC [<string>] back to available state "
	::= 20200006

hHPOC-20200010 TRAP-TYPE
	ENTERPRISE openCall
	VARIABLES { sourcePlatformEntity, sourceObjectID, perceivedSeverity, alarmText, probableCause, correctiveAction, timeStamp }
DESCRIPTION "LPC [<string>] all CICs reset"
	::= 20200010

hHPOC-20200011 TRAP-TYPE
	ENTERPRISE openCall
	VARIABLES { sourcePlatformEntity, sourceObjectID, perceivedSeverity, alarmText, probableCause, correctiveAction, timeStamp }
DESCRIPTION "LPC [<string>] all CICs blocked"
	::= 20200011

hHPOC-20300001 TRAP-TYPE
	ENTERPRISE openCall
	VARIABLES { sourcePlatformEntity, sourceObjectID, perceivedSeverity, alarmText, probableCause, correctiveAction, timeStamp }
DESCRIPTION "Card [<string>] LOS Alarm"
	::= 20300001

hHPOC-20300003 TRAP-TYPE
	ENTERPRISE openCall
	VARIABLES { sourcePlatformEntity, sourceObjectID, perceivedSeverity, alarmText, probableCause, correctiveAction, timeStamp }
DESCRIPTION "Card [<string>] LOS Alarm cleared"
	::= 20300003

hHPOC-20300069 TRAP-TYPE
	ENTERPRISE openCall
	VARIABLES { sourcePlatformEntity, sourceObjectID, perceivedSeverity, alarmText, probableCause, correctiveAction, timeStamp }
DESCRIPTION "Card [<string>] DS3_LOS Alarm"
	::= 20300069

hHPOC-20300070 TRAP-TYPE
	ENTERPRISE openCall
	VARIABLES { sourcePlatformEntity, sourceObjectID, perceivedSeverity, alarmText, probableCause, correctiveAction, timeStamp }
DESCRIPTION "Card [<string>] DS3_LOS Alarm cleared"
	::= 20300070

hHPOC-20300085 TRAP-TYPE
	ENTERPRISE openCall
	VARIABLES { sourcePlatformEntity, sourceObjectID, perceivedSeverity, alarmText, probableCause, correctiveAction, timeStamp }
DESCRIPTION "E1/T1/J1 [<string>] LOS Alarm"
	::= 20300085

hHPOC-20300086 TRAP-TYPE
	ENTERPRISE openCall
	VARIABLES { sourcePlatformEntity, sourceObjectID, perceivedSeverity, alarmText, probableCause, correctiveAction, timeStamp }
DESCRIPTION "E1/T1/J1 [<string>] LOS Alarm cleared"
	::= 20300086

hHPOC-20400003 TRAP-TYPE
	ENTERPRISE openCall
	VARIABLES { sourcePlatformEntity, sourceObjectID, perceivedSeverity, alarmText, probableCause, correctiveAction, timeStamp }
DESCRIPTION "Configuration [<string>] loading failed."
	::= 20400003

hHPOC-20500003 TRAP-TYPE
	ENTERPRISE openCall
	VARIABLES { sourcePlatformEntity, sourceObjectID, perceivedSeverity, alarmText, probableCause, correctiveAction, timeStamp }
DESCRIPTION " EchoCanceller Card [<string>] failure"
	::= 20500003

hHPOC-20500004 TRAP-TYPE
        ENTERPRISE openCall
        VARIABLES { sourcePlatformEntity, sourceObjectID, perceivedSeverity, alarmText, probableCause, correctiveAction, timeStamp }
DESCRIPTION " EchoCanceller Card [<string>] failure cleared"
        ::= 20500004

hHPOC-20600002 TRAP-TYPE
	ENTERPRISE openCall
	VARIABLES { sourcePlatformEntity, sourceObjectID, perceivedSeverity, alarmText, probableCause, correctiveAction, timeStamp }
DESCRIPTION " Unable to connect to ASR/TTS server [<string>] (IP : [<string>]), connection closed or server DEAD"
	::= 20600002

hHPOC-20600005 TRAP-TYPE
	ENTERPRISE openCall
	VARIABLES { sourcePlatformEntity, sourceObjectID, perceivedSeverity, alarmText, probableCause, correctiveAction, timeStamp }
DESCRIPTION " Connection to the ASR/TTS server [<string>] is up, server ACTIVE."
        ::= 20600005

END
