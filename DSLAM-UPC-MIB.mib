-- $Workfile:   pgupc.my  $

-- $Revision:   1.1  $
-- $Date:   14 Jan 2000 13:37:42  $

-- Copyright 1998 PairGain Technologies, Inc.  All Rights
-- Reserved.  Reproduction of this document is authorized on
-- condition that the foregoing copyright notice is included.
-- This PairGain SNMP Management Information Base Specification
-- (Specification) embodies PairGain's confidential and
-- proprietary intellectual property.  PairGain retains all
-- title and ownership in the Specification, including any
-- revisions.
--
-- It is PairGain's intent to encourage the widespread use of
-- this Specification in connection with the management of
-- PairGain products. PairGain grants vendors, end-users,
-- and other interested parties a non-exclusive license to
-- use this Specification in connection with the management
-- of PairGain products.
--
-- This Specification is supplied "AS IS," and PairGain makes
-- no warranty, either expressed or implied, as to the use,
-- operation, condition, or performance of the Specification.

DSLAM-UPC-MIB DEFINITIONS ::= BEGIN

	IMPORTS
		enterprises, Gauge
            FROM RFC1155-SMI

        OBJECT-TYPE
            FROM RFC-1212
				
		Counter64, MODULE-IDENTITY FROM SNMPv2-SMI

	ifIndex
	    FROM RFC1213-MIB

	atmVplVpi, atmVclVpi, atmVclVci
		FROM ATM-MIB

	pgainDSLAM
		FROM PAIRGAIN-COMMON-HD-MIB;

	pgUpcMIB MODULE-IDENTITY
		LAST-UPDATED "9911081200Z"
		ORGANIZATION "PairGain Technologies, Inc."
		CONTACT-INFO ""
		DESCRIPTION
			"The MIB Module for UPC."
		::= { pgainDSLAM 11 }

	pgUpcObjects OBJECT IDENTIFIER ::= { pgUpcMIB 1 }

	pgAtmUpcPortTable OBJECT-TYPE
		SYNTAX	SEQUENCE OF PgAtmUpcPortEntry
		MAX-ACCESS	not-accessible
		STATUS	mandatory
		DESCRIPTION
			"A list of UPC entries for all interfaces."
		::= { pgUpcObjects 1 }

	pgAtmUpcPortEntry OBJECT-TYPE
		SYNTAX	PgAtmUpcPortEntry
		MAX-ACCESS	not-accessible
		STATUS	mandatory
		DESCRIPTION
			"An entry containing the UPC information for the ifIndex."
       INDEX   { ifIndex}
       ::= { pgAtmUpcPortTable 1 }

	PgAtmUpcPortEntry ::=
		SEQUENCE {
			pgAtmUpcPortAdminStatus	INTEGER
		}

	pgAtmUpcPortAdminStatus OBJECT-TYPE
		SYNTAX	INTEGER {
			enable(1),
			disable(2)
		}
		MAX-ACCESS  read-write
		STATUS      mandatory
		DESCRIPTION
			"The desired UPC state of the ifIndex."
		::= { pgAtmUpcPortEntry 1 }

	pgAtmUpcVplTable OBJECT-TYPE
		SYNTAX	SEQUENCE OF PgAtmUpcVplEntry
		MAX-ACCESS	not-accessible
		STATUS	mandatory
		DESCRIPTION
			"A list of UPC entries for all VPLs."
		::= { pgUpcObjects 2 }

	pgAtmUpcVplEntry OBJECT-TYPE
		SYNTAX	PgAtmUpcVplEntry
		MAX-ACCESS	not-accessible
		STATUS	mandatory
		DESCRIPTION
			"An entry containing UPC information."
		INDEX   { ifIndex, atmVplVpi}
		::= { pgAtmUpcVplTable 1 }

	PgAtmUpcVplEntry ::=
		SEQUENCE {
			pgAtmUpcVplAdminStatus	INTEGER
		}

	pgAtmUpcVplAdminStatus OBJECT-TYPE
		SYNTAX  INTEGER {
			enable(1),
			disable(2)
		}
       MAX-ACCESS  read-write
       STATUS      mandatory
       DESCRIPTION
               "The desired UPC state of the VPL."
       ::= { pgAtmUpcVplEntry 1 }

	pgAtmUpcVclTable OBJECT-TYPE
		SYNTAX	SEQUENCE OF PgAtmUpcVclEntry
		MAX-ACCESS	not-accessible
		STATUS	mandatory
		DESCRIPTION
			"A list of UPC entries for all VCLs."
		::= { pgUpcObjects 3 }

	pgAtmUpcVclEntry OBJECT-TYPE
		SYNTAX	PgAtmUpcVclEntry
		MAX-ACCESS	not-accessible
		STATUS	mandatory
		DESCRIPTION
			"An entry containing UPC information."
		INDEX   { ifIndex, atmVclVpi, atmVclVci}
		::= { pgAtmUpcVclTable 1 }

	PgAtmUpcVclEntry ::=
		SEQUENCE {
			pgAtmUpcVclAdminStatus	INTEGER
		}

	pgAtmUpcVclAdminStatus OBJECT-TYPE
		SYNTAX  INTEGER {
			enable(1),
			disable(2)
		}
		MAX-ACCESS  read-write
		STATUS      mandatory
		DESCRIPTION
			"The desired UPC state of the VCL."
		::= { pgAtmUpcVclEntry 1 }

	pgAtmVplStatTable   OBJECT-TYPE
		SYNTAX       SEQUENCE OF PgAtmVplStatEntry
		MAX-ACCESS   not-accessible
		STATUS       mandatory
		DESCRIPTION
			"This table contains all the statistics counters for
			each VPL.  Use the table to monitor VPL
			incoming cell and outgoing cell usage."
		::= { pgUpcObjects 4 }

	pgAtmVplStatEntry    OBJECT-TYPE
		SYNTAX       PgAtmVplStatEntry
		MAX-ACCESS   not-accessible
		STATUS       mandatory
		DESCRIPTION
			"Each entry in this table represents a VPL."
		INDEX { ifIndex, atmVplVpi }
		::= { pgAtmVplStatTable 1 }

	PgAtmVplStatEntry ::=
		SEQUENCE {
			pgAtmVplStatTotalCellIns		Counter64,
			pgAtmVplStatClp0CellIns			Counter64,
			pgAtmVplStatTotalDiscards		Counter64,
			pgAtmVplStatClp0Discards		Counter64,
			pgAtmVplStatTotalCellOuts		Counter64,
			pgAtmVplStatClp0CellOuts		Counter64,
			pgAtmVplStatTaggedOuts			Counter64,
			pgAtmVplStatTotalNonConforming	Counter64,
			pgAtmVplStatClearCounters     INTEGER
		}

	pgAtmVplStatTotalCellIns OBJECT-TYPE
		SYNTAX	Counter64
			MAX-ACCESS   read-only
			STATUS       mandatory
			DESCRIPTION
				"The total number of valid ATM cells received by
				this VPL including both CLP=0 and CLP=1 cells.
				The cells are counted prior to the application of
				the traffic policing."
		::= { pgAtmVplStatEntry 1 }

	pgAtmVplStatClp0CellIns OBJECT-TYPE
		SYNTAX       Counter64
		MAX-ACCESS   read-only
		STATUS       mandatory
		DESCRIPTION
			"The number of valid ATM cells received by this
			VPL with CLP=0.  The cells are counted prior to
			the application of the traffic policing."
		::= { pgAtmVplStatEntry 2 }

	pgAtmVplStatTotalDiscards OBJECT-TYPE
		SYNTAX       Counter64
		MAX-ACCESS   read-only
		STATUS       mandatory
		DESCRIPTION
			"The total number of valid ATM cells discarded by
			the traffic policing entity.  This includes cells
			originally received with CLP=0 and CLP=1."
		::= { pgAtmVplStatEntry 3 }

	pgAtmVplStatClp0Discards OBJECT-TYPE
		SYNTAX       Counter64
		MAX-ACCESS   read-only
		STATUS       mandatory
		DESCRIPTION
			"The total number of valid ATM cells received with
			CLP=0 and discarded by the traffic policing
			entity."
		::= { pgAtmVplStatEntry 4 }

	pgAtmVplStatTotalCellOuts OBJECT-TYPE
		SYNTAX       Counter64
		MAX-ACCESS   read-only
		STATUS       mandatory
		DESCRIPTION
			"The total number of valid ATM cells transmitted
			by this VPL.  This includes both CLP=0 and CLP=1
			cells."
		::= { pgAtmVplStatEntry 5 }

	pgAtmVplStatClp0CellOuts OBJECT-TYPE
		SYNTAX       Counter64
		MAX-ACCESS   read-only
		STATUS       mandatory
		DESCRIPTION
			"The total number of valid ATM cells transmitted
			with CLP=0 by this VPL."
		::= { pgAtmVplStatEntry 6 }

	pgAtmVplStatTaggedOuts OBJECT-TYPE
		SYNTAX       Counter64
		MAX-ACCESS   read-only
		STATUS       mandatory
		DESCRIPTION
			"The total number of valid ATM cells tagged by the
			traffic policing entity from CLP=0 to CLP=1 and
			transmitted by this VPL."
		::= { pgAtmVplStatEntry 7 }

	pgAtmVplStatTotalNonConforming OBJECT-TYPE
		SYNTAX       Counter64
		MAX-ACCESS   read-only
		STATUS       mandatory
		DESCRIPTION
			"For this VPL, the total number of valid ATM cells
			that violated the traffic service contract."
		::= { pgAtmVplStatEntry 8 }

	pgAtmVplStatClearCounters OBJECT-TYPE
		SYNTAX  INTEGER {
			clear(1)
		}
		MAX-ACCESS  write-only
		STATUS  mandatory
		DESCRIPTION
			"For this VPL, clear the statistics counters to zero."
		::= { pgAtmVplStatEntry 9 }

	pgAtmVplStatAllClearCounters OBJECT-TYPE
		SYNTAX  INTEGER {
			clear(1)
		}
		MAX-ACCESS  read-write
		STATUS  mandatory
		DESCRIPTION
			"For all VPLs, clear the statistics counters to zero."
		::= { pgUpcObjects 5 }

	-- ATM VCL Statistics Table

	pgAtmVclStatTable   OBJECT-TYPE
		SYNTAX       SEQUENCE OF PgAtmVclStatEntry
		MAX-ACCESS   not-accessible
		STATUS       mandatory
		DESCRIPTION
			"This table contains all the statistics counters for
			each VCL.  Use the table to monitor VCL
			incoming cell and outgoing cell usage."
		::= { pgUpcObjects 6 }

	pgAtmVclStatEntry    OBJECT-TYPE
		SYNTAX       PgAtmVclStatEntry
		MAX-ACCESS   not-accessible
		STATUS       mandatory
		DESCRIPTION
			"Each entry in this table represents a VCL."
		INDEX { ifIndex, atmVclVpi, atmVclVci }
		::= { pgAtmVclStatTable 1 }

	PgAtmVclStatEntry ::=
		SEQUENCE {
			pgAtmVclStatTotalCellIns		Counter64,
			pgAtmVclStatClp0CellIns			Counter64,
			pgAtmVclStatTotalDiscards		Counter64,
			pgAtmVclStatClp0Discards		Counter64,
			pgAtmVclStatTotalCellOuts		Counter64,
			pgAtmVclStatClp0CellOuts		Counter64,
			pgAtmVclStatTaggedOuts			Counter64,
			pgAtmVclStatTotalNonConforming	Counter64,
			pgAtmVclStatClearCounters     INTEGER
		}

	pgAtmVclStatTotalCellIns OBJECT-TYPE
		SYNTAX       Counter64
		MAX-ACCESS   read-only
		STATUS       mandatory
		DESCRIPTION
			"The total number of valid ATM cells received by
			this VCL including both CLP=0 and CLP=1 cells.
			The cells are counted prior to the application of
			the traffic policing."
		::= { pgAtmVclStatEntry 1 }

	pgAtmVclStatClp0CellIns OBJECT-TYPE
		SYNTAX       Counter64
		MAX-ACCESS   read-only
		STATUS       mandatory
		DESCRIPTION
			"The number of valid ATM cells received by this
			VCL with CLP=0.  The cells are counted prior to
			the application of the traffic policing."
		::= { pgAtmVclStatEntry 2 }

	pgAtmVclStatTotalDiscards OBJECT-TYPE
		SYNTAX       Counter64
		MAX-ACCESS   read-only
		STATUS       mandatory
		DESCRIPTION
			"The total number of valid ATM cells discarded by
			the traffic policing entity.  This includes cells
			originally received with CLP=0 and CLP=1."
		::= { pgAtmVclStatEntry 3 }

	pgAtmVclStatClp0Discards OBJECT-TYPE
		SYNTAX       Counter64
		MAX-ACCESS   read-only
		STATUS       mandatory
		DESCRIPTION
			"The total number of valid ATM cells received with
			CLP=0 and discarded by the traffic policing
			entity."
		::= { pgAtmVclStatEntry 4 }

	pgAtmVclStatTotalCellOuts OBJECT-TYPE
		SYNTAX       Counter64
		MAX-ACCESS   read-only
		STATUS       mandatory
		DESCRIPTION
			"The total number of valid ATM cells transmitted
			by this VCL.  This includes both CLP=0 and CLP=1
			cells."
		::= { pgAtmVclStatEntry 5 }

	pgAtmVclStatClp0CellOuts OBJECT-TYPE
		SYNTAX       Counter64
		MAX-ACCESS   read-only
		STATUS       mandatory
		DESCRIPTION
			"The total number of valid ATM cells transmitted
			with CLP=0 by this VCL."
		::= { pgAtmVclStatEntry 6 }

	pgAtmVclStatTaggedOuts OBJECT-TYPE
		SYNTAX       Counter64
		MAX-ACCESS   read-only
		STATUS       mandatory
		DESCRIPTION
			"The total number of valid ATM cells tagged by the
			traffic policing entity from CLP=0 to CLP=1 and
			transmitted by this VCL."
		::= { pgAtmVclStatEntry 7 }

	pgAtmVclStatTotalNonConforming OBJECT-TYPE
		SYNTAX       Counter64
		MAX-ACCESS   read-only
		STATUS       mandatory
		DESCRIPTION
			"For this VCL, the total number of valid ATM cells that
			violated the traffic service contract."
		::= { pgAtmVclStatEntry 8 }

	pgAtmVclStatClearCounters OBJECT-TYPE
		SYNTAX  INTEGER {
			clear(1)
		}
		MAX-ACCESS  write-only
		STATUS  mandatory
		DESCRIPTION
			"For this VCL, clear statistics counters to zero."
		::= { pgAtmVclStatEntry 9 }

	pgAtmVclStatAllClearCounters OBJECT-TYPE
		SYNTAX  INTEGER {
			clear(1)
		}
		MAX-ACCESS  read-write
		STATUS  mandatory
		DESCRIPTION
			"For all VCLs, clear statistics counters to zero."
		::= { pgUpcObjects 7 }

END
