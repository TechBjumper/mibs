----------------------------------------------------------------
-- SOCOMEC DIRIS BCMS 720 MIB FILE
--
-- Revision 1.01
-- Feb 15 2013
----------------------------------------------------------------
DIRISBCMS DEFINITIONS ::= BEGIN

IMPORTS
  org, iso, dod, internet, directory, mgmt, experimental, private, enterprises
    FROM RFC1155-SMI
  OBJECT-TYPE
    FROM RFC-1212
  DisplayString
    FROM RFC-1213;

----------------------------------------------------------------
-- OID hierarchy
----------------------------------------------------------------

socomec        OBJECT IDENTIFIER ::= { enterprises 24436 }
diris        OBJECT IDENTIFIER ::= { socomec 1 }
bcms720                                              OBJECT IDENTIFIER ::= { diris 3 }
measures              OBJECT IDENTIFIER ::= { bcms720 2 }
registers                OBJECT IDENTIFIER ::= { measures 8 }
panelboard1        OBJECT IDENTIFIER ::= { registers 1 }
panelboard2        OBJECT IDENTIFIER ::= { registers 2 }

----------------------------------------------------------------
-- BCMS register values
----------------------------------------------------------------

pb1-branch1-current
                OBJECT-TYPE
                SYNTAX  INTEGER
                ACCESS  read-only
                STATUS  mandatory
                DESCRIPTION "BRANCH 1 Current
                                    Note for all currents: 100 = 10.0 amps"
                              ::= { panelboard1 101 }

pb1-branch2-current
                OBJECT-TYPE
                SYNTAX  INTEGER
                ACCESS  read-only
                STATUS  mandatory
                DESCRIPTION "BRANCH 2 Current"
                              ::= { panelboard1 102 }

pb1-branch3-current
                OBJECT-TYPE
                SYNTAX  INTEGER
                ACCESS  read-only
                STATUS  mandatory
                DESCRIPTION "BRANCH 3 Current"
                              ::= { panelboard1 103 }

pb1-branch4-current
                OBJECT-TYPE
                SYNTAX  INTEGER
                ACCESS  read-only
                STATUS  mandatory
                DESCRIPTION "BRANCH 4 Current"
                              ::= { panelboard1 104 }

pb1-branch5-current
                OBJECT-TYPE
                SYNTAX  INTEGER
                ACCESS  read-only
                STATUS  mandatory
                DESCRIPTION "BRANCH 5 Current"
                              ::= { panelboard1 105 }

pb1-branch6-current
                OBJECT-TYPE
                SYNTAX  INTEGER
                ACCESS  read-only
                STATUS  mandatory
                DESCRIPTION "BRANCH 6 Current"
                              ::= { panelboard1 106 }

pb1-branch7-current
                OBJECT-TYPE
                SYNTAX  INTEGER
                ACCESS  read-only
                STATUS  mandatory
                DESCRIPTION "BRANCH 7 Current"
                              ::= { panelboard1 107 }

pb1-branch8-current
                OBJECT-TYPE
                SYNTAX  INTEGER
                ACCESS  read-only
                STATUS  mandatory
                DESCRIPTION "BRANCH 8 Current"
                              ::= { panelboard1 108 }

pb1-branch9-current
                OBJECT-TYPE
                SYNTAX  INTEGER
                ACCESS  read-only
                STATUS  mandatory
                DESCRIPTION "BRANCH 9 Current"
                              ::= { panelboard1 109 }

pb1-branch10-current
                OBJECT-TYPE
                SYNTAX  INTEGER
                ACCESS  read-only
                STATUS  mandatory
                DESCRIPTION "BRANCH 10 Current"
                              ::= { panelboard1 110 }

pb1-branch11-current
                OBJECT-TYPE
                SYNTAX  INTEGER
                ACCESS  read-only
                STATUS  mandatory
                DESCRIPTION "BRANCH 11 Current"
                              ::= { panelboard1 111 }

pb1-branch12-current
                OBJECT-TYPE
                SYNTAX  INTEGER
                ACCESS  read-only
                STATUS  mandatory
                DESCRIPTION "BRANCH 12 Current"
                              ::= { panelboard1 112 }

pb1-branch13-current
                OBJECT-TYPE
                SYNTAX  INTEGER
                ACCESS  read-only
                STATUS  mandatory
                DESCRIPTION "BRANCH 13 Current"
                              ::= { panelboard1 113 }

pb1-branch14-current
                OBJECT-TYPE
                SYNTAX  INTEGER
                ACCESS  read-only
                STATUS  mandatory
                DESCRIPTION "BRANCH 14 Current"
                              ::= { panelboard1 114 }

pb1-branch15-current
                OBJECT-TYPE
                SYNTAX  INTEGER
                ACCESS  read-only
                STATUS  mandatory
                DESCRIPTION "BRANCH 15 Current"
                              ::= { panelboard1 115 }

pb1-branch16-current
                OBJECT-TYPE
                SYNTAX  INTEGER
                ACCESS  read-only
                STATUS  mandatory
                DESCRIPTION "BRANCH 16 Current"
                              ::= { panelboard1 116 }

pb1-branch17-current
                OBJECT-TYPE
                SYNTAX  INTEGER
                ACCESS  read-only
                STATUS  mandatory
                DESCRIPTION "BRANCH 17 Current"
                              ::= { panelboard1 117 }

pb1-branch18-current
                OBJECT-TYPE
                SYNTAX  INTEGER
                ACCESS  read-only
                STATUS  mandatory
                DESCRIPTION "BRANCH 18 Current"
                              ::= { panelboard1 118 }

pb1-branch19-current
                OBJECT-TYPE
                SYNTAX  INTEGER
                ACCESS  read-only
                STATUS  mandatory
                DESCRIPTION "BRANCH 19 Current"
                              ::= { panelboard1 119 }

pb1-branch20-current
                OBJECT-TYPE
                SYNTAX  INTEGER
                ACCESS  read-only
                STATUS  mandatory
                DESCRIPTION "BRANCH 20 Current"
                              ::= { panelboard1 120 }

pb1-branch21-current
                OBJECT-TYPE
                SYNTAX  INTEGER
                ACCESS  read-only
                STATUS  mandatory
                DESCRIPTION "BRANCH 21 Current"
                              ::= { panelboard1 121 }

pb1-branch22-current
                OBJECT-TYPE
                SYNTAX  INTEGER
                ACCESS  read-only
                STATUS  mandatory
                DESCRIPTION "BRANCH 22 Current"
                              ::= { panelboard1 122 }

pb1-branch23-current
                OBJECT-TYPE
                SYNTAX  INTEGER
                ACCESS  read-only
                STATUS  mandatory
                DESCRIPTION "BRANCH 23 Current"
                              ::= { panelboard1 123 }

pb1-branch24-current
                OBJECT-TYPE
                SYNTAX  INTEGER
                ACCESS  read-only
                STATUS  mandatory
                DESCRIPTION "BRANCH 24 Current"
                              ::= { panelboard1 124 }

pb1-branch25-current
                OBJECT-TYPE
                SYNTAX  INTEGER
                ACCESS  read-only
                STATUS  mandatory
                DESCRIPTION "BRANCH 25 Current"
                              ::= { panelboard1 125 }

pb1-branch26-current
                OBJECT-TYPE
                SYNTAX  INTEGER
                ACCESS  read-only
                STATUS  mandatory
                DESCRIPTION "BRANCH26 Current"
                              ::= { panelboard1 126 }

pb1-branch27-current
                OBJECT-TYPE
                SYNTAX  INTEGER
                ACCESS  read-only
                STATUS  mandatory
                DESCRIPTION "BRANCH27 Current"
                              ::= { panelboard1 127 }

pb1-branch28-current
                OBJECT-TYPE
                SYNTAX  INTEGER
                ACCESS  read-only
                STATUS  mandatory
                DESCRIPTION "BRANCH 28 Current"
                              ::= { panelboard1 128 }

pb1-branch29-current
                OBJECT-TYPE
                SYNTAX  INTEGER
                ACCESS  read-only
                STATUS  mandatory
                DESCRIPTION "BRANCH 29 Current"
                              ::= { panelboard1 129 }

pb1-branch30-current
                OBJECT-TYPE
                SYNTAX  INTEGER
                ACCESS  read-only
                STATUS  mandatory
                DESCRIPTION "BRANCH 30 Current"
                              ::= { panelboard1 130 }

pb1-branch31-current
                OBJECT-TYPE
                SYNTAX  INTEGER
                ACCESS  read-only
                STATUS  mandatory
                DESCRIPTION "BRANCH 31 Current"
                              ::= { panelboard1 131 }

pb1-branch32-current
                OBJECT-TYPE
                SYNTAX  INTEGER
                ACCESS  read-only
                STATUS  mandatory
                DESCRIPTION "BRANCH 32 Current"
                              ::= { panelboard1 132 }

pb1-branch33-current
                OBJECT-TYPE
                SYNTAX  INTEGER
                ACCESS  read-only
                STATUS  mandatory
                DESCRIPTION "BRANCH 33 Current"
                              ::= { panelboard1 133 }

pb1-branch34-current
                OBJECT-TYPE
                SYNTAX  INTEGER
                ACCESS  read-only
                STATUS  mandatory
                DESCRIPTION "BRANCH 34 Current"
                              ::= { panelboard1 134 }

pb1-branch35-current
                OBJECT-TYPE
                SYNTAX  INTEGER
                ACCESS  read-only
                STATUS  mandatory
                DESCRIPTION "BRANCH 35 Current"
                              ::= { panelboard1 135 }

pb1-branch36-current
                OBJECT-TYPE
                SYNTAX  INTEGER
                ACCESS  read-only
                STATUS  mandatory
                DESCRIPTION "BRANCH 36 Current"
                              ::= { panelboard1 136 }

pb1-branch37-current
                OBJECT-TYPE
                SYNTAX  INTEGER
                ACCESS  read-only
                STATUS  mandatory
                DESCRIPTION "BRANCH 37 Current"
                              ::= { panelboard1 137 }

pb1-branch38-current
                OBJECT-TYPE
                SYNTAX  INTEGER
                ACCESS  read-only
                STATUS  mandatory
                DESCRIPTION "BRANCH 38 Current"
                              ::= { panelboard1 138 }

pb1-branch39-current
                OBJECT-TYPE
                SYNTAX  INTEGER
                ACCESS  read-only
                STATUS  mandatory
                DESCRIPTION "BRANCH39 Current"
                              ::= { panelboard1 139 }

pb1-branch40-current
                OBJECT-TYPE
                SYNTAX  INTEGER
                ACCESS  read-only
                STATUS  mandatory
                DESCRIPTION "BRANCH 40 Current"
                              ::= { panelboard1 140 }

pb1-branch41-current
                OBJECT-TYPE
                SYNTAX  INTEGER
                ACCESS  read-only
                STATUS  mandatory
                DESCRIPTION "BRANCH 41 Current"
                              ::= { panelboard1 141 }

pb1-branch42-current
                OBJECT-TYPE
                SYNTAX  INTEGER
                ACCESS  read-only
                STATUS  mandatory
                DESCRIPTION "BRANCH 42 Current"
                              ::= { panelboard1 142 }

pb1-branch43-current
                OBJECT-TYPE
                SYNTAX  INTEGER
                ACCESS  read-only
                STATUS  mandatory
                DESCRIPTION "BRANCH 43 Current"
                              ::= { panelboard1 143 }

pb1-branch44-current
                OBJECT-TYPE
                SYNTAX  INTEGER
                ACCESS  read-only
                STATUS  mandatory
                DESCRIPTION "BRANCH 44 Current"
                              ::= { panelboard1 144 }

pb1-branch45-current
                OBJECT-TYPE
                SYNTAX  INTEGER
                ACCESS  read-only
                STATUS  mandatory
                DESCRIPTION "BRANCH 45 Current"
                              ::= { panelboard1 145 }

pb1-branch46-current
                OBJECT-TYPE
                SYNTAX  INTEGER
                ACCESS  read-only
                STATUS  mandatory
                DESCRIPTION "BRANCH 46 Current"
                              ::= { panelboard1 146 }

pb1-branch47-current
                OBJECT-TYPE
                SYNTAX  INTEGER
                ACCESS  read-only
                STATUS  mandatory
                DESCRIPTION "BRANCH 47 Current"
                              ::= { panelboard1 147 }

pb1-branch48-current
                OBJECT-TYPE
                SYNTAX  INTEGER
                ACCESS  read-only
                STATUS  mandatory
                DESCRIPTION "BRANCH 48 Current"
                              ::= { panelboard1 148 }

pb1-branch49-current
                OBJECT-TYPE
                SYNTAX  INTEGER
                ACCESS  read-only
                STATUS  mandatory
                DESCRIPTION "BRANCH 49 Current"
                              ::= { panelboard1 149 }

pb1-branch50-current
                OBJECT-TYPE
                SYNTAX  INTEGER
                ACCESS  read-only
                STATUS  mandatory
                DESCRIPTION "BRANCH 50 Current"
                              ::= { panelboard1 150 }

pb1-branch51-current
                OBJECT-TYPE
                SYNTAX  INTEGER
                ACCESS  read-only
                STATUS  mandatory
                DESCRIPTION "BRANCH 51 Current"
                              ::= { panelboard1 151 }

pb1-branch52-current
                OBJECT-TYPE
                SYNTAX  INTEGER
                ACCESS  read-only
                STATUS  mandatory
                DESCRIPTION "BRANCH 52 Current"
                              ::= { panelboard1 152 }

pb1-branch53-current
                OBJECT-TYPE
                SYNTAX  INTEGER
                ACCESS  read-only
                STATUS  mandatory
                DESCRIPTION "BRANCH 53 Current"
                              ::= { panelboard1 153 }

pb1-branch54-current
                OBJECT-TYPE
                SYNTAX  INTEGER
                ACCESS  read-only
                STATUS  mandatory
                DESCRIPTION "BRANCH 54 Current"
                              ::= { panelboard1 154 }

pb1-branch55-current
                OBJECT-TYPE
                SYNTAX  INTEGER
                ACCESS  read-only
                STATUS  mandatory
                DESCRIPTION "BRANCH 55 Current"
                              ::= { panelboard1 155 }

pb1-branch56-current
                OBJECT-TYPE
                SYNTAX  INTEGER
                ACCESS  read-only
                STATUS  mandatory
                DESCRIPTION "BRANCH 56 Current"
                              ::= { panelboard1 156 }

pb1-branch57-current
                OBJECT-TYPE
                SYNTAX  INTEGER
                ACCESS  read-only
                STATUS  mandatory
                DESCRIPTION "BRANCH 57 Current"
                              ::= { panelboard1 157 }

pb1-branch58-current
                OBJECT-TYPE
                SYNTAX  INTEGER
                ACCESS  read-only
                STATUS  mandatory
                DESCRIPTION "BRANCH 58 Current"
                              ::= { panelboard1 158 }

pb1-branch59-current
                OBJECT-TYPE
                SYNTAX  INTEGER
                ACCESS  read-only
                STATUS  mandatory
                DESCRIPTION "BRANCH 59 Current"
                              ::= { panelboard1 159 }

pb1-branch60-current
                OBJECT-TYPE
                SYNTAX  INTEGER
                ACCESS  read-only
                STATUS  mandatory
                DESCRIPTION "BRANCH 60 Current"
                              ::= { panelboard1 160 }

pb1-branch61-current
                OBJECT-TYPE
                SYNTAX  INTEGER
                ACCESS  read-only
                STATUS  mandatory
                DESCRIPTION "BRANCH 61 Current"
                              ::= { panelboard1 161 }

pb1-branch62-current
                OBJECT-TYPE
                SYNTAX  INTEGER
                ACCESS  read-only
                STATUS  mandatory
                DESCRIPTION "BRANCH 62 Current"
                              ::= { panelboard1 162 }

pb1-branch63-current
                OBJECT-TYPE
                SYNTAX  INTEGER
                ACCESS  read-only
                STATUS  mandatory
                DESCRIPTION "BRANCH 63 Current"
                              ::= { panelboard1 163 }

pb1-branch64-current
                OBJECT-TYPE
                SYNTAX  INTEGER
                ACCESS  read-only
                STATUS  mandatory
                DESCRIPTION "BRANCH 64 Current"
                              ::= { panelboard1 164 }

pb1-branch65-current
                OBJECT-TYPE
                SYNTAX  INTEGER
                ACCESS  read-only
                STATUS  mandatory
                DESCRIPTION "BRANCH 65 Current"
                              ::= { panelboard1 165 }

pb1-branch66-current
                OBJECT-TYPE
                SYNTAX  INTEGER
                ACCESS  read-only
                STATUS  mandatory
                DESCRIPTION "BRANCH 66 Current"
                              ::= { panelboard1 166 }

pb1-branch67-current
                OBJECT-TYPE
                SYNTAX  INTEGER
                ACCESS  read-only
                STATUS  mandatory
                DESCRIPTION "BRANCH 67 Current"
                              ::= { panelboard1 167 }

pb1-branch68-current
                OBJECT-TYPE
                SYNTAX  INTEGER
                ACCESS  read-only
                STATUS  mandatory
                DESCRIPTION "BRANCH 68 Current"
                              ::= { panelboard1 168 }

pb1-branch69-current
                OBJECT-TYPE
                SYNTAX  INTEGER
                ACCESS  read-only
                STATUS  mandatory
                DESCRIPTION "BRANCH 69 Current"
                              ::= { panelboard1 169 }

pb1-branch70-current
                OBJECT-TYPE
                SYNTAX  INTEGER
                ACCESS  read-only
                STATUS  mandatory
                DESCRIPTION "BRANCH 70 Current"
                              ::= { panelboard1 170 }

pb1-branch71-current
                OBJECT-TYPE
                SYNTAX  INTEGER
                ACCESS  read-only
                STATUS  mandatory
                DESCRIPTION "BRANCH 71 Current"
                              ::= { panelboard1 171 }

pb1-branch72-current
                OBJECT-TYPE
                SYNTAX  INTEGER
                ACCESS  read-only
                STATUS  mandatory
                DESCRIPTION "BRANCH 72 Current"
                              ::= { panelboard1 172 }

pb1-branch1-min
                OBJECT-TYPE
                SYNTAX  INTEGER
                ACCESS  read-only
                STATUS  mandatory
                DESCRIPTION "BRANCH 1 Min
                                    Note for all minimum currents: 100 = 10.0 amps"
                              ::= { panelboard1 201 }

pb1-branch2-min
                OBJECT-TYPE
                SYNTAX  INTEGER
                ACCESS  read-only
                STATUS  mandatory
                DESCRIPTION "BRANCH 2 Min"
                              ::= { panelboard1 202 }

pb1-branch3-min
                OBJECT-TYPE
                SYNTAX  INTEGER
                ACCESS  read-only
                STATUS  mandatory
                DESCRIPTION "BRANCH 3 Min"
                              ::= { panelboard1 203 }

pb1-branch4-min
                OBJECT-TYPE
                SYNTAX  INTEGER
                ACCESS  read-only
                STATUS  mandatory
                DESCRIPTION "BRANCH 4 Min"
                              ::= { panelboard1 204 }

pb1-branch5-min
                OBJECT-TYPE
                SYNTAX  INTEGER
                ACCESS  read-only
                STATUS  mandatory
                DESCRIPTION "BRANCH 5 Min"
                              ::= { panelboard1 205 }

pb1-branch6-min
                OBJECT-TYPE
                SYNTAX  INTEGER
                ACCESS  read-only
                STATUS  mandatory
                DESCRIPTION "BRANCH 6 Min"
                              ::= { panelboard1 206 }

pb1-branch7-min
                OBJECT-TYPE
                SYNTAX  INTEGER
                ACCESS  read-only
                STATUS  mandatory
                DESCRIPTION "BRANCH 7 Min"
                              ::= { panelboard1 207 }

pb1-branch8-min
                OBJECT-TYPE
                SYNTAX  INTEGER
                ACCESS  read-only
                STATUS  mandatory
                DESCRIPTION "BRANCH 8 Min"
                              ::= { panelboard1 208 }

pb1-branch9-min
                OBJECT-TYPE
                SYNTAX  INTEGER
                ACCESS  read-only
                STATUS  mandatory
                DESCRIPTION "BRANCH 9 Min"
                              ::= { panelboard1 209 }

pb1-branch10-min
                OBJECT-TYPE
                SYNTAX  INTEGER
                ACCESS  read-only
                STATUS  mandatory
                DESCRIPTION "BRANCH 10 Min"
                              ::= { panelboard1 210 }

pb1-branch11-min
                OBJECT-TYPE
                SYNTAX  INTEGER
                ACCESS  read-only
                STATUS  mandatory
                DESCRIPTION "BRANCH 11 Min"
                              ::= { panelboard1 211 }

pb1-branch12-min
                OBJECT-TYPE
                SYNTAX  INTEGER
                ACCESS  read-only
                STATUS  mandatory
                DESCRIPTION "BRANCH 12 Min"
                              ::= { panelboard1 212 }

pb1-branch13-min
                OBJECT-TYPE
                SYNTAX  INTEGER
                ACCESS  read-only
                STATUS  mandatory
                DESCRIPTION "BRANCH 13 Min"
                              ::= { panelboard1 213 }

pb1-branch14-min
                OBJECT-TYPE
                SYNTAX  INTEGER
                ACCESS  read-only
                STATUS  mandatory
                DESCRIPTION "BRANCH 14 Min"
                              ::= { panelboard1 214 }

pb1-branch15-min
                OBJECT-TYPE
                SYNTAX  INTEGER
                ACCESS  read-only
                STATUS  mandatory
                DESCRIPTION "BRANCH 15 Min"
                              ::= { panelboard1 215 }

pb1-branch16-min
                OBJECT-TYPE
                SYNTAX  INTEGER
                ACCESS  read-only
                STATUS  mandatory
                DESCRIPTION "BRANCH 16 Min"
                              ::= { panelboard1 216 }

pb1-branch17-min
                OBJECT-TYPE
                SYNTAX  INTEGER
                ACCESS  read-only
                STATUS  mandatory
                DESCRIPTION "BRANCH 17 Min"
                              ::= { panelboard1 217 }

pb1-branch18-min
                OBJECT-TYPE
                SYNTAX  INTEGER
                ACCESS  read-only
                STATUS  mandatory
                DESCRIPTION "BRANCH 18 Min"
                              ::= { panelboard1 218 }

pb1-branch19-min
                OBJECT-TYPE
                SYNTAX  INTEGER
                ACCESS  read-only
                STATUS  mandatory
                DESCRIPTION "BRANCH 19 Min"
                              ::= { panelboard1 219 }

pb1-branch20-min
                OBJECT-TYPE
                SYNTAX  INTEGER
                ACCESS  read-only
                STATUS  mandatory
                DESCRIPTION "BRANCH 20 Min"
                              ::= { panelboard1 220 }

pb1-branch21-min
                OBJECT-TYPE
                SYNTAX  INTEGER
                ACCESS  read-only
                STATUS  mandatory
                DESCRIPTION "BRANCH 21 Min"
                              ::= { panelboard1 221 }

pb1-branch22-min
                OBJECT-TYPE
                SYNTAX  INTEGER
                ACCESS  read-only
                STATUS  mandatory
                DESCRIPTION "BRANCH 22 Min"
                              ::= { panelboard1 222 }

pb1-branch23-min
                OBJECT-TYPE
                SYNTAX  INTEGER
                ACCESS  read-only
                STATUS  mandatory
                DESCRIPTION "BRANCH 23 Min"
                              ::= { panelboard1 223 }

pb1-branch24-min
                OBJECT-TYPE
                SYNTAX  INTEGER
                ACCESS  read-only
                STATUS  mandatory
                DESCRIPTION "BRANCH 24 Min"
                              ::= { panelboard1 224 }

pb1-branch25-min
                OBJECT-TYPE
                SYNTAX  INTEGER
                ACCESS  read-only
                STATUS  mandatory
                DESCRIPTION "BRANCH 25 Min"
                              ::= { panelboard1 225 }

pb1-branch26-min
                OBJECT-TYPE
                SYNTAX  INTEGER
                ACCESS  read-only
                STATUS  mandatory
                DESCRIPTION "BRANCH 26 Min"
                              ::= { panelboard1 226 }

pb1-branch27-min
                OBJECT-TYPE
                SYNTAX  INTEGER
                ACCESS  read-only
                STATUS  mandatory
                DESCRIPTION "BRANCH 27 Min"
                              ::= { panelboard1 227 }

pb1-branch28-min
                OBJECT-TYPE
                SYNTAX  INTEGER
                ACCESS  read-only
                STATUS  mandatory
                DESCRIPTION "BRANCH 28 Min"
                              ::= { panelboard1 228 }

pb1-branch29-min
                OBJECT-TYPE
                SYNTAX  INTEGER
                ACCESS  read-only
                STATUS  mandatory
                DESCRIPTION "BRANCH 29 Min"
                              ::= { panelboard1 229 }

pb1-branch30-min
                OBJECT-TYPE
                SYNTAX  INTEGER
                ACCESS  read-only
                STATUS  mandatory
                DESCRIPTION "BRANCH 30 Min"
                              ::= { panelboard1 230 }

pb1-branch31-min
                OBJECT-TYPE
                SYNTAX  INTEGER
                ACCESS  read-only
                STATUS  mandatory
                DESCRIPTION "BRANCH 31 Min"
                              ::= { panelboard1 231 }

pb1-branch32-min
                OBJECT-TYPE
                SYNTAX  INTEGER
                ACCESS  read-only
                STATUS  mandatory
                DESCRIPTION "BRANCH 32 Min"
                              ::= { panelboard1 232 }

pb1-branch33-min
                OBJECT-TYPE
                SYNTAX  INTEGER
                ACCESS  read-only
                STATUS  mandatory
                DESCRIPTION "BRANCH 33 Min"
                              ::= { panelboard1 233 }

pb1-branch34-min
                OBJECT-TYPE
                SYNTAX  INTEGER
                ACCESS  read-only
                STATUS  mandatory
                DESCRIPTION "BRANCH 34 Min"
                              ::= { panelboard1 234 }

pb1-branch35-min
                OBJECT-TYPE
                SYNTAX  INTEGER
                ACCESS  read-only
                STATUS  mandatory
                DESCRIPTION "BRANCH 35 Min"
                              ::= { panelboard1 235 }

pb1-branch36-min
                OBJECT-TYPE
                SYNTAX  INTEGER
                ACCESS  read-only
                STATUS  mandatory
                DESCRIPTION "BRANCH 36 Min"
                              ::= { panelboard1 236 }

pb1-branch37-min
                OBJECT-TYPE
                SYNTAX  INTEGER
                ACCESS  read-only
                STATUS  mandatory
                DESCRIPTION "BRANCH 37 Min"
                              ::= { panelboard1 237 }

pb1-branch38-min
                OBJECT-TYPE
                SYNTAX  INTEGER
                ACCESS  read-only
                STATUS  mandatory
                DESCRIPTION "BRANCH 38 Min"
                              ::= { panelboard1 238 }

pb1-branch39-min
                OBJECT-TYPE
                SYNTAX  INTEGER
                ACCESS  read-only
                STATUS  mandatory
                DESCRIPTION "BRANCH 39 Min"
                              ::= { panelboard1 239 }

pb1-branch40-min
                OBJECT-TYPE
                SYNTAX  INTEGER
                ACCESS  read-only
                STATUS  mandatory
                DESCRIPTION "BRANCH 40 Min"
                              ::= { panelboard1 240 }

pb1-branch41-min
                OBJECT-TYPE
                SYNTAX  INTEGER
                ACCESS  read-only
                STATUS  mandatory
                DESCRIPTION "BRANCH 41 Min"
                              ::= { panelboard1 241 }

pb1-branch42-min
                OBJECT-TYPE
                SYNTAX  INTEGER
                ACCESS  read-only
                STATUS  mandatory
                DESCRIPTION "BRANCH 42 Min"
                              ::= { panelboard1 242 }

pb1-branch43-min
                OBJECT-TYPE
                SYNTAX  INTEGER
                ACCESS  read-only
                STATUS  mandatory
                DESCRIPTION "BRANCH 43 Min"
                              ::= { panelboard1 243 }

pb1-branch44-min
                OBJECT-TYPE
                SYNTAX  INTEGER
                ACCESS  read-only
                STATUS  mandatory
                DESCRIPTION "BRANCH 44 Min"
                              ::= { panelboard1 244 }

pb1-branch45-min
                OBJECT-TYPE
                SYNTAX  INTEGER
                ACCESS  read-only
                STATUS  mandatory
                DESCRIPTION "BRANCH 45 Min"
                              ::= { panelboard1 245 }

pb1-branch46-min
                OBJECT-TYPE
                SYNTAX  INTEGER
                ACCESS  read-only
                STATUS  mandatory
                DESCRIPTION "BRANCH 46 Min"
                              ::= { panelboard1 246 }

pb1-branch47-min
                OBJECT-TYPE
                SYNTAX  INTEGER
                ACCESS  read-only
                STATUS  mandatory
                DESCRIPTION "BRANCH 47 Min"
                              ::= { panelboard1 247 }

pb1-branch48-min
                OBJECT-TYPE
                SYNTAX  INTEGER
                ACCESS  read-only
                STATUS  mandatory
                DESCRIPTION "BRANCH 48 Min"
                              ::= { panelboard1 248 }

pb1-branch49-min
                OBJECT-TYPE
                SYNTAX  INTEGER
                ACCESS  read-only
                STATUS  mandatory
                DESCRIPTION "BRANCH 49 Min"
                              ::= { panelboard1 249 }

pb1-branch50-min
                OBJECT-TYPE
                SYNTAX  INTEGER
                ACCESS  read-only
                STATUS  mandatory
                DESCRIPTION "BRANCH 50 Min"
                              ::= { panelboard1 250 }

pb1-branch51-min
                OBJECT-TYPE
                SYNTAX  INTEGER
                ACCESS  read-only
                STATUS  mandatory
                DESCRIPTION "BRANCH 51 Min"
                              ::= { panelboard1 251 }

pb1-branch52-min
                OBJECT-TYPE
                SYNTAX  INTEGER
                ACCESS  read-only
                STATUS  mandatory
                DESCRIPTION "BRANCH 52 Min"
                              ::= { panelboard1 252 }

pb1-branch53-min
                OBJECT-TYPE
                SYNTAX  INTEGER
                ACCESS  read-only
                STATUS  mandatory
                DESCRIPTION "BRANCH 53 Min"
                              ::= { panelboard1 253 }

pb1-branch54-min
                OBJECT-TYPE
                SYNTAX  INTEGER
                ACCESS  read-only
                STATUS  mandatory
                DESCRIPTION "BRANCH 54 Min"
                              ::= { panelboard1 254 }

pb1-branch55-min
                OBJECT-TYPE
                SYNTAX  INTEGER
                ACCESS  read-only
                STATUS  mandatory
                DESCRIPTION "BRANCH 55 Min"
                              ::= { panelboard1 255 }

pb1-branch56-min
                OBJECT-TYPE
                SYNTAX  INTEGER
                ACCESS  read-only
                STATUS  mandatory
                DESCRIPTION "BRANCH 56 Min"
                              ::= { panelboard1 256 }

pb1-branch57-min
                OBJECT-TYPE
                SYNTAX  INTEGER
                ACCESS  read-only
                STATUS  mandatory
                DESCRIPTION "BRANCH 57 Min"
                              ::= { panelboard1 257 }

pb1-branch58-min
                OBJECT-TYPE
                SYNTAX  INTEGER
                ACCESS  read-only
                STATUS  mandatory
                DESCRIPTION "BRANCH 58 Min"
                              ::= { panelboard1 258 }

pb1-branch59-min
                OBJECT-TYPE
                SYNTAX  INTEGER
                ACCESS  read-only
                STATUS  mandatory
                DESCRIPTION "BRANCH 59 Min"
                              ::= { panelboard1 259 }

pb1-branch60-min
                OBJECT-TYPE
                SYNTAX  INTEGER
                ACCESS  read-only
                STATUS  mandatory
                DESCRIPTION "BRANCH 60 Min"
                              ::= { panelboard1 260 }

pb1-branch61-min
                OBJECT-TYPE
                SYNTAX  INTEGER
                ACCESS  read-only
                STATUS  mandatory
                DESCRIPTION "BRANCH 61 Min"
                              ::= { panelboard1 261 }

pb1-branch62-min
                OBJECT-TYPE
                SYNTAX  INTEGER
                ACCESS  read-only
                STATUS  mandatory
                DESCRIPTION "BRANCH 62 Min"
                              ::= { panelboard1 262 }

pb1-branch63-min
                OBJECT-TYPE
                SYNTAX  INTEGER
                ACCESS  read-only
                STATUS  mandatory
                DESCRIPTION "BRANCH 63 Min"
                              ::= { panelboard1 263 }

pb1-branch64-min
                OBJECT-TYPE
                SYNTAX  INTEGER
                ACCESS  read-only
                STATUS  mandatory
                DESCRIPTION "BRANCH 64 Min"
                              ::= { panelboard1 264 }

pb1-branch65-min
                OBJECT-TYPE
                SYNTAX  INTEGER
                ACCESS  read-only
                STATUS  mandatory
                DESCRIPTION "BRANCH 65 Min"
                              ::= { panelboard1 265 }

pb1-branch66-min
                OBJECT-TYPE
                SYNTAX  INTEGER
                ACCESS  read-only
                STATUS  mandatory
                DESCRIPTION "BRANCH 66 Min"
                              ::= { panelboard1 266 }

pb1-branch67-min
                OBJECT-TYPE
                SYNTAX  INTEGER
                ACCESS  read-only
                STATUS  mandatory
                DESCRIPTION "BRANCH 67 Min"
                              ::= { panelboard1 267 }

pb1-branch68-min
                OBJECT-TYPE
                SYNTAX  INTEGER
                ACCESS  read-only
                STATUS  mandatory
                DESCRIPTION "BRANCH 68 Min"
                              ::= { panelboard1 268 }

pb1-branch69-min
                OBJECT-TYPE
                SYNTAX  INTEGER
                ACCESS  read-only
                STATUS  mandatory
                DESCRIPTION "BRANCH 69 Min"
                              ::= { panelboard1 269 }

pb1-branch70-min
                OBJECT-TYPE
                SYNTAX  INTEGER
                ACCESS  read-only
                STATUS  mandatory
                DESCRIPTION "BRANCH 70 Min"
                              ::= { panelboard1 270 }

pb1-branch71-min
                OBJECT-TYPE
                SYNTAX  INTEGER
                ACCESS  read-only
                STATUS  mandatory
                DESCRIPTION "BRANCH 71 Min"
                              ::= { panelboard1 271 }

pb1-branch72-min
                OBJECT-TYPE
                SYNTAX  INTEGER
                ACCESS  read-only
                STATUS  mandatory
                DESCRIPTION "BRANCH 72 Min"
                              ::= { panelboard1 272 }

pb1-branch1-max
                OBJECT-TYPE
                SYNTAX  INTEGER
                ACCESS  read-only
                STATUS  mandatory
                DESCRIPTION "BRANCH 1 Max
                                    Note for all maximum currents: 100 = 10.0 amps"
                              ::= { panelboard1 301 }

pb1-branch2-max
                OBJECT-TYPE
                SYNTAX  INTEGER
                ACCESS  read-only
                STATUS  mandatory
                DESCRIPTION "BRANCH 2 Max"
                              ::= { panelboard1 302 }

pb1-branch3-max
                OBJECT-TYPE
                SYNTAX  INTEGER
                ACCESS  read-only
                STATUS  mandatory
                DESCRIPTION "BRANCH 3 Max"
                              ::= { panelboard1 303 }

pb1-branch4-max
                OBJECT-TYPE
                SYNTAX  INTEGER
                ACCESS  read-only
                STATUS  mandatory
                DESCRIPTION "BRANCH 4 Max"
                              ::= { panelboard1 304 }

pb1-branch5-max
                OBJECT-TYPE
                SYNTAX  INTEGER
                ACCESS  read-only
                STATUS  mandatory
                DESCRIPTION "BRANCH 5 Max"
                              ::= { panelboard1 305 }

pb1-branch6-max
                OBJECT-TYPE
                SYNTAX  INTEGER
                ACCESS  read-only
                STATUS  mandatory
                DESCRIPTION "BRANCH 6 Max"
                              ::= { panelboard1 306 }

pb1-branch7-max
                OBJECT-TYPE
                SYNTAX  INTEGER
                ACCESS  read-only
                STATUS  mandatory
                DESCRIPTION "BRANCH 7 Max"
                              ::= { panelboard1 307 }

pb1-branch8-max
                OBJECT-TYPE
                SYNTAX  INTEGER
                ACCESS  read-only
                STATUS  mandatory
                DESCRIPTION "BRANCH 8 Max"
                              ::= { panelboard1 308 }

pb1-branch9-max
                OBJECT-TYPE
                SYNTAX  INTEGER
                ACCESS  read-only
                STATUS  mandatory
                DESCRIPTION "BRANCH 9 Max"
                              ::= { panelboard1 309 }

pb1-branch10-max
                OBJECT-TYPE
                SYNTAX  INTEGER
                ACCESS  read-only
                STATUS  mandatory
                DESCRIPTION "BRANCH 10 Max"
                              ::= { panelboard1 310 }

pb1-branch11-max
                OBJECT-TYPE
                SYNTAX  INTEGER
                ACCESS  read-only
                STATUS  mandatory
                DESCRIPTION "BRANCH 11 Max"
                              ::= { panelboard1 311 }

pb1-branch12-max
                OBJECT-TYPE
                SYNTAX  INTEGER
                ACCESS  read-only
                STATUS  mandatory
                DESCRIPTION "BRANCH 12 Max"
                              ::= { panelboard1 312 }

pb1-branch13-max
                OBJECT-TYPE
                SYNTAX  INTEGER
                ACCESS  read-only
                STATUS  mandatory
                DESCRIPTION "BRANCH 13 Max"
                              ::= { panelboard1 313 }

pb1-branch14-max
                OBJECT-TYPE
                SYNTAX  INTEGER
                ACCESS  read-only
                STATUS  mandatory
                DESCRIPTION "BRANCH 14 Max"
                              ::= { panelboard1 314 }

pb1-branch15-max
                OBJECT-TYPE
                SYNTAX  INTEGER
                ACCESS  read-only
                STATUS  mandatory
                DESCRIPTION "BRANCH 15 Max"
                              ::= { panelboard1 315 }

pb1-branch16-max
                OBJECT-TYPE
                SYNTAX  INTEGER
                ACCESS  read-only
                STATUS  mandatory
                DESCRIPTION "BRANCH 16 Max"
                              ::= { panelboard1 316 }

pb1-branch17-max
                OBJECT-TYPE
                SYNTAX  INTEGER
                ACCESS  read-only
                STATUS  mandatory
                DESCRIPTION "BRANCH 17 Max"
                              ::= { panelboard1 317 }

pb1-branch18-max
                OBJECT-TYPE
                SYNTAX  INTEGER
                ACCESS  read-only
                STATUS  mandatory
                DESCRIPTION "BRANCH 18 Max"
                              ::= { panelboard1 318 }

pb1-branch19-max
                OBJECT-TYPE
                SYNTAX  INTEGER
                ACCESS  read-only
                STATUS  mandatory
                DESCRIPTION "BRANCH 19 Max"
                              ::= { panelboard1 319 }

pb1-branch20-max
                OBJECT-TYPE
                SYNTAX  INTEGER
                ACCESS  read-only
                STATUS  mandatory
                DESCRIPTION "BRANCH 20 Max"
                              ::= { panelboard1 320 }

pb1-branch21-max
                OBJECT-TYPE
                SYNTAX  INTEGER
                ACCESS  read-only
                STATUS  mandatory
                DESCRIPTION "BRANCH 21 Max"
                              ::= { panelboard1 321 }

pb1-branch22-max
                OBJECT-TYPE
                SYNTAX  INTEGER
                ACCESS  read-only
                STATUS  mandatory
                DESCRIPTION "BRANCH22 Max"
                              ::= { panelboard1 322 }

pb1-branch23-max
                OBJECT-TYPE
                SYNTAX  INTEGER
                ACCESS  read-only
                STATUS  mandatory
                DESCRIPTION "BRANCH23 Max"
                              ::= { panelboard1 323 }

pb1-branch24-max
                OBJECT-TYPE
                SYNTAX  INTEGER
                ACCESS  read-only
                STATUS  mandatory
                DESCRIPTION "BRANCH24 Max"
                              ::= { panelboard1 324 }

pb1-branch25-max
                OBJECT-TYPE
                SYNTAX  INTEGER
                ACCESS  read-only
                STATUS  mandatory
                DESCRIPTION "BRANCH 25 Max"
                              ::= { panelboard1 325 }

pb1-branch26-max
                OBJECT-TYPE
                SYNTAX  INTEGER
                ACCESS  read-only
                STATUS  mandatory
                DESCRIPTION "BRANCH 26 Max"
                              ::= { panelboard1 326 }

pb1-branch27-max
                OBJECT-TYPE
                SYNTAX  INTEGER
                ACCESS  read-only
                STATUS  mandatory
                DESCRIPTION "BRANCH 27 Max"
                              ::= { panelboard1 327 }

pb1-branch28-max
                OBJECT-TYPE
                SYNTAX  INTEGER
                ACCESS  read-only
                STATUS  mandatory
                DESCRIPTION "BRANCH 28 Max"
                              ::= { panelboard1 328 }

pb1-branch29-max
                OBJECT-TYPE
                SYNTAX  INTEGER
                ACCESS  read-only
                STATUS  mandatory
                DESCRIPTION "BRANCH 29 Max"
                              ::= { panelboard1 329 }

pb1-branch30-max
                OBJECT-TYPE
                SYNTAX  INTEGER
                ACCESS  read-only
                STATUS  mandatory
                DESCRIPTION "BRANCH 30 Max"
                              ::= { panelboard1 330 }

pb1-branch31-max
                OBJECT-TYPE
                SYNTAX  INTEGER
                ACCESS  read-only
                STATUS  mandatory
                DESCRIPTION "BRANCH31 Max"
                              ::= { panelboard1 331 }

pb1-branch32-max
                OBJECT-TYPE
                SYNTAX  INTEGER
                ACCESS  read-only
                STATUS  mandatory
                DESCRIPTION "BRANCH32 Max"
                              ::= { panelboard1 332 }

pb1-branch33-max
                OBJECT-TYPE
                SYNTAX  INTEGER
                ACCESS  read-only
                STATUS  mandatory
                DESCRIPTION "BRANCH33 Max"
                              ::= { panelboard1 333 }

pb1-branch34-max
                OBJECT-TYPE
                SYNTAX  INTEGER
                ACCESS  read-only
                STATUS  mandatory
                DESCRIPTION "BRANCH34 Max"
                              ::= { panelboard1 334 }

pb1-branch35-max
                OBJECT-TYPE
                SYNTAX  INTEGER
                ACCESS  read-only
                STATUS  mandatory
                DESCRIPTION "BRANCH35 Max"
                              ::= { panelboard1 335 }

pb1-branch36-max
                OBJECT-TYPE
                SYNTAX  INTEGER
                ACCESS  read-only
                STATUS  mandatory
                DESCRIPTION "BRANCH36 Max"
                              ::= { panelboard1 336 }

pb1-branch37-max
                OBJECT-TYPE
                SYNTAX  INTEGER
                ACCESS  read-only
                STATUS  mandatory
                DESCRIPTION "BRANCH 37 Max"
                                ::= { panelboard1 337 }

pb1-branch38-max
                OBJECT-TYPE
                SYNTAX  INTEGER
                ACCESS  read-only
                STATUS  mandatory
                DESCRIPTION "BRANCH 38 Max"
                              ::= { panelboard1 338 }

pb1-branch39-max
                OBJECT-TYPE
                SYNTAX  INTEGER
                ACCESS  read-only
                STATUS  mandatory
                DESCRIPTION "BRANCH 39 Max"
                              ::= { panelboard1 339 }

pb1-branch40-max
                OBJECT-TYPE
                SYNTAX  INTEGER
                ACCESS  read-only
                STATUS  mandatory
                DESCRIPTION "BRANCH 40 Max"
                              ::= { panelboard1 340 }

pb1-branch41-max
                OBJECT-TYPE
                SYNTAX  INTEGER
                ACCESS  read-only
                STATUS  mandatory
                DESCRIPTION "BRANCH 41 Max"
                              ::= { panelboard1 341 }

pb1-branch42-max
                OBJECT-TYPE
                SYNTAX  INTEGER
                ACCESS  read-only
                STATUS  mandatory
                DESCRIPTION "BRANCH 42 Max"
                              ::= { panelboard1 342 }

pb1-branch43-max
                OBJECT-TYPE
                SYNTAX  INTEGER
                ACCESS  read-only
                STATUS  mandatory
                DESCRIPTION "BRANCH 43 Max"
                              ::= { panelboard1 343 }

pb1-branch44-max
                OBJECT-TYPE
                SYNTAX  INTEGER
                ACCESS  read-only
                STATUS  mandatory
                DESCRIPTION "BRANCH 44 Max"
                              ::= { panelboard1 344 }

pb1-branch45-max
                OBJECT-TYPE
                SYNTAX  INTEGER
                ACCESS  read-only
                STATUS  mandatory
                DESCRIPTION "BRANCH 45 Max"
                              ::= { panelboard1 345 }

pb1-branch46-max
                OBJECT-TYPE
                SYNTAX  INTEGER
                ACCESS  read-only
                STATUS  mandatory
                DESCRIPTION "BRANCH 46 Max"
                              ::= { panelboard1 346 }

pb1-branch47-max
                OBJECT-TYPE
                SYNTAX  INTEGER
                ACCESS  read-only
                STATUS  mandatory
                DESCRIPTION "BRANCH 47 Max"
                              ::= { panelboard1 347 }

pb1-branch48-max
                OBJECT-TYPE
                SYNTAX  INTEGER
                ACCESS  read-only
                STATUS  mandatory
                DESCRIPTION "BRANCH 48 Max"
                              ::= { panelboard1 348 }

pb1-branch49-max
                OBJECT-TYPE
                SYNTAX  INTEGER
                ACCESS  read-only
                STATUS  mandatory
                DESCRIPTION "BRANCH 49 Max"
                              ::= { panelboard1 349 }

pb1-branch50-max
                OBJECT-TYPE
                SYNTAX  INTEGER
                ACCESS  read-only
                STATUS  mandatory
                DESCRIPTION "BRANCH 50 Max"
                              ::= { panelboard1 350 }

pb1-branch51-max
                OBJECT-TYPE
                SYNTAX  INTEGER
                ACCESS  read-only
                STATUS  mandatory
                DESCRIPTION "BRANCH 51 Max"
                              ::= { panelboard1 351 }

pb1-branch52-max
                OBJECT-TYPE
                SYNTAX  INTEGER
                ACCESS  read-only
                STATUS  mandatory
                DESCRIPTION "BRANCH 52 Max"
                              ::= { panelboard1 352 }

pb1-branch53-max
                OBJECT-TYPE
                SYNTAX  INTEGER
                ACCESS  read-only
                STATUS  mandatory
                DESCRIPTION "BRANCH 53 Max"
                              ::= { panelboard1 353 }

pb1-branch54-max
                OBJECT-TYPE
                SYNTAX  INTEGER
                ACCESS  read-only
                STATUS  mandatory
                DESCRIPTION "BRANCH 54 Max"
                              ::= { panelboard1 354 }

pb1-branch55-max
                OBJECT-TYPE
                SYNTAX  INTEGER
                ACCESS  read-only
                STATUS  mandatory
                DESCRIPTION "BRANCH 55 Max"
                              ::= { panelboard1 355 }

pb1-branch56-max
                OBJECT-TYPE
                SYNTAX  INTEGER
                ACCESS  read-only
                STATUS  mandatory
                DESCRIPTION "BRANCH 56 Max"
                              ::= { panelboard1 356 }

pb1-branch57-max
                OBJECT-TYPE
                SYNTAX  INTEGER
                ACCESS  read-only
                STATUS  mandatory
                DESCRIPTION "BRANCH 57 Max"
                              ::= { panelboard1 357 }

pb1-branch58-max
                OBJECT-TYPE
                SYNTAX  INTEGER
                ACCESS  read-only
                STATUS  mandatory
                DESCRIPTION "BRANCH 58 Max"
                              ::= { panelboard1 358 }

pb1-branch59-max
                OBJECT-TYPE
                SYNTAX  INTEGER
                ACCESS  read-only
                STATUS  mandatory
                DESCRIPTION "BRANCH 59 Max"
                              ::= { panelboard1 359 }

pb1-branch60-max
                OBJECT-TYPE
                SYNTAX  INTEGER
                ACCESS  read-only
                STATUS  mandatory
                DESCRIPTION "BRANCH 60 Max"
                              ::= { panelboard1 360 }

pb1-branch61-max
                OBJECT-TYPE
                SYNTAX  INTEGER
                ACCESS  read-only
                STATUS  mandatory
                DESCRIPTION "BRANCH 61 Max"
                              ::= { panelboard1 361 }

pb1-branch62-max
                OBJECT-TYPE
                SYNTAX  INTEGER
                ACCESS  read-only
                STATUS  mandatory
                DESCRIPTION "BRANCH 62 Max"
                              ::= { panelboard1 362 }

pb1-branch63-max
                OBJECT-TYPE
                SYNTAX  INTEGER
                ACCESS  read-only
                STATUS  mandatory
                DESCRIPTION "BRANCH 63 Max"
                              ::= { panelboard1 363 }

pb1-branch64-max
                OBJECT-TYPE
                SYNTAX  INTEGER
                ACCESS  read-only
                STATUS  mandatory
                DESCRIPTION "BRANCH 64 Max"
                              ::= { panelboard1 364 }

pb1-branch65-max
                OBJECT-TYPE
                SYNTAX  INTEGER
                ACCESS  read-only
                STATUS  mandatory
                DESCRIPTION "BRANCH 65 Max"
                              ::= { panelboard1 365 }

pb1-branch66-max
                OBJECT-TYPE
                SYNTAX  INTEGER
                ACCESS  read-only
                STATUS  mandatory
                DESCRIPTION "BRANCH 66 Max"
                              ::= { panelboard1 366 }

pb1-branch67-max
                OBJECT-TYPE
                SYNTAX  INTEGER
                ACCESS  read-only
                STATUS  mandatory
                DESCRIPTION "BRANCH 67 Max"
                              ::= { panelboard1 367 }

pb1-branch68-max
                OBJECT-TYPE
                SYNTAX  INTEGER
                ACCESS  read-only
                STATUS  mandatory
                DESCRIPTION "BRANCH 68 Max"
                              ::= { panelboard1 368 }

pb1-branch69-max
                OBJECT-TYPE
                SYNTAX  INTEGER
                ACCESS  read-only
                STATUS  mandatory
                DESCRIPTION "BRANCH 69 Max"
                              ::= { panelboard1 369 }

pb1-branch70-max
                OBJECT-TYPE
                SYNTAX  INTEGER
                ACCESS  read-only
                STATUS  mandatory
                DESCRIPTION "BRANCH 70 Max"
                              ::= { panelboard1 370 }

pb1-branch71-max
                OBJECT-TYPE
                SYNTAX  INTEGER
                ACCESS  read-only
                STATUS  mandatory
                DESCRIPTION "BRANCH 71 Max"
                              ::= { panelboard1 371 }

pb1-branch72-max
                OBJECT-TYPE
                SYNTAX  INTEGER
                ACCESS  read-only
                STATUS  mandatory
                DESCRIPTION "BRANCH 72 Max"
                              ::= { panelboard1 372 }

pb1-branch1-16-zero
                OBJECT-TYPE
                SYNTAX  INTEGER
                ACCESS  read-write
                STATUS  mandatory
                DESCRIPTION "BRANCH 1-16 Zero
                                      Bit 0 = BRANCH 1
                  Bit 15 = BRANCH 16"
                              ::= { panelboard1 401 }

pb1-branch17-32-zero
                OBJECT-TYPE
                SYNTAX  INTEGER
                ACCESS  read-write
                STATUS  mandatory
                DESCRIPTION "BRANCH 17-32 Zero
                                      Bit 0 = BRANCH 17
                  Bit 15 = BRANCH 32"
                              ::= { panelboard1 402 }

pb1-branch33-48-zero
                OBJECT-TYPE
                SYNTAX  INTEGER
                ACCESS  read-write
                STATUS  mandatory
                DESCRIPTION "BRANCH 33-48 Zero
                                      Bit 0 = BRANCH 33
                  Bit 15 = BRANCH 48"
                              ::= { panelboard1 403 }

pb1-branch49-64-zero
                OBJECT-TYPE
                SYNTAX  INTEGER
                ACCESS  read-write
                STATUS  mandatory
                DESCRIPTION "BRANCH 49-64 Zero
                                      Bit 0 = BRANCH 49
                  Bit 15 = BRANCH 64"
                              ::= { panelboard1 404 }

pb1-branch65-72-zero
                OBJECT-TYPE
                SYNTAX  INTEGER
                ACCESS  read-write
                STATUS  mandatory
                DESCRIPTION "BRANCH 65-72 Zero
                                      Bit 0 = BRANCH 65
                  Bit 7 = BRANCH 72
                  Bit 8-15 not used"
                              ::= { panelboard1 405 }

pb1-branch1-16-prealarm
                OBJECT-TYPE
                SYNTAX  INTEGER
                ACCESS  read-write
                STATUS  mandatory
                DESCRIPTION "BRANCH 1-16 prealarm
                                      Bit 0 = BRANCH 1
                  Bit 15 = BRANCH 16"
                              ::= { panelboard1 406 }

pb1-branch17-32-prealarm
                OBJECT-TYPE
                SYNTAX  INTEGER
                ACCESS  read-write
                STATUS  mandatory
                DESCRIPTION "BRANCH 17-32 prealarm
                                      Bit 0 = BRANCH 17
                  Bit 15 = BRANCH 32"
                              ::= { panelboard1 407 }

pb1-branch33-48-prealarm
                OBJECT-TYPE
                SYNTAX  INTEGER
                ACCESS  read-write
                STATUS  mandatory
                DESCRIPTION "BRANCH 33-48 prealarm
                                      Bit 0 = BRANCH 33
                  Bit 15 = BRANCH 48"
                              ::= { panelboard1 408 }

pb1-branch49-64-prealarm
                OBJECT-TYPE
                SYNTAX  INTEGER
                ACCESS  read-write
                STATUS  mandatory
                DESCRIPTION "BRANCH 49-64 prealarm
                                      Bit 0 = BRANCH 49
                  Bit 15 = BRANCH 64"
                              ::= { panelboard1 409 }

pb1-branch65-72-prealarm
                OBJECT-TYPE
                SYNTAX  INTEGER
                ACCESS  read-write
                STATUS  mandatory
                DESCRIPTION "BRANCH 65-72 prealarm
                                      Bit 0 = BRANCH 65
                  Bit 7 = BRANCH 72
                  Bits 8-25 not used"
                              ::= { panelboard1 410 }

pb1-branch1-16-alarm
                OBJECT-TYPE
                SYNTAX  INTEGER
                ACCESS  read-write
                STATUS  mandatory
                DESCRIPTION "BRANCH 1-16 Alarm
                                      Bit 0 = BRANCH 1
                  Bit 15 = BRANCH 16"
                              ::= { panelboard1 411 }

pb1-branch17-32-alarm
                OBJECT-TYPE
                SYNTAX  INTEGER
                ACCESS  read-write
                STATUS  mandatory
                DESCRIPTION "BRANCH 17-32 Alarm
                                      Bit 0 = BRANCH 17
                  Bit 15 = BRANCH 32"
                              ::= { panelboard1 412 }

pb1-branch33-48-alarm
                OBJECT-TYPE
                SYNTAX  INTEGER
                ACCESS  read-write
                STATUS  mandatory
                DESCRIPTION "BRANCH 33-48 Alarm
                                      Bit 0 = BRANCH 33
                  Bit 15 = BRANCH 48"
                              ::= { panelboard1 413 }

pb1-branch49-64-alarm
                OBJECT-TYPE
                SYNTAX  INTEGER
                ACCESS  read-write
                STATUS  mandatory
                DESCRIPTION "BRANCH48-64 Alarm
                                      Bit 0 = BRANCH 49
                  Bit 15 = BRANCH 64"
                              ::= { panelboard1 414 }

pb1-branch65-72-alarm
                OBJECT-TYPE
                SYNTAX  INTEGER
                ACCESS  read-write
                STATUS  mandatory
                DESCRIPTION "BRANCH 65-72 Alarm
                                      Bit 0 = BRANCH 65
                  Bit 7 = BRANCH 72
                  Bits 8-25 not used"
                              ::= { panelboard1 415 }

pb1-global-branch-rated-current
                OBJECT-TYPE
                SYNTAX  INTEGER
                ACCESS  read-write
                STATUS  mandatory
                DESCRIPTION "Global-branch-rated-current
                                    Note for global branch rated-current: 10 = 10 amps
                    Range is 6 to 100 amps"
                              ::= { panelboard1 416 }

pb1-global-prealarm-threshold
                OBJECT-TYPE
                SYNTAX  INTEGER
                ACCESS  read-write
                STATUS  mandatory
                DESCRIPTION "Global-prealarm-threshold
                                    Note for global prealarm threshold: 70 = 70% of branch rated-current
                    range is 40-100%"
                              ::= { panelboard1 417 }

pb1-global-alarm-threshold
                OBJECT-TYPE
                SYNTAX  INTEGER
                ACCESS  read-write
                STATUS  mandatory
                DESCRIPTION "Global-alarm-threshold
                                    Note for global alarm threshold: 80 = 80% of branch rated-current
                    range is 50-100%"
                              ::= { panelboard1 418 }

pb1-global-prealarm-time-delay
                OBJECT-TYPE
                SYNTAX  INTEGER
                ACCESS  read-write
                STATUS  mandatory
                DESCRIPTION "Global-prealarm-time-delay
                                    Note for global prealarm time delay: units are in seconds"
                              ::= { panelboard1 419 }

pb1-global-alarm-time-delay
                OBJECT-TYPE
                SYNTAX  INTEGER
                ACCESS  read-write
                STATUS  mandatory
                DESCRIPTION "Global-alarm-time-delay
                                    Note for global alarm time delay: units are in seconds"
                              ::= { panelboard1 420 }

pb1-min-max-reset
                OBJECT-TYPE
                SYNTAX  INTEGER
                ACCESS  read-write
                STATUS  mandatory
                DESCRIPTION "Min-Max-Reset
                    Note for Min-max Reset: writing to this register will clear minimum
                                    and maximum current values"
                              ::= { panelboard1 421 }

pb1-alarm-status-latching
                OBJECT-TYPE
                SYNTAX  INTEGER
                ACCESS  read-write
                STATUS  mandatory
                DESCRIPTION "Alarm-Status-Latching
                                              bit 0:      prealarm Register
                                              bit 1:      Alarm Register
                                              bit 2:      Zero Current Register
                                              bit 3:      Over Voltage main
                                              bit 4:      Under Voltage main
                                              bit 5:      Over Voltage alternate
                                              bit 6:      Under Voltage alternate
                                              bit 7:      Over Current Panel
                                              bit 8:      Under Current Panel
                                              bits 9 - 15: Not Used"
                              ::= { panelboard1 422 }

pb1-alarm-status-nonlatching
                OBJECT-TYPE
                SYNTAX  INTEGER
                ACCESS  read-only
                STATUS  mandatory
                DESCRIPTION "Alarm-Status-Nonlatching
                                              bit 0:      prealarm Register
                                              bit 1:      Alarm Register
                                              bit 2:      Zero Current Register
                                              bit 3:      Over Voltage main
                                              bit 4:      Under Voltage main
                                              bit 5:      Over Voltage alternate
                                              bit 6:      Under Voltage alternate
                                              bit 7:      Over Current Panel
                                              bit 8:      Under Current Panel
                                              bits 9 - 15: Not Used"
                              ::= { panelboard1 423 }

pb1-digital-input-status
                OBJECT-TYPE
                SYNTAX  INTEGER
                ACCESS  read-only
                STATUS  mandatory
                DESCRIPTION "Digital-input-Status
                                              bit 0:      Digital input 1
                                              bit 1:      Digital input 2
                                              bit 2:      Digital input 3
                                              bit 3:      Digital input 4
                                              bits 4 - 15: Not Used"
                              ::= { panelboard1 424 }

pb1-current-option-setting
                OBJECT-TYPE
                SYNTAX  INTEGER
                ACCESS  read-write
                STATUS  mandatory
                DESCRIPTION "Current-Option-Setting
                                              bit 0-13: Reserved
                                              bit 14:    Always Low
                                              bit 15:    Current Loss"
                              ::= { panelboard1 425 }

pb1-voltage-option-setting
                OBJECT-TYPE
                SYNTAX  INTEGER
                ACCESS  read-only
                STATUS  mandatory
                DESCRIPTION "Voltage-Option-Setting
                                              bit 0:      option 0
                                              bit 1:      option 1
                                              bit 2:      option 2
                                              bit 3:      option 3
                  bit 4:      Voltage THD
                  bit 5:      Set to 50Hz
                  bit 6:      KW,KVA,KVAR read in hundreths
                  bit 7:      High Voltage Board
                  bit 8-9:    Reserved
                                              bits 10 - 15: Not Used
                    Option 0: no voltage monitoring.
                    Option 1: One voltage feeding 1 or 2 panel boards.
                    Option 2: One voltage feeding panelboard 1 and another feeding panelboard 2.
                    Option 3: Two voltages tied together through changeover switch feeding both panelboards.
                              Digital input 1 and 2 are used to determine which is feeding the panelboard. A set bit
                              indicated closed.  If both are closed, main voltage is used."
                              ::= { panelboard1 426 }

pb1-voltage-a-b-main
                OBJECT-TYPE
                SYNTAX  INTEGER
                ACCESS  read-only
                STATUS  mandatory
                DESCRIPTION "Voltage-A-B-Main
                    Note for all voltages: 1200 = 120.0 volts"
                              ::= { panelboard1 427 }

pb1-voltage-b-c-main
                OBJECT-TYPE
                SYNTAX  INTEGER
                ACCESS  read-only
                STATUS  mandatory
                DESCRIPTION "Voltage-B-C-Main"
                              ::= { panelboard1 428 }

pb1-voltage-c-a-main
                OBJECT-TYPE
                SYNTAX  INTEGER
                ACCESS  read-only
                STATUS  mandatory
                DESCRIPTION "Voltage-C-A-Main"
                              ::= { panelboard1 429 }

pb1-voltage-a-n-main
                OBJECT-TYPE
                SYNTAX  INTEGER
                ACCESS  read-only
                STATUS  mandatory
                DESCRIPTION "Voltage-A-N-Main"
                              ::= { panelboard1 430 }

pb1-voltage-b-n-main
                OBJECT-TYPE
                SYNTAX  INTEGER
                ACCESS  read-only
                STATUS  mandatory
                DESCRIPTION "Voltage-B-N-Main"
                              ::= { panelboard1 431 }

pb1-voltage-c-n-main
                OBJECT-TYPE
                SYNTAX  INTEGER
                ACCESS  read-only
                STATUS  mandatory
                DESCRIPTION "Voltage-C-N-Main"
                              ::= { panelboard1 432 }

pb1-over-voltage-alarm-threshhold-main
                OBJECT-TYPE
                SYNTAX  INTEGER
                ACCESS  read-write
                STATUS  mandatory
                DESCRIPTION "Over-Voltage-Alarm-Threshhold-Main
                    Note All Over and Under Voltage is for L-L values"
                              ::= { panelboard1 433 }

pb1-under-voltage-alarm-threshhold-main
                OBJECT-TYPE
                SYNTAX  INTEGER
                ACCESS  read-write
                STATUS  mandatory
                DESCRIPTION "Under-Voltage-Alarm-Threshhold-Main"
                              ::= { panelboard1 434 }

pb1-voltage-frequency-main
                OBJECT-TYPE
                SYNTAX  INTEGER
                ACCESS  read-only
                STATUS  mandatory
                DESCRIPTION "Voltage-Frequency-Main
                    note for frequency: 600 = 60.0Hz
                    Range is 40-70Hz
                    Note if insufficient voltage is present frequency will read 0xFFFF"
                              ::= { panelboard1 435 }

pb1-voltage-a-b-alternate
                OBJECT-TYPE
                SYNTAX  INTEGER
                ACCESS  read-only
                STATUS  mandatory
                DESCRIPTION "Voltage-A-B-Alternate"
                              ::= { panelboard1 436 }

pb1-voltage-b-c-alternate
                OBJECT-TYPE
                SYNTAX  INTEGER
                ACCESS  read-only
                STATUS  mandatory
                DESCRIPTION "Voltage-B-C-Alternate"
                              ::= { panelboard1 437 }

pb1-voltage-c-a-alternate
                OBJECT-TYPE
                SYNTAX  INTEGER
                ACCESS  read-only
                STATUS  mandatory
                DESCRIPTION "Voltage-C-A-Alternate"
                              ::= { panelboard1 438 }

pb1-voltage-a-n-alternate
                OBJECT-TYPE
                SYNTAX  INTEGER
                ACCESS  read-only
                STATUS  mandatory
                DESCRIPTION "Voltage-A-N-Alternate"
                              ::= { panelboard1 439 }

pb1-voltage-b-N-alternate
                OBJECT-TYPE
                SYNTAX  INTEGER
                ACCESS  read-only
                STATUS  mandatory
                DESCRIPTION "Voltage-B-N-Alternate"
                              ::= { panelboard1 440 }

pb1-voltage-c-n-alternate
                OBJECT-TYPE
                SYNTAX  INTEGER
                ACCESS  read-only
                STATUS  mandatory
                DESCRIPTION "Voltage-C-N-Alternate"
                              ::= { panelboard1 441 }

pb1-over-voltage-alarm-threshhold-alternate
                OBJECT-TYPE
                SYNTAX  INTEGER
                ACCESS  read-write
                STATUS  mandatory
                DESCRIPTION "Over-Voltage-Alarm-Threshhold-Alternate"
                              ::= { panelboard1 442 }

pb1-under-voltage-alarm-threshhold-alternate
                OBJECT-TYPE
                SYNTAX  INTEGER
                ACCESS  read-write
                STATUS  mandatory
                DESCRIPTION "Under-Voltage-Alarm-Threshhold-Alternate"
                              ::= { panelboard1 443 }

pb1-kwh-reset
                OBJECT-TYPE
                SYNTAX  INTEGER
                ACCESS  read-write
                STATUS  mandatory
                DESCRIPTION "KWH Reset
                    Resets all KWH values to zero"
                              ::= { panelboard1 444 }

pb1-current-phase-a-panelboard
                OBJECT-TYPE
                SYNTAX  INTEGER
                ACCESS  read-only
                STATUS  mandatory
                DESCRIPTION "Current-Phase-A-Panelboard"
                              ::= { panelboard1 445 }

pb1-current-phase-b-panelboard
                OBJECT-TYPE
                SYNTAX  INTEGER
                ACCESS  read-only
                STATUS  mandatory
                DESCRIPTION "Current-Phase-B-Panelboard"
                              ::= { panelboard1 446 }

pb1-current-phase-c-panelboard
                OBJECT-TYPE
                SYNTAX  INTEGER
                ACCESS  read-only
                STATUS  mandatory
                DESCRIPTION "Current-Phase-C-Panelboard"
                              ::= { panelboard1 447 }

pb1-current-neutral-panelboard
                OBJECT-TYPE
                SYNTAX  INTEGER
                ACCESS  read-only
                STATUS  mandatory
                DESCRIPTION "Current-Neutral-Panelboard"
                              ::= { panelboard1 448 }

pb1-current-ground-panelboard
                OBJECT-TYPE
                SYNTAX  INTEGER
                ACCESS  read-only
                STATUS  mandatory
                DESCRIPTION "Current-Ground-Panelboard"
                              ::= { panelboard1 449 }

pb1-over-current-alarm-threshhold
                OBJECT-TYPE
                SYNTAX  INTEGER
                ACCESS  read-write
                STATUS  mandatory
                DESCRIPTION "Over-Current-Alarm-Threshhold"
                              ::= { panelboard1 450 }

pb1-under-current-alarm-threshhold
                OBJECT-TYPE
                SYNTAX  INTEGER
                ACCESS  read-write
                STATUS  mandatory
                DESCRIPTION "Under-Current-Alarm-Threshhold"
                              ::= { panelboard1 451 }

pb1-real-power-kw-total
                OBJECT-TYPE
                SYNTAX  INTEGER
                ACCESS  read-only
                STATUS  mandatory
                DESCRIPTION "Real-Power-KW-Total"
                              ::= { panelboard1 452 }

pb1-real-power-kw-phase-a
                OBJECT-TYPE
                SYNTAX  INTEGER
                ACCESS  read-only
                STATUS  mandatory
                DESCRIPTION "Real-Power-KW-Phase-A"
                              ::= { panelboard1 453 }

pb1-real-power-kw-phase-b
                OBJECT-TYPE
                SYNTAX  INTEGER
                ACCESS  read-only
                STATUS  mandatory
                DESCRIPTION "Real-Power-KW-Phase-B"
                              ::= { panelboard1 454 }

pb1-real-power-kw-phase-c
                OBJECT-TYPE
                SYNTAX  INTEGER
                ACCESS  read-only
                STATUS  mandatory
                DESCRIPTION "Real-Power-KW-Phase-C"
                              ::= { panelboard1 455 }

pb1-apparent-power-kva-total
                OBJECT-TYPE
                SYNTAX  INTEGER
                ACCESS  read-only
                STATUS  mandatory
                DESCRIPTION "Apparent-Power-KVA-Total"
                              ::= { panelboard1 456 }

pb1-reactive-power-kvar-total
                OBJECT-TYPE
                SYNTAX  INTEGER
                ACCESS  read-only
                STATUS  mandatory
                DESCRIPTION "Reactive-Power-KVAR-Total"
                              ::= { panelboard1 457 }

pb1-power-factor-total
                OBJECT-TYPE
                SYNTAX  INTEGER
                ACCESS  read-only
                STATUS  mandatory
                DESCRIPTION "Power-Factor-Total"
                              ::= { panelboard1 458 }

pb1-power-factor-phase-a
                OBJECT-TYPE
                SYNTAX  INTEGER
                ACCESS  read-only
                STATUS  mandatory
                DESCRIPTION "Power-Factor-Phase-A"
                              ::= { panelboard1 459 }

pb1-power-factor-phase-b
                OBJECT-TYPE
                SYNTAX  INTEGER
                ACCESS  read-only
                STATUS  mandatory
                DESCRIPTION "power-Factor-Phase-B"
                                ::= { panelboard1 460 }

pb1-power-factor-phase-c
                OBJECT-TYPE
                SYNTAX  INTEGER
                ACCESS  read-only
                STATUS  mandatory
                DESCRIPTION "Power-Factor-Phase-C"
                              ::= { panelboard1 461 }

pb1-energy-consumption-kwh-low-word-integer
                OBJECT-TYPE
                SYNTAX  INTEGER
                ACCESS  read-only
                STATUS  mandatory
                DESCRIPTION "Energy-Consumption-KWh-Low-Word-Integer"
                              ::= { panelboard1 462 }

pb1-energy-consumption-kwh-high-word-integer
                OBJECT-TYPE
                SYNTAX  INTEGER
                ACCESS  read-only
                STATUS  mandatory
                DESCRIPTION "Energy-Consumption-KWh-High-Word-Integer"
                              ::= { panelboard1 463 }

pb1-main-kwh-reset
                OBJECT-TYPE
                SYNTAX  INTEGER
                ACCESS  read-only
                STATUS  mandatory
                DESCRIPTION "Main-KWH-Reset"
                              ::= { panelboard1 464 }

pb1-percent-load-phase-a
                OBJECT-TYPE
                SYNTAX  INTEGER
                ACCESS  read-only
                STATUS  mandatory
                DESCRIPTION "Percent-Load-Phase-A"
                              ::= { panelboard1 465 }

pb1-percent-load-phase-b
                OBJECT-TYPE
                SYNTAX  INTEGER
                ACCESS  read-only
                STATUS  mandatory
                DESCRIPTION "Percent-Load-Phase-B"
                              ::= { panelboard1 466 }

pb1-percent-load-phase-c
                OBJECT-TYPE
                SYNTAX  INTEGER
                ACCESS  read-only
                STATUS  mandatory
                DESCRIPTION "Percent-Load-Phase-C"
                              ::= { panelboard1 467 }

pb1-full-load
                OBJECT-TYPE
                SYNTAX  INTEGER
                ACCESS  read-write
                STATUS  mandatory
                DESCRIPTION "Full-Load, used to calculate percent load (250.0A = 2500)"
                              ::= { panelboard1 468 }

pb1-branch1-rated-current-size
                OBJECT-TYPE
                SYNTAX  INTEGER
                ACCESS  read-write
                STATUS  mandatory
                DESCRIPTION "BRANCH 1 rated-current Size
                                    Note for all rated-current sizes 1-72: 10 = 10 amps
                    Range is 10 to 100 amps"
                              ::= { panelboard1 501 }
pb1-branch2-rated-current-size
                OBJECT-TYPE
                SYNTAX  INTEGER
                ACCESS  read-write
                STATUS  mandatory
                DESCRIPTION "BRANCH 2 rated-current Size"
                              ::= { panelboard1 502 }

pb1-branch3-rated-current-size
                OBJECT-TYPE
                SYNTAX  INTEGER
                ACCESS  read-write
                STATUS  mandatory
                DESCRIPTION "BRANCH 3 rated-current Size"
                              ::= { panelboard1 503 }

pb1-branch4-rated-current-size
                OBJECT-TYPE
                SYNTAX  INTEGER
                ACCESS  read-write
                STATUS  mandatory
                DESCRIPTION "BRANCH 4 rated-current Size"
                              ::= { panelboard1 504 }

pb1-branch5-rated-current-size
                OBJECT-TYPE
                SYNTAX  INTEGER
                ACCESS  read-write
                STATUS  mandatory
                DESCRIPTION "BRANCH 5 rated-current Size"
                              ::= { panelboard1 505 }

pb1-branch6-rated-current-size
                OBJECT-TYPE
                SYNTAX  INTEGER
                ACCESS  read-write
                STATUS  mandatory
                DESCRIPTION "BRANCH 6 rated-current Size"
                              ::= { panelboard1 506 }

pb1-branch7-rated-current-size
                OBJECT-TYPE
                SYNTAX  INTEGER
                ACCESS  read-write
                STATUS  mandatory
                DESCRIPTION "BRANCH 7 rated-current Size"
                              ::= { panelboard1 507 }

pb1-branch8-rated-current-size
                OBJECT-TYPE
                SYNTAX  INTEGER
                ACCESS  read-write
                STATUS  mandatory
                DESCRIPTION "BRANCH 8 rated-current Size"
                              ::= { panelboard1 508 }

pb1-branch9-rated-current-size
                OBJECT-TYPE
                SYNTAX  INTEGER
                ACCESS  read-write
                STATUS  mandatory
                DESCRIPTION "BRANCH 9 rated-current Size"
                              ::= { panelboard1 509 }

pb1-branch10-rated-current-size
                OBJECT-TYPE
                SYNTAX  INTEGER
                ACCESS  read-write
                STATUS  mandatory
                DESCRIPTION "BRANCH 10 rated-current Size"
                              ::= { panelboard1 510 }

pb1-branch11-rated-current-size
                OBJECT-TYPE
                SYNTAX  INTEGER
                ACCESS  read-write
                STATUS  mandatory
                DESCRIPTION "BRANCH 11 rated-current Size"
                              ::= { panelboard1 511 }

pb1-branch12-rated-current-size
                OBJECT-TYPE
                SYNTAX  INTEGER
                ACCESS  read-write
                STATUS  mandatory
                DESCRIPTION "BRANCH 12 rated-current Size"
                              ::= { panelboard1 512 }

pb1-branch13-rated-current-size
                OBJECT-TYPE
                SYNTAX  INTEGER
                ACCESS  read-write
                STATUS  mandatory
                DESCRIPTION "BRANCH 13 rated-current Size"
                              ::= { panelboard1 513 }

pb1-branch14-rated-current-size
                OBJECT-TYPE
                SYNTAX  INTEGER
                ACCESS  read-write
                STATUS  mandatory
                DESCRIPTION "BRANCH 14 rated-current Size"
                              ::= { panelboard1 514 }

pb1-branch15-rated-current-size
                OBJECT-TYPE
                SYNTAX  INTEGER
                ACCESS  read-write
                STATUS  mandatory
                DESCRIPTION "BRANCH 15 rated-current Size"
                              ::= { panelboard1 515 }

pb1-branch16-rated-current-size
                OBJECT-TYPE
                SYNTAX  INTEGER
                ACCESS  read-write
                STATUS  mandatory
                DESCRIPTION "BRANCH 16 rated-current Size"
                              ::= { panelboard1 516 }

pb1-branch17-rated-current-size
                OBJECT-TYPE
                SYNTAX  INTEGER
                ACCESS  read-write
                STATUS  mandatory
                DESCRIPTION "BRANCH 17 rated-current Size"
                              ::= { panelboard1 517 }

pb1-branch18-rated-current-size
                OBJECT-TYPE
                SYNTAX  INTEGER
                ACCESS  read-write
                STATUS  mandatory
                DESCRIPTION "BRANCH 18 rated-current Size"
                              ::= { panelboard1 518 }

pb1-branch19-rated-current-size
                OBJECT-TYPE
                SYNTAX  INTEGER
                ACCESS  read-write
                STATUS  mandatory
                DESCRIPTION "BRANCH 19 rated-current Size"
                              ::= { panelboard1 519 }

pb1-branch20-rated-current-size
                OBJECT-TYPE
                SYNTAX  INTEGER
                ACCESS  read-write
                STATUS  mandatory
                DESCRIPTION "BRANCH 20 rated-current Size"
                              ::= { panelboard1 520 }

pb1-branch21-rated-current-size
                OBJECT-TYPE
                SYNTAX  INTEGER
                ACCESS  read-write
                STATUS  mandatory
                DESCRIPTION "BRANCH 21 rated-current Size"
                              ::= { panelboard1 521 }

pb1-branch22-rated-current-size
                OBJECT-TYPE
                SYNTAX  INTEGER
                ACCESS  read-write
                STATUS  mandatory
                DESCRIPTION "BRANCH 22 rated-current Size"
                              ::= { panelboard1 522 }

pb1-branch23-rated-current-size
                OBJECT-TYPE
                SYNTAX  INTEGER
                ACCESS  read-write
                STATUS  mandatory
                DESCRIPTION "BRANCH 23 rated-current Size"
                              ::= { panelboard1 523 }

pb1-branch24-rated-current-size
                OBJECT-TYPE
                SYNTAX  INTEGER
                ACCESS  read-write
                STATUS  mandatory
                DESCRIPTION "BRANCH 24 rated-current Size"
                              ::= { panelboard1 524 }

pb1-branch25-rated-current-size
                OBJECT-TYPE
                SYNTAX  INTEGER
                ACCESS  read-write
                STATUS  mandatory
                DESCRIPTION "BRANCH 25 rated-current Size"
                              ::= { panelboard1 525 }

pb1-branch26-rated-current-size
                OBJECT-TYPE
                SYNTAX  INTEGER
                ACCESS  read-write
                STATUS  mandatory
                DESCRIPTION "BRANCH 26 rated-current Size"
                              ::= { panelboard1 526 }

pb1-branch27-rated-current-size
                OBJECT-TYPE
                SYNTAX  INTEGER
                ACCESS  read-write
                STATUS  mandatory
                DESCRIPTION "BRANCH 27 rated-current Size"
                              ::= { panelboard1 527 }

pb1-branch28-rated-current-size
                OBJECT-TYPE
                SYNTAX  INTEGER
                ACCESS  read-write
                STATUS  mandatory
                DESCRIPTION "BRANCH 28 rated-current Size"
                              ::= { panelboard1 528 }

pb1-branch29-rated-current-size
                OBJECT-TYPE
                SYNTAX  INTEGER
                ACCESS  read-write
                STATUS  mandatory
                DESCRIPTION "BRANCH 29 rated-current Size"
                              ::= { panelboard1 529 }

pb1-branch30-rated-current-size
                OBJECT-TYPE
                SYNTAX  INTEGER
                ACCESS  read-write
                STATUS  mandatory
                DESCRIPTION "BRANCH 30 rated-current Size"
                              ::= { panelboard1 530 }

pb1-branch31-rated-current-size
                OBJECT-TYPE
                SYNTAX  INTEGER
                ACCESS  read-write
                STATUS  mandatory
                DESCRIPTION "BRANCH 31 rated-current Size"
                              ::= { panelboard1 531 }

pb1-branch32-rated-current-size
                OBJECT-TYPE
                SYNTAX  INTEGER
                ACCESS  read-write
                STATUS  mandatory
                DESCRIPTION "BRANCH 32 rated-current Size"
                              ::= { panelboard1 532 }

pb1-branch33-rated-current-size
                OBJECT-TYPE
                SYNTAX  INTEGER
                ACCESS  read-write
                STATUS  mandatory
                DESCRIPTION "BRANCH 33 rated-current Size"
                              ::= { panelboard1 533 }

pb1-branch34-rated-current-size
                OBJECT-TYPE
                SYNTAX  INTEGER
                ACCESS  read-write
                STATUS  mandatory
                DESCRIPTION "BRANCH 34 rated-current Size"
                              ::= { panelboard1 534 }

pb1-branch35-rated-current-size
                OBJECT-TYPE
                SYNTAX  INTEGER
                ACCESS  read-write
                STATUS  mandatory
                DESCRIPTION "BRANCH 35 rated-current Size"
                              ::= { panelboard1 535 }

pb1-branch36-rated-current-size
                OBJECT-TYPE
                SYNTAX  INTEGER
                ACCESS  read-write
                STATUS  mandatory
                DESCRIPTION "BRANCH 36 rated-current Size"
                              ::= { panelboard1 536 }

pb1-branch37-rated-current-size
                OBJECT-TYPE
                SYNTAX  INTEGER
                ACCESS  read-write
                STATUS  mandatory
                DESCRIPTION "BRANCH 37 rated-current Size"
                              ::= { panelboard1 537 }

pb1-branch38-rated-current-size
                OBJECT-TYPE
                SYNTAX  INTEGER
                ACCESS  read-write
                STATUS  mandatory
                DESCRIPTION "BRANCH 38 rated-current Size"
                              ::= { panelboard1 538 }

pb1-branch39-rated-current-size
                OBJECT-TYPE
                SYNTAX  INTEGER
                ACCESS  read-write
                STATUS  mandatory
                DESCRIPTION "BRANCH 39 rated-current Size"
                              ::= { panelboard1 539 }

pb1-branch40-rated-current-size
                OBJECT-TYPE
                SYNTAX  INTEGER
                ACCESS  read-write
                STATUS  mandatory
                DESCRIPTION "BRANCH 40 rated-current Size"
                              ::= { panelboard1 540 }

pb1-branch41-rated-current-size
                OBJECT-TYPE
                SYNTAX  INTEGER
                ACCESS  read-write
                STATUS  mandatory
                DESCRIPTION "BRANCH 41 rated-current Size"
                              ::= { panelboard1 541 }

pb1-branch42-rated-current-size
                OBJECT-TYPE
                SYNTAX  INTEGER
                ACCESS  read-write
                STATUS  mandatory
                DESCRIPTION "BRANCH 42 rated-current Size"
                              ::= { panelboard1 542 }

pb1-branch43-rated-current-size
                OBJECT-TYPE
                SYNTAX  INTEGER
                ACCESS  read-write
                STATUS  mandatory
                DESCRIPTION "BRANCH 43 rated-current Size"
                              ::= { panelboard1 543 }

pb1-branch44-rated-current-size
                OBJECT-TYPE
                SYNTAX  INTEGER
                ACCESS  read-write
                STATUS  mandatory
                DESCRIPTION "BRANCH 44 rated-current Size"
                              ::= { panelboard1 544 }

pb1-branch45-rated-current-size
                OBJECT-TYPE
                SYNTAX  INTEGER
                ACCESS  read-write
                STATUS  mandatory
                DESCRIPTION "BRANCH 45 rated-current Size"
                              ::= { panelboard1 545 }

pb1-branch46-rated-current-size
                OBJECT-TYPE
                SYNTAX  INTEGER
                ACCESS  read-write
                STATUS  mandatory
                DESCRIPTION "BRANCH 46 rated-current Size"
                              ::= { panelboard1 546 }

pb1-branch47-rated-current-size
                OBJECT-TYPE
                SYNTAX  INTEGER
                ACCESS  read-write
                STATUS  mandatory
                DESCRIPTION "BRANCH 47 rated-current Size"
                              ::= { panelboard1 547 }

pb1-branch48-rated-current-size
                OBJECT-TYPE
                SYNTAX  INTEGER
                ACCESS  read-write
                STATUS  mandatory
                DESCRIPTION "BRANCH 48 rated-current Size"
                              ::= { panelboard1 548 }

pb1-branch49-rated-current-size
                OBJECT-TYPE
                SYNTAX  INTEGER
                ACCESS  read-write
                STATUS  mandatory
                DESCRIPTION "BRANCH 49 rated-current Size"
                              ::= { panelboard1 549 }

pb1-branch50-rated-current-size
                OBJECT-TYPE
                SYNTAX  INTEGER
                ACCESS  read-write
                STATUS  mandatory
                DESCRIPTION "BRANCH 50 rated-current Size"
                              ::= { panelboard1 550 }

pb1-branch51-rated-current-size
                OBJECT-TYPE
                SYNTAX  INTEGER
                ACCESS  read-write
                STATUS  mandatory
                DESCRIPTION "BRANCH 51 rated-current Size"
                              ::= { panelboard1 551 }

pb1-branch52-rated-current-size
                OBJECT-TYPE
                SYNTAX  INTEGER
                ACCESS  read-write
                STATUS  mandatory
                DESCRIPTION "BRANCH 52 rated-current Size"
                              ::= { panelboard1 552 }

pb1-branch53-rated-current-size
                OBJECT-TYPE
                SYNTAX  INTEGER
                ACCESS  read-write
                STATUS  mandatory
                DESCRIPTION "BRANCH 53 rated-current Size"
                              ::= { panelboard1 553 }

pb1-branch54-rated-current-size
                OBJECT-TYPE
                SYNTAX  INTEGER
                ACCESS  read-write
                STATUS  mandatory
                DESCRIPTION "BRANCH 54 rated-current Size"
                              ::= { panelboard1 554 }

pb1-branch55-rated-current-size
                OBJECT-TYPE
                SYNTAX  INTEGER
                ACCESS  read-write
                STATUS  mandatory
                DESCRIPTION "BRANCH 55 rated-current Size"
                              ::= { panelboard1 555 }

pb1-branch56-rated-current-size
                OBJECT-TYPE
                SYNTAX  INTEGER
                ACCESS  read-write
                STATUS  mandatory
                DESCRIPTION "BRANCH 56 rated-current Size"
                              ::= { panelboard1 556 }

pb1-branch57-rated-current-size
                OBJECT-TYPE
                SYNTAX  INTEGER
                ACCESS  read-write
                STATUS  mandatory
                DESCRIPTION "BRANCH 57 rated-current Size"
                              ::= { panelboard1 557 }

pb1-branch58-rated-current-size
                OBJECT-TYPE
                SYNTAX  INTEGER
                ACCESS  read-write
                STATUS  mandatory
                DESCRIPTION "BRANCH 58 rated-current Size"
                              ::= { panelboard1 558 }

pb1-branch59-rated-current-size
                OBJECT-TYPE
                SYNTAX  INTEGER
                ACCESS  read-write
                STATUS  mandatory
                DESCRIPTION "BRANCH 59 rated-current Size"
                              ::= { panelboard1 559 }

pb1-branch60-rated-current-size
                OBJECT-TYPE
                SYNTAX  INTEGER
                ACCESS  read-write
                STATUS  mandatory
                DESCRIPTION "BRANCH 60 rated-current Size"
                              ::= { panelboard1 560 }

pb1-branch61-rated-current-size
                OBJECT-TYPE
                SYNTAX  INTEGER
                ACCESS  read-write
                STATUS  mandatory
                DESCRIPTION "BRANCH 61 rated-current Size"
                              ::= { panelboard1 561 }

pb1-branch62-rated-current-size
                OBJECT-TYPE
                SYNTAX  INTEGER
                ACCESS  read-write
                STATUS  mandatory
                DESCRIPTION "BRANCH 62 rated-current Size"
                              ::= { panelboard1 562 }

pb1-branch63-rated-current-size
                OBJECT-TYPE
                SYNTAX  INTEGER
                ACCESS  read-write
                STATUS  mandatory
                DESCRIPTION "BRANCH 63 rated-current Size"
                              ::= { panelboard1 563 }

pb1-branch64-rated-current-size
                OBJECT-TYPE
                SYNTAX  INTEGER
                ACCESS  read-write
                STATUS  mandatory
                DESCRIPTION "BRANCH 64 rated-current Size"
                              ::= { panelboard1 564 }

pb1-branch65-rated-current-size
                OBJECT-TYPE
                SYNTAX  INTEGER
                ACCESS  read-write
                STATUS  mandatory
                DESCRIPTION "BRANCH 65 rated-current Size"
                              ::= { panelboard1 565 }

pb1-branch66-rated-current-size
                OBJECT-TYPE
                SYNTAX  INTEGER
                ACCESS  read-write
                STATUS  mandatory
                DESCRIPTION "BRANCH 66 rated-current Size"
                              ::= { panelboard1 566 }

pb1-branch67-rated-current-size
                OBJECT-TYPE
                SYNTAX  INTEGER
                ACCESS  read-write
                STATUS  mandatory
                DESCRIPTION "BRANCH 67 rated-current Size"
                              ::= { panelboard1 567 }

pb1-branch68-rated-current-size
                OBJECT-TYPE
                SYNTAX  INTEGER
                ACCESS  read-write
                STATUS  mandatory
                DESCRIPTION "BRANCH 68 rated-current Size"
                              ::= { panelboard1 568 }

pb1-branch69-rated-current-size
                OBJECT-TYPE
                SYNTAX  INTEGER
                ACCESS  read-write
                STATUS  mandatory
                DESCRIPTION "BRANCH 69 rated-current Size"
                              ::= { panelboard1 569 }

pb1-branch70-rated-current-size
                OBJECT-TYPE
                SYNTAX  INTEGER
                ACCESS  read-write
                STATUS  mandatory
                DESCRIPTION "BRANCH 70 rated-current Size"
                              ::= { panelboard1 570 }

pb1-branch71-rated-current-size
                OBJECT-TYPE
                SYNTAX  INTEGER
                ACCESS  read-write
                STATUS  mandatory
                DESCRIPTION "BRANCH 71 rated-current Size"
                              ::= { panelboard1 571 }

pb1-branch72-rated-current-size
                OBJECT-TYPE
                SYNTAX  INTEGER
                ACCESS  read-write
                STATUS  mandatory
                DESCRIPTION "BRANCH 72 rated-current Size"
                              ::= { panelboard1 572 }

pb1-branch1-kw
                OBJECT-TYPE
                SYNTAX  INTEGER
                ACCESS  read-only
                STATUS  mandatory
                DESCRIPTION "BRANCH1 KW
                                    Note for all KW: 100 = 10.0 or 1.00 kw depending on setup"
                              ::= { panelboard1 601 }

pb1-branch2-kw
                OBJECT-TYPE
                SYNTAX  INTEGER
                ACCESS  read-only
                STATUS  mandatory
                DESCRIPTION "BRANCH 2 KW"
                              ::= { panelboard1 602 }

pb1-branch3-kw
                OBJECT-TYPE
                SYNTAX  INTEGER
                ACCESS  read-only
                STATUS  mandatory
                DESCRIPTION "BRANCH 3 KW"
                              ::= { panelboard1 603 }

pb1-branch4-kw
                OBJECT-TYPE
                SYNTAX  INTEGER
                ACCESS  read-only
                STATUS  mandatory
                DESCRIPTION "BRANCH 4 KW"
                              ::= { panelboard1 604 }

pb1-branch5-kw
                OBJECT-TYPE
                SYNTAX  INTEGER
                ACCESS  read-only
                STATUS  mandatory
                DESCRIPTION "BRANCH 5 KW"
                              ::= { panelboard1 605 }

pb1-branch6-kw
                OBJECT-TYPE
                SYNTAX  INTEGER
                ACCESS  read-only
                STATUS  mandatory
                DESCRIPTION "BRANCH 6 KW"
                              ::= { panelboard1 606 }

pb1-branch7-kw
                OBJECT-TYPE
                SYNTAX  INTEGER
                ACCESS  read-only
                STATUS  mandatory
                DESCRIPTION "BRANCH 7 KW"
                              ::= { panelboard1 607 }

pb1-branch8-kw
                OBJECT-TYPE
                SYNTAX  INTEGER
                ACCESS  read-only
                STATUS  mandatory
                DESCRIPTION "BRANCH 8 KW"
                              ::= { panelboard1 608 }

pb1-branch9-kw
                OBJECT-TYPE
                SYNTAX  INTEGER
                ACCESS  read-only
                STATUS  mandatory
                DESCRIPTION "BRANCH 9 KW"
                              ::= { panelboard1 609 }

pb1-branch10-kw
                OBJECT-TYPE
                SYNTAX  INTEGER
                ACCESS  read-only
                STATUS  mandatory
                DESCRIPTION "BRANCH 10 KW"
                              ::= { panelboard1 610 }

pb1-branch11-kw
                OBJECT-TYPE
                SYNTAX  INTEGER
                ACCESS  read-only
                STATUS  mandatory
                DESCRIPTION "BRANCH 11 KW"
                              ::= { panelboard1 611 }

pb1-branch12-kw
                OBJECT-TYPE
                SYNTAX  INTEGER
                ACCESS  read-only
                STATUS  mandatory
                DESCRIPTION "BRANCH 12 KW"
                              ::= { panelboard1 612 }

pb1-branch13-kw
                OBJECT-TYPE
                SYNTAX  INTEGER
                ACCESS  read-only
                STATUS  mandatory
                DESCRIPTION "BRANCH 13 KW"
                              ::= { panelboard1 613 }

pb1-branch14-kw
                OBJECT-TYPE
                SYNTAX  INTEGER
                ACCESS  read-only
                STATUS  mandatory
                DESCRIPTION "BRANCH 14 KW"
                              ::= { panelboard1 614 }

pb1-branch15-kw
                OBJECT-TYPE
                SYNTAX  INTEGER
                ACCESS  read-only
                STATUS  mandatory
                DESCRIPTION "BRANCH 15 KW"
                              ::= { panelboard1 615 }

pb1-branch16-kw
                OBJECT-TYPE
                SYNTAX  INTEGER
                ACCESS  read-only
                STATUS  mandatory
                DESCRIPTION "BRANCH 16 KW"
                              ::= { panelboard1 616 }

pb1-branch17-kw
                OBJECT-TYPE
                SYNTAX  INTEGER
                ACCESS  read-only
                STATUS  mandatory
                DESCRIPTION "BRANCH 17 KW"
                              ::= { panelboard1 617 }

pb1-branch18-kw
                OBJECT-TYPE
                SYNTAX  INTEGER
                ACCESS  read-only
                STATUS  mandatory
                DESCRIPTION "BRANCH 18 KW"
                              ::= { panelboard1 618 }

pb1-branch19-kw
                OBJECT-TYPE
                SYNTAX  INTEGER
                ACCESS  read-only
                STATUS  mandatory
                DESCRIPTION "BRANCH 19 KW"
                              ::= { panelboard1 619 }

pb1-branch20-kw
                OBJECT-TYPE
                SYNTAX  INTEGER
                ACCESS  read-only
                STATUS  mandatory
                DESCRIPTION "BRANCH 20 KW"
                              ::= { panelboard1 620 }

pb1-branch21-kw
                OBJECT-TYPE
                SYNTAX  INTEGER
                ACCESS  read-only
                STATUS  mandatory
                DESCRIPTION "BRANCH 21 KW"
                              ::= { panelboard1 621 }

pb1-branch22-kw
                OBJECT-TYPE
                SYNTAX  INTEGER
                ACCESS  read-only
                STATUS  mandatory
                DESCRIPTION "BRANCH 22 KW"
                              ::= { panelboard1 622 }

pb1-branch23-kw
                OBJECT-TYPE
                SYNTAX  INTEGER
                ACCESS  read-only
                STATUS  mandatory
                DESCRIPTION "BRANCH 23 KW"
                              ::= { panelboard1 623 }

pb1-branch24-kw
                OBJECT-TYPE
                SYNTAX  INTEGER
                ACCESS  read-only
                STATUS  mandatory
                DESCRIPTION "BRANCH 24 KW"
                              ::= { panelboard1 624 }

pb1-branch25-kw
                OBJECT-TYPE
                SYNTAX  INTEGER
                ACCESS  read-only
                STATUS  mandatory
                DESCRIPTION "BRANCH 25 KW"
                              ::= { panelboard1 625 }

pb1-branch26-kw
                OBJECT-TYPE
                SYNTAX  INTEGER
                ACCESS  read-only
                STATUS  mandatory
                DESCRIPTION "BRANCH 26 KW"
                              ::= { panelboard1 626 }

pb1-branch27-kw
                OBJECT-TYPE
                SYNTAX  INTEGER
                ACCESS  read-only
                STATUS  mandatory
                DESCRIPTION "BRANCH 27 KW"
                              ::= { panelboard1 627 }

pb1-branch28-kw
                OBJECT-TYPE
                SYNTAX  INTEGER
                ACCESS  read-only
                STATUS  mandatory
                DESCRIPTION "BRANCH 28 KW"
                              ::= { panelboard1 628 }

pb1-branch29-kw
                OBJECT-TYPE
                SYNTAX  INTEGER
                ACCESS  read-only
                STATUS  mandatory
                DESCRIPTION "BRANCH 29 KW"
                              ::= { panelboard1 629 }

pb1-branch30-kw
                OBJECT-TYPE
                SYNTAX  INTEGER
                ACCESS  read-only
                STATUS  mandatory
                DESCRIPTION "BRANCH 30 KW"
                              ::= { panelboard1 630 }

pb1-branch31-kw
                OBJECT-TYPE
                SYNTAX  INTEGER
                ACCESS  read-only
                STATUS  mandatory
                DESCRIPTION "BRANCH 31 KW"
                              ::= { panelboard1 631 }

pb1-branch32-kw
                OBJECT-TYPE
                SYNTAX  INTEGER
                ACCESS  read-only
                STATUS  mandatory
                DESCRIPTION "BRANCH 32 KW"
                              ::= { panelboard1 632 }

pb1-branch33-kw
                OBJECT-TYPE
                SYNTAX  INTEGER
                ACCESS  read-only
                STATUS  mandatory
                DESCRIPTION "BRANCH 33 KW"
                              ::= { panelboard1 633 }

pb1-branch34-kw
                OBJECT-TYPE
                SYNTAX  INTEGER
                ACCESS  read-only
                STATUS  mandatory
                DESCRIPTION "BRANCH 34 KW"
                              ::= { panelboard1 634 }

pb1-branch35-kw
                OBJECT-TYPE
                SYNTAX  INTEGER
                ACCESS  read-only
                STATUS  mandatory
                DESCRIPTION "BRANCH 35 KW"
                              ::= { panelboard1 635 }

pb1-branch36-kw
                OBJECT-TYPE
                SYNTAX  INTEGER
                ACCESS  read-only
                STATUS  mandatory
                DESCRIPTION "BRANCH 36 KW"
                              ::= { panelboard1 636 }

pb1-branch37-kw
                OBJECT-TYPE
                SYNTAX  INTEGER
                ACCESS  read-only
                STATUS  mandatory
                DESCRIPTION "BRANCH 37 KW"
                              ::= { panelboard1 637 }

pb1-branch38-kw
                OBJECT-TYPE
                SYNTAX  INTEGER
                ACCESS  read-only
                STATUS  mandatory
                DESCRIPTION "BRANCH 38 KW"
                              ::= { panelboard1 638 }

pb1-branch39-kw
                OBJECT-TYPE
                SYNTAX  INTEGER
                ACCESS  read-only
                STATUS  mandatory
                DESCRIPTION "BRANCH 39 KW"
                              ::= { panelboard1 639 }

pb1-branch40-kw
                OBJECT-TYPE
                SYNTAX  INTEGER
                ACCESS  read-only
                STATUS  mandatory
                DESCRIPTION "BRANCH 40 KW"
                              ::= { panelboard1 640 }

pb1-branch41-kw
                OBJECT-TYPE
                SYNTAX  INTEGER
                ACCESS  read-only
                STATUS  mandatory
                DESCRIPTION "BRANCH 41 KW"
                              ::= { panelboard1 641 }

pb1-branch42-kw
                OBJECT-TYPE
                SYNTAX  INTEGER
                ACCESS  read-only
                STATUS  mandatory
                DESCRIPTION "BRANCH 42 KW"
                              ::= { panelboard1 642 }

pb1-branch43-kw
                OBJECT-TYPE
                SYNTAX  INTEGER
                ACCESS  read-only
                STATUS  mandatory
                DESCRIPTION "BRANCH 43 KW"
                              ::= { panelboard1 643 }

pb1-branch44-kw
                OBJECT-TYPE
                SYNTAX  INTEGER
                ACCESS  read-only
                STATUS  mandatory
                DESCRIPTION "BRANCH 44 KW"
                              ::= { panelboard1 644 }

pb1-branch45-kw
                OBJECT-TYPE
                SYNTAX  INTEGER
                ACCESS  read-only
                STATUS  mandatory
                DESCRIPTION "BRANCH 45 KW"
                              ::= { panelboard1 645 }

pb1-branch46-kw
                OBJECT-TYPE
                SYNTAX  INTEGER
                ACCESS  read-only
                STATUS  mandatory
                DESCRIPTION "BRANCH 46 KW"
                              ::= { panelboard1 646 }

pb1-branch47-kw
                OBJECT-TYPE
                SYNTAX  INTEGER
                ACCESS  read-only
                STATUS  mandatory
                DESCRIPTION "BRANCH 47 KW"
                              ::= { panelboard1 647 }

pb1-branch48-kw
                OBJECT-TYPE
                SYNTAX  INTEGER
                ACCESS  read-only
                STATUS  mandatory
                DESCRIPTION "BRANCH 48 KW"
                              ::= { panelboard1 648 }

pb1-branch49-kw
                OBJECT-TYPE
                SYNTAX  INTEGER
                ACCESS  read-only
                STATUS  mandatory
                DESCRIPTION "BRANCH 49 KW"
                              ::= { panelboard1 649 }

pb1-branch50-kw
                OBJECT-TYPE
                SYNTAX  INTEGER
                ACCESS  read-only
                STATUS  mandatory
                DESCRIPTION "BRANCH 50 KW"
                              ::= { panelboard1 650 }

pb1-branch51-kw
                OBJECT-TYPE
                SYNTAX  INTEGER
                ACCESS  read-only
                STATUS  mandatory
                DESCRIPTION "BRANCH 51 KW"
                              ::= { panelboard1 651 }

pb1-branch52-kw
                OBJECT-TYPE
                SYNTAX  INTEGER
                ACCESS  read-only
                STATUS  mandatory
                DESCRIPTION "BRANCH 52 KW"
                              ::= { panelboard1 652 }

pb1-branch53-kw
                OBJECT-TYPE
                SYNTAX  INTEGER
                ACCESS  read-only
                STATUS  mandatory
                DESCRIPTION "BRANCH 53 KW"
                              ::= { panelboard1 653 }

pb1-branch54-kw
                OBJECT-TYPE
                SYNTAX  INTEGER
                ACCESS  read-only
                STATUS  mandatory
                DESCRIPTION "BRANCH 54 KW"
                              ::= { panelboard1 654 }

pb1-branch55-kw
                OBJECT-TYPE
                SYNTAX  INTEGER
                ACCESS  read-only
                STATUS  mandatory
                DESCRIPTION "BRANCH 55 KW"
                              ::= { panelboard1 655 }

pb1-branch56-kw
                OBJECT-TYPE
                SYNTAX  INTEGER
                ACCESS  read-only
                STATUS  mandatory
                DESCRIPTION "BRANCH 56 KW"
                              ::= { panelboard1 656 }

pb1-branch57-kw
                OBJECT-TYPE
                SYNTAX  INTEGER
                ACCESS  read-only
                STATUS  mandatory
                DESCRIPTION "BRANCH 57 KW"
                              ::= { panelboard1 657 }

pb1-branch58-kw
                OBJECT-TYPE
                SYNTAX  INTEGER
                ACCESS  read-only
                STATUS  mandatory
                DESCRIPTION "BRANCH 58 KW"
                              ::= { panelboard1 658 }

pb1-branch59-kw
                OBJECT-TYPE
                SYNTAX  INTEGER
                ACCESS  read-only
                STATUS  mandatory
                DESCRIPTION "BRANCH 59 KW"
                              ::= { panelboard1 659 }

pb1-branch60-kw
                OBJECT-TYPE
                SYNTAX  INTEGER
                ACCESS  read-only
                STATUS  mandatory
                DESCRIPTION "BRANCH 60 KW"
                              ::= { panelboard1 660 }

pb1-branch61-kw
                OBJECT-TYPE
                SYNTAX  INTEGER
                ACCESS  read-only
                STATUS  mandatory
                DESCRIPTION "BRANCH 61 KW"
                              ::= { panelboard1 661 }

pb1-branch62-kw
                OBJECT-TYPE
                SYNTAX  INTEGER
                ACCESS  read-only
                STATUS  mandatory
                DESCRIPTION "BRANCH 62 KW"
                              ::= { panelboard1 662 }

pb1-branch63-kw
                OBJECT-TYPE
                SYNTAX  INTEGER
                ACCESS  read-only
                STATUS  mandatory
                DESCRIPTION "BRANCH 63 KW"
                              ::= { panelboard1 663 }

pb1-branch64-kw
                OBJECT-TYPE
                SYNTAX  INTEGER
                ACCESS  read-only
                STATUS  mandatory
                DESCRIPTION "BRANCH 64 KW"
                              ::= { panelboard1 664 }

pb1-branch65-kw
                OBJECT-TYPE
                SYNTAX  INTEGER
                ACCESS  read-only
                STATUS  mandatory
                DESCRIPTION "BRANCH 65 KW"
                              ::= { panelboard1 665 }

pb1-branch66-kw
                OBJECT-TYPE
                SYNTAX  INTEGER
                ACCESS  read-only
                STATUS  mandatory
                DESCRIPTION "BRANCH 66 KW"
                              ::= { panelboard1 666 }

pb1-branch67-kw
                OBJECT-TYPE
                SYNTAX  INTEGER
                ACCESS  read-only
                STATUS  mandatory
                DESCRIPTION "BRANCH 67 KW"
                              ::= { panelboard1 667 }

pb1-branch68-kw
                OBJECT-TYPE
                SYNTAX  INTEGER
                ACCESS  read-only
                STATUS  mandatory
                DESCRIPTION "BRANCH 68 KW"
                              ::= { panelboard1 668 }

pb1-branch69-kw
                OBJECT-TYPE
                SYNTAX  INTEGER
                ACCESS  read-only
                STATUS  mandatory
                DESCRIPTION "BRANCH 69 KW"
                              ::= { panelboard1 669 }

pb1-branch70-kw
                OBJECT-TYPE
                SYNTAX  INTEGER
                ACCESS  read-only
                STATUS  mandatory
                DESCRIPTION "BRANCH 70 KW"
                              ::= { panelboard1 670 }

pb1-branch71-kw
                OBJECT-TYPE
                SYNTAX  INTEGER
                ACCESS  read-only
                STATUS  mandatory
                DESCRIPTION "BRANCH 71 KW"
                              ::= { panelboard1 671 }

pb1-branch72-kw
                OBJECT-TYPE
                SYNTAX  INTEGER
                ACCESS  read-only
                STATUS  mandatory
                DESCRIPTION "BRANCH 72 KW"
                              ::= { panelboard1 672 }

pb1-branch1-kva
                OBJECT-TYPE
                SYNTAX  INTEGER
                ACCESS  read-only
                STATUS  mandatory
                DESCRIPTION "BRANCH 1 KVA
                                    Note for all KVA: 100 = 10.0 or 1.00 kva depending on setup"
                              ::= { panelboard1 701 }

pb1-branch2-kva
                OBJECT-TYPE
                SYNTAX  INTEGER
                ACCESS  read-only
                STATUS  mandatory
                DESCRIPTION "BRANCH 2 KVA"
                                ::= { panelboard1 702 }

pb1-branch3-kva
                OBJECT-TYPE
                SYNTAX  INTEGER
                ACCESS  read-only
                STATUS  mandatory
                DESCRIPTION "BRANCH 3 KVA"
                              ::= { panelboard1 703 }

pb1-branch4-kva
                OBJECT-TYPE
                SYNTAX  INTEGER
                ACCESS  read-only
                STATUS  mandatory
                DESCRIPTION "BRANCH 4 KVA"
                              ::= { panelboard1 704 }

pb1-branch5-kva
                OBJECT-TYPE
                SYNTAX  INTEGER
                ACCESS  read-only
                STATUS  mandatory
                DESCRIPTION "BRANCH 5 KVA"
                              ::= { panelboard1 705 }

pb1-branch6-kva
                OBJECT-TYPE
                SYNTAX  INTEGER
                ACCESS  read-only
                STATUS  mandatory
                DESCRIPTION "BRANCH 6 KVA"
                              ::= { panelboard1 706 }

pb1-branch7-kva
                OBJECT-TYPE
                SYNTAX  INTEGER
                ACCESS  read-only
                STATUS  mandatory
                DESCRIPTION "BRANCH 7 KVA"
                              ::= { panelboard1 707 }

pb1-branch8-kva
                OBJECT-TYPE
                SYNTAX  INTEGER
                ACCESS  read-only
                STATUS  mandatory
                DESCRIPTION "BRANCH 8 KVA"
                              ::= { panelboard1 708 }

pb1-branch9-kva
                OBJECT-TYPE
                SYNTAX  INTEGER
                ACCESS  read-only
                STATUS  mandatory
                DESCRIPTION "BRANCH 9 KVA"
                              ::= { panelboard1 709 }

pb1-branch10-kva
                OBJECT-TYPE
                SYNTAX  INTEGER
                ACCESS  read-only
                STATUS  mandatory
                DESCRIPTION "BRANCH 10 KVA"
                              ::= { panelboard1 710 }

pb1-branch11-kva
                OBJECT-TYPE
                SYNTAX  INTEGER
                ACCESS  read-only
                STATUS  mandatory
                DESCRIPTION "BRANCH 11 KVA"
                              ::= { panelboard1 711 }

pb1-branch12-kva
                OBJECT-TYPE
                SYNTAX  INTEGER
                ACCESS  read-only
                STATUS  mandatory
                DESCRIPTION "BRANCH 12 KVA"
                              ::= { panelboard1 712 }

pb1-branch13-kva
                OBJECT-TYPE
                SYNTAX  INTEGER
                ACCESS  read-only
                STATUS  mandatory
                DESCRIPTION "BRANCH 13 KVA"
                              ::= { panelboard1 713 }

pb1-branch14-kva
                OBJECT-TYPE
                SYNTAX  INTEGER
                ACCESS  read-only
                STATUS  mandatory
                DESCRIPTION "BRANCH 14 KVA"
                              ::= { panelboard1 714 }

pb1-branch15-kva
                OBJECT-TYPE
                SYNTAX  INTEGER
                ACCESS  read-only
                STATUS  mandatory
                DESCRIPTION "BRANCH 15 KVA"
                              ::= { panelboard1 715 }

pb1-branch16-kva
                OBJECT-TYPE
                SYNTAX  INTEGER
                ACCESS  read-only
                STATUS  mandatory
                DESCRIPTION "BRANCH 16 KVA"
                              ::= { panelboard1 716 }

pb1-branch17-kva
                OBJECT-TYPE
                SYNTAX  INTEGER
                ACCESS  read-only
                STATUS  mandatory
                DESCRIPTION "BRANCH 17 KVA"
                              ::= { panelboard1 717 }

pb1-branch18-kva
                OBJECT-TYPE
                SYNTAX  INTEGER
                ACCESS  read-only
                STATUS  mandatory
                DESCRIPTION "BRANCH 18 KVA"
                              ::= { panelboard1 718 }

pb1-branch19-kva
                OBJECT-TYPE
                SYNTAX  INTEGER
                ACCESS  read-only
                STATUS  mandatory
                DESCRIPTION "BRANCH 19 KVA"
                              ::= { panelboard1 719 }

pb1-branch20-kva
                OBJECT-TYPE
                SYNTAX  INTEGER
                ACCESS  read-only
                STATUS  mandatory
                DESCRIPTION "BRANCH 20 KVA"
                              ::= { panelboard1 720 }

pb1-branch21-kva
                OBJECT-TYPE
                SYNTAX  INTEGER
                ACCESS  read-only
                STATUS  mandatory
                DESCRIPTION "BRANCH 21 KVA"
                              ::= { panelboard1 721 }

pb1-branch22-kva
                OBJECT-TYPE
                SYNTAX  INTEGER
                ACCESS  read-only
                STATUS  mandatory
                DESCRIPTION "BRANCH 22 KVA"
                              ::= { panelboard1 722 }

pb1-branch23-kva
                OBJECT-TYPE
                SYNTAX  INTEGER
                ACCESS  read-only
                STATUS  mandatory
                DESCRIPTION "BRANCH 23 KVA"
                              ::= { panelboard1 723 }

pb1-branch24-kva
                OBJECT-TYPE
                SYNTAX  INTEGER
                ACCESS  read-only
                STATUS  mandatory
                DESCRIPTION "BRANCH 24 KVA"
                              ::= { panelboard1 724 }

pb1-branch25-kva
                OBJECT-TYPE
                SYNTAX  INTEGER
                ACCESS  read-only
                STATUS  mandatory
                DESCRIPTION "BRANCH 25 KVA"
                              ::= { panelboard1 725 }

pb1-branch26-kva
                OBJECT-TYPE
                SYNTAX  INTEGER
                ACCESS  read-only
                STATUS  mandatory
                DESCRIPTION "BRANCH 26 KVA"
                              ::= { panelboard1 726 }

pb1-branch27-kva
                OBJECT-TYPE
                SYNTAX  INTEGER
                ACCESS  read-only
                STATUS  mandatory
                DESCRIPTION "BRANCH 27 KVA"
                              ::= { panelboard1 727 }

pb1-branch28-kva
                OBJECT-TYPE
                SYNTAX  INTEGER
                ACCESS  read-only
                STATUS  mandatory
                DESCRIPTION "BRANCH 28 KVA"
                              ::= { panelboard1 728 }

pb1-branch29-kva
                OBJECT-TYPE
                SYNTAX  INTEGER
                ACCESS  read-only
                STATUS  mandatory
                DESCRIPTION "BRANCH 29 KVA"
                              ::= { panelboard1 729 }

pb1-branch30-kva
                OBJECT-TYPE
                SYNTAX  INTEGER
                ACCESS  read-only
                STATUS  mandatory
                DESCRIPTION "BRANCH 30 KVA"
                              ::= { panelboard1 730 }

pb1-branch31-kva
                OBJECT-TYPE
                SYNTAX  INTEGER
                ACCESS  read-only
                STATUS  mandatory
                DESCRIPTION "BRANCH 31 KVA"
                              ::= { panelboard1 731 }

pb1-branch32-kva
                OBJECT-TYPE
                SYNTAX  INTEGER
                ACCESS  read-only
                STATUS  mandatory
                DESCRIPTION "BRANCH 32 KVA"
                              ::= { panelboard1 732 }

pb1-branch33-kva
                OBJECT-TYPE
                SYNTAX  INTEGER
                ACCESS  read-only
                STATUS  mandatory
                DESCRIPTION "BRANCH 33 KVA"
                              ::= { panelboard1 733 }

pb1-branch34-kva
                OBJECT-TYPE
                SYNTAX  INTEGER
                ACCESS  read-only
                STATUS  mandatory
                DESCRIPTION "BRANCH 34 KVA"
                              ::= { panelboard1 734 }

pb1-branch35-kva
                OBJECT-TYPE
                SYNTAX  INTEGER
                ACCESS  read-only
                STATUS  mandatory
                DESCRIPTION "BRANCH 35 KVA"
                              ::= { panelboard1 735 }

pb1-branch36-kva
                OBJECT-TYPE
                SYNTAX  INTEGER
                ACCESS  read-only
                STATUS  mandatory
                DESCRIPTION "BRANCH 36 KVA"
                              ::= { panelboard1 736 }

pb1-branch37-kva
                OBJECT-TYPE
                SYNTAX  INTEGER
                ACCESS  read-only
                STATUS  mandatory
                DESCRIPTION "BRANCH 37 KVA"
                              ::= { panelboard1 737 }

pb1-branch38-kva
                OBJECT-TYPE
                SYNTAX  INTEGER
                ACCESS  read-only
                STATUS  mandatory
                DESCRIPTION "BRANCH 38 KVA"
                              ::= { panelboard1 738 }

pb1-branch39-kva
                OBJECT-TYPE
                SYNTAX  INTEGER
                ACCESS  read-only
                STATUS  mandatory
                DESCRIPTION "BRANCH 39 KVA"
                              ::= { panelboard1 739 }

pb1-branch40-kva
                OBJECT-TYPE
                SYNTAX  INTEGER
                ACCESS  read-only
                STATUS  mandatory
                DESCRIPTION "BRANCH 40 KVA"
                              ::= { panelboard1 740 }

pb1-branch41-kva
                OBJECT-TYPE
                SYNTAX  INTEGER
                ACCESS  read-only
                STATUS  mandatory
                DESCRIPTION "BRANCH 41 KVA"
                              ::= { panelboard1 741 }

pb1-branch42-kva
                OBJECT-TYPE
                SYNTAX  INTEGER
                ACCESS  read-only
                STATUS  mandatory
                DESCRIPTION "BRANCH 42 KVA"
                              ::= { panelboard1 742 }

pb1-branch43-kva
                OBJECT-TYPE
                SYNTAX  INTEGER
                ACCESS  read-only
                STATUS  mandatory
                DESCRIPTION "BRANCH 43 KVA"
                              ::= { panelboard1 743 }

pb1-branch44-kva
                OBJECT-TYPE
                SYNTAX  INTEGER
                ACCESS  read-only
                STATUS  mandatory
                DESCRIPTION "BRANCH 44 KVA"
                              ::= { panelboard1 744 }

pb1-branch45-kva
                OBJECT-TYPE
                SYNTAX  INTEGER
                ACCESS  read-only
                STATUS  mandatory
                DESCRIPTION "BRANCH 45 KVA"
                              ::= { panelboard1 745 }

pb1-branch46-kva
                OBJECT-TYPE
                SYNTAX  INTEGER
                ACCESS  read-only
                STATUS  mandatory
                DESCRIPTION "BRANCH 46 KVA"
                              ::= { panelboard1 746 }

pb1-branch47-kva
                OBJECT-TYPE
                SYNTAX  INTEGER
                ACCESS  read-only
                STATUS  mandatory
                DESCRIPTION "BRANCH 47 KVA"
                              ::= { panelboard1 747 }

pb1-branch48-kva
                OBJECT-TYPE
                SYNTAX  INTEGER
                ACCESS  read-only
                STATUS  mandatory
                DESCRIPTION "BRANCH 48 KVA"
                              ::= { panelboard1 748 }

pb1-branch49-kva
                OBJECT-TYPE
                SYNTAX  INTEGER
                ACCESS  read-only
                STATUS  mandatory
                DESCRIPTION "BRANCH 49 KVA"
                              ::= { panelboard1 749 }

pb1-branch50-kva
                OBJECT-TYPE
                SYNTAX  INTEGER
                ACCESS  read-only
                STATUS  mandatory
                DESCRIPTION "BRANCH 50 KVA"
                              ::= { panelboard1 750 }

pb1-branch51-kva
                OBJECT-TYPE
                SYNTAX  INTEGER
                ACCESS  read-only
                STATUS  mandatory
                DESCRIPTION "BRANCH 51 KVA"
                              ::= { panelboard1 751 }

pb1-branch52-kva
                OBJECT-TYPE
                SYNTAX  INTEGER
                ACCESS  read-only
                STATUS  mandatory
                DESCRIPTION "BRANCH 52 KVA"
                              ::= { panelboard1 752 }

pb1-branch53-kva
                OBJECT-TYPE
                SYNTAX  INTEGER
                ACCESS  read-only
                STATUS  mandatory
                DESCRIPTION "BRANCH 53 KVA"
                              ::= { panelboard1 753 }

pb1-branch54-kva
                OBJECT-TYPE
                SYNTAX  INTEGER
                ACCESS  read-only
                STATUS  mandatory
                DESCRIPTION "BRANCH 54 KVA"
                              ::= { panelboard1 754 }

pb1-branch55-kva
                OBJECT-TYPE
                SYNTAX  INTEGER
                ACCESS  read-only
                STATUS  mandatory
                DESCRIPTION "BRANCH 55 KVA"
                              ::= { panelboard1 755 }

pb1-branch56-kva
                OBJECT-TYPE
                SYNTAX  INTEGER
                ACCESS  read-only
                STATUS  mandatory
                DESCRIPTION "BRANCH 56 KVA"
                              ::= { panelboard1 756 }

pb1-branch57-kva
                OBJECT-TYPE
                SYNTAX  INTEGER
                ACCESS  read-only
                STATUS  mandatory
                DESCRIPTION "BRANCH 57 KVA"
                              ::= { panelboard1 757 }

pb1-branch58-kva
                OBJECT-TYPE
                SYNTAX  INTEGER
                ACCESS  read-only
                STATUS  mandatory
                DESCRIPTION "BRANCH 58 KVA"
                              ::= { panelboard1 758 }

pb1-branch59-kva
                OBJECT-TYPE
                SYNTAX  INTEGER
                ACCESS  read-only
                STATUS  mandatory
                DESCRIPTION "BRANCH 59 KVA"
                              ::= { panelboard1 759 }

pb1-branch60-kva
                OBJECT-TYPE
                SYNTAX  INTEGER
                ACCESS  read-only
                STATUS  mandatory
                DESCRIPTION "BRANCH 60 KVA"
                              ::= { panelboard1 760 }

pb1-branch61-kva
                OBJECT-TYPE
                SYNTAX  INTEGER
                ACCESS  read-only
                STATUS  mandatory
                DESCRIPTION "BRANCH 61 KVA"
                              ::= { panelboard1 761 }

pb1-branch62-kva
                OBJECT-TYPE
                SYNTAX  INTEGER
                ACCESS  read-only
                STATUS  mandatory
                DESCRIPTION "BRANCH 62 KVA"
                              ::= { panelboard1 762 }

pb1-branch63-kva
                OBJECT-TYPE
                SYNTAX  INTEGER
                ACCESS  read-only
                STATUS  mandatory
                DESCRIPTION "BRANCH 63 KVA"
                              ::= { panelboard1 763 }

pb1-branch64-kva
                OBJECT-TYPE
                SYNTAX  INTEGER
                ACCESS  read-only
                STATUS  mandatory
                DESCRIPTION "BRANCH 64 KVA"
                              ::= { panelboard1 764 }

pb1-branch65-kva
                OBJECT-TYPE
                SYNTAX  INTEGER
                ACCESS  read-only
                STATUS  mandatory
                DESCRIPTION "BRANCH 65 KVA"
                              ::= { panelboard1 765 }

pb1-branch66-kva
                OBJECT-TYPE
                SYNTAX  INTEGER
                ACCESS  read-only
                STATUS  mandatory
                DESCRIPTION "BRANCH 66 KVA"
                              ::= { panelboard1 766 }

pb1-branch67-kva
                OBJECT-TYPE
                SYNTAX  INTEGER
                ACCESS  read-only
                STATUS  mandatory
                DESCRIPTION "BRANCH 67 KVA"
                              ::= { panelboard1 767 }

pb1-branch68-kva
                OBJECT-TYPE
                SYNTAX  INTEGER
                ACCESS  read-only
                STATUS  mandatory
                DESCRIPTION "BRANCH 68 KVA"
                              ::= { panelboard1 768 }

pb1-branch69-kva
                OBJECT-TYPE
                SYNTAX  INTEGER
                ACCESS  read-only
                STATUS  mandatory
                DESCRIPTION "BRANCH 69 KVA"
                              ::= { panelboard1 769 }

pb1-branch70-kva
                OBJECT-TYPE
                SYNTAX  INTEGER
                ACCESS  read-only
                STATUS  mandatory
                DESCRIPTION "BRANCH 70 KVA"
                              ::= { panelboard1 770 }

pb1-branch71-kva
                OBJECT-TYPE
                SYNTAX  INTEGER
                ACCESS  read-only
                STATUS  mandatory
                DESCRIPTION "BRANCH 71 KVA"
                              ::= { panelboard1 771 }

pb1-branch72-kva
                OBJECT-TYPE
                SYNTAX  INTEGER
                ACCESS  read-only
                STATUS  mandatory
                DESCRIPTION "BRANCH 72 KVA"
                              ::= { panelboard1 772 }

pb1-branch1-kvar
                OBJECT-TYPE
                SYNTAX  INTEGER
                ACCESS  read-only
                STATUS  mandatory
                DESCRIPTION "BRANCH 1 KVAR
                                    Note for all KVAR: 100 = 10.0 or 1.00 kvar depending on setup"
                              ::= { panelboard1 801 }

pb1-branch2-kvar
                OBJECT-TYPE
                SYNTAX  INTEGER
                ACCESS  read-only
                STATUS  mandatory
                DESCRIPTION "BRANCH 2 KVAR"
                              ::= { panelboard1 802 }

pb1-branch3-kvar
                OBJECT-TYPE
                SYNTAX  INTEGER
                ACCESS  read-only
                STATUS  mandatory
                DESCRIPTION "BRANCH 3 KVAR"
                              ::= { panelboard1 803 }

pb1-branch4-kvar
                OBJECT-TYPE
                SYNTAX  INTEGER
                ACCESS  read-only
                STATUS  mandatory
                DESCRIPTION "BRANCH 4 KVAR"
                              ::= { panelboard1 804 }

pb1-branch5-kvar
                OBJECT-TYPE
                SYNTAX  INTEGER
                ACCESS  read-only
                STATUS  mandatory
                DESCRIPTION "BRANCH 5 KVAR"
                              ::= { panelboard1 805 }

pb1-branch6-kvar
                OBJECT-TYPE
                SYNTAX  INTEGER
                ACCESS  read-only
                STATUS  mandatory
                DESCRIPTION "BRANCH 6 KVAR"
                              ::= { panelboard1 806 }

pb1-branch7-kvar
                OBJECT-TYPE
                SYNTAX  INTEGER
                ACCESS  read-only
                STATUS  mandatory
                DESCRIPTION "BRANCH 7 KVAR"
                              ::= { panelboard1 807 }

pb1-branch8-kvar
                OBJECT-TYPE
                SYNTAX  INTEGER
                ACCESS  read-only
                STATUS  mandatory
                DESCRIPTION "BRANCH 8 KVAR"
                              ::= { panelboard1 808 }

pb1-branch9-kvar
                OBJECT-TYPE
                SYNTAX  INTEGER
                ACCESS  read-only
                STATUS  mandatory
                DESCRIPTION "BRANCH 9 KVAR"
                              ::= { panelboard1 809 }

pb1-branch10-kvar
                OBJECT-TYPE
                SYNTAX  INTEGER
                ACCESS  read-only
                STATUS  mandatory
                DESCRIPTION "BRANCH 10 KVAR"
                              ::= { panelboard1 810 }

pb1-branch11-kvar
                OBJECT-TYPE
                SYNTAX  INTEGER
                ACCESS  read-only
                STATUS  mandatory
                DESCRIPTION "BRANCH 11 KVAR"
                              ::= { panelboard1 811 }

pb1-branch12-kvar
                OBJECT-TYPE
                SYNTAX  INTEGER
                ACCESS  read-only
                STATUS  mandatory
                DESCRIPTION "BRANCH 12 KVAR"
                              ::= { panelboard1 812 }

pb1-branch13-kvar
                OBJECT-TYPE
                SYNTAX  INTEGER
                ACCESS  read-only
                STATUS  mandatory
                DESCRIPTION "BRANCH 13 KVAR"
                              ::= { panelboard1 813 }

pb1-branch14-kvar
                OBJECT-TYPE
                SYNTAX  INTEGER
                ACCESS  read-only
                STATUS  mandatory
                DESCRIPTION "BRANCH 14 KVAR"
                              ::= { panelboard1 814 }

pb1-branch15-kvar
                OBJECT-TYPE
                SYNTAX  INTEGER
                ACCESS  read-only
                STATUS  mandatory
                DESCRIPTION "BRANCH 15 KVAR"
                              ::= { panelboard1 815 }

pb1-branch16-kvar
                OBJECT-TYPE
                SYNTAX  INTEGER
                ACCESS  read-only
                STATUS  mandatory
                DESCRIPTION "BRANCH 16 KVAR"
                              ::= { panelboard1 816 }

pb1-branch17-kvar
                OBJECT-TYPE
                SYNTAX  INTEGER
                ACCESS  read-only
                STATUS  mandatory
                DESCRIPTION "BRANCH 17 KVAR"
                              ::= { panelboard1 817 }

pb1-branch18-kvar
                OBJECT-TYPE
                SYNTAX  INTEGER
                ACCESS  read-only
                STATUS  mandatory
                DESCRIPTION "BRANCH 18 KVAR"
                              ::= { panelboard1 818 }

pb1-branch19-kvar
                OBJECT-TYPE
                SYNTAX  INTEGER
                ACCESS  read-only
                STATUS  mandatory
                DESCRIPTION "BRANCH 19 KVAR"
                              ::= { panelboard1 819 }

pb1-branch20-kvar
                OBJECT-TYPE
                SYNTAX  INTEGER
                ACCESS  read-only
                STATUS  mandatory
                DESCRIPTION "BRANCH 20 KVAR"
                              ::= { panelboard1 820 }

pb1-branch21-kvar
                OBJECT-TYPE
                SYNTAX  INTEGER
                ACCESS  read-only
                STATUS  mandatory
                DESCRIPTION "BRANCH 21 KVAR"
                              ::= { panelboard1 821 }

pb1-branch22-kvar
                OBJECT-TYPE
                SYNTAX  INTEGER
                ACCESS  read-only
                STATUS  mandatory
                DESCRIPTION "BRANCH 22 KVAR"
                              ::= { panelboard1 822 }

pb1-branch23-kvar
                OBJECT-TYPE
                SYNTAX  INTEGER
                ACCESS  read-only
                STATUS  mandatory
                DESCRIPTION "BRANCH 23 KVAR"
                              ::= { panelboard1 823 }

pb1-branch24-kvar
                OBJECT-TYPE
                SYNTAX  INTEGER
                ACCESS  read-only
                STATUS  mandatory
                DESCRIPTION "BRANCH 24 KVAR"
                              ::= { panelboard1 824 }

pb1-branch25-kvar
                OBJECT-TYPE
                SYNTAX  INTEGER
                ACCESS  read-only
                STATUS  mandatory
                DESCRIPTION "BRANCH 25 KVAR"
                              ::= { panelboard1 825 }

pb1-branch26-kvar
                OBJECT-TYPE
                SYNTAX  INTEGER
                ACCESS  read-only
                STATUS  mandatory
                DESCRIPTION "BRANCH 26 KVAR"
                              ::= { panelboard1 826 }

pb1-branch27-kvar
                OBJECT-TYPE
                SYNTAX  INTEGER
                ACCESS  read-only
                STATUS  mandatory
                DESCRIPTION "BRANCH 27 KVAR"
                              ::= { panelboard1 827 }

pb1-branch28-kvar
                OBJECT-TYPE
                SYNTAX  INTEGER
                ACCESS  read-only
                STATUS  mandatory
                DESCRIPTION "BRANCH 28 KVAR"
                              ::= { panelboard1 828 }

pb1-branch29-kvar
                OBJECT-TYPE
                SYNTAX  INTEGER
                ACCESS  read-only
                STATUS  mandatory
                DESCRIPTION "BRANCH 29 KVAR"
                              ::= { panelboard1 829 }

pb1-branch30-kvar
                OBJECT-TYPE
                SYNTAX  INTEGER
                ACCESS  read-only
                STATUS  mandatory
                DESCRIPTION "BRANCH 30 KVAR"
                              ::= { panelboard1 830 }

pb1-branch31-kvar
                OBJECT-TYPE
                SYNTAX  INTEGER
                ACCESS  read-only
                STATUS  mandatory
                DESCRIPTION "BRANCH 31 KVAR"
                              ::= { panelboard1 831 }

pb1-branch32-kvar
                OBJECT-TYPE
                SYNTAX  INTEGER
                ACCESS  read-only
                STATUS  mandatory
                DESCRIPTION "BRANCH 32 KVAR"
                              ::= { panelboard1 832 }

pb1-branch33-kvar
                OBJECT-TYPE
                SYNTAX  INTEGER
                ACCESS  read-only
                STATUS  mandatory
                DESCRIPTION "BRANCH 33 KVAR"
                              ::= { panelboard1 833 }

pb1-branch34-kvar
                OBJECT-TYPE
                SYNTAX  INTEGER
                ACCESS  read-only
                STATUS  mandatory
                DESCRIPTION "BRANCH 34 KVAR"
                              ::= { panelboard1 834 }

pb1-branch35-kvar
                OBJECT-TYPE
                SYNTAX  INTEGER
                ACCESS  read-only
                STATUS  mandatory
                DESCRIPTION "BRANCH 35 KVAR"
                              ::= { panelboard1 835 }

pb1-branch36-kvar
                OBJECT-TYPE
                SYNTAX  INTEGER
                ACCESS  read-only
                STATUS  mandatory
                DESCRIPTION "BRANCH 36 KVAR"
                              ::= { panelboard1 836 }

pb1-branch37-kvar
                OBJECT-TYPE
                SYNTAX  INTEGER
                ACCESS  read-only
                STATUS  mandatory
                DESCRIPTION "BRANCH 37 KVAR"
                              ::= { panelboard1 837 }

pb1-branch38-kvar
                OBJECT-TYPE
                SYNTAX  INTEGER
                ACCESS  read-only
                STATUS  mandatory
                DESCRIPTION "BRANCH 38 KVAR"
                              ::= { panelboard1 838 }

pb1-branch39-kvar
                OBJECT-TYPE
                SYNTAX  INTEGER
                ACCESS  read-only
                STATUS  mandatory
                DESCRIPTION "BRANCH 39 KVAR"
                              ::= { panelboard1 839 }

pb1-branch40-kvar
                OBJECT-TYPE
                SYNTAX  INTEGER
                ACCESS  read-only
                STATUS  mandatory
                DESCRIPTION "BRANCH 40 KVAR"
                              ::= { panelboard1 840 }

pb1-branch41-kvar
                OBJECT-TYPE
                SYNTAX  INTEGER
                ACCESS  read-only
                STATUS  mandatory
                DESCRIPTION "BRANCH 41 KVAR"
                              ::= { panelboard1 841 }

pb1-branch42-kvar
                OBJECT-TYPE
                SYNTAX  INTEGER
                ACCESS  read-only
                STATUS  mandatory
                DESCRIPTION "BRANCH 42 KVAR"
                              ::= { panelboard1 842 }

pb1-branch43-kvar
                OBJECT-TYPE
                SYNTAX  INTEGER
                ACCESS  read-only
                STATUS  mandatory
                DESCRIPTION "BRANCH 43 KVAR"
                              ::= { panelboard1 843 }

pb1-branch44-kvar
                OBJECT-TYPE
                SYNTAX  INTEGER
                ACCESS  read-only
                STATUS  mandatory
                DESCRIPTION "BRANCH 44 KVAR"
                              ::= { panelboard1 844 }

pb1-branch45-kvar
                OBJECT-TYPE
                SYNTAX  INTEGER
                ACCESS  read-only
                STATUS  mandatory
                DESCRIPTION "BRANCH 45 KVAR"
                              ::= { panelboard1 845 }

pb1-branch46-kvar
                OBJECT-TYPE
                SYNTAX  INTEGER
                ACCESS  read-only
                STATUS  mandatory
                DESCRIPTION "BRANCH 46 KVAR"
                              ::= { panelboard1 846 }

pb1-branch47-kvar
                OBJECT-TYPE
                SYNTAX  INTEGER
                ACCESS  read-only
                STATUS  mandatory
                DESCRIPTION "BRANCH 47 KVAR"
                              ::= { panelboard1 847 }

pb1-branch48-kvar
                OBJECT-TYPE
                SYNTAX  INTEGER
                ACCESS  read-only
                STATUS  mandatory
                DESCRIPTION "BRANCH 48 KVAR"
                              ::= { panelboard1 848 }

pb1-branch49-kvar
                OBJECT-TYPE
                SYNTAX  INTEGER
                ACCESS  read-only
                STATUS  mandatory
                DESCRIPTION "BRANCH 49 KVAR"
                              ::= { panelboard1 849 }

pb1-branch50-kvar
                OBJECT-TYPE
                SYNTAX  INTEGER
                ACCESS  read-only
                STATUS  mandatory
                DESCRIPTION "BRANCH 50 KVAR"
                              ::= { panelboard1 850 }

pb1-branch51-kvar
                OBJECT-TYPE
                SYNTAX  INTEGER
                ACCESS  read-only
                STATUS  mandatory
                DESCRIPTION "BRANCH 51 KVAR"
                              ::= { panelboard1 851 }

pb1-branch52-kvar
                OBJECT-TYPE
                SYNTAX  INTEGER
                ACCESS  read-only
                STATUS  mandatory
                DESCRIPTION "BRANCH 52 KVAR"
                              ::= { panelboard1 852 }

pb1-branch53-kvar
                OBJECT-TYPE
                SYNTAX  INTEGER
                ACCESS  read-only
                STATUS  mandatory
                DESCRIPTION "BRANCH 53 KVAR"
                              ::= { panelboard1 853 }

pb1-branch54-kvar
                OBJECT-TYPE
                SYNTAX  INTEGER
                ACCESS  read-only
                STATUS  mandatory
                DESCRIPTION "BRANCH 54 KVAR"
                              ::= { panelboard1 854 }

pb1-branch55-kvar
                OBJECT-TYPE
                SYNTAX  INTEGER
                ACCESS  read-only
                STATUS  mandatory
                DESCRIPTION "BRANCH 55 KVAR"
                              ::= { panelboard1 855 }

pb1-branch56-kvar
                OBJECT-TYPE
                SYNTAX  INTEGER
                ACCESS  read-only
                STATUS  mandatory
                DESCRIPTION "BRANCH 56 KVAR"
                              ::= { panelboard1 856 }

pb1-branch57-kvar
                OBJECT-TYPE
                SYNTAX  INTEGER
                ACCESS  read-only
                STATUS  mandatory
                DESCRIPTION "BRANCH 57 KVAR"
                              ::= { panelboard1 857 }

pb1-branch58-kvar
                OBJECT-TYPE
                SYNTAX  INTEGER
                ACCESS  read-only
                STATUS  mandatory
                DESCRIPTION "BRANCH 58 KVAR"
                              ::= { panelboard1 858 }

pb1-branch59-kvar
                OBJECT-TYPE
                SYNTAX  INTEGER
                ACCESS  read-only
                STATUS  mandatory
                DESCRIPTION "BRANCH 59 KVAR"
                              ::= { panelboard1 859 }

pb1-branch60-kvar
                OBJECT-TYPE
                SYNTAX  INTEGER
                ACCESS  read-only
                STATUS  mandatory
                DESCRIPTION "BRANCH 60 KVAR"
                              ::= { panelboard1 860 }

pb1-branch61-kvar
                OBJECT-TYPE
                SYNTAX  INTEGER
                ACCESS  read-only
                STATUS  mandatory
                DESCRIPTION "BRANCH 61 KVAR"
                              ::= { panelboard1 861 }

pb1-branch62-kvar
                OBJECT-TYPE
                SYNTAX  INTEGER
                ACCESS  read-only
                STATUS  mandatory
                DESCRIPTION "BRANCH 62 KVAR"
                              ::= { panelboard1 862 }

pb1-branch63-kvar
                OBJECT-TYPE
                SYNTAX  INTEGER
                ACCESS  read-only
                STATUS  mandatory
                DESCRIPTION "BRANCH 63 KVAR"
                              ::= { panelboard1 863 }

pb1-branch64-kvar
                OBJECT-TYPE
                SYNTAX  INTEGER
                ACCESS  read-only
                STATUS  mandatory
                DESCRIPTION "BRANCH 64 KVAR"
                              ::= { panelboard1 864 }

pb1-branch65-kvar
                OBJECT-TYPE
                SYNTAX  INTEGER
                ACCESS  read-only
                STATUS  mandatory
                DESCRIPTION "BRANCH 65 KVAR"
                              ::= { panelboard1 865 }

pb1-branch66-kvar
                OBJECT-TYPE
                SYNTAX  INTEGER
                ACCESS  read-only
                STATUS  mandatory
                DESCRIPTION "BRANCH 66 KVAR"
                              ::= { panelboard1 866 }

pb1-branch67-kvar
                OBJECT-TYPE
                SYNTAX  INTEGER
                ACCESS  read-only
                STATUS  mandatory
                DESCRIPTION "BRANCH 67 KVAR"
                              ::= { panelboard1 867 }

pb1-branch68-kvar
                OBJECT-TYPE
                SYNTAX  INTEGER
                ACCESS  read-only
                STATUS  mandatory
                DESCRIPTION "BRANCH 68 KVAR"
                              ::= { panelboard1 868 }

pb1-branch69-kvar
                OBJECT-TYPE
                SYNTAX  INTEGER
                ACCESS  read-only
                STATUS  mandatory
                DESCRIPTION "BRANCH 69 KVAR"
                              ::= { panelboard1 869 }

pb1-branch70-kvar
                OBJECT-TYPE
                SYNTAX  INTEGER
                ACCESS  read-only
                STATUS  mandatory
                DESCRIPTION "BRANCH 70 KVAR"
                              ::= { panelboard1 870 }

pb1-branch71-kvar
                OBJECT-TYPE
                SYNTAX  INTEGER
                ACCESS  read-only
                STATUS  mandatory
                DESCRIPTION "BRANCH 71 KVAR"
                              ::= { panelboard1 871 }

pb1-branch72-kvar
                OBJECT-TYPE
                SYNTAX  INTEGER
                ACCESS  read-only
                STATUS  mandatory
                DESCRIPTION "BRANCH 72 KVAR"
                              ::= { panelboard1 872 }

pb1-branch1-pf
                OBJECT-TYPE
                SYNTAX  INTEGER
                ACCESS  read-only
                STATUS  mandatory
                DESCRIPTION "BRANCH 1 PF
                                    Note for all PF: 1000 = 1.000"
                              ::= { panelboard1 901 }

pb1-branch2-pf
                OBJECT-TYPE
                SYNTAX  INTEGER
                ACCESS  read-only
                STATUS  mandatory
                DESCRIPTION "BRANCH 2 PF"
                              ::= { panelboard1 902 }

pb1-branch3-pf
                OBJECT-TYPE
                SYNTAX  INTEGER
                ACCESS  read-only
                STATUS  mandatory
                DESCRIPTION "BRANCH 3 PF"
                              ::= { panelboard1 903 }

pb1-branch4-pf
                OBJECT-TYPE
                SYNTAX  INTEGER
                ACCESS  read-only
                STATUS  mandatory
                DESCRIPTION "BRANCH 4 PF"
                              ::= { panelboard1 904 }

pb1-branch5-pf
                OBJECT-TYPE
                SYNTAX  INTEGER
                ACCESS  read-only
                STATUS  mandatory
                DESCRIPTION "BRANCH 5 PF"
                              ::= { panelboard1 905 }

pb1-branch6-pf
                OBJECT-TYPE
                SYNTAX  INTEGER
                ACCESS  read-only
                STATUS  mandatory
                DESCRIPTION "BRANCH 6 PF"
                              ::= { panelboard1 906 }

pb1-branch7-pf
                OBJECT-TYPE
                SYNTAX  INTEGER
                ACCESS  read-only
                STATUS  mandatory
                DESCRIPTION "BRANCH 7 PF"
                              ::= { panelboard1 907 }

pb1-branch8-pf
                OBJECT-TYPE
                SYNTAX  INTEGER
                ACCESS  read-only
                STATUS  mandatory
                DESCRIPTION "BRANCH 8 PF"
                              ::= { panelboard1 908 }

pb1-branch9-pf
                OBJECT-TYPE
                SYNTAX  INTEGER
                ACCESS  read-only
                STATUS  mandatory
                DESCRIPTION "BRANCH 9 PF"
                              ::= { panelboard1 909 }

pb1-branch10-pf
                OBJECT-TYPE
                SYNTAX  INTEGER
                ACCESS  read-only
                STATUS  mandatory
                DESCRIPTION "BRANCH 10 PF"
                              ::= { panelboard1 910 }

pb1-branch11-pf
                OBJECT-TYPE
                SYNTAX  INTEGER
                ACCESS  read-only
                STATUS  mandatory
                DESCRIPTION "BRANCH 11 PF"
                              ::= { panelboard1 911 }

pb1-branch12-pf
                OBJECT-TYPE
                SYNTAX  INTEGER
                ACCESS  read-only
                STATUS  mandatory
                DESCRIPTION "BRANCH 12 PF"
                              ::= { panelboard1 912 }

pb1-branch13-pf
                OBJECT-TYPE
                SYNTAX  INTEGER
                ACCESS  read-only
                STATUS  mandatory
                DESCRIPTION "BRANCH 13 PF"
                              ::= { panelboard1 913 }

pb1-branch14-pf
                OBJECT-TYPE
                SYNTAX  INTEGER
                ACCESS  read-only
                STATUS  mandatory
                DESCRIPTION "BRANCH 14 PF"
                              ::= { panelboard1 914 }

pb1-branch15-pf
                OBJECT-TYPE
                SYNTAX  INTEGER
                ACCESS  read-only
                STATUS  mandatory
                DESCRIPTION "BRANCH 15 PF"
                              ::= { panelboard1 915 }

pb1-branch16-pf
                OBJECT-TYPE
                SYNTAX  INTEGER
                ACCESS  read-only
                STATUS  mandatory
                DESCRIPTION "BRANCH 16 PF"
                              ::= { panelboard1 916 }

pb1-branch17-pf
                OBJECT-TYPE
                SYNTAX  INTEGER
                ACCESS  read-only
                STATUS  mandatory
                DESCRIPTION "BRANCH 17 PF"
                              ::= { panelboard1 917 }

pb1-branch18-pf
                OBJECT-TYPE
                SYNTAX  INTEGER
                ACCESS  read-only
                STATUS  mandatory
                DESCRIPTION "BRANCH 18 PF"
                              ::= { panelboard1 918 }

pb1-branch19-pf
                OBJECT-TYPE
                SYNTAX  INTEGER
                ACCESS  read-only
                STATUS  mandatory
                DESCRIPTION "BRANCH 19 PF"
                              ::= { panelboard1 919 }

pb1-branch20-pf
                OBJECT-TYPE
                SYNTAX  INTEGER
                ACCESS  read-only
                STATUS  mandatory
                DESCRIPTION "BRANCH 20 PF"
                              ::= { panelboard1 920 }

pb1-branch21-pf
                OBJECT-TYPE
                SYNTAX  INTEGER
                ACCESS  read-only
                STATUS  mandatory
                DESCRIPTION "BRANCH 21 PF"
                              ::= { panelboard1 921 }

pb1-branch22-pf
                OBJECT-TYPE
                SYNTAX  INTEGER
                ACCESS  read-only
                STATUS  mandatory
                DESCRIPTION "BRANCH 22 PF"
                              ::= { panelboard1 922 }

pb1-branch23-pf
                OBJECT-TYPE
                SYNTAX  INTEGER
                ACCESS  read-only
                STATUS  mandatory
                DESCRIPTION "BRANCH 23 PF"
                              ::= { panelboard1 923 }

pb1-branch24-pf
                OBJECT-TYPE
                SYNTAX  INTEGER
                ACCESS  read-only
                STATUS  mandatory
                DESCRIPTION "BRANCH 24 PF"
                              ::= { panelboard1 924 }

pb1-branch25-pf
                OBJECT-TYPE
                SYNTAX  INTEGER
                ACCESS  read-only
                STATUS  mandatory
                DESCRIPTION "BRANCH 25 PF"
                              ::= { panelboard1 925 }

pb1-branch26-pf
                OBJECT-TYPE
                SYNTAX  INTEGER
                ACCESS  read-only
                STATUS  mandatory
                DESCRIPTION "BRANCH 26 PF"
                              ::= { panelboard1 926 }

pb1-branch27-pf
                OBJECT-TYPE
                SYNTAX  INTEGER
                ACCESS  read-only
                STATUS  mandatory
                DESCRIPTION "BRANCH 27 PF"
                              ::= { panelboard1 927 }

pb1-branch28-pf
                OBJECT-TYPE
                SYNTAX  INTEGER
                ACCESS  read-only
                STATUS  mandatory
                DESCRIPTION "BRANCH 28 PF"
                              ::= { panelboard1 928 }

pb1-branch29-pf
                OBJECT-TYPE
                SYNTAX  INTEGER
                ACCESS  read-only
                STATUS  mandatory
                DESCRIPTION "BRANCH 29 PF"
                              ::= { panelboard1 929 }

pb1-branch30-pf
                OBJECT-TYPE
                SYNTAX  INTEGER
                ACCESS  read-only
                STATUS  mandatory
                DESCRIPTION "BRANCH 30 PF"
                              ::= { panelboard1 930 }

pb1-branch31-pf
                OBJECT-TYPE
                SYNTAX  INTEGER
                ACCESS  read-only
                STATUS  mandatory
                DESCRIPTION "BRANCH 31 PF"
                              ::= { panelboard1 931 }

pb1-branch32-pf
                OBJECT-TYPE
                SYNTAX  INTEGER
                ACCESS  read-only
                STATUS  mandatory
                DESCRIPTION "BRANCH 32 PF"
                              ::= { panelboard1 932 }

pb1-branch33-pf
                OBJECT-TYPE
                SYNTAX  INTEGER
                ACCESS  read-only
                STATUS  mandatory
                DESCRIPTION "BRANCH 33 PF"
                              ::= { panelboard1 933 }

pb1-branch34-pf
                OBJECT-TYPE
                SYNTAX  INTEGER
                ACCESS  read-only
                STATUS  mandatory
                DESCRIPTION "BRANCH 34 PF"
                              ::= { panelboard1 934 }

pb1-branch35-pf
                OBJECT-TYPE
                SYNTAX  INTEGER
                ACCESS  read-only
                STATUS  mandatory
                DESCRIPTION "BRANCH 35 PF"
                              ::= { panelboard1 935 }

pb1-branch36-pf
                OBJECT-TYPE
                SYNTAX  INTEGER
                ACCESS  read-only
                STATUS  mandatory
                DESCRIPTION "BRANCH 36 PF"
                              ::= { panelboard1 936 }

pb1-branch37-pf
                OBJECT-TYPE
                SYNTAX  INTEGER
                ACCESS  read-only
                STATUS  mandatory
                DESCRIPTION "BRANCH 37 PF"
                              ::= { panelboard1 937 }

pb1-branch38-pf
                OBJECT-TYPE
                SYNTAX  INTEGER
                ACCESS  read-only
                STATUS  mandatory
                DESCRIPTION "BRANCH 38 PF"
                              ::= { panelboard1 938 }

pb1-branch39-pf
                OBJECT-TYPE
                SYNTAX  INTEGER
                ACCESS  read-only
                STATUS  mandatory
                DESCRIPTION "BRANCH 39 PF"
                              ::= { panelboard1 939 }

pb1-branch40-pf
                OBJECT-TYPE
                SYNTAX  INTEGER
                ACCESS  read-only
                STATUS  mandatory
                DESCRIPTION "BRANCH 40 PF"
                              ::= { panelboard1 940 }

pb1-branch41-pf
                OBJECT-TYPE
                SYNTAX  INTEGER
                ACCESS  read-only
                STATUS  mandatory
                DESCRIPTION "BRANCH 41 PF"
                              ::= { panelboard1 941 }

pb1-branch42-pf
                OBJECT-TYPE
                SYNTAX  INTEGER
                ACCESS  read-only
                STATUS  mandatory
                DESCRIPTION "BRANCH 42 PF"
                              ::= { panelboard1 942 }

pb1-branch43-pf
                OBJECT-TYPE
                SYNTAX  INTEGER
                ACCESS  read-only
                STATUS  mandatory
                DESCRIPTION "BRANCH 43 PF"
                              ::= { panelboard1 943 }

pb1-branch44-pf
                OBJECT-TYPE
                SYNTAX  INTEGER
                ACCESS  read-only
                STATUS  mandatory
                DESCRIPTION "BRANCH 44 PF"
                              ::= { panelboard1 944 }

pb1-branch45-pf
                OBJECT-TYPE
                SYNTAX  INTEGER
                ACCESS  read-only
                STATUS  mandatory
                DESCRIPTION "BRANCH 45 PF"
                              ::= { panelboard1 945 }

pb1-branch46-pf
                OBJECT-TYPE
                SYNTAX  INTEGER
                ACCESS  read-only
                STATUS  mandatory
                DESCRIPTION "BRANCH 46 PF"
                              ::= { panelboard1 946 }

pb1-branch47-pf
                OBJECT-TYPE
                SYNTAX  INTEGER
                ACCESS  read-only
                STATUS  mandatory
                DESCRIPTION "BRANCH 47 PF"
                              ::= { panelboard1 947 }

pb1-branch48-pf
                OBJECT-TYPE
                SYNTAX  INTEGER
                ACCESS  read-only
                STATUS  mandatory
                DESCRIPTION "BRANCH 48 PF"
                              ::= { panelboard1 948 }

pb1-branch49-pf
                OBJECT-TYPE
                SYNTAX  INTEGER
                ACCESS  read-only
                STATUS  mandatory
                DESCRIPTION "BRANCH 49 PF"
                              ::= { panelboard1 949 }

pb1-branch50-pf
                OBJECT-TYPE
                SYNTAX  INTEGER
                ACCESS  read-only
                STATUS  mandatory
                DESCRIPTION "BRANCH 50 PF"
                              ::= { panelboard1 950 }

pb1-branch51-pf
                OBJECT-TYPE
                SYNTAX  INTEGER
                ACCESS  read-only
                STATUS  mandatory
                DESCRIPTION "BRANCH 51 PF"
                              ::= { panelboard1 951 }

pb1-branch52-pf
                OBJECT-TYPE
                SYNTAX  INTEGER
                ACCESS  read-only
                STATUS  mandatory
                DESCRIPTION "BRANCH 52 PF"
                              ::= { panelboard1 952 }

pb1-branch53-pf
                OBJECT-TYPE
                SYNTAX  INTEGER
                ACCESS  read-only
                STATUS  mandatory
                DESCRIPTION "BRANCH 53 PF"
                              ::= { panelboard1 953 }

pb1-branch54-pf
                OBJECT-TYPE
                SYNTAX  INTEGER
                ACCESS  read-only
                STATUS  mandatory
                DESCRIPTION "BRANCH 54 PF"
                              ::= { panelboard1 954 }

pb1-branch55-pf
                OBJECT-TYPE
                SYNTAX  INTEGER
                ACCESS  read-only
                STATUS  mandatory
                DESCRIPTION "BRANCH 55 PF"
                              ::= { panelboard1 955 }

pb1-branch56-pf
                OBJECT-TYPE
                SYNTAX  INTEGER
                ACCESS  read-only
                STATUS  mandatory
                DESCRIPTION "BRANCH 56 PF"
                              ::= { panelboard1 956 }

pb1-branch57-pf
                OBJECT-TYPE
                SYNTAX  INTEGER
                ACCESS  read-only
                STATUS  mandatory
                DESCRIPTION "BRANCH 57 PF"
                              ::= { panelboard1 957 }

pb1-branch58-pf
                OBJECT-TYPE
                SYNTAX  INTEGER
                ACCESS  read-only
                STATUS  mandatory
                DESCRIPTION "BRANCH 58 PF"
                              ::= { panelboard1 958 }

pb1-branch59-pf
                OBJECT-TYPE
                SYNTAX  INTEGER
                ACCESS  read-only
                STATUS  mandatory
                DESCRIPTION "BRANCH 59 PF"
                              ::= { panelboard1 959 }

pb1-branch60-pf
                OBJECT-TYPE
                SYNTAX  INTEGER
                ACCESS  read-only
                STATUS  mandatory
                DESCRIPTION "BRANCH 60 PF"
                              ::= { panelboard1 960 }

pb1-branch61-pf
                OBJECT-TYPE
                SYNTAX  INTEGER
                ACCESS  read-only
                STATUS  mandatory
                DESCRIPTION "BRANCH 61 PF"
                              ::= { panelboard1 961 }

pb1-branch62-pf
                OBJECT-TYPE
                SYNTAX  INTEGER
                ACCESS  read-only
                STATUS  mandatory
                DESCRIPTION "BRANCH 62 PF"
                              ::= { panelboard1 962 }

pb1-branch63-pf
                OBJECT-TYPE
                SYNTAX  INTEGER
                ACCESS  read-only
                STATUS  mandatory
                DESCRIPTION "BRANCH 63 PF"
                              ::= { panelboard1 963 }

pb1-branch64-pf
                OBJECT-TYPE
                SYNTAX  INTEGER
                ACCESS  read-only
                STATUS  mandatory
                DESCRIPTION "BRANCH 64 PF"
                              ::= { panelboard1 964 }

pb1-branch65-pf
                OBJECT-TYPE
                SYNTAX  INTEGER
                ACCESS  read-only
                STATUS  mandatory
                DESCRIPTION "BRANCH 65 PF"
                              ::= { panelboard1 965 }

pb1-branch66-pf
                OBJECT-TYPE
                SYNTAX  INTEGER
                ACCESS  read-only
                STATUS  mandatory
                DESCRIPTION "BRANCH 66 PF"
                              ::= { panelboard1 966 }

pb1-branch67-pf
                OBJECT-TYPE
                SYNTAX  INTEGER
                ACCESS  read-only
                STATUS  mandatory
                DESCRIPTION "BRANCH 67 PF"
                              ::= { panelboard1 967 }

pb1-branch68-pf
                OBJECT-TYPE
                SYNTAX  INTEGER
                ACCESS  read-only
                STATUS  mandatory
                DESCRIPTION "BRANCH 68 PF"
                              ::= { panelboard1 968 }

pb1-branch69-pf
                OBJECT-TYPE
                SYNTAX  INTEGER
                ACCESS  read-only
                STATUS  mandatory
                DESCRIPTION "BRANCH 69 PF"
                              ::= { panelboard1 969 }

pb1-branch70-pf
                OBJECT-TYPE
                SYNTAX  INTEGER
                ACCESS  read-only
                STATUS  mandatory
                DESCRIPTION "BRANCH 70 PF"
                              ::= { panelboard1 970 }

pb1-branch71-pf
                OBJECT-TYPE
                SYNTAX  INTEGER
                ACCESS  read-only
                STATUS  mandatory
                DESCRIPTION "BRANCH 71 PF"
                              ::= { panelboard1 971 }

pb1-branch72-pf
                OBJECT-TYPE
                SYNTAX  INTEGER
                ACCESS  read-only
                STATUS  mandatory
                DESCRIPTION "BRANCH 72 PF"
                              ::= { panelboard1 972 }

pb1-branch1-pf-sign
                OBJECT-TYPE
                SYNTAX  INTEGER
                ACCESS  read-only
                STATUS  mandatory
                DESCRIPTION "BRANCH 1 PF Sign
                                    Note for all PF sign: set = leading, reset = lagging"
                              ::= { panelboard1 1001 }

pb1-branch2-pf-sign
                OBJECT-TYPE
                SYNTAX  INTEGER
                ACCESS  read-only
                STATUS  mandatory
                DESCRIPTION "BRANCH 2 PF Sign"
                              ::= { panelboard1 1002 }

pb1-branch3-pf-sign
                OBJECT-TYPE
                SYNTAX  INTEGER
                ACCESS  read-only
                STATUS  mandatory
                DESCRIPTION "BRANCH 3 PF Sign"
                              ::= { panelboard1 1003 }

pb1-branch4-pf-sign
                OBJECT-TYPE
                SYNTAX  INTEGER
                ACCESS  read-only
                STATUS  mandatory
                DESCRIPTION "BRANCH 4 PF Sign"
                              ::= { panelboard1 1004 }

pb1-branch5-pf-sign
                OBJECT-TYPE
                SYNTAX  INTEGER
                ACCESS  read-only
                STATUS  mandatory
                DESCRIPTION "BRANCH 5 PF Sign"
                              ::= { panelboard1 1005 }

pb1-branch6-pf-sign
                OBJECT-TYPE
                SYNTAX  INTEGER
                ACCESS  read-only
                STATUS  mandatory
                DESCRIPTION "BRANCH 6 PF Sign"
                              ::= { panelboard1 1006 }

pb1-branch7-pf-sign
                OBJECT-TYPE
                SYNTAX  INTEGER
                ACCESS  read-only
                STATUS  mandatory
                DESCRIPTION "BRANCH 7 PF Sign"
                              ::= { panelboard1 1007 }

pb1-branch8-pf-sign
                OBJECT-TYPE
                SYNTAX  INTEGER
                ACCESS  read-only
                STATUS  mandatory
                DESCRIPTION "BRANCH 8 PF Sign"
                              ::= { panelboard1 1008 }

pb1-branch9-pf-sign
                OBJECT-TYPE
                SYNTAX  INTEGER
                ACCESS  read-only
                STATUS  mandatory
                DESCRIPTION "BRANCH 9 PF Sign"
                              ::= { panelboard1 1009 }

pb1-branch10-pf-sign
                OBJECT-TYPE
                SYNTAX  INTEGER
                ACCESS  read-only
                STATUS  mandatory
                DESCRIPTION "BRANCH 10 PF Sign"
                              ::= { panelboard1 1010 }

pb1-branch11-pf-sign
                OBJECT-TYPE
                SYNTAX  INTEGER
                ACCESS  read-only
                STATUS  mandatory
                DESCRIPTION "BRANCH 11 PF Sign"
                              ::= { panelboard1 1011 }

pb1-branch12-pf-sign
                OBJECT-TYPE
                SYNTAX  INTEGER
                ACCESS  read-only
                STATUS  mandatory
                DESCRIPTION "BRANCH 12 PF Sign"
                              ::= { panelboard1 1012 }

pb1-branch13-pf-sign
                OBJECT-TYPE
                SYNTAX  INTEGER
                ACCESS  read-only
                STATUS  mandatory
                DESCRIPTION "BRANCH 13 PF Sign"
                              ::= { panelboard1 1013 }

pb1-branch14-pf-sign
                OBJECT-TYPE
                SYNTAX  INTEGER
                ACCESS  read-only
                STATUS  mandatory
                DESCRIPTION "BRANCH 14 PF Sign"
                              ::= { panelboard1 1014 }

pb1-branch15-pf-sign
                OBJECT-TYPE
                SYNTAX  INTEGER
                ACCESS  read-only
                STATUS  mandatory
                DESCRIPTION "BRANCH 15 PF Sign"
                              ::= { panelboard1 1015 }

pb1-branch16-pf-sign
                OBJECT-TYPE
                SYNTAX  INTEGER
                ACCESS  read-only
                STATUS  mandatory
                DESCRIPTION "BRANCH 16 PF Sign"
                              ::= { panelboard1 1016 }

pb1-branch17-pf-sign
                OBJECT-TYPE
                SYNTAX  INTEGER
                ACCESS  read-only
                STATUS  mandatory
                DESCRIPTION "BRANCH 17 PF Sign"
                              ::= { panelboard1 1017 }

pb1-branch18-pf-sign
                OBJECT-TYPE
                SYNTAX  INTEGER
                ACCESS  read-only
                STATUS  mandatory
                DESCRIPTION "BRANCH 18 PF Sign"
                              ::= { panelboard1 1018 }

pb1-branch19-pf-sign
                OBJECT-TYPE
                SYNTAX  INTEGER
                ACCESS  read-only
                STATUS  mandatory
                DESCRIPTION "BRANCH 19 PF Sign"
                              ::= { panelboard1 1019 }

pb1-branch20-pf-sign
                OBJECT-TYPE
                SYNTAX  INTEGER
                ACCESS  read-only
                STATUS  mandatory
                DESCRIPTION "BRANCH 20 PF Sign"
                              ::= { panelboard1 1020 }

pb1-branch21-pf-sign
                OBJECT-TYPE
                SYNTAX  INTEGER
                ACCESS  read-only
                STATUS  mandatory
                DESCRIPTION "BRANCH 21 PF Sign"
                              ::= { panelboard1 1021 }

pb1-branch22-pf-sign
                OBJECT-TYPE
                SYNTAX  INTEGER
                ACCESS  read-only
                STATUS  mandatory
                DESCRIPTION "BRANCH 22 PF Sign"
                              ::= { panelboard1 1022 }

pb1-branch23-pf-sign
                OBJECT-TYPE
                SYNTAX  INTEGER
                ACCESS  read-only
                STATUS  mandatory
                DESCRIPTION "BRANCH 23 PF Sign"
                              ::= { panelboard1 1023 }

pb1-branch24-pf-sign
                OBJECT-TYPE
                SYNTAX  INTEGER
                ACCESS  read-only
                STATUS  mandatory
                DESCRIPTION "BRANCH 24 PF Sign"
                              ::= { panelboard1 1024 }

pb1-branch25-pf-sign
                OBJECT-TYPE
                SYNTAX  INTEGER
                ACCESS  read-only
                STATUS  mandatory
                DESCRIPTION "BRANCH 25 PF Sign"
                              ::= { panelboard1 1025 }

pb1-branch26-pf-sign
                OBJECT-TYPE
                SYNTAX  INTEGER
                ACCESS  read-only
                STATUS  mandatory
                DESCRIPTION "BRANCH 26 PF Sign"
                              ::= { panelboard1 1026 }

pb1-branch27-pf-sign
                OBJECT-TYPE
                SYNTAX  INTEGER
                ACCESS  read-only
                STATUS  mandatory
                DESCRIPTION "BRANCH 27 PF Sign"
                              ::= { panelboard1 1027 }

pb1-branch28-pf-sign
                OBJECT-TYPE
                SYNTAX  INTEGER
                ACCESS  read-only
                STATUS  mandatory
                DESCRIPTION "BRANCH 28 PF Sign"
                              ::= { panelboard1 1028 }

pb1-branch29-pf-sign
                OBJECT-TYPE
                SYNTAX  INTEGER
                ACCESS  read-only
                STATUS  mandatory
                DESCRIPTION "BRANCH 29 PF Sign"
                              ::= { panelboard1 1029 }

pb1-branch30-pf-sign
                OBJECT-TYPE
                SYNTAX  INTEGER
                ACCESS  read-only
                STATUS  mandatory
                DESCRIPTION "BRANCH 30 PF Sign"
                              ::= { panelboard1 1030 }

pb1-branch31-pf-sign
                OBJECT-TYPE
                SYNTAX  INTEGER
                ACCESS  read-only
                STATUS  mandatory
                DESCRIPTION "BRANCH 31 PF Sign"
                              ::= { panelboard1 1031 }

pb1-branch32-pf-sign
                OBJECT-TYPE
                SYNTAX  INTEGER
                ACCESS  read-only
                STATUS  mandatory
                DESCRIPTION "BRANCH 32 PF Sign"
                              ::= { panelboard1 1032 }

pb1-branch33-pf-sign
                OBJECT-TYPE
                SYNTAX  INTEGER
                ACCESS  read-only
                STATUS  mandatory
                DESCRIPTION "BRANCH 33 PF Sign"
                              ::= { panelboard1 1033 }

pb1-branch34-pf-sign
                OBJECT-TYPE
                SYNTAX  INTEGER
                ACCESS  read-only
                STATUS  mandatory
                DESCRIPTION "BRANCH 34 PF Sign"
                              ::= { panelboard1 1034 }

pb1-branch35-pf-sign
                OBJECT-TYPE
                SYNTAX  INTEGER
                ACCESS  read-only
                STATUS  mandatory
                DESCRIPTION "BRANCH 35 PF Sign"
                              ::= { panelboard1 1035 }

pb1-branch36-pf-sign
                OBJECT-TYPE
                SYNTAX  INTEGER
                ACCESS  read-only
                STATUS  mandatory
                DESCRIPTION "BRANCH 36 PF Sign"
                              ::= { panelboard1 1036 }

pb1-branch37-pf-sign
                OBJECT-TYPE
                SYNTAX  INTEGER
                ACCESS  read-only
                STATUS  mandatory
                DESCRIPTION "BRANCH 37 PF Sign"
                              ::= { panelboard1 1037 }

pb1-branch38-pf-sign
                OBJECT-TYPE
                SYNTAX  INTEGER
                ACCESS  read-only
                STATUS  mandatory
                DESCRIPTION "BRANCH 38 PF Sign"
                              ::= { panelboard1 1038 }

pb1-branch39-pf-sign
                OBJECT-TYPE
                SYNTAX  INTEGER
                ACCESS  read-only
                STATUS  mandatory
                DESCRIPTION "BRANCH 39 PF Sign"
                              ::= { panelboard1 1039 }

pb1-branch40-pf-sign
                OBJECT-TYPE
                SYNTAX  INTEGER
                ACCESS  read-only
                STATUS  mandatory
                DESCRIPTION "BRANCH 40 PF Sign"
                              ::= { panelboard1 1040 }

pb1-branch41-pf-sign
                OBJECT-TYPE
                SYNTAX  INTEGER
                ACCESS  read-only
                STATUS  mandatory
                DESCRIPTION "BRANCH 41 PF Sign"
                              ::= { panelboard1 1041 }

pb1-branch42-pf-sign
                OBJECT-TYPE
                SYNTAX  INTEGER
                ACCESS  read-only
                STATUS  mandatory
                DESCRIPTION "BRANCH 42 PF Sign"
                              ::= { panelboard1 1042 }

pb1-branch43-pf-sign
                OBJECT-TYPE
                SYNTAX  INTEGER
                ACCESS  read-only
                STATUS  mandatory
                DESCRIPTION "BRANCH 43 PF Sign"
                              ::= { panelboard1 1043 }

pb1-branch44-pf-sign
                OBJECT-TYPE
                SYNTAX  INTEGER
                ACCESS  read-only
                STATUS  mandatory
                DESCRIPTION "BRANCH 44 PF Sign"
                              ::= { panelboard1 1044 }

pb1-branch45-pf-sign
                OBJECT-TYPE
                SYNTAX  INTEGER
                ACCESS  read-only
                STATUS  mandatory
                DESCRIPTION "BRANCH 45 PF Sign"
                              ::= { panelboard1 1045 }

pb1-branch46-pf-sign
                OBJECT-TYPE
                SYNTAX  INTEGER
                ACCESS  read-only
                STATUS  mandatory
                DESCRIPTION "BRANCH 46 PF Sign"
                              ::= { panelboard1 1046 }

pb1-branch47-pf-sign
                OBJECT-TYPE
                SYNTAX  INTEGER
                ACCESS  read-only
                STATUS  mandatory
                DESCRIPTION "BRANCH 47 PF Sign"
                              ::= { panelboard1 1047 }

pb1-branch48-pf-sign
                OBJECT-TYPE
                SYNTAX  INTEGER
                ACCESS  read-only
                STATUS  mandatory
                DESCRIPTION "BRANCH 48 PF Sign"
                              ::= { panelboard1 1048 }

pb1-branch49-pf-sign
                OBJECT-TYPE
                SYNTAX  INTEGER
                ACCESS  read-only
                STATUS  mandatory
                DESCRIPTION "BRANCH 49 PF Sign"
                              ::= { panelboard1 1049 }

pb1-branch50-pf-sign
                OBJECT-TYPE
                SYNTAX  INTEGER
                ACCESS  read-only
                STATUS  mandatory
                DESCRIPTION "BRANCH 50 PF Sign"
                              ::= { panelboard1 1050 }

pb1-branch51-pf-sign
                OBJECT-TYPE
                SYNTAX  INTEGER
                ACCESS  read-only
                STATUS  mandatory
                DESCRIPTION "BRANCH 51 PF Sign"
                              ::= { panelboard1 1051 }

pb1-branch52-pf-sign
                OBJECT-TYPE
                SYNTAX  INTEGER
                ACCESS  read-only
                STATUS  mandatory
                DESCRIPTION "BRANCH 52 PF Sign"
                              ::= { panelboard1 1052 }

pb1-branch53-pf-sign
                OBJECT-TYPE
                SYNTAX  INTEGER
                ACCESS  read-only
                STATUS  mandatory
                DESCRIPTION "BRANCH 53 PF Sign"
                              ::= { panelboard1 1053 }

pb1-branch54-pf-sign
                OBJECT-TYPE
                SYNTAX  INTEGER
                ACCESS  read-only
                STATUS  mandatory
                DESCRIPTION "BRANCH 54 PF Sign"
                              ::= { panelboard1 1054 }

pb1-branch55-pf-sign
                OBJECT-TYPE
                SYNTAX  INTEGER
                ACCESS  read-only
                STATUS  mandatory
                DESCRIPTION "BRANCH 55 PF Sign"
                              ::= { panelboard1 1055 }

pb1-branch56-pf-sign
                OBJECT-TYPE
                SYNTAX  INTEGER
                ACCESS  read-only
                STATUS  mandatory
                DESCRIPTION "BRANCH 56 PF Sign"
                              ::= { panelboard1 1056 }

pb1-branch57-pf-sign
                OBJECT-TYPE
                SYNTAX  INTEGER
                ACCESS  read-only
                STATUS  mandatory
                DESCRIPTION "BRANCH 57 PF Sign"
                              ::= { panelboard1 1057 }

pb1-branch58-pf-sign
                OBJECT-TYPE
                SYNTAX  INTEGER
                ACCESS  read-only
                STATUS  mandatory
                DESCRIPTION "BRANCH 58 PF Sign"
                              ::= { panelboard1 1058 }

pb1-branch59-pf-sign
                OBJECT-TYPE
                SYNTAX  INTEGER
                ACCESS  read-only
                STATUS  mandatory
                DESCRIPTION "BRANCH 59 PF Sign"
                              ::= { panelboard1 1059 }

pb1-branch60-pf-sign
                OBJECT-TYPE
                SYNTAX  INTEGER
                ACCESS  read-only
                STATUS  mandatory
                DESCRIPTION "BRANCH 60 PF Sign"
                              ::= { panelboard1 1060 }

pb1-branch61-pf-sign
                OBJECT-TYPE
                SYNTAX  INTEGER
                ACCESS  read-only
                STATUS  mandatory
                DESCRIPTION "BRANCH 61 PF Sign"
                              ::= { panelboard1 1061 }

pb1-branch62-pf-sign
                OBJECT-TYPE
                SYNTAX  INTEGER
                ACCESS  read-only
                STATUS  mandatory
                DESCRIPTION "BRANCH 62 PF Sign"
                              ::= { panelboard1 1062 }

pb1-branch63-pf-sign
                OBJECT-TYPE
                SYNTAX  INTEGER
                ACCESS  read-only
                STATUS  mandatory
                DESCRIPTION "BRANCH 63 PF Sign"
                              ::= { panelboard1 1063 }

pb1-branch64-pf-sign
                OBJECT-TYPE
                SYNTAX  INTEGER
                ACCESS  read-only
                STATUS  mandatory
                DESCRIPTION "BRANCH 64 PF Sign"
                              ::= { panelboard1 1064 }

pb1-branch65-pf-sign
                OBJECT-TYPE
                SYNTAX  INTEGER
                ACCESS  read-only
                STATUS  mandatory
                DESCRIPTION "BRANCH 65 PF Sign"
                              ::= { panelboard1 1065 }

pb1-branch66-pf-sign
                OBJECT-TYPE
                SYNTAX  INTEGER
                ACCESS  read-only
                STATUS  mandatory
                DESCRIPTION "BRANCH 66 PF Sign"
                              ::= { panelboard1 1066 }

pb1-branch67-pf-sign
                OBJECT-TYPE
                SYNTAX  INTEGER
                ACCESS  read-only
                STATUS  mandatory
                DESCRIPTION "BRANCH 67 PF Sign"
                              ::= { panelboard1 1067 }

pb1-branch68-pf-sign
                OBJECT-TYPE
                SYNTAX  INTEGER
                ACCESS  read-only
                STATUS  mandatory
                DESCRIPTION "BRANCH 68 PF Sign"
                              ::= { panelboard1 1068 }

pb1-branch69-pf-sign
                OBJECT-TYPE
                SYNTAX  INTEGER
                ACCESS  read-only
                STATUS  mandatory
                DESCRIPTION "BRANCH 69 PF Sign"
                              ::= { panelboard1 1069 }

pb1-branch70-pf-sign
                OBJECT-TYPE
                SYNTAX  INTEGER
                ACCESS  read-only
                STATUS  mandatory
                DESCRIPTION "BRANCH 70 PF Sign"
                              ::= { panelboard1 1070 }

pb1-branch71-pf-sign
                OBJECT-TYPE
                SYNTAX  INTEGER
                ACCESS  read-only
                STATUS  mandatory
                DESCRIPTION "BRANCH 71 PF Sign"
                              ::= { panelboard1 1071 }

pb1-branch72-pf-sign
                OBJECT-TYPE
                SYNTAX  INTEGER
                ACCESS  read-only
                STATUS  mandatory
                DESCRIPTION "BRANCH 72 PF Sign"
                              ::= { panelboard1 1072 }

pb1-branch1-kwh-low
                OBJECT-TYPE
                SYNTAX  INTEGER
                ACCESS  read-write
                STATUS  mandatory
                DESCRIPTION "BRANCH 1 KWH Low
                                    Note for all KWH: 100 = 100 KWH
                Valus is 32 bits (High * 65536) + Low"
                              ::= { panelboard1 1101 }

pb1-branch-kwh-high
                OBJECT-TYPE
                SYNTAX  INTEGER
                ACCESS  read-write
                STATUS  mandatory
                DESCRIPTION "BRANCH 1 KWH High"
                              ::= { panelboard1 1102 }

pb1-branch2-kwh-low
                OBJECT-TYPE
                SYNTAX  INTEGER
                ACCESS  read-write
                STATUS  mandatory
                DESCRIPTION "BRANCH 2 KWH Low"
                              ::= { panelboard1 1103 }

pb1-branch2-kwh-high
                OBJECT-TYPE
                SYNTAX  INTEGER
                ACCESS  read-write
                STATUS  mandatory
                DESCRIPTION "BRANCH 2 KWH High"
                              ::= { panelboard1 1104 }

pb1-branch3-kwh-low
                OBJECT-TYPE
                SYNTAX  INTEGER
                ACCESS  read-write
                STATUS  mandatory
                DESCRIPTION "BRANCH 3 KWH Low"
                              ::= { panelboard1 1105 }

pb1-branch3-kwh-high
                OBJECT-TYPE
                SYNTAX  INTEGER
                ACCESS  read-write
                STATUS  mandatory
                DESCRIPTION "BRANCH 3 KWH High"
                              ::= { panelboard1 1106 }

pb1-branch4-kwh-low
                OBJECT-TYPE
                SYNTAX  INTEGER
                ACCESS  read-write
                STATUS  mandatory
                DESCRIPTION "BRANCH 4 KWH Low"
                              ::= { panelboard1 1107 }

pb1-branch4-kwh-high
                OBJECT-TYPE
                SYNTAX  INTEGER
                ACCESS  read-write
                STATUS  mandatory
                DESCRIPTION "BRANCH 4 KWH High"
                              ::= { panelboard1 1108 }

pb1-branch5-kwh-low
                OBJECT-TYPE
                SYNTAX  INTEGER
                ACCESS  read-write
                STATUS  mandatory
                DESCRIPTION "BRANCH 5 KWH Low"
                              ::= { panelboard1 1109 }

pb1-branch5-kwh-high
                OBJECT-TYPE
                SYNTAX  INTEGER
                ACCESS  read-write
                STATUS  mandatory
                DESCRIPTION "BRANCH 5 KWH High"
                              ::= { panelboard1 1110 }

pb1-branch6-kwh-low
                OBJECT-TYPE
                SYNTAX  INTEGER
                ACCESS  read-write
                STATUS  mandatory
                DESCRIPTION "BRANCH 6 KWH Low"
                              ::= { panelboard1 1111 }

pb1-branch6-kwh-high
                OBJECT-TYPE
                SYNTAX  INTEGER
                ACCESS  read-write
                STATUS  mandatory
                DESCRIPTION "BRANCH 6 KWH High"
                              ::= { panelboard1 1112 }

pb1-branch7-kwh-low
                OBJECT-TYPE
                SYNTAX  INTEGER
                ACCESS  read-write
                STATUS  mandatory
                DESCRIPTION "BRANCH 7 KWH Low"
                              ::= { panelboard1 1113 }

pb1-branch7-kwh-high
                OBJECT-TYPE
                SYNTAX  INTEGER
                ACCESS  read-write
                STATUS  mandatory
                DESCRIPTION "BRANCH 7 KWH High"
                              ::= { panelboard1 1114 }

pb1-branch8-kwh-low
                OBJECT-TYPE
                SYNTAX  INTEGER
                ACCESS  read-write
                STATUS  mandatory
                DESCRIPTION "BRANCH 8 KWH Low"
                              ::= { panelboard1 1115 }

pb1-branch8-kwh-high
                OBJECT-TYPE
                SYNTAX  INTEGER
                ACCESS  read-write
                STATUS  mandatory
                DESCRIPTION "BRANCH 8 KWH High"
                              ::= { panelboard1 1116 }

pb1-branch9-kwh-low
                OBJECT-TYPE
                SYNTAX  INTEGER
                ACCESS  read-write
                STATUS  mandatory
                DESCRIPTION "BRANCH 9 KWH Low"
                              ::= { panelboard1 1117 }

pb1-branch9-kwh-high
                OBJECT-TYPE
                SYNTAX  INTEGER
                ACCESS  read-write
                STATUS  mandatory
                DESCRIPTION "BRANCH 9 KWH High"
                              ::= { panelboard1 1118 }

pb1-branch10-kwh-low
                OBJECT-TYPE
                SYNTAX  INTEGER
                ACCESS  read-write
                STATUS  mandatory
                DESCRIPTION "BRANCH 10 KWH Low"
                              ::= { panelboard1 1119 }

pb1-branch10-kwh-high
                OBJECT-TYPE
                SYNTAX  INTEGER
                ACCESS  read-write
                STATUS  mandatory
                DESCRIPTION "BRANCH 10 KWH High"
                              ::= { panelboard1 1120 }

pb1-branch11-kwh-low
                OBJECT-TYPE
                SYNTAX  INTEGER
                ACCESS  read-write
                STATUS  mandatory
                DESCRIPTION "BRANCH 11 KWH Low"
                              ::= { panelboard1 1121 }

pb1-branch11-kwh-high
                OBJECT-TYPE
                SYNTAX  INTEGER
                ACCESS  read-write
                STATUS  mandatory
                DESCRIPTION "BRANCH 11 KWH High"
                              ::= { panelboard1 1122 }

pb1-branch12-kwh-low
                OBJECT-TYPE
                SYNTAX  INTEGER
                ACCESS  read-write
                STATUS  mandatory
                DESCRIPTION "BRANCH 12 KWH Low"
                              ::= { panelboard1 1123 }

pb1-branch12-kwh-high
                OBJECT-TYPE
                SYNTAX  INTEGER
                ACCESS  read-write
                STATUS  mandatory
                DESCRIPTION "BRANCH 12 KWH High"
                              ::= { panelboard1 1124 }

pb1-branch13-kwh-low
                OBJECT-TYPE
                SYNTAX  INTEGER
                ACCESS  read-write
                STATUS  mandatory
                DESCRIPTION "BRANCH 13 KWH Low"
                              ::= { panelboard1 1125 }

pb1-branch13-kwh-high
                OBJECT-TYPE
                SYNTAX  INTEGER
                ACCESS  read-write
                STATUS  mandatory
                DESCRIPTION "BRANCH 13 KWH High"
                              ::= { panelboard1 1126 }

pb1-branch14-kwh-low
                OBJECT-TYPE
                SYNTAX  INTEGER
                ACCESS  read-write
                STATUS  mandatory
                DESCRIPTION "BRANCH 14 KWH Low"
                              ::= { panelboard1 1127 }

pb1-branch14-kwh-high
                OBJECT-TYPE
                SYNTAX  INTEGER
                ACCESS  read-write
                STATUS  mandatory
                DESCRIPTION "BRANCH 14 KWH High"
                              ::= { panelboard1 1128 }

pb1-branch15-kwh-low
                OBJECT-TYPE
                SYNTAX  INTEGER
                ACCESS  read-write
                STATUS  mandatory
                DESCRIPTION "BRANCH 15 KWH Low"
                              ::= { panelboard1 1129 }

pb1-branch15-kwh-high
                OBJECT-TYPE
                SYNTAX  INTEGER
                ACCESS  read-write
                STATUS  mandatory
                DESCRIPTION "BRANCH 15 KWH High"
                              ::= { panelboard1 1130 }

pb1-branch16-kwh-low
                OBJECT-TYPE
                SYNTAX  INTEGER
                ACCESS  read-write
                STATUS  mandatory
                DESCRIPTION "BRANCH 16 KWH Low"
                              ::= { panelboard1 1131 }

pb1-branch16-kwh-high
                OBJECT-TYPE
                SYNTAX  INTEGER
                ACCESS  read-write
                STATUS  mandatory
                DESCRIPTION "BRANCH 16 KWH High"
                              ::= { panelboard1 1132 }

pb1-branch17-kwh-low
                OBJECT-TYPE
                SYNTAX  INTEGER
                ACCESS  read-write
                STATUS  mandatory
                DESCRIPTION "BRANCH 17 KWH Low"
                              ::= { panelboard1 1133 }

pb1-branch17-kwh-high
                OBJECT-TYPE
                SYNTAX  INTEGER
                ACCESS  read-write
                STATUS  mandatory
                DESCRIPTION "BRANCH 17 KWH High"
                              ::= { panelboard1 1134 }

pb1-branch18-kwh-low
                OBJECT-TYPE
                SYNTAX  INTEGER
                ACCESS  read-write
                STATUS  mandatory
                DESCRIPTION "BRANCH 18 KWH Low"
                              ::= { panelboard1 1135 }

pb1-branch18-kwh-high
                OBJECT-TYPE
                SYNTAX  INTEGER
                ACCESS  read-write
                STATUS  mandatory
                DESCRIPTION "BRANCH 18 KWH High"
                              ::= { panelboard1 1136 }

pb1-branch19-kwh-low
                OBJECT-TYPE
                SYNTAX  INTEGER
                ACCESS  read-write
                STATUS  mandatory
                DESCRIPTION "BRANCH 19KWH Low"
                              ::= { panelboard1 1137 }

pb1-branch19-kwh-high
                OBJECT-TYPE
                SYNTAX  INTEGER
                ACCESS  read-write
                STATUS  mandatory
                DESCRIPTION "BRANCH 19 KWH High"
                              ::= { panelboard1 1138 }

pb1-branch20-kwh-low
                OBJECT-TYPE
                SYNTAX  INTEGER
                ACCESS  read-write
                STATUS  mandatory
                DESCRIPTION "BRANCH 20 KWH Low"
                              ::= { panelboard1 1139 }

pb1-branch20-kwh-high
                OBJECT-TYPE
                SYNTAX  INTEGER
                ACCESS  read-write
                STATUS  mandatory
                DESCRIPTION "BRANCH 20 KWH High"
                              ::= { panelboard1 1140 }

pb1-branch21-kwh-low
                OBJECT-TYPE
                SYNTAX  INTEGER
                ACCESS  read-write
                STATUS  mandatory
                DESCRIPTION "BRANCH 21 KWH Low"
                              ::= { panelboard1 1141 }

pb1-branch21-kwh-high
                OBJECT-TYPE
                SYNTAX  INTEGER
                ACCESS  read-write
                STATUS  mandatory
                DESCRIPTION "BRANCH 21 KWH High"
                              ::= { panelboard1 1142 }

pb1-branch22-kwh-low
                OBJECT-TYPE
                SYNTAX  INTEGER
                ACCESS  read-write
                STATUS  mandatory
                DESCRIPTION "BRANCH 22 KWH Low"
                              ::= { panelboard1 1143 }

pb1-branch22-kwh-high
                OBJECT-TYPE
                SYNTAX  INTEGER
                ACCESS  read-write
                STATUS  mandatory
                DESCRIPTION "BRANCH 22 KWH High"
                              ::= { panelboard1 1144 }

pb1-branch23-kwh-low
                OBJECT-TYPE
                SYNTAX  INTEGER
                ACCESS  read-write
                STATUS  mandatory
                DESCRIPTION "BRANCH 23 KWH Low"
                              ::= { panelboard1 1145 }

pb1-branch23-kwh-high
                OBJECT-TYPE
                SYNTAX  INTEGER
                ACCESS  read-write
                STATUS  mandatory
                DESCRIPTION "BRANCH 23 KWH High"
                              ::= { panelboard1 1146 }

pb1-branch24-kwh-low
                OBJECT-TYPE
                SYNTAX  INTEGER
                ACCESS  read-write
                STATUS  mandatory
                DESCRIPTION "BRANCH 24 KWH Low"
                              ::= { panelboard1 1147 }

pb1-branch24-kwh-high
                OBJECT-TYPE
                SYNTAX  INTEGER
                ACCESS  read-write
                STATUS  mandatory
                DESCRIPTION "BRANCH 24 KWH High"
                              ::= { panelboard1 1148 }

pb1-branch25-kwh-low
                OBJECT-TYPE
                SYNTAX  INTEGER
                ACCESS  read-write
                STATUS  mandatory
                DESCRIPTION "BRANCH 25 KWH Low"
                              ::= { panelboard1 1149 }

pb1-branch25-kwh-high
                OBJECT-TYPE
                SYNTAX  INTEGER
                ACCESS  read-write
                STATUS  mandatory
                DESCRIPTION "BRANCH 25 KWH High"
                              ::= { panelboard1 1150 }

pb1-branch26-kwh-low
                OBJECT-TYPE
                SYNTAX  INTEGER
                ACCESS  read-write
                STATUS  mandatory
                DESCRIPTION "BRANCH 26 KWH Low"
                              ::= { panelboard1 1151 }

pb1-branch26-kwh-high
                OBJECT-TYPE
                SYNTAX  INTEGER
                ACCESS  read-write
                STATUS  mandatory
                DESCRIPTION "BRANCH 26 KWH High"
                                ::= { panelboard1 1152 }

pb1-branch27-kwh-low
                OBJECT-TYPE
                SYNTAX  INTEGER
                ACCESS  read-write
                STATUS  mandatory
                DESCRIPTION "BRANCH 27 KWH Low"
                              ::= { panelboard1 1153 }

pb1-branch27-kwh-high
                OBJECT-TYPE
                SYNTAX  INTEGER
                ACCESS  read-write
                STATUS  mandatory
                DESCRIPTION "BRANCH 27 KWH High"
                              ::= { panelboard1 1154 }

pb1-branch28-kwh-low
                OBJECT-TYPE
                SYNTAX  INTEGER
                ACCESS  read-write
                STATUS  mandatory
                DESCRIPTION "BRANCH 28 KWH Low"
                              ::= { panelboard1 1155 }

pb1-branch28-kwh-high
                OBJECT-TYPE
                SYNTAX  INTEGER
                ACCESS  read-write
                STATUS  mandatory
                DESCRIPTION "BRANCH 28 KWH High"
                              ::= { panelboard1 1156 }

pb1-branch29-kwh-low
                OBJECT-TYPE
                SYNTAX  INTEGER
                ACCESS  read-write
                STATUS  mandatory
                DESCRIPTION "BRANCH 29 KWH Low"
                              ::= { panelboard1 1157 }

pb1-branch29-kwh-high
                OBJECT-TYPE
                SYNTAX  INTEGER
                ACCESS  read-write
                STATUS  mandatory
                DESCRIPTION "BRANCH 29 KWH High"
                              ::= { panelboard1 1158 }

pb1-branch30-kwh-low
                OBJECT-TYPE
                SYNTAX  INTEGER
                ACCESS  read-write
                STATUS  mandatory
                DESCRIPTION "BRANCH 30 KWH Low"
                              ::= { panelboard1 1159 }

pb1-branch30-kwh-high
                OBJECT-TYPE
                SYNTAX  INTEGER
                ACCESS  read-write
                STATUS  mandatory
                DESCRIPTION "BRANCH 30 KWH High"
                              ::= { panelboard1 1160 }

pb1-branch31-kwh-low
                OBJECT-TYPE
                SYNTAX  INTEGER
                ACCESS  read-write
                STATUS  mandatory
                DESCRIPTION "BRANCH 31 KWH Low"
                              ::= { panelboard1 1161 }

pb1-branch31-kwh-high
                OBJECT-TYPE
                SYNTAX  INTEGER
                ACCESS  read-write
                STATUS  mandatory
                DESCRIPTION "BRANCH 31 KWH High"
                              ::= { panelboard1 1162 }

pb1-branch32-kwh-low
                OBJECT-TYPE
                SYNTAX  INTEGER
                ACCESS  read-write
                STATUS  mandatory
                DESCRIPTION "BRANCH 32 KWH Low"
                              ::= { panelboard1 1163 }

pb1-branch32-kwh-high
                OBJECT-TYPE
                SYNTAX  INTEGER
                ACCESS  read-write
                STATUS  mandatory
                DESCRIPTION "BRANCH 32 KWH High"
                              ::= { panelboard1 1164 }

pb1-branch33-kwh-low
                OBJECT-TYPE
                SYNTAX  INTEGER
                ACCESS  read-write
                STATUS  mandatory
                DESCRIPTION "BRANCH 33 KWH Low"
                              ::= { panelboard1 1165 }

pb1-branch33-kwh-high
                OBJECT-TYPE
                SYNTAX  INTEGER
                ACCESS  read-write
                STATUS  mandatory
                DESCRIPTION "BRANCH 33 KWH High"
                              ::= { panelboard1 1166 }

pb1-branch34-kwh-low
                OBJECT-TYPE
                SYNTAX  INTEGER
                ACCESS  read-write
                STATUS  mandatory
                DESCRIPTION "BRANCH 34 KWH Low"
                              ::= { panelboard1 1167 }

pb1-branch34-kwh-high
                OBJECT-TYPE
                SYNTAX  INTEGER
                ACCESS  read-write
                STATUS  mandatory
                DESCRIPTION "BRANCH 34 KWH High"
                              ::= { panelboard1 1168 }

pb1-branch35-kwh-low
                OBJECT-TYPE
                SYNTAX  INTEGER
                ACCESS  read-write
                STATUS  mandatory
                DESCRIPTION "BRANCH 35 KWH Low"
                              ::= { panelboard1 1169 }

pb1-branch35-kwh-high
                OBJECT-TYPE
                SYNTAX  INTEGER
                ACCESS  read-write
                STATUS  mandatory
                DESCRIPTION "BRANCH 35 KWH High"
                              ::= { panelboard1 1170 }

pb1-branch36-kwh-low
                OBJECT-TYPE
                SYNTAX  INTEGER
                ACCESS  read-write
                STATUS  mandatory
                DESCRIPTION "BRANCH 36 KWH Low"
                              ::= { panelboard1 1171 }

pb1-branch36-kwh-high
                OBJECT-TYPE
                SYNTAX  INTEGER
                ACCESS  read-write
                STATUS  mandatory
                DESCRIPTION "BRANCH 36 KWH High"
                              ::= { panelboard1 1172 }

pb1-branch37-kwh-low
                OBJECT-TYPE
                SYNTAX  INTEGER
                ACCESS  read-write
                STATUS  mandatory
                DESCRIPTION "BRANCH 37 KWH Low"
                              ::= { panelboard1 1173 }

pb1-branch37-kwh-high
                OBJECT-TYPE
                SYNTAX  INTEGER
                ACCESS  read-write
                STATUS  mandatory
                DESCRIPTION "BRANCH 37 KWH High"
                              ::= { panelboard1 1174 }

pb1-branch38-kwh-low
                OBJECT-TYPE
                SYNTAX  INTEGER
                ACCESS  read-write
                STATUS  mandatory
                DESCRIPTION "BRANCH 38 KWH Low"
                              ::= { panelboard1 1175 }

pb1-branch38-kwh-high
                OBJECT-TYPE
                SYNTAX  INTEGER
                ACCESS  read-write
                STATUS  mandatory
                DESCRIPTION "BRANCH 38 KWH High"
                              ::= { panelboard1 1176 }

pb1-branch39-kwh-low
                OBJECT-TYPE
                SYNTAX  INTEGER
                ACCESS  read-write
                STATUS  mandatory
                DESCRIPTION "BRANCH 39 KWH Low"
                              ::= { panelboard1 1177 }

pb1-branch39-kwh-high
                OBJECT-TYPE
                SYNTAX  INTEGER
                ACCESS  read-write
                STATUS  mandatory
                DESCRIPTION "BRANCH 39 KWH High"
                              ::= { panelboard1 1178 }

pb1-branch40-kwh-low
                OBJECT-TYPE
                SYNTAX  INTEGER
                ACCESS  read-write
                STATUS  mandatory
                DESCRIPTION "BRANCH 40 KWH Low"
                              ::= { panelboard1 1179 }

pb1-branch40-kwh-high
                OBJECT-TYPE
                SYNTAX  INTEGER
                ACCESS  read-write
                STATUS  mandatory
                DESCRIPTION "BRANCH 40 KWH High"
                              ::= { panelboard1 1180 }

pb1-branch41-kwh-low
                OBJECT-TYPE
                SYNTAX  INTEGER
                ACCESS  read-write
                STATUS  mandatory
                DESCRIPTION "BRANCH 41 KWH Low"
                              ::= { panelboard1 1181 }

pb1-branch41-kwh-high
                OBJECT-TYPE
                SYNTAX  INTEGER
                ACCESS  read-write
                STATUS  mandatory
                DESCRIPTION "BRANCH 41 KWH High"
                              ::= { panelboard1 1182 }

pb1-branch42-kwh-low
                OBJECT-TYPE
                SYNTAX  INTEGER
                ACCESS  read-write
                STATUS  mandatory
                DESCRIPTION "BRANCH 42 KWH Low"
                              ::= { panelboard1 1183 }

pb1-branch42-kwh-high
                OBJECT-TYPE
                SYNTAX  INTEGER
                ACCESS  read-write
                STATUS  mandatory
                DESCRIPTION "BRANCH 42 KWH High"
                              ::= { panelboard1 1184 }

pb1-branch43-kwh-low
                OBJECT-TYPE
                SYNTAX  INTEGER
                ACCESS  read-write
                STATUS  mandatory
                DESCRIPTION "BRANCH 43 KWH Low"
                              ::= { panelboard1 1185 }

pb1-branch43-kwh-high
                OBJECT-TYPE
                SYNTAX  INTEGER
                ACCESS  read-write
                STATUS  mandatory
                DESCRIPTION "BRANCH 43 KWH High"
                              ::= { panelboard1 1186 }

pb1-branch44-kwh-low
                OBJECT-TYPE
                SYNTAX  INTEGER
                ACCESS  read-write
                STATUS  mandatory
                DESCRIPTION "BRANCH 44 KWH Low"
                              ::= { panelboard1 1187 }

pb1-branch44-kwh-high
                OBJECT-TYPE
                SYNTAX  INTEGER
                ACCESS  read-write
                STATUS  mandatory
                DESCRIPTION "BRANCH 44 KWH High"
                              ::= { panelboard1 1188 }

pb1-branch45-kwh-low
                OBJECT-TYPE
                SYNTAX  INTEGER
                ACCESS  read-write
                STATUS  mandatory
                DESCRIPTION "BRANCH 45 KWH Low"
                              ::= { panelboard1 1189 }

pb1-branch45-kwh-high
                OBJECT-TYPE
                SYNTAX  INTEGER
                ACCESS  read-write
                STATUS  mandatory
                DESCRIPTION "BRANCH 45 KWH High"
                              ::= { panelboard1 1190 }

pb1-branch46-kwh-low
                OBJECT-TYPE
                SYNTAX  INTEGER
                ACCESS  read-write
                STATUS  mandatory
                DESCRIPTION "BRANCH 46 KWH Low"
                              ::= { panelboard1 1191 }

pb1-branch46-kwh-high
                OBJECT-TYPE
                SYNTAX  INTEGER
                ACCESS  read-write
                STATUS  mandatory
                DESCRIPTION "BRANCH 46 KWH High"
                              ::= { panelboard1 1192 }

pb1-branch47-kwh-low
                OBJECT-TYPE
                SYNTAX  INTEGER
                ACCESS  read-write
                STATUS  mandatory
                DESCRIPTION "BRANCH 47 KWH Low"
                              ::= { panelboard1 1193 }

pb1-branch47-kwh-high
                OBJECT-TYPE
                SYNTAX  INTEGER
                ACCESS  read-write
                STATUS  mandatory
                DESCRIPTION "BRANCH 47 KWH High"
                              ::= { panelboard1 1194 }

pb1-branch48-kwh-low
                OBJECT-TYPE
                SYNTAX  INTEGER
                ACCESS  read-write
                STATUS  mandatory
                DESCRIPTION "BRANCH 48 KWH Low"
                              ::= { panelboard1 1195 }

pb1-branch48-kwh-high
                OBJECT-TYPE
                SYNTAX  INTEGER
                ACCESS  read-write
                STATUS  mandatory
                DESCRIPTION "BRANCH 48 KWH High"
                              ::= { panelboard1 1196 }

pb1-branch49-kwh-low
                OBJECT-TYPE
                SYNTAX  INTEGER
                ACCESS  read-write
                STATUS  mandatory
                DESCRIPTION "BRANCH 49 KWH Low"
                              ::= { panelboard1 1197 }

pb1-branch49-kwh-high
                OBJECT-TYPE
                SYNTAX  INTEGER
                ACCESS  read-write
                STATUS  mandatory
                DESCRIPTION "BRANCH 49 KWH High"
                              ::= { panelboard1 1198 }

pb1-branch50-kwh-low
                OBJECT-TYPE
                SYNTAX  INTEGER
                ACCESS  read-write
                STATUS  mandatory
                DESCRIPTION "BRANCH 50 KWH Low"
                              ::= { panelboard1 1199 }

pb1-branch50-kwh-high
                OBJECT-TYPE
                SYNTAX  INTEGER
                ACCESS  read-write
                STATUS  mandatory
                DESCRIPTION "BRANCH 50 KWH High"
                              ::= { panelboard1 1200 }

pb1-branch51-kwh-low
                OBJECT-TYPE
                SYNTAX  INTEGER
                ACCESS  read-write
                STATUS  mandatory
                DESCRIPTION "BRANCH 51 KWH Low"
                              ::= { panelboard1 1201 }

pb1-branch51-kwh-high
                OBJECT-TYPE
                SYNTAX  INTEGER
                ACCESS  read-write
                STATUS  mandatory
                DESCRIPTION "BRANCH 51 KWH High"
                                ::= { panelboard1 1202 }

pb1-branch52-kwh-low
                OBJECT-TYPE
                SYNTAX  INTEGER
                ACCESS  read-write
                STATUS  mandatory
                DESCRIPTION "BRANCH 52 KWH Low"
                              ::= { panelboard1 1203 }

pb1-branch52-kwh-high
                OBJECT-TYPE
                SYNTAX  INTEGER
                ACCESS  read-write
                STATUS  mandatory
                DESCRIPTION "BRANCH 52 KWH High"
                              ::= { panelboard1 1204 }

pb1-branch53-kwh-low
                OBJECT-TYPE
                SYNTAX  INTEGER
                ACCESS  read-write
                STATUS  mandatory
                DESCRIPTION "BRANCH 53 KWH Low"
                              ::= { panelboard1 1205 }

pb1-branch53-kwh-high
                OBJECT-TYPE
                SYNTAX  INTEGER
                ACCESS  read-write
                STATUS  mandatory
                DESCRIPTION "BRANCH 53 KWH High"
                              ::= { panelboard1 1206 }

pb1-branch54-kwh-low
                OBJECT-TYPE
                SYNTAX  INTEGER
                ACCESS  read-write
                STATUS  mandatory
                DESCRIPTION "BRANCH 54 KWH Low"
                              ::= { panelboard1 1207 }

pb1-branch54-kwh-high
                OBJECT-TYPE
                SYNTAX  INTEGER
                ACCESS  read-write
                STATUS  mandatory
                DESCRIPTION "BRANCH 54 KWH High"
                              ::= { panelboard1 1208 }

pb1-branch55-kwh-low
                OBJECT-TYPE
                SYNTAX  INTEGER
                ACCESS  read-write
                STATUS  mandatory
                DESCRIPTION "BRANCH 55 KWH Low"
                              ::= { panelboard1 1209 }

pb1-branch55-kwh-high
                OBJECT-TYPE
                SYNTAX  INTEGER
                ACCESS  read-write
                STATUS  mandatory
                DESCRIPTION "BRANCH 55 KWH High"
                              ::= { panelboard1 1210 }

pb1-branch56-kwh-low
                OBJECT-TYPE
                SYNTAX  INTEGER
                ACCESS  read-write
                STATUS  mandatory
                DESCRIPTION "BRANCH 56 KWH Low"
                              ::= { panelboard1 1211 }

pb1-branch56-kwh-high
                OBJECT-TYPE
                SYNTAX  INTEGER
                ACCESS  read-write
                STATUS  mandatory
                DESCRIPTION "BRANCH 56 KWH High"
                                ::= { panelboard1 1212 }

pb1-branch57-kwh-low
                OBJECT-TYPE
                SYNTAX  INTEGER
                ACCESS  read-write
                STATUS  mandatory
                DESCRIPTION "BRANCH 57 KWH Low"
                              ::= { panelboard1 1213 }

pb1-branch57-kwh-high
                OBJECT-TYPE
                SYNTAX  INTEGER
                ACCESS  read-write
                STATUS  mandatory
                DESCRIPTION "BRANCH 57 KWH High"
                              ::= { panelboard1 1214 }

pb1-branch58-kwh-low
                OBJECT-TYPE
                SYNTAX  INTEGER
                ACCESS  read-write
                STATUS  mandatory
                DESCRIPTION "BRANCH 58 KWH Low"
                              ::= { panelboard1 1215 }

pb1-branch58-kwh-high
                OBJECT-TYPE
                SYNTAX  INTEGER
                ACCESS  read-write
                STATUS  mandatory
                DESCRIPTION "BRANCH 58 KWH High"
                              ::= { panelboard1 1216 }

pb1-branch59-kwh-low
                OBJECT-TYPE
                SYNTAX  INTEGER
                ACCESS  read-write
                STATUS  mandatory
                DESCRIPTION "BRANCH 59 KWH Low"
                              ::= { panelboard1 1217 }

pb1-branch59-kwh-high
                OBJECT-TYPE
                SYNTAX  INTEGER
                ACCESS  read-write
                STATUS  mandatory
                DESCRIPTION "BRANCH 59 KWH High"
                              ::= { panelboard1 1218 }

pb1-branch60-kwh-low
                OBJECT-TYPE
                SYNTAX  INTEGER
                ACCESS  read-write
                STATUS  mandatory
                DESCRIPTION "BRANCH 60 KWH Low"
                              ::= { panelboard1 1219 }

pb1-branch60-kwh-high
                OBJECT-TYPE
                SYNTAX  INTEGER
                ACCESS  read-write
                STATUS  mandatory
                DESCRIPTION "BRANCH 60 KWH High"
                              ::= { panelboard1 1220 }

pb1-branch61-kwh-low
                OBJECT-TYPE
                SYNTAX  INTEGER
                ACCESS  read-write
                STATUS  mandatory
                DESCRIPTION "BRANCH 61 KWH Low"
                              ::= { panelboard1 1221 }

pb1-branch61-kwh-high
                OBJECT-TYPE
                SYNTAX  INTEGER
                ACCESS  read-write
                STATUS  mandatory
                DESCRIPTION "BRANCH 61 KWH High"
                              ::= { panelboard1 1222 }

pb1-branch62-kwh-low
                OBJECT-TYPE
                SYNTAX  INTEGER
                ACCESS  read-write
                STATUS  mandatory
                DESCRIPTION "BRANCH 62 KWH Low"
                              ::= { panelboard1 1223 }

pb1-branch62-kwh-high
                OBJECT-TYPE
                SYNTAX  INTEGER
                ACCESS  read-write
                STATUS  mandatory
                DESCRIPTION "BRANCH 62 KWH High"
                              ::= { panelboard1 1224 }

pb1-branch63-kwh-low
                OBJECT-TYPE
                SYNTAX  INTEGER
                ACCESS  read-write
                STATUS  mandatory
                DESCRIPTION "BRANCH 63 KWH Low"
                              ::= { panelboard1 1225 }

pb1-branch63-kwh-high
                OBJECT-TYPE
                SYNTAX  INTEGER
                ACCESS  read-write
                STATUS  mandatory
                DESCRIPTION "BRANCH 63 KWH High"
                              ::= { panelboard1 1226 }

pb1-branch64-kwh-low
                OBJECT-TYPE
                SYNTAX  INTEGER
                ACCESS  read-write
                STATUS  mandatory
                DESCRIPTION "BRANCH 64 KWH Low"
                              ::= { panelboard1 1227 }

pb1-branch64-kwh-high
                OBJECT-TYPE
                SYNTAX  INTEGER
                ACCESS  read-write
                STATUS  mandatory
                DESCRIPTION "BRANCH 64 KWH High"
                              ::= { panelboard1 1228 }

pb1-branch65-kwh-low
                OBJECT-TYPE
                SYNTAX  INTEGER
                ACCESS  read-write
                STATUS  mandatory
                DESCRIPTION "BRANCH 65 KWH Low"
                              ::= { panelboard1 1229 }

pb1-branch65-kwh-high
                OBJECT-TYPE
                SYNTAX  INTEGER
                ACCESS  read-write
                STATUS  mandatory
                DESCRIPTION "BRANCH 65 KWH High"
                              ::= { panelboard1 1230 }

pb1-branch66-kwh-low
                OBJECT-TYPE
                SYNTAX  INTEGER
                ACCESS  read-write
                STATUS  mandatory
                DESCRIPTION "BRANCH 66 KWH Low"
                              ::= { panelboard1 1231 }

pb1-branch66-kwh-high
                OBJECT-TYPE
                SYNTAX  INTEGER
                ACCESS  read-write
                STATUS  mandatory
                DESCRIPTION "BRANCH 66 KWH High"
                              ::= { panelboard1 1232 }

pb1-branch67-kwh-low
                OBJECT-TYPE
                SYNTAX  INTEGER
                ACCESS  read-write
                STATUS  mandatory
                DESCRIPTION "BRANCH 67 KWH Low"
                              ::= { panelboard1 1233 }

pb1-branch67-kwh-high
                OBJECT-TYPE
                SYNTAX  INTEGER
                ACCESS  read-write
                STATUS  mandatory
                DESCRIPTION "BRANCH 67 KWH High"
                              ::= { panelboard1 1234 }

pb1-branch68-kwh-low
                OBJECT-TYPE
                SYNTAX  INTEGER
                ACCESS  read-write
                STATUS  mandatory
                DESCRIPTION "BRANCH 68 KWH Low"
                              ::= { panelboard1 1235 }

pb1-branch68-kwh-high
                OBJECT-TYPE
                SYNTAX  INTEGER
                ACCESS  read-write
                STATUS  mandatory
                DESCRIPTION "BRANCH 68 KWH High"
                              ::= { panelboard1 1236 }

pb1-branch69-kwh-low
                OBJECT-TYPE
                SYNTAX  INTEGER
                ACCESS  read-write
                STATUS  mandatory
                DESCRIPTION "BRANCH 69 KWH Low"
                              ::= { panelboard1 1237 }

pb1-branch69-kwh-high
                OBJECT-TYPE
                SYNTAX  INTEGER
                ACCESS  read-write
                STATUS  mandatory
                DESCRIPTION "BRANCH 69 KWH High"
                              ::= { panelboard1 1238 }

pb1-branch70-kwh-low
                OBJECT-TYPE
                SYNTAX  INTEGER
                ACCESS  read-write
                STATUS  mandatory
                DESCRIPTION "BRANCH 70 KWH Low"
                              ::= { panelboard1 1239 }

pb1-branch70-kwh-high
                OBJECT-TYPE
                SYNTAX  INTEGER
                ACCESS  read-write
                STATUS  mandatory
                DESCRIPTION "BRANCH 70 KWH High"
                              ::= { panelboard1 1240 }

pb1-branch71-kwh-low
                OBJECT-TYPE
                SYNTAX  INTEGER
                ACCESS  read-write
                STATUS  mandatory
                DESCRIPTION "BRANCH 71 KWH Low"
                              ::= { panelboard1 1241 }

pb1-branch71-kwh-high
                OBJECT-TYPE
                SYNTAX  INTEGER
                ACCESS  read-write
                STATUS  mandatory
                DESCRIPTION "BRANCH 71 KWH High"
                                ::= { panelboard1 1242 }

pb1-branch72-kwh-low
                OBJECT-TYPE
                SYNTAX  INTEGER
                ACCESS  read-write
                STATUS  mandatory
                DESCRIPTION "BRANCH 72 KWH Low"
                              ::= { panelboard1 1243 }

pb1-branch72-kwh-high
                OBJECT-TYPE
                SYNTAX  INTEGER
                ACCESS  read-write
                STATUS  mandatory
                DESCRIPTION "BRANCH 72 KWH High"
                              ::= { panelboard1 1244 }

--------------------------------------------------------------------------------

pb2-branch1-current
                OBJECT-TYPE
                SYNTAX  INTEGER
                ACCESS  read-only
                STATUS  mandatory
                DESCRIPTION "BRANCH 1 Current
                                    Note for all currents: 100 = 10.0 amps"
                              ::= { panelboard2 101 }

pb2-branch2-current
                OBJECT-TYPE
                SYNTAX  INTEGER
                ACCESS  read-only
                STATUS  mandatory
                DESCRIPTION "BRANCH 2 Current"
                              ::= { panelboard2 102 }

pb2-branch3-current
                OBJECT-TYPE
                SYNTAX  INTEGER
                ACCESS  read-only
                STATUS  mandatory
                DESCRIPTION "BRANCH 3 Current"
                              ::= { panelboard2 103 }

pb2-branch4-current
                OBJECT-TYPE
                SYNTAX  INTEGER
                ACCESS  read-only
                STATUS  mandatory
                DESCRIPTION "BRANCH 4 Current"
                              ::= { panelboard2 104 }

pb2-branch5-current
                OBJECT-TYPE
                SYNTAX  INTEGER
                ACCESS  read-only
                STATUS  mandatory
                DESCRIPTION "BRANCH 5 Current"
                              ::= { panelboard2 105 }

pb2-branch6-current
                OBJECT-TYPE
                SYNTAX  INTEGER
                ACCESS  read-only
                STATUS  mandatory
                DESCRIPTION "BRANCH 6 Current"
                              ::= { panelboard2 106 }

pb2-branch7-current
                OBJECT-TYPE
                SYNTAX  INTEGER
                ACCESS  read-only
                STATUS  mandatory
                DESCRIPTION "BRANCH 7 Current"
                              ::= { panelboard2 107 }

pb2-branch8-current
                OBJECT-TYPE
                SYNTAX  INTEGER
                ACCESS  read-only
                STATUS  mandatory
                DESCRIPTION "BRANCH 8 Current"
                              ::= { panelboard2 108 }

pb2-branch9-current
                OBJECT-TYPE
                SYNTAX  INTEGER
                ACCESS  read-only
                STATUS  mandatory
                DESCRIPTION "BRANCH 9 Current"
                              ::= { panelboard2 109 }

pb2-branch10-current
                OBJECT-TYPE
                SYNTAX  INTEGER
                ACCESS  read-only
                STATUS  mandatory
                DESCRIPTION "BRANCH 10 Current"
                              ::= { panelboard2 110 }

pb2-branch11-current
                OBJECT-TYPE
                SYNTAX  INTEGER
                ACCESS  read-only
                STATUS  mandatory
                DESCRIPTION "BRANCH 11 Current"
                              ::= { panelboard2 111 }

pb2-branch12-current
                OBJECT-TYPE
                SYNTAX  INTEGER
                ACCESS  read-only
                STATUS  mandatory
                DESCRIPTION "BRANCH 12 Current"
                              ::= { panelboard2 112 }

pb2-branch13-current
                OBJECT-TYPE
                SYNTAX  INTEGER
                ACCESS  read-only
                STATUS  mandatory
                DESCRIPTION "BRANCH 13 Current"
                              ::= { panelboard2 113 }

pb2-branch14-current
                OBJECT-TYPE
                SYNTAX  INTEGER
                ACCESS  read-only
                STATUS  mandatory
                DESCRIPTION "BRANCH 14 Current"
                              ::= { panelboard2 114 }

pb2-branch15-current
                OBJECT-TYPE
                SYNTAX  INTEGER
                ACCESS  read-only
                STATUS  mandatory
                DESCRIPTION "BRANCH 15 Current"
                              ::= { panelboard2 115 }

pb2-branch16-current
                OBJECT-TYPE
                SYNTAX  INTEGER
                ACCESS  read-only
                STATUS  mandatory
                DESCRIPTION "BRANCH 16 Current"
                              ::= { panelboard2 116 }

pb2-branch17-current
                OBJECT-TYPE
                SYNTAX  INTEGER
                ACCESS  read-only
                STATUS  mandatory
                DESCRIPTION "BRANCH 17 Current"
                              ::= { panelboard2 117 }

pb2-branch18-current
                OBJECT-TYPE
                SYNTAX  INTEGER
                ACCESS  read-only
                STATUS  mandatory
                DESCRIPTION "BRANCH 18 Current"
                              ::= { panelboard2 118 }

pb2-branch19-current
                OBJECT-TYPE
                SYNTAX  INTEGER
                ACCESS  read-only
                STATUS  mandatory
                DESCRIPTION "BRANCH 19 Current"
                              ::= { panelboard2 119 }

pb2-branch20-current
                OBJECT-TYPE
                SYNTAX  INTEGER
                ACCESS  read-only
                STATUS  mandatory
                DESCRIPTION "BRANCH 20 Current"
                              ::= { panelboard2 120 }

pb2-branch21-current
                OBJECT-TYPE
                SYNTAX  INTEGER
                ACCESS  read-only
                STATUS  mandatory
                DESCRIPTION "BRANCH 21 Current"
                              ::= { panelboard2 121 }

pb2-branch22-current
                OBJECT-TYPE
                SYNTAX  INTEGER
                ACCESS  read-only
                STATUS  mandatory
                DESCRIPTION "BRANCH 22 Current"
                              ::= { panelboard2 122 }

pb2-branch23-current
                OBJECT-TYPE
                SYNTAX  INTEGER
                ACCESS  read-only
                STATUS  mandatory
                DESCRIPTION "BRANCH 23 Current"
                              ::= { panelboard2 123 }

pb2-branch24-current
                OBJECT-TYPE
                SYNTAX  INTEGER
                ACCESS  read-only
                STATUS  mandatory
                DESCRIPTION "BRANCH 24 Current"
                              ::= { panelboard2 124 }

pb2-branch25-current
                OBJECT-TYPE
                SYNTAX  INTEGER
                ACCESS  read-only
                STATUS  mandatory
                DESCRIPTION "BRANCH 25 Current"
                              ::= { panelboard2 125 }

pb2-branch26-current
                OBJECT-TYPE
                SYNTAX  INTEGER
                ACCESS  read-only
                STATUS  mandatory
                DESCRIPTION "BRANCH 26 Current"
                              ::= { panelboard2 126 }

pb2-branch27-current
                OBJECT-TYPE
                SYNTAX  INTEGER
                ACCESS  read-only
                STATUS  mandatory
                DESCRIPTION "BRANCH 27 Current"
                              ::= { panelboard2 127 }

pb2-branch28-current
                OBJECT-TYPE
                SYNTAX  INTEGER
                ACCESS  read-only
                STATUS  mandatory
                DESCRIPTION "BRANCH 28 Current"
                              ::= { panelboard2 128 }

pb2-branch29-current
                OBJECT-TYPE
                SYNTAX  INTEGER
                ACCESS  read-only
                STATUS  mandatory
                DESCRIPTION "BRANCH 29 Current"
                              ::= { panelboard2 129 }

pb2-branch30-current
                OBJECT-TYPE
                SYNTAX  INTEGER
                ACCESS  read-only
                STATUS  mandatory
                DESCRIPTION "BRANCH 30 Current"
                              ::= { panelboard2 130 }

pb2-branch31-current
                OBJECT-TYPE
                SYNTAX  INTEGER
                ACCESS  read-only
                STATUS  mandatory
                DESCRIPTION "BRANCH 31 Current"
                              ::= { panelboard2 131 }

pb2-branch32-current
                OBJECT-TYPE
                SYNTAX  INTEGER
                ACCESS  read-only
                STATUS  mandatory
                DESCRIPTION "BRANCH 32 Current"
                              ::= { panelboard2 132 }

pb2-branch33-current
                OBJECT-TYPE
                SYNTAX  INTEGER
                ACCESS  read-only
                STATUS  mandatory
                DESCRIPTION "BRANCH 33 Current"
                              ::= { panelboard2 133 }

pb2-branch34-current
                OBJECT-TYPE
                SYNTAX  INTEGER
                ACCESS  read-only
                STATUS  mandatory
                DESCRIPTION "BRANCH 34 Current"
                              ::= { panelboard2 134 }

pb2-branch35-current
                OBJECT-TYPE
                SYNTAX  INTEGER
                ACCESS  read-only
                STATUS  mandatory
                DESCRIPTION "BRANCH 35 Current"
                              ::= { panelboard2 135 }

pb2-branch36-current
                OBJECT-TYPE
                SYNTAX  INTEGER
                ACCESS  read-only
                STATUS  mandatory
                DESCRIPTION "BRANCH 36 Current"
                              ::= { panelboard2 136 }

pb2-branch1-min
                OBJECT-TYPE
                SYNTAX  INTEGER
                ACCESS  read-only
                STATUS  mandatory
                DESCRIPTION "BRANCH 1 Min
                                    Note for all minimum currents: 100 = 10.0 amps"
                              ::= { panelboard2 201 }

pb2-branch2-min
                OBJECT-TYPE
                SYNTAX  INTEGER
                ACCESS  read-only
                STATUS  mandatory
                DESCRIPTION "BRANCH 2 Min"
                              ::= { panelboard2 202 }

pb2-branch3-min
                OBJECT-TYPE
                SYNTAX  INTEGER
                ACCESS  read-only
                STATUS  mandatory
                DESCRIPTION "BRANCH 3 Min"
                              ::= { panelboard2 203 }

pb2-branch4-min
                OBJECT-TYPE
                SYNTAX  INTEGER
                ACCESS  read-only
                STATUS  mandatory
                DESCRIPTION "BRANCH 4 Min"
                              ::= { panelboard2 204 }

pb2-branch5-min
                OBJECT-TYPE
                SYNTAX  INTEGER
                ACCESS  read-only
                STATUS  mandatory
                DESCRIPTION "BRANCH 5 Min"
                              ::= { panelboard2 205 }

pb2-branch6-min
                OBJECT-TYPE
                SYNTAX  INTEGER
                ACCESS  read-only
                STATUS  mandatory
                DESCRIPTION "BRANCH 6 Min"
                              ::= { panelboard2 206 }

pb2-branch7-min
                OBJECT-TYPE
                SYNTAX  INTEGER
                ACCESS  read-only
                STATUS  mandatory
                DESCRIPTION "BRANCH 7 Min"
                              ::= { panelboard2 207 }

pb2-branch8-min
                OBJECT-TYPE
                SYNTAX  INTEGER
                ACCESS  read-only
                STATUS  mandatory
                DESCRIPTION "BRANCH 8 Min"
                              ::= { panelboard2 208 }

pb2-branch9-min
                OBJECT-TYPE
                SYNTAX  INTEGER
                ACCESS  read-only
                STATUS  mandatory
                DESCRIPTION "BRANCH 9 Min"
                              ::= { panelboard2 209 }

pb2-branch10-min
                OBJECT-TYPE
                SYNTAX  INTEGER
                ACCESS  read-only
                STATUS  mandatory
                DESCRIPTION "BRANCH 10 Min"
                              ::= { panelboard2 210 }

pb2-branch11-min
                OBJECT-TYPE
                SYNTAX  INTEGER
                ACCESS  read-only
                STATUS  mandatory
                DESCRIPTION "BRANCH 11 Min"
                              ::= { panelboard2 211 }

pb2-branch12-min
                OBJECT-TYPE
                SYNTAX  INTEGER
                ACCESS  read-only
                STATUS  mandatory
                DESCRIPTION "BRANCH 12 Min"
                              ::= { panelboard2 212 }

pb2-branch13-min
                OBJECT-TYPE
                SYNTAX  INTEGER
                ACCESS  read-only
                STATUS  mandatory
                DESCRIPTION "BRANCH 13 Min"
                              ::= { panelboard2 213 }

pb2-branch14-min
                OBJECT-TYPE
                SYNTAX  INTEGER
                ACCESS  read-only
                STATUS  mandatory
                DESCRIPTION "BRANCH 14 Min"
                              ::= { panelboard2 214 }

pb2-branch15-min
                OBJECT-TYPE
                SYNTAX  INTEGER
                ACCESS  read-only
                STATUS  mandatory
                DESCRIPTION "BRANCH 15 Min"
                              ::= { panelboard2 215 }

pb2-branch16-min
                OBJECT-TYPE
                SYNTAX  INTEGER
                ACCESS  read-only
                STATUS  mandatory
                DESCRIPTION "BRANCH 16 Min"
                              ::= { panelboard2 216 }

pb2-branch17-min
                OBJECT-TYPE
                SYNTAX  INTEGER
                ACCESS  read-only
                STATUS  mandatory
                DESCRIPTION "BRANCH 17 Min"
                              ::= { panelboard2 217 }

pb2-branch18-min
                OBJECT-TYPE
                SYNTAX  INTEGER
                ACCESS  read-only
                STATUS  mandatory
                DESCRIPTION "BRANCH 18 Min"
                              ::= { panelboard2 218 }

pb2-branch19-min
                OBJECT-TYPE
                SYNTAX  INTEGER
                ACCESS  read-only
                STATUS  mandatory
                DESCRIPTION "BRANCH 19 Min"
                              ::= { panelboard2 219 }

pb2-branch20-min
                OBJECT-TYPE
                SYNTAX  INTEGER
                ACCESS  read-only
                STATUS  mandatory
                DESCRIPTION "BRANCH 20 Min"
                              ::= { panelboard2 220 }

pb2-branch21-min
                OBJECT-TYPE
                SYNTAX  INTEGER
                ACCESS  read-only
                STATUS  mandatory
                DESCRIPTION "BRANCH 21 Min"
                              ::= { panelboard2 221 }

pb2-branch22-min
                OBJECT-TYPE
                SYNTAX  INTEGER
                ACCESS  read-only
                STATUS  mandatory
                DESCRIPTION "BRANCH 22 Min"
                              ::= { panelboard2 222 }

pb2-branch23-min
                OBJECT-TYPE
                SYNTAX  INTEGER
                ACCESS  read-only
                STATUS  mandatory
                DESCRIPTION "BRANCH 23 Min"
                              ::= { panelboard2 223 }

pb2-branch24-min
                OBJECT-TYPE
                SYNTAX  INTEGER
                ACCESS  read-only
                STATUS  mandatory
                DESCRIPTION "BRANCH 24 Min"
                              ::= { panelboard2 224 }

pb2-branch25-min
                OBJECT-TYPE
                SYNTAX  INTEGER
                ACCESS  read-only
                STATUS  mandatory
                DESCRIPTION "BRANCH 25 Min"
                              ::= { panelboard2 225 }

pb2-branch26-min
                OBJECT-TYPE
                SYNTAX  INTEGER
                ACCESS  read-only
                STATUS  mandatory
                DESCRIPTION "BRANCH 26 Min"
                              ::= { panelboard2 226 }

pb2-branch27-min
                OBJECT-TYPE
                SYNTAX  INTEGER
                ACCESS  read-only
                STATUS  mandatory
                DESCRIPTION "BRANCH 27 Min"
                              ::= { panelboard2 227 }

pb2-branch28-min
                OBJECT-TYPE
                SYNTAX  INTEGER
                ACCESS  read-only
                STATUS  mandatory
                DESCRIPTION "BRANCH 28 Min"
                              ::= { panelboard2 228 }

pb2-branch29-min
                OBJECT-TYPE
                SYNTAX  INTEGER
                ACCESS  read-only
                STATUS  mandatory
                DESCRIPTION "BRANCH 29 Min"
                              ::= { panelboard2 229 }

pb2-branch30-min
                OBJECT-TYPE
                SYNTAX  INTEGER
                ACCESS  read-only
                STATUS  mandatory
                DESCRIPTION "BRANCH 30 Min"
                              ::= { panelboard2 230 }

pb2-branch31-min
                OBJECT-TYPE
                SYNTAX  INTEGER
                ACCESS  read-only
                STATUS  mandatory
                DESCRIPTION "BRANCH 31 Min"
                              ::= { panelboard2 231 }

pb2-branch32-min
                OBJECT-TYPE
                SYNTAX  INTEGER
                ACCESS  read-only
                STATUS  mandatory
                DESCRIPTION "BRANCH 32 Min"
                              ::= { panelboard2 232 }

pb2-branch33-min
                OBJECT-TYPE
                SYNTAX  INTEGER
                ACCESS  read-only
                STATUS  mandatory
                DESCRIPTION "BRANCH 33 Min"
                              ::= { panelboard2 233 }

pb2-branch34-min
                OBJECT-TYPE
                SYNTAX  INTEGER
                ACCESS  read-only
                STATUS  mandatory
                DESCRIPTION "BRANCH 34 Min"
                              ::= { panelboard2 234 }

pb2-branch35-min
                OBJECT-TYPE
                SYNTAX  INTEGER
                ACCESS  read-only
                STATUS  mandatory
                DESCRIPTION "BRANCH 35 Min"
                              ::= { panelboard2 235 }

pb2-branch36-min
                OBJECT-TYPE
                SYNTAX  INTEGER
                ACCESS  read-only
                STATUS  mandatory
                DESCRIPTION "BRANCH 36 Min"
                              ::= { panelboard2 236 }

pb2-branch1-max
                OBJECT-TYPE
                SYNTAX  INTEGER
                ACCESS  read-only
                STATUS  mandatory
                DESCRIPTION "BRANCH 1 Max
                                    Note for all maximum currents: 100 = 10.0 amps"
                              ::= { panelboard2 301 }

pb2-branch2-max
                OBJECT-TYPE
                SYNTAX  INTEGER
                ACCESS  read-only
                STATUS  mandatory
                DESCRIPTION "BRANCH 2 Max"
                              ::= { panelboard2 302 }

pb2-branch3-max
                OBJECT-TYPE
                SYNTAX  INTEGER
                ACCESS  read-only
                STATUS  mandatory
                DESCRIPTION "BRANCH 3 Max"
                              ::= { panelboard2 303 }

pb2-branch4-max
                OBJECT-TYPE
                SYNTAX  INTEGER
                ACCESS  read-only
                STATUS  mandatory
                DESCRIPTION "BRANCH 4 Max"
                              ::= { panelboard2 304 }

pb2-branch5-max
                OBJECT-TYPE
                SYNTAX  INTEGER
                ACCESS  read-only
                STATUS  mandatory
                DESCRIPTION "BRANCH 5 Max"
                              ::= { panelboard2 305 }

pb2-branch6-max
                OBJECT-TYPE
                SYNTAX  INTEGER
                ACCESS  read-only
                STATUS  mandatory
                DESCRIPTION "BRANCH 6 Max"
                              ::= { panelboard2 306 }

pb2-branch7-max
                OBJECT-TYPE
                SYNTAX  INTEGER
                ACCESS  read-only
                STATUS  mandatory
                DESCRIPTION "BRANCH 7 Max"
                              ::= { panelboard2 307 }

pb2-branch8-max
                OBJECT-TYPE
                SYNTAX  INTEGER
                ACCESS  read-only
                STATUS  mandatory
                DESCRIPTION "BRANCH 8 Max"
                              ::= { panelboard2 308 }

pb2-branch9-max
                OBJECT-TYPE
                SYNTAX  INTEGER
                ACCESS  read-only
                STATUS  mandatory
                DESCRIPTION "BRANCH 9 Max"
                              ::= { panelboard2 309 }

pb2-branch10-max
                OBJECT-TYPE
                SYNTAX  INTEGER
                ACCESS  read-only
                STATUS  mandatory
                DESCRIPTION "BRANCH 10 Max"
                              ::= { panelboard2 310 }

pb2-branch11-max
                OBJECT-TYPE
                SYNTAX  INTEGER
                ACCESS  read-only
                STATUS  mandatory
                DESCRIPTION "BRANCH 11 Max"
                              ::= { panelboard2 311 }

pb2-branch12-max
                OBJECT-TYPE
                SYNTAX  INTEGER
                ACCESS  read-only
                STATUS  mandatory
                DESCRIPTION "BRANCH 12 Max"
                              ::= { panelboard2 312 }

pb2-branch13-max
                OBJECT-TYPE
                SYNTAX  INTEGER
                ACCESS  read-only
                STATUS  mandatory
                DESCRIPTION "BRANCH 13 Max"
                              ::= { panelboard2 313 }

pb2-branch14-max
                OBJECT-TYPE
                SYNTAX  INTEGER
                ACCESS  read-only
                STATUS  mandatory
                DESCRIPTION "BRANCH 14 Max"
                              ::= { panelboard2 314 }

pb2-branch15-max
                OBJECT-TYPE
                SYNTAX  INTEGER
                ACCESS  read-only
                STATUS  mandatory
                DESCRIPTION "BRANCH 15 Max"
                              ::= { panelboard2 315 }

pb2-branch16-max
                OBJECT-TYPE
                SYNTAX  INTEGER
                ACCESS  read-only
                STATUS  mandatory
                DESCRIPTION "BRANCH 16 Max"
                              ::= { panelboard2 316 }

pb2-branch17-max
                OBJECT-TYPE
                SYNTAX  INTEGER
                ACCESS  read-only
                STATUS  mandatory
                DESCRIPTION "BRANCH 17 Max"
                              ::= { panelboard2 317 }

pb2-branch18-max
                OBJECT-TYPE
                SYNTAX  INTEGER
                ACCESS  read-only
                STATUS  mandatory
                DESCRIPTION "BRANCH 18 Max"
                              ::= { panelboard2 318 }

pb2-branch19-max
                OBJECT-TYPE
                SYNTAX  INTEGER
                ACCESS  read-only
                STATUS  mandatory
                DESCRIPTION "BRANCH 19 Max"
                              ::= { panelboard2 319 }

pb2-branch20-max
                OBJECT-TYPE
                SYNTAX  INTEGER
                ACCESS  read-only
                STATUS  mandatory
                DESCRIPTION "BRANCH 20 Max"
                              ::= { panelboard2 320 }

pb2-branch21-max
                OBJECT-TYPE
                SYNTAX  INTEGER
                ACCESS  read-only
                STATUS  mandatory
                DESCRIPTION "BRANCH 21 Max"
                              ::= { panelboard2 321 }

pb2-branch22-max
                OBJECT-TYPE
                SYNTAX  INTEGER
                ACCESS  read-only
                STATUS  mandatory
                DESCRIPTION "BRANCH 22 Max"
                              ::= { panelboard2 322 }

pb2-branch23-max
                OBJECT-TYPE
                SYNTAX  INTEGER
                ACCESS  read-only
                STATUS  mandatory
                DESCRIPTION "BRANCH 23 Max"
                              ::= { panelboard2 323 }

pb2-branch24-max
                OBJECT-TYPE
                SYNTAX  INTEGER
                ACCESS  read-only
                STATUS  mandatory
                DESCRIPTION "BRANCH 24 Max"
                              ::= { panelboard2 324 }

pb2-branch25-max
                OBJECT-TYPE
                SYNTAX  INTEGER
                ACCESS  read-only
                STATUS  mandatory
                DESCRIPTION "BRANCH 25 Max"
                              ::= { panelboard2 325 }

pb2-branch26-max
                OBJECT-TYPE
                SYNTAX  INTEGER
                ACCESS  read-only
                STATUS  mandatory
                DESCRIPTION "BRANCH 26 Max"
                              ::= { panelboard2 326 }

pb2-branch27-max
                OBJECT-TYPE
                SYNTAX  INTEGER
                ACCESS  read-only
                STATUS  mandatory
                DESCRIPTION "BRANCH 27 Max"
                              ::= { panelboard2 327 }

pb2-branch28-max
                OBJECT-TYPE
                SYNTAX  INTEGER
                ACCESS  read-only
                STATUS  mandatory
                DESCRIPTION "BRANCH 28 Max"
                              ::= { panelboard2 328 }

pb2-branch29-max
                OBJECT-TYPE
                SYNTAX  INTEGER
                ACCESS  read-only
                STATUS  mandatory
                DESCRIPTION "BRANCH 29 Max"
                              ::= { panelboard2 329 }

pb2-branch30-max
                OBJECT-TYPE
                SYNTAX  INTEGER
                ACCESS  read-only
                STATUS  mandatory
                DESCRIPTION "BRANCH 30 Max"
                              ::= { panelboard2 330 }

pb2-branch31-max
                OBJECT-TYPE
                SYNTAX  INTEGER
                ACCESS  read-only
                STATUS  mandatory
                DESCRIPTION "BRANCH 31 Max"
                              ::= { panelboard2 331 }

pb2-branch32-max
                OBJECT-TYPE
                SYNTAX  INTEGER
                ACCESS  read-only
                STATUS  mandatory
                DESCRIPTION "BRANCH 32 Max"
                              ::= { panelboard2 332 }

pb2-branch33-max
                OBJECT-TYPE
                SYNTAX  INTEGER
                ACCESS  read-only
                STATUS  mandatory
                DESCRIPTION "BRANCH 33 Max"
                              ::= { panelboard2 333 }

pb2-branch34-max
                OBJECT-TYPE
                SYNTAX  INTEGER
                ACCESS  read-only
                STATUS  mandatory
                DESCRIPTION "BRANCH 34 Max"
                              ::= { panelboard2 334 }

pb2-branch35-max
                OBJECT-TYPE
                SYNTAX  INTEGER
                ACCESS  read-only
                STATUS  mandatory
                DESCRIPTION "BRANCH 35 Max"
                              ::= { panelboard2 335 }

pb2-branch36-max
                OBJECT-TYPE
                SYNTAX  INTEGER
                ACCESS  read-only
                STATUS  mandatory
                DESCRIPTION "BRANCH 36 Max"
                              ::= { panelboard2 336 }

pb2-branch1-16-zero
                OBJECT-TYPE
                SYNTAX  INTEGER
                ACCESS  read-write
                STATUS  mandatory
                DESCRIPTION "BRANCH 1-16 Zero
                                      Bit 0 = BRANCH 1
                  Bit 15 = BRANCH 16"
                              ::= { panelboard2 401 }

pb2-branch17-32-zero
                OBJECT-TYPE
                SYNTAX  INTEGER
                ACCESS  read-write
                STATUS  mandatory
                DESCRIPTION "BRANCH 17-32 Zero
                                      Bit 0 = BRANCH 17
                  Bit 15 = BRANCH 32"
                              ::= { panelboard2 402 }

pb2-branch33-48-zero
                OBJECT-TYPE
                SYNTAX  INTEGER
                ACCESS  read-write
                STATUS  mandatory
                DESCRIPTION "BRANCH 33-48 Zero
                                      Bit 0 = BRANCH 33
                  Bit 15 = BRANCH 48"
                              ::= { panelboard2 403 }

pb2-branch49-64-zero
                OBJECT-TYPE
                SYNTAX  INTEGER
                ACCESS  read-write
                STATUS  mandatory
                DESCRIPTION "BRANCH 49-64 Zero
                                      Bit 0 = BRANCH 49
                  Bit 15 = BRANCH 64"
                              ::= { panelboard2 404 }

pb2-branch65-72-zero
                OBJECT-TYPE
                SYNTAX  INTEGER
                ACCESS  read-write
                STATUS  mandatory
                DESCRIPTION "BRANCH 65-72 Zero
                                      Bit 0 = BRANCH 65
                  Bit 7 = BRANCH 72
                  Bit 8-15 not used"
                              ::= { panelboard2 405 }

pb2-branch1-16-prealarm
                OBJECT-TYPE
                SYNTAX  INTEGER
                ACCESS  read-write
                STATUS  mandatory
                DESCRIPTION "BRANCH 1-16 prealarm
                                      Bit 0 = BRANCH 1
                  Bit 15 = BRANCH 16"
                              ::= { panelboard2 406 }

pb2-branch17-32-prealarm
                OBJECT-TYPE
                SYNTAX  INTEGER
                ACCESS  read-write
                STATUS  mandatory
                DESCRIPTION "BRANCH 17-32 prealarm
                                      Bit 0 = BRANCH 17
                  Bit 15 = BRANCH 32"
                              ::= { panelboard2 407 }

pb2-branch33-48-prealarm
                OBJECT-TYPE
                SYNTAX  INTEGER
                ACCESS  read-write
                STATUS  mandatory
                DESCRIPTION "BRANCH 33-48 prealarm
                                      Bit 0 = BRANCH 33
                  Bit 15 = BRANCH 48"
                              ::= { panelboard2 408 }

pb2-branch49-64-prealarm
                OBJECT-TYPE
                SYNTAX  INTEGER
                ACCESS  read-write
                STATUS  mandatory
                DESCRIPTION "BRANCH 49-64 prealarm
                                      Bit 0 = BRANCH 49
                  Bit 15 = BRANCH 64"
                              ::= { panelboard2 409 }

pb2-branch65-72-prealarm
                OBJECT-TYPE
                SYNTAX  INTEGER
                ACCESS  read-write
                STATUS  mandatory
                DESCRIPTION "BRANCH 65-72 prealarm
                                      Bit 0 = BRANCH 65
                  Bit 7 = BRANCH 72
                  Bits 8-25 not used"
                              ::= { panelboard2 410 }

pb2-branch1-16-alarm
                OBJECT-TYPE
                SYNTAX  INTEGER
                ACCESS  read-write
                STATUS  mandatory
                DESCRIPTION "BRANCH 1-16 Alarm
                                      Bit 0 = BRANCH 1
                  Bit 15 = BRANCH 16"
                              ::= { panelboard2 411 }

pb2-branch17-32-alarm
                OBJECT-TYPE
                SYNTAX  INTEGER
                ACCESS  read-write
                STATUS  mandatory
                DESCRIPTION "BRANCH 17-32 Alarm
                                      Bit 0 = BRANCH 17
                  Bit 15 = BRANCH 32"
                              ::= { panelboard2 412 }

pb2-branch33-48-alarm
                OBJECT-TYPE
                SYNTAX  INTEGER
                ACCESS  read-write
                STATUS  mandatory
                DESCRIPTION "BRANCH 33-48 Alarm
                                      Bit 0 = BRANCH 33
                  Bit 15 = BRANCH 48"
                              ::= { panelboard2 413 }

pb2-branch49-64-alarm
                OBJECT-TYPE
                SYNTAX  INTEGER
                ACCESS  read-write
                STATUS  mandatory
                DESCRIPTION "BRANCH 49-64 Alarm
                                      Bit 0 = BRANCH 49
                  Bit 15 =BRANCH 64"
                              ::= { panelboard2 414 }

pb2-branch65-72-alarm
                OBJECT-TYPE
                SYNTAX  INTEGER
                ACCESS  read-write
                STATUS  mandatory
                DESCRIPTION "BRANCH 65-72 Alarm
                                      Bit 0 = BRANCH 65
                  Bit 7 = BRANCH 72
                  Bits 8-25 not used"
                              ::= { panelboard2 415 }

pb2-global-rated-current-size
                OBJECT-TYPE
                SYNTAX  INTEGER
                ACCESS  read-write
                STATUS  mandatory
                DESCRIPTION "Global-rated-current-size
                                    Note for global rated-current size: 10 = 10 amps
                    Range is 6 to 100 amps"
                              ::= { panelboard2 416 }

pb2-global-prealarm-threshold
                OBJECT-TYPE
                SYNTAX  INTEGER
                ACCESS  read-write
                STATUS  mandatory
                DESCRIPTION "Global-prealarm-threshold
                                    Note for global prealarm threshold: 70 = 70% of rated-current size
                    range is 40-100%"
                              ::= { panelboard2 417 }

pb2-global-alarm-threshold
                OBJECT-TYPE
                SYNTAX  INTEGER
                ACCESS  read-write
                STATUS  mandatory
                DESCRIPTION "Global-alarm-threshold
                                    Note for global alarm threshold: 80 = 80% of rated-current size
                    range is 50-100%"
                              ::= { panelboard2 418 }

pb2-global-prealarm-time-delay
                OBJECT-TYPE
                SYNTAX  INTEGER
                ACCESS  read-write
                STATUS  mandatory
                DESCRIPTION "Global-prealarm-time-delay
                                    Note for global prealarm time delay: units are in seconds"
                              ::= { panelboard2 419 }

pb2-global-alarm-time-delay
                OBJECT-TYPE
                SYNTAX  INTEGER
                ACCESS  read-write
                STATUS  mandatory
                DESCRIPTION "Global-alarm-time-delay
                                    Note for global alarm time delay: units are in seconds"
                              ::= { panelboard2 420 }

pb2-min-max-reset
                OBJECT-TYPE
                SYNTAX  INTEGER
                ACCESS  read-write
                STATUS  mandatory
                DESCRIPTION "Min-Max-Reset
                    Note for Min-max Reset: writing to this register will clear minimum
                                    and maximum current values"
                              ::= { panelboard2 421 }

pb2-alarm-status-latching
                OBJECT-TYPE
                SYNTAX  INTEGER
                ACCESS  read-write
                STATUS  mandatory
                DESCRIPTION "Alarm-Status-Latching
                                              bit 0:      prealarm Register
                                              bit 1:      Alarm Register
                                              bit 2:      Zero Current Register
                                              bit 3:      Over Voltage main
                                              bit 4:      Under Voltage main
                                              bit 5:      Over Voltage alternate
                                              bit 6:      Under Voltage alternate
                                              bit 7:      Over Current Panel
                                              bit 8:      Under Current Panel
                                              bits 9 - 15: Not Used"
                              ::= { panelboard2 422 }

pb2-alarm-status-nonlatching
                OBJECT-TYPE
                SYNTAX  INTEGER
                ACCESS  read-only
                STATUS  mandatory
                DESCRIPTION "Alarm-Status-Nonlatching
                                              bit 0:      prealarm Register
                                              bit 1:      Alarm Register
                                              bit 2:      Zero Current Register
                                              bit 3:      Over Voltage main
                                              bit 4:      Under Voltage main
                                              bit 5:      Over Voltage alternate
                                              bit 6:      Under Voltage alternate
                                              bit 7:      Over Current Panel
                                              bit 8:      Under Current Panel
                                              bits 9 - 15: Not Used"
                              ::= { panelboard2 423 }

pb2-digital-alarm-status
                OBJECT-TYPE
                SYNTAX  INTEGER
                ACCESS  read-only
                STATUS  mandatory
                DESCRIPTION "Digital-Alarm-Status
                                              bit 0:      Digital alarm 1
                                              bit 1:      Digital alarm 2
                                              bit 2:      Digital alarm 3
                                              bit 3:      Digital alarm 4
                                              bits 4 - 15: Not Used"
                              ::= { panelboard2 424 }

pb2-current-option-setting
                OBJECT-TYPE
                SYNTAX  INTEGER
                ACCESS  read-write
                STATUS  mandatory
                DESCRIPTION "Current-Option-Setting
                                              bit 0-13: Reserved
                                              bit 14:    Always Low
                                              bit 15:    Current Loss"
                              ::= { panelboard2 425 }

pb2-voltage-option-setting
                OBJECT-TYPE
                SYNTAX  INTEGER
                ACCESS  read-only
                STATUS  mandatory
                DESCRIPTION "Voltage-Option-Setting
                                              bit 0:      option 0
                                              bit 1:      option 1
                                              bit 2:      option 2
                                              bit 3:      option 3
                  bit 4:      Voltage THD
                  bit 5:      Set to 50Hz
                  bit 6:      KW,KVA,KVAR read in hundreths
                  bit 7:      High Voltage Board
                  bit 8-9:    Reserved
                                              bits 10 - 15: Not Used
                    Option 0: no voltage monitoring.
                    Option 1: One voltage feeding 1 or 2 panel boards.
                    Option 2: One voltage feeding panelboard 1 and another feeding panelboard 2.
                    Option 3: Two voltages tied together through interlocked circuit rated-currents feeding both panelboards.
                              Digital input 1 and 2 are used to determine which is feeding the panelboard. A set bit
                              indicated closed.  If both are closed, main voltage is used."
                              ::= { panelboard2 426 }

pb2-voltage-a-b-main
                OBJECT-TYPE
                SYNTAX  INTEGER
                ACCESS  read-only
                STATUS  mandatory
                DESCRIPTION "Voltage-A-B-Main
                    Note for all voltages: 1200 = 120.0 volts"
                              ::= { panelboard2 427 }

pb2-voltage-b-c-main
                OBJECT-TYPE
                SYNTAX  INTEGER
                ACCESS  read-only
                STATUS  mandatory
                DESCRIPTION "Voltage-B-C-Main"
                              ::= { panelboard2 428 }

pb2-voltage-c-a-main
                OBJECT-TYPE
                SYNTAX  INTEGER
                ACCESS  read-only
                STATUS  mandatory
                DESCRIPTION "Voltage-C-A-Main"
                              ::= { panelboard2 429 }

pb2-voltage-a-n-main
                OBJECT-TYPE
                SYNTAX  INTEGER
                ACCESS  read-only
                STATUS  mandatory
                DESCRIPTION "Voltage-A-N-Main"
                              ::= { panelboard2 430 }

pb2-voltage-b-n-main
                OBJECT-TYPE
                SYNTAX  INTEGER
                ACCESS  read-only
                STATUS  mandatory
                DESCRIPTION "Voltage-B-N-Main"
                              ::= { panelboard2 431 }

pb2-voltage-c-n-main
                OBJECT-TYPE
                SYNTAX  INTEGER
                ACCESS  read-only
                STATUS  mandatory
                DESCRIPTION "Voltage-C-N-Main"
                              ::= { panelboard2 432 }

pb2-over-voltage-alarm-threshhold-main
                OBJECT-TYPE
                SYNTAX  INTEGER
                ACCESS  read-write
                STATUS  mandatory
                DESCRIPTION "Over-Voltage-Alarm-Threshhold-Main
                    Note All Over and Under Voltage is for L-L values"
                              ::= { panelboard2 433 }

pb2-under-voltage-alarm-threshhold-main
                OBJECT-TYPE
                SYNTAX  INTEGER
                ACCESS  read-write
                STATUS  mandatory
                DESCRIPTION "Under-Voltage-Alarm-Threshhold-Main"
                              ::= { panelboard2 434 }

pb2-voltage-frequency-main
                OBJECT-TYPE
                SYNTAX  INTEGER
                ACCESS  read-only
                STATUS  mandatory
                DESCRIPTION "Voltage-Frequency-Main
                    note for frequency: 600 = 60.0Hz
                    Range is 40-70Hz
                    Note if insufficient voltage is present frequency will read 0xFFFF"
                              ::= { panelboard2 435 }

pb2-voltage-a-b-alternate
                OBJECT-TYPE
                SYNTAX  INTEGER
                ACCESS  read-only
                STATUS  mandatory
                DESCRIPTION "Voltage-A-B-Alternate"
                              ::= { panelboard2 436 }

pb2-voltage-b-c-alternate
                OBJECT-TYPE
                SYNTAX  INTEGER
                ACCESS  read-only
                STATUS  mandatory
                DESCRIPTION "Voltage-B-C-Alternate"
                              ::= { panelboard2 437 }

pb2-voltage-c-a-alternate
                OBJECT-TYPE
                SYNTAX  INTEGER
                ACCESS  read-only
                STATUS  mandatory
                DESCRIPTION "Voltage-C-A-Alternate"
                              ::= { panelboard2 438 }

pb2-voltage-a-n-alternate
                OBJECT-TYPE
                SYNTAX  INTEGER
                ACCESS  read-only
                STATUS  mandatory
                DESCRIPTION "Voltage-A-N-Alternate"
                              ::= { panelboard2 439 }

pb2-voltage-b-N-alternate
                OBJECT-TYPE
                SYNTAX  INTEGER
                ACCESS  read-only
                STATUS  mandatory
                DESCRIPTION "Voltage-B-N-Alternate"
                              ::= { panelboard2 440 }

pb2-voltage-c-n-alternate
                OBJECT-TYPE
                SYNTAX  INTEGER
                ACCESS  read-only
                STATUS  mandatory
                DESCRIPTION "Voltage-C-N-Alternate"
                              ::= { panelboard2 441 }

pb2-over-voltage-alarm-threshhold-alternate
                OBJECT-TYPE
                SYNTAX  INTEGER
                ACCESS  read-write
                STATUS  mandatory
                DESCRIPTION "Over-Voltage-Alarm-Threshhold-Alternate"
                              ::= { panelboard2 442 }

pb2-under-voltage-alarm-threshhold-alternate
                OBJECT-TYPE
                SYNTAX  INTEGER
                ACCESS  read-write
                STATUS  mandatory
                DESCRIPTION "Under-Voltage-Alarm-Threshhold-Alternate"
                              ::= { panelboard2 443 }


pb2-kwh-reset
                OBJECT-TYPE
                SYNTAX  INTEGER
                ACCESS  read-write
                STATUS  mandatory
                DESCRIPTION "KWH Reset
                    Resets all KWH values to zero"
                              ::= { panelboard2 444 }

pb2-current-phase-a-panelboard
                OBJECT-TYPE
                SYNTAX  INTEGER
                ACCESS  read-only
                STATUS  mandatory
                DESCRIPTION "Current-Phase-A-Panelboard"
                              ::= { panelboard2 445 }

pb2-current-phase-b-panelboard
                OBJECT-TYPE
                SYNTAX  INTEGER
                ACCESS  read-only
                STATUS  mandatory
                DESCRIPTION "Current-Phase-B-Panelboard"
                              ::= { panelboard2 446 }

pb2-current-phase-c-panelboard
                OBJECT-TYPE
                SYNTAX  INTEGER
                ACCESS  read-only
                STATUS  mandatory
                DESCRIPTION "Current-Phase-C-Panelboard"
                              ::= { panelboard2 447 }

pb2-current-neutral-panelboard
                OBJECT-TYPE
                SYNTAX  INTEGER
                ACCESS  read-only
                STATUS  mandatory
                DESCRIPTION "Current-Neutral-Panelboard"
                              ::= { panelboard2 448 }

pb2-current-ground-panelboard
                OBJECT-TYPE
                SYNTAX  INTEGER
                ACCESS  read-only
                STATUS  mandatory
                DESCRIPTION "Current-Ground-Panelboard"
                              ::= { panelboard2 449 }

pb2-over-current-alarm-threshhold
                OBJECT-TYPE
                SYNTAX  INTEGER
                ACCESS  read-write
                STATUS  mandatory
                DESCRIPTION "Over-Current-Alarm-Threshhold"
                              ::= { panelboard2 450 }

pb2-under-current-alarm-threshhold
                OBJECT-TYPE
                SYNTAX  INTEGER
                ACCESS  read-write
                STATUS  mandatory
                DESCRIPTION "Under-Current-Alarm-Threshhold"
                              ::= { panelboard2 451 }

pb2-real-power-kw-total
                OBJECT-TYPE
                SYNTAX  INTEGER
                ACCESS  read-only
                STATUS  mandatory
                DESCRIPTION "Real-Power-KW-Total"
                              ::= { panelboard2 452 }

pb2-real-power-kw-phase-a
                OBJECT-TYPE
                SYNTAX  INTEGER
                ACCESS  read-only
                STATUS  mandatory
                DESCRIPTION "Real-Power-KW-Phase-A"
                              ::= { panelboard2 453 }

pb2-real-power-kw-phase-b
                OBJECT-TYPE
                SYNTAX  INTEGER
                ACCESS  read-only
                STATUS  mandatory
                DESCRIPTION "Real-Power-KW-Phase-B"
                              ::= { panelboard2 454 }

pb2-real-power-kw-phase-c
                OBJECT-TYPE
                SYNTAX  INTEGER
                ACCESS  read-only
                STATUS  mandatory
                DESCRIPTION "Real-Power-KW-Phase-C"
                              ::= { panelboard2 455 }

pb2-apparent-power-kva-total
                OBJECT-TYPE
                SYNTAX  INTEGER
                ACCESS  read-only
                STATUS  mandatory
                DESCRIPTION "Apparent-Power-KVA-Total"
                              ::= { panelboard2 456 }

pb2-reactive-power-kvar-total
                OBJECT-TYPE
                SYNTAX  INTEGER
                ACCESS  read-only
                STATUS  mandatory
                DESCRIPTION "Reactive-Power-KVAR-Total"
                              ::= { panelboard2 457 }

pb2-power-factor-total
                OBJECT-TYPE
                SYNTAX  INTEGER
                ACCESS  read-only
                STATUS  mandatory
                DESCRIPTION "Power-Factor-Total"
                              ::= { panelboard2 458 }

pb2-power-factor-phase-a
                OBJECT-TYPE
                SYNTAX  INTEGER
                ACCESS  read-only
                STATUS  mandatory
                DESCRIPTION "Power-Factor-Phase-A"
                              ::= { panelboard2 459 }

pb2-power-factor-phase-b
                OBJECT-TYPE
                SYNTAX  INTEGER
                ACCESS  read-only
                STATUS  mandatory
                DESCRIPTION "power-Factor-Phase-B"
                              ::= { panelboard2 460 }

pb2-power-factor-phase-c
                OBJECT-TYPE
                SYNTAX  INTEGER
                ACCESS  read-only
                STATUS  mandatory
                DESCRIPTION "Power-Factor-Phase-C"
                              ::= { panelboard2 461 }

pb2-energy-consumption-kwh-low-word-integer
                OBJECT-TYPE
                SYNTAX  INTEGER
                ACCESS  read-only
                STATUS  mandatory
                DESCRIPTION "Energy-Consumption-KWh-Low-Word-Integer"
                              ::= { panelboard2 462 }

pb2-energy-consumption-kwh-high-word-integer
                OBJECT-TYPE
                SYNTAX  INTEGER
                ACCESS  read-only
                STATUS  mandatory
                DESCRIPTION "Energy-Consumption-KWh-High-Word-Integer"
                              ::= { panelboard2 463 }

pb2-main-kwh-reset
                OBJECT-TYPE
                SYNTAX  INTEGER
                ACCESS  read-only
                STATUS  mandatory
                DESCRIPTION "Main-KWH-Reset"
                              ::= { panelboard2 464 }

pb1-percent-load-phase-a
                OBJECT-TYPE
                SYNTAX  INTEGER
                ACCESS  read-only
                STATUS  mandatory
                DESCRIPTION "Percent-Load-Phase-A"
                              ::= { panelboard2 465 }

pb2-percent-load-phase-b
                OBJECT-TYPE
                SYNTAX  INTEGER
                ACCESS  read-only
                STATUS  mandatory
                DESCRIPTION "Percent-Load-Phase-B"
                              ::= { panelboard2 466 }

pb2-percent-load-phase-c
                OBJECT-TYPE
                SYNTAX  INTEGER
                ACCESS  read-only
                STATUS  mandatory
                DESCRIPTION "Percent-Load-Phase-C"
                              ::= { panelboard2 467 }

pb2-full-load
                OBJECT-TYPE
                SYNTAX  INTEGER
                ACCESS  read-write
                STATUS  mandatory
                DESCRIPTION "Full-Load, used to calculate percent load (250.0A = 2500)"
                              ::= { panelboard2 468 }

pb2-branch1-rated-current-size
                OBJECT-TYPE
                SYNTAX  INTEGER
                ACCESS  read-write
                STATUS  mandatory
                DESCRIPTION "BRANCH 1 rated-current Size
                                    Note for all rated-current sizes 1-42: 10 = 10 amps
                    Range is 10 to 100 amps"
                              ::= { panelboard2 501 }
pb2-branch2-rated-current-size
                OBJECT-TYPE
                SYNTAX  INTEGER
                ACCESS  read-write
                STATUS  mandatory
                DESCRIPTION "BRANCH 2 rated-current Size"
                              ::= { panelboard2 502 }

pb2-branch3-rated-current-size
                OBJECT-TYPE
                SYNTAX  INTEGER
                ACCESS  read-write
                STATUS  mandatory
                DESCRIPTION "BRANCH 3 rated-current Size"
                              ::= { panelboard2 503 }

pb2-branch4-rated-current-size
                OBJECT-TYPE
                SYNTAX  INTEGER
                ACCESS  read-write
                STATUS  mandatory
                DESCRIPTION "BRANCH 4 rated-current Size"
                              ::= { panelboard2 504 }

pb2-branch5-rated-current-size
                OBJECT-TYPE
                SYNTAX  INTEGER
                ACCESS  read-write
                STATUS  mandatory
                DESCRIPTION "BRANCH 5 rated-current Size"
                              ::= { panelboard2 505 }

pb2-branch6-rated-current-size
                OBJECT-TYPE
                SYNTAX  INTEGER
                ACCESS  read-write
                STATUS  mandatory
                DESCRIPTION "BRANCH 6 rated-current Size"
                              ::= { panelboard2 506 }

pb2-branch7-rated-current-size
                OBJECT-TYPE
                SYNTAX  INTEGER
                ACCESS  read-write
                STATUS  mandatory
                DESCRIPTION "BRANCH 7 rated-current Size"
                              ::= { panelboard2 507 }

pb2-branch8-rated-current-size
                OBJECT-TYPE
                SYNTAX  INTEGER
                ACCESS  read-write
                STATUS  mandatory
                DESCRIPTION "BRANCH 8 rated-current Size"
                              ::= { panelboard2 508 }

pb2-branch9-rated-current-size
                OBJECT-TYPE
                SYNTAX  INTEGER
                ACCESS  read-write
                STATUS  mandatory
                DESCRIPTION "BRANCH 9 rated-current Size"
                              ::= { panelboard2 509 }

pb2-branch10-rated-current-size
                OBJECT-TYPE
                SYNTAX  INTEGER
                ACCESS  read-write
                STATUS  mandatory
                DESCRIPTION "BRANCH 10 rated-current Size"
                              ::= { panelboard2 510 }

pb2-branch11-rated-current-size
                OBJECT-TYPE
                SYNTAX  INTEGER
                ACCESS  read-write
                STATUS  mandatory
                DESCRIPTION "BRANCH 11 rated-current Size"
                              ::= { panelboard2 511 }

pb2-branch12-rated-current-size
                OBJECT-TYPE
                SYNTAX  INTEGER
                ACCESS  read-write
                STATUS  mandatory
                DESCRIPTION "BRANCH 12 rated-current Size"
                              ::= { panelboard2 512 }

pb2-branch13-rated-current-size
                OBJECT-TYPE
                SYNTAX  INTEGER
                ACCESS  read-write
                STATUS  mandatory
                DESCRIPTION "BRANCH 13 rated-current Size"
                              ::= { panelboard2 513 }

pb2-branch14-rated-current-size
                OBJECT-TYPE
                SYNTAX  INTEGER
                ACCESS  read-write
                STATUS  mandatory
                DESCRIPTION "BRANCH 14 rated-current Size"
                              ::= { panelboard2 514 }

pb2-branch15-rated-current-size
                OBJECT-TYPE
                SYNTAX  INTEGER
                ACCESS  read-write
                STATUS  mandatory
                DESCRIPTION "BRANCH 15 rated-current Size"
                              ::= { panelboard2 515 }

pb2-branch16-rated-current-size
                OBJECT-TYPE
                SYNTAX  INTEGER
                ACCESS  read-write
                STATUS  mandatory
                DESCRIPTION "BRANCH 16 rated-current Size"
                              ::= { panelboard2 516 }

pb2-branch17-rated-current-size
                OBJECT-TYPE
                SYNTAX  INTEGER
                ACCESS  read-write
                STATUS  mandatory
                DESCRIPTION "BRANCH 17 rated-current Size"
                              ::= { panelboard2 517 }

pb2-branch18-rated-current-size
                OBJECT-TYPE
                SYNTAX  INTEGER
                ACCESS  read-write
                STATUS  mandatory
                DESCRIPTION "BRANCH 18 rated-current Size"
                              ::= { panelboard2 518 }

pb2-branch19-rated-current-size
                OBJECT-TYPE
                SYNTAX  INTEGER
                ACCESS  read-write
                STATUS  mandatory
                DESCRIPTION "BRANCH 19 rated-current Size"
                              ::= { panelboard2 519 }

pb2-branch20-rated-current-size
                OBJECT-TYPE
                SYNTAX  INTEGER
                ACCESS  read-write
                STATUS  mandatory
                DESCRIPTION "BRANCH 20 rated-current Size"
                              ::= { panelboard2 520 }

pb2-branch21-rated-current-size
                OBJECT-TYPE
                SYNTAX  INTEGER
                ACCESS  read-write
                STATUS  mandatory
                DESCRIPTION "BRANCH 21 rated-current Size"
                              ::= { panelboard2 521 }

pb2-branch22-rated-current-size
                OBJECT-TYPE
                SYNTAX  INTEGER
                ACCESS  read-write
                STATUS  mandatory
                DESCRIPTION "BRANCH 22 rated-current Size"
                              ::= { panelboard2 522 }

pb2-branch23-rated-current-size
                OBJECT-TYPE
                SYNTAX  INTEGER
                ACCESS  read-write
                STATUS  mandatory
                DESCRIPTION "BRANCH 23 rated-current Size"
                              ::= { panelboard2 523 }

pb2-branch24-rated-current-size
                OBJECT-TYPE
                SYNTAX  INTEGER
                ACCESS  read-write
                STATUS  mandatory
                DESCRIPTION "BRANCH 24 rated-current Size"
                              ::= { panelboard2 524 }

pb2-branch25-rated-current-size
                OBJECT-TYPE
                SYNTAX  INTEGER
                ACCESS  read-write
                STATUS  mandatory
                DESCRIPTION "BRANCH 25 rated-current Size"
                              ::= { panelboard2 525 }

pb2-branch26-rated-current-size
                OBJECT-TYPE
                SYNTAX  INTEGER
                ACCESS  read-write
                STATUS  mandatory
                DESCRIPTION "BRANCH 26 rated-current Size"
                              ::= { panelboard2 526 }

pb2-branch27-rated-current-size
                OBJECT-TYPE
                SYNTAX  INTEGER
                ACCESS  read-write
                STATUS  mandatory
                DESCRIPTION "BRANCH 27 rated-current Size"
                              ::= { panelboard2 527 }

pb2-branch28-rated-current-size
                OBJECT-TYPE
                SYNTAX  INTEGER
                ACCESS  read-write
                STATUS  mandatory
                DESCRIPTION "BRANCH 28 rated-current Size"
                              ::= { panelboard2 528 }

pb2-branch29-rated-current-size
                OBJECT-TYPE
                SYNTAX  INTEGER
                ACCESS  read-write
                STATUS  mandatory
                DESCRIPTION "BRANCH 29 rated-current Size"
                              ::= { panelboard2 529 }

pb2-branch30-rated-current-size
                OBJECT-TYPE
                SYNTAX  INTEGER
                ACCESS  read-write
                STATUS  mandatory
                DESCRIPTION "BRANCH 30 rated-current Size"
                              ::= { panelboard2 530 }

pb2-branch31-rated-current-size
                OBJECT-TYPE
                SYNTAX  INTEGER
                ACCESS  read-write
                STATUS  mandatory
                DESCRIPTION "BRANCH 31 rated-current Size"
                              ::= { panelboard2 531 }

pb2-branch32-rated-current-size
                OBJECT-TYPE
                SYNTAX  INTEGER
                ACCESS  read-write
                STATUS  mandatory
                DESCRIPTION "BRANCH 32 rated-current Size"
                              ::= { panelboard2 532 }

pb2-branch33-rated-current-size
                OBJECT-TYPE
                SYNTAX  INTEGER
                ACCESS  read-write
                STATUS  mandatory
                DESCRIPTION "BRANCH 33 rated-current Size"
                              ::= { panelboard2 533 }

pb2-branch34-rated-current-size
                OBJECT-TYPE
                SYNTAX  INTEGER
                ACCESS  read-write
                STATUS  mandatory
                DESCRIPTION "BRANCH 34 rated-current Size"
                              ::= { panelboard2 534 }

pb2-branch35-rated-current-size
                OBJECT-TYPE
                SYNTAX  INTEGER
                ACCESS  read-write
                STATUS  mandatory
                DESCRIPTION "BRANCH 35 rated-current Size"
                              ::= { panelboard2 535 }

pb2-branch36-rated-current-size
                OBJECT-TYPE
                SYNTAX  INTEGER
                ACCESS  read-write
                STATUS  mandatory
                DESCRIPTION "BRANCH 36 rated-current Size"
                              ::= { panelboard2 536 }

pb2-branch1-kw
                OBJECT-TYPE
                SYNTAX  INTEGER
                ACCESS  read-only
                STATUS  mandatory
                DESCRIPTION "BRANCH 1 KW
                                    Note for all KW: 100 = 10.0 or 1.00 kw depending on setup"
                              ::= { panelboard2 601 }

pb2-branch2-kw
                OBJECT-TYPE
                SYNTAX  INTEGER
                ACCESS  read-only
                STATUS  mandatory
                DESCRIPTION "BRANCH 2 KW"
                              ::= { panelboard2 602 }

pb2-branch3-kw
                OBJECT-TYPE
                SYNTAX  INTEGER
                ACCESS  read-only
                STATUS  mandatory
                DESCRIPTION "BRANCH 3 KW"
                              ::= { panelboard2 603 }

pb2-branch4-kw
                OBJECT-TYPE
                SYNTAX  INTEGER
                ACCESS  read-only
                STATUS  mandatory
                DESCRIPTION "BRANCH 4 KW"
                              ::= { panelboard2 604 }

pb2-branch5-kw
                OBJECT-TYPE
                SYNTAX  INTEGER
                ACCESS  read-only
                STATUS  mandatory
                DESCRIPTION "BRANCH 5 KW"
                              ::= { panelboard2 605 }

pb2-branch6-kw
                OBJECT-TYPE
                SYNTAX  INTEGER
                ACCESS  read-only
                STATUS  mandatory
                DESCRIPTION "BRANCH 6 KW"
                              ::= { panelboard2 606 }

pb2-branch7-kw
                OBJECT-TYPE
                SYNTAX  INTEGER
                ACCESS  read-only
                STATUS  mandatory
                DESCRIPTION "BRANCH 7 KW"
                              ::= { panelboard2 607 }

pb2-branch8-kw
                OBJECT-TYPE
                SYNTAX  INTEGER
                ACCESS  read-only
                STATUS  mandatory
                DESCRIPTION "BRANCH 8 KW"
                              ::= { panelboard2 608 }

pb2-branch9-kw
                OBJECT-TYPE
                SYNTAX  INTEGER
                ACCESS  read-only
                STATUS  mandatory
                DESCRIPTION "BRANCH 9 KW"
                              ::= { panelboard2 609 }

pb2-branch10-kw
                OBJECT-TYPE
                SYNTAX  INTEGER
                ACCESS  read-only
                STATUS  mandatory
                DESCRIPTION "BRANCH 10 KW"
                              ::= { panelboard2 610 }

pb2-branch11-kw
                OBJECT-TYPE
                SYNTAX  INTEGER
                ACCESS  read-only
                STATUS  mandatory
                DESCRIPTION "BRANCH 11 KW"
                              ::= { panelboard2 611 }

pb2-branch12-kw
                OBJECT-TYPE
                SYNTAX  INTEGER
                ACCESS  read-only
                STATUS  mandatory
                DESCRIPTION "BRANCH 12 KW"
                              ::= { panelboard2 612 }

pb2-branch13-kw
                OBJECT-TYPE
                SYNTAX  INTEGER
                ACCESS  read-only
                STATUS  mandatory
                DESCRIPTION "BRANCH 13 KW"
                              ::= { panelboard2 613 }

pb2-branch14-kw
                OBJECT-TYPE
                SYNTAX  INTEGER
                ACCESS  read-only
                STATUS  mandatory
                DESCRIPTION "BRANCH 14 KW"
                              ::= { panelboard2 614 }

pb2-branch15-kw
                OBJECT-TYPE
                SYNTAX  INTEGER
                ACCESS  read-only
                STATUS  mandatory
                DESCRIPTION "BRANCH 15 KW"
                              ::= { panelboard2 615 }

pb2-branch16-kw
                OBJECT-TYPE
                SYNTAX  INTEGER
                ACCESS  read-only
                STATUS  mandatory
                DESCRIPTION "BRANCH 16 KW"
                              ::= { panelboard2 616 }

pb2-branch17-kw
                OBJECT-TYPE
                SYNTAX  INTEGER
                ACCESS  read-only
                STATUS  mandatory
                DESCRIPTION "BRANCH 17 KW"
                              ::= { panelboard2 617 }

pb2-branch18-kw
                OBJECT-TYPE
                SYNTAX  INTEGER
                ACCESS  read-only
                STATUS  mandatory
                DESCRIPTION "BRANCH 18 KW"
                              ::= { panelboard2 618 }

pb2-branch19-kw
                OBJECT-TYPE
                SYNTAX  INTEGER
                ACCESS  read-only
                STATUS  mandatory
                DESCRIPTION "BRANCH 19 KW"
                              ::= { panelboard2 619 }

pb2-branch20-kw
                OBJECT-TYPE
                SYNTAX  INTEGER
                ACCESS  read-only
                STATUS  mandatory
                DESCRIPTION "BRANCH 20 KW"
                              ::= { panelboard2 620 }

pb2-branch21-kw
                OBJECT-TYPE
                SYNTAX  INTEGER
                ACCESS  read-only
                STATUS  mandatory
                DESCRIPTION "BRANCH 21 KW"
                              ::= { panelboard2 621 }

pb2-branch22-kw
                OBJECT-TYPE
                SYNTAX  INTEGER
                ACCESS  read-only
                STATUS  mandatory
                DESCRIPTION "BRANCH 22 KW"
                              ::= { panelboard2 622 }

pb2-branch23-kw
                OBJECT-TYPE
                SYNTAX  INTEGER
                ACCESS  read-only
                STATUS  mandatory
                DESCRIPTION "BRANCH 23 KW"
                              ::= { panelboard2 623 }

pb2-branch24-kw
                OBJECT-TYPE
                SYNTAX  INTEGER
                ACCESS  read-only
                STATUS  mandatory
                DESCRIPTION "BRANCH 24 KW"
                              ::= { panelboard2 624 }

pb2-branch25-kw
                OBJECT-TYPE
                SYNTAX  INTEGER
                ACCESS  read-only
                STATUS  mandatory
                DESCRIPTION "BRANCH 25 KW"
                              ::= { panelboard2 625 }

pb2-branch26-kw
                OBJECT-TYPE
                SYNTAX  INTEGER
                ACCESS  read-only
                STATUS  mandatory
                DESCRIPTION "BRANCH 26 KW"
                              ::= { panelboard2 626 }

pb2-branch27-kw
                OBJECT-TYPE
                SYNTAX  INTEGER
                ACCESS  read-only
                STATUS  mandatory
                DESCRIPTION "BRANCH 27 KW"
                              ::= { panelboard2 627 }

pb2-branch28-kw
                OBJECT-TYPE
                SYNTAX  INTEGER
                ACCESS  read-only
                STATUS  mandatory
                DESCRIPTION "BRANCH 28 KW"
                              ::= { panelboard2 628 }

pb2-branch29-kw
                OBJECT-TYPE
                SYNTAX  INTEGER
                ACCESS  read-only
                STATUS  mandatory
                DESCRIPTION "BRANCH 29 KW"
                              ::= { panelboard2 629 }

pb2-branch30-kw
                OBJECT-TYPE
                SYNTAX  INTEGER
                ACCESS  read-only
                STATUS  mandatory
                DESCRIPTION "BRANCH 30 KW"
                              ::= { panelboard2 630 }

pb2-branch31-kw
                OBJECT-TYPE
                SYNTAX  INTEGER
                ACCESS  read-only
                STATUS  mandatory
                DESCRIPTION "BRANCH 31 KW"
                              ::= { panelboard2 631 }

pb2-branch32-kw
                OBJECT-TYPE
                SYNTAX  INTEGER
                ACCESS  read-only
                STATUS  mandatory
                DESCRIPTION "BRANCH 32 KW"
                              ::= { panelboard2 632 }

pb2-branch33-kw
                OBJECT-TYPE
                SYNTAX  INTEGER
                ACCESS  read-only
                STATUS  mandatory
                DESCRIPTION "BRANCH 33 KW"
                              ::= { panelboard2 633 }

pb2-branch34-kw
                OBJECT-TYPE
                SYNTAX  INTEGER
                ACCESS  read-only
                STATUS  mandatory
                DESCRIPTION "BRANCH 34 KW"
                              ::= { panelboard2 634 }

pb2-branch35-kw
                OBJECT-TYPE
                SYNTAX  INTEGER
                ACCESS  read-only
                STATUS  mandatory
                DESCRIPTION "BRANCH 35 KW"
                              ::= { panelboard2 635 }

pb2-branch36-kw
                OBJECT-TYPE
                SYNTAX  INTEGER
                ACCESS  read-only
                STATUS  mandatory
                DESCRIPTION "BRANCH 36 KW"
                              ::= { panelboard2 636 }

pb2-branch1-kva
                OBJECT-TYPE
                SYNTAX  INTEGER
                ACCESS  read-only
                STATUS  mandatory
                DESCRIPTION "BRANCH 1 KVA
                                    Note for all KVA: 100 = 10.0 or 1.00 kva depending on setup"
                              ::= { panelboard2 701 }

pb2-branch2-kva
                OBJECT-TYPE
                SYNTAX  INTEGER
                ACCESS  read-only
                STATUS  mandatory
                DESCRIPTION "BRANCH 2 KVA"
                              ::= { panelboard2 702 }

pb2-branch3-kva
                OBJECT-TYPE
                SYNTAX  INTEGER
                ACCESS  read-only
                STATUS  mandatory
                DESCRIPTION "BRANCH 3 KVA"
                              ::= { panelboard2 703 }

pb2-branch4-kva
                OBJECT-TYPE
                SYNTAX  INTEGER
                ACCESS  read-only
                STATUS  mandatory
                DESCRIPTION "BRANCH 4 KVA"
                              ::= { panelboard2 704 }

pb2-branch5-kva
                OBJECT-TYPE
                SYNTAX  INTEGER
                ACCESS  read-only
                STATUS  mandatory
                DESCRIPTION "BRANCH 5 KVA"
                              ::= { panelboard2 705 }

pb2-branch6-kva
                OBJECT-TYPE
                SYNTAX  INTEGER
                ACCESS  read-only
                STATUS  mandatory
                DESCRIPTION "BRANCH 6 KVA"
                              ::= { panelboard2 706 }

pb2-branch7-kva
                OBJECT-TYPE
                SYNTAX  INTEGER
                ACCESS  read-only
                STATUS  mandatory
                DESCRIPTION "BRANCH 7 KVA"
                              ::= { panelboard2 707 }

pb2-branch8-kva
                OBJECT-TYPE
                SYNTAX  INTEGER
                ACCESS  read-only
                STATUS  mandatory
                DESCRIPTION "BRANCH 8 KVA"
                              ::= { panelboard2 708 }

pb2-branch9-kva
                OBJECT-TYPE
                SYNTAX  INTEGER
                ACCESS  read-only
                STATUS  mandatory
                DESCRIPTION "BRANCH 9 KVA"
                              ::= { panelboard2 709 }

pb2-branch10-kva
                OBJECT-TYPE
                SYNTAX  INTEGER
                ACCESS  read-only
                STATUS  mandatory
                DESCRIPTION "BRANCH 10 KVA"
                              ::= { panelboard2 710 }

pb2-branch11-kva
                OBJECT-TYPE
                SYNTAX  INTEGER
                ACCESS  read-only
                STATUS  mandatory
                DESCRIPTION "BRANCH 11 KVA"
                              ::= { panelboard2 711 }

pb2-branch12-kva
                OBJECT-TYPE
                SYNTAX  INTEGER
                ACCESS  read-only
                STATUS  mandatory
                DESCRIPTION "BRANCH 12 KVA"
                              ::= { panelboard2 712 }

pb2-branch13-kva
                OBJECT-TYPE
                SYNTAX  INTEGER
                ACCESS  read-only
                STATUS  mandatory
                DESCRIPTION "BRANCH 13 KVA"
                                ::= { panelboard2 713 }

pb2-branch14-kva
                OBJECT-TYPE
                SYNTAX  INTEGER
                ACCESS  read-only
                STATUS  mandatory
                DESCRIPTION "BRANCH 14 KVA"
                              ::= { panelboard2 714 }

pb2-branch15-kva
                OBJECT-TYPE
                SYNTAX  INTEGER
                ACCESS  read-only
                STATUS  mandatory
                DESCRIPTION "BRANCH 15 KVA"
                              ::= { panelboard2 715 }

pb2-branch16-kva
                OBJECT-TYPE
                SYNTAX  INTEGER
                ACCESS  read-only
                STATUS  mandatory
                DESCRIPTION "BRANCH 16 KVA"
                              ::= { panelboard2 716 }

pb2-branch17-kva
                OBJECT-TYPE
                SYNTAX  INTEGER
                ACCESS  read-only
                STATUS  mandatory
                DESCRIPTION "BRANCH 17 KVA"
                              ::= { panelboard2 717 }

pb2-branch18-kva
                OBJECT-TYPE
                SYNTAX  INTEGER
                ACCESS  read-only
                STATUS  mandatory
                DESCRIPTION "BRANCH 18 KVA"
                              ::= { panelboard2 718 }

pb2-branch19-kva
                OBJECT-TYPE
                SYNTAX  INTEGER
                ACCESS  read-only
                STATUS  mandatory
                DESCRIPTION "BRANCH 19 KVA"
                              ::= { panelboard2 719 }

pb2-branch20-kva
                OBJECT-TYPE
                SYNTAX  INTEGER
                ACCESS  read-only
                STATUS  mandatory
                DESCRIPTION "BRANCH 20 KVA"
                              ::= { panelboard2 720 }

pb2-branch21-kva
                OBJECT-TYPE
                SYNTAX  INTEGER
                ACCESS  read-only
                STATUS  mandatory
                DESCRIPTION "BRANCH 21 KVA"
                              ::= { panelboard2 721 }

pb2-branch22-kva
                OBJECT-TYPE
                SYNTAX  INTEGER
                ACCESS  read-only
                STATUS  mandatory
                DESCRIPTION "BRANCH 22 KVA"
                              ::= { panelboard2 722 }

pb2-branch23-kva
                OBJECT-TYPE
                SYNTAX  INTEGER
                ACCESS  read-only
                STATUS  mandatory
                DESCRIPTION "BRANCH 23 KVA"
                              ::= { panelboard2 723 }

pb2-branch24-kva
                OBJECT-TYPE
                SYNTAX  INTEGER
                ACCESS  read-only
                STATUS  mandatory
                DESCRIPTION "BRANCH 24 KVA"
                              ::= { panelboard2 724 }

pb2-branch25-kva
                OBJECT-TYPE
                SYNTAX  INTEGER
                ACCESS  read-only
                STATUS  mandatory
                DESCRIPTION "BRANCH 25 KVA"
                              ::= { panelboard2 725 }

pb2-branch26-kva
                OBJECT-TYPE
                SYNTAX  INTEGER
                ACCESS  read-only
                STATUS  mandatory
                DESCRIPTION "BRANCH 26 KVA"
                              ::= { panelboard2 726 }

pb2-branch27-kva
                OBJECT-TYPE
                SYNTAX  INTEGER
                ACCESS  read-only
                STATUS  mandatory
                DESCRIPTION "BRANCH 27 KVA"
                              ::= { panelboard2 727 }

pb2-branch28-kva
                OBJECT-TYPE
                SYNTAX  INTEGER
                ACCESS  read-only
                STATUS  mandatory
                DESCRIPTION "BRANCH 28 KVA"
                              ::= { panelboard2 728 }

pb2-branch29-kva
                OBJECT-TYPE
                SYNTAX  INTEGER
                ACCESS  read-only
                STATUS  mandatory
                DESCRIPTION "BRANCH 29 KVA"
                              ::= { panelboard2 729 }

pb2-branch30-kva
                OBJECT-TYPE
                SYNTAX  INTEGER
                ACCESS  read-only
                STATUS  mandatory
                DESCRIPTION "BRANCH 30 KVA"
                              ::= { panelboard2 730 }

pb2-branch31-kva
                OBJECT-TYPE
                SYNTAX  INTEGER
                ACCESS  read-only
                STATUS  mandatory
                DESCRIPTION "BRANCH 31 KVA"
                              ::= { panelboard2 731 }

pb2-branch32-kva
                OBJECT-TYPE
                SYNTAX  INTEGER
                ACCESS  read-only
                STATUS  mandatory
                DESCRIPTION "BRANCH 32 KVA"
                              ::= { panelboard2 732 }

pb2-branch33-kva
                OBJECT-TYPE
                SYNTAX  INTEGER
                ACCESS  read-only
                STATUS  mandatory
                DESCRIPTION "BRANCH 33 KVA"
                              ::= { panelboard2 733 }

pb2-branch34-kva
                OBJECT-TYPE
                SYNTAX  INTEGER
                ACCESS  read-only
                STATUS  mandatory
                DESCRIPTION "BRANCH 34 KVA"
                              ::= { panelboard2 734 }

pb2-branch35-kva
                OBJECT-TYPE
                SYNTAX  INTEGER
                ACCESS  read-only
                STATUS  mandatory
                DESCRIPTION "BRANCH 35 KVA"
                              ::= { panelboard2 735 }

pb2-branch36-kva
                OBJECT-TYPE
                SYNTAX  INTEGER
                ACCESS  read-only
                STATUS  mandatory
                DESCRIPTION "BRANCH 36 KVA"
                              ::= { panelboard2 736 }

pb2-branch1-kvar
                OBJECT-TYPE
                SYNTAX  INTEGER
                ACCESS  read-only
                STATUS  mandatory
                DESCRIPTION "BRANCH 1 KVAR
                                    Note for all KVAR: 100 = 10.0 or 1.00 kvar depending on setup"
                              ::= { panelboard2 801 }

pb2-branch2-kvar
                OBJECT-TYPE
                SYNTAX  INTEGER
                ACCESS  read-only
                STATUS  mandatory
                DESCRIPTION "BRANCH 2 KVAR"
                              ::= { panelboard2 802 }

pb2-branch3-kvar
                OBJECT-TYPE
                SYNTAX  INTEGER
                ACCESS  read-only
                STATUS  mandatory
                DESCRIPTION "BRANCH 3 KVAR"
                              ::= { panelboard2 803 }

pb2-branch4-kvar
                OBJECT-TYPE
                SYNTAX  INTEGER
                ACCESS  read-only
                STATUS  mandatory
                DESCRIPTION "BRANCH 4 KVAR"
                              ::= { panelboard2 804 }

pb2-branch5-kvar
                OBJECT-TYPE
                SYNTAX  INTEGER
                ACCESS  read-only
                STATUS  mandatory
                DESCRIPTION "BRANCH 5 KVAR"
                              ::= { panelboard2 805 }

pb2-branch6-kvar
                OBJECT-TYPE
                SYNTAX  INTEGER
                ACCESS  read-only
                STATUS  mandatory
                DESCRIPTION "BRANCH 6 KVAR"
                              ::= { panelboard2 806 }

pb2-branch7-kvar
                OBJECT-TYPE
                SYNTAX  INTEGER
                ACCESS  read-only
                STATUS  mandatory
                DESCRIPTION "BRANCH 7 KVAR"
                              ::= { panelboard2 807 }

pb2-branch8-kvar
                OBJECT-TYPE
                SYNTAX  INTEGER
                ACCESS  read-only
                STATUS  mandatory
                DESCRIPTION "BRANCH 8 KVAR"
                              ::= { panelboard2 808 }

pb2-branch9-kvar
                OBJECT-TYPE
                SYNTAX  INTEGER
                ACCESS  read-only
                STATUS  mandatory
                DESCRIPTION "BRANCH 9 KVAR"
                              ::= { panelboard2 809 }

pb2-branch10-kvar
                OBJECT-TYPE
                SYNTAX  INTEGER
                ACCESS  read-only
                STATUS  mandatory
                DESCRIPTION "BRANCH 10 KVAR"
                              ::= { panelboard2 810 }

pb2-branch11-kvar
                OBJECT-TYPE
                SYNTAX  INTEGER
                ACCESS  read-only
                STATUS  mandatory
                DESCRIPTION "BRANCH 11 KVAR"
                              ::= { panelboard2 811 }

pb2-branch12-kvar
                OBJECT-TYPE
                SYNTAX  INTEGER
                ACCESS  read-only
                STATUS  mandatory
                DESCRIPTION "BRANCH 12 KVAR"
                              ::= { panelboard2 812 }

pb2-branch13-kvar
                OBJECT-TYPE
                SYNTAX  INTEGER
                ACCESS  read-only
                STATUS  mandatory
                DESCRIPTION "BRANCH 13 KVAR"
                              ::= { panelboard2 813 }

pb2-branch14-kvar
                OBJECT-TYPE
                SYNTAX  INTEGER
                ACCESS  read-only
                STATUS  mandatory
                DESCRIPTION "BRANCH 14 KVAR"
                              ::= { panelboard2 814 }

pb2-branch15-kvar
                OBJECT-TYPE
                SYNTAX  INTEGER
                ACCESS  read-only
                STATUS  mandatory
                DESCRIPTION "BRANCH 15 KVAR"
                              ::= { panelboard2 815 }

pb2-branch16-kvar
                OBJECT-TYPE
                SYNTAX  INTEGER
                ACCESS  read-only
                STATUS  mandatory
                DESCRIPTION "BRANCH 16 KVAR"
                              ::= { panelboard2 816 }

pb2-branch17-kvar
                OBJECT-TYPE
                SYNTAX  INTEGER
                ACCESS  read-only
                STATUS  mandatory
                DESCRIPTION "BRANCH 17 KVAR"
                              ::= { panelboard2 817 }

pb2-branch18-kvar
                OBJECT-TYPE
                SYNTAX  INTEGER
                ACCESS  read-only
                STATUS  mandatory
                DESCRIPTION "BRANCH 18 KVAR"
                              ::= { panelboard2 818 }

pb2-branch19-kvar
                OBJECT-TYPE
                SYNTAX  INTEGER
                ACCESS  read-only
                STATUS  mandatory
                DESCRIPTION "BRANCH 19 KVAR"
                              ::= { panelboard2 819 }

pb2-branch20-kvar
                OBJECT-TYPE
                SYNTAX  INTEGER
                ACCESS  read-only
                STATUS  mandatory
                DESCRIPTION "BRANCH 20 KVAR"
                              ::= { panelboard2 820 }

pb2-branch21-kvar
                OBJECT-TYPE
                SYNTAX  INTEGER
                ACCESS  read-only
                STATUS  mandatory
                DESCRIPTION "BRANCH 21 KVAR"
                              ::= { panelboard2 821 }

pb2-branch22-kvar
                OBJECT-TYPE
                SYNTAX  INTEGER
                ACCESS  read-only
                STATUS  mandatory
                DESCRIPTION "BRANCH 22 KVAR"
                              ::= { panelboard2 822 }

pb2-branch23-kvar
                OBJECT-TYPE
                SYNTAX  INTEGER
                ACCESS  read-only
                STATUS  mandatory
                DESCRIPTION "BRANCH 23 KVAR"
                              ::= { panelboard2 823 }

pb2-branch24-kvar
                OBJECT-TYPE
                SYNTAX  INTEGER
                ACCESS  read-only
                STATUS  mandatory
                DESCRIPTION "BRANCH 24 KVAR"
                              ::= { panelboard2 824 }

pb2-branch25-kvar
                OBJECT-TYPE
                SYNTAX  INTEGER
                ACCESS  read-only
                STATUS  mandatory
                DESCRIPTION "BRANCH 25 KVAR"
                              ::= { panelboard2 825 }

pb2-branch26-kvar
                OBJECT-TYPE
                SYNTAX  INTEGER
                ACCESS  read-only
                STATUS  mandatory
                DESCRIPTION "BRANCH 26 KVAR"
                              ::= { panelboard2 826 }

pb2-branch27-kvar
                OBJECT-TYPE
                SYNTAX  INTEGER
                ACCESS  read-only
                STATUS  mandatory
                DESCRIPTION "BRANCH 27 KVAR"
                              ::= { panelboard2 827 }

pb2-branch28-kvar
                OBJECT-TYPE
                SYNTAX  INTEGER
                ACCESS  read-only
                STATUS  mandatory
                DESCRIPTION "BRANCH 28 KVAR"
                              ::= { panelboard2 828 }

pb2-branch29-kvar
                OBJECT-TYPE
                SYNTAX  INTEGER
                ACCESS  read-only
                STATUS  mandatory
                DESCRIPTION "BRANCH 29 KVAR"
                              ::= { panelboard2 829 }

pb2-branch30-kvar
                OBJECT-TYPE
                SYNTAX  INTEGER
                ACCESS  read-only
                STATUS  mandatory
                DESCRIPTION "BRANCH 30 KVAR"
                              ::= { panelboard2 830 }

pb2-branch31-kvar
                OBJECT-TYPE
                SYNTAX  INTEGER
                ACCESS  read-only
                STATUS  mandatory
                DESCRIPTION "BRANCH 31 KVAR"
                              ::= { panelboard2 831 }

pb2-branch32-kvar
                OBJECT-TYPE
                SYNTAX  INTEGER
                ACCESS  read-only
                STATUS  mandatory
                DESCRIPTION "BRANCH 32 KVAR"
                              ::= { panelboard2 832 }

pb2-branch33-kvar
                OBJECT-TYPE
                SYNTAX  INTEGER
                ACCESS  read-only
                STATUS  mandatory
                DESCRIPTION "BRANCH 33 KVAR"
                              ::= { panelboard2 833 }

pb2-branch34-kvar
                OBJECT-TYPE
                SYNTAX  INTEGER
                ACCESS  read-only
                STATUS  mandatory
                DESCRIPTION "BRANCH 34 KVAR"
                              ::= { panelboard2 834 }

pb2-branch35-kvar
                OBJECT-TYPE
                SYNTAX  INTEGER
                ACCESS  read-only
                STATUS  mandatory
                DESCRIPTION "BRANCH 35 KVAR"
                              ::= { panelboard2 835 }

pb2-branch36-kvar
                OBJECT-TYPE
                SYNTAX  INTEGER
                ACCESS  read-only
                STATUS  mandatory
                DESCRIPTION "BRANCH 36 KVAR"
                              ::= { panelboard2 836 }

pb2-branch1-pf
                OBJECT-TYPE
                SYNTAX  INTEGER
                ACCESS  read-only
                STATUS  mandatory
                DESCRIPTION "BRANCH 1 PF
                                    Note for all PF: 1000 = 1.000"
                              ::= { panelboard2 901 }

pb2-branch2-pf
                OBJECT-TYPE
                SYNTAX  INTEGER
                ACCESS  read-only
                STATUS  mandatory
                DESCRIPTION "BRANCH 2 PF"
                              ::= { panelboard2 902 }

pb2-branch3-pf
                OBJECT-TYPE
                SYNTAX  INTEGER
                ACCESS  read-only
                STATUS  mandatory
                DESCRIPTION "BRANCH 3 PF"
                              ::= { panelboard2 903 }

pb2-branch4-pf
                OBJECT-TYPE
                SYNTAX  INTEGER
                ACCESS  read-only
                STATUS  mandatory
                DESCRIPTION "BRANCH 4 PF"
                              ::= { panelboard2 904 }

pb2-branch5-pf
                OBJECT-TYPE
                SYNTAX  INTEGER
                ACCESS  read-only
                STATUS  mandatory
                DESCRIPTION "BRANCH 5 PF"
                              ::= { panelboard2 905 }

pb2-branch6-pf
                OBJECT-TYPE
                SYNTAX  INTEGER
                ACCESS  read-only
                STATUS  mandatory
                DESCRIPTION "BRANCH 6 PF"
                              ::= { panelboard2 906 }

pb2-branch7-pf
                OBJECT-TYPE
                SYNTAX  INTEGER
                ACCESS  read-only
                STATUS  mandatory
                DESCRIPTION "BRANCH 7 PF"
                              ::= { panelboard2 907 }

pb2-branch8-pf
                OBJECT-TYPE
                SYNTAX  INTEGER
                ACCESS  read-only
                STATUS  mandatory
                DESCRIPTION "BRANCH 8 PF"
                              ::= { panelboard2 908 }

pb2-branch9-pf
                OBJECT-TYPE
                SYNTAX  INTEGER
                ACCESS  read-only
                STATUS  mandatory
                DESCRIPTION "BRANCH 9 PF"
                              ::= { panelboard2 909 }

pb2-branch10-pf
                OBJECT-TYPE
                SYNTAX  INTEGER
                ACCESS  read-only
                STATUS  mandatory
                DESCRIPTION "BRANCH 10 PF"
                              ::= { panelboard2 910 }

pb2-branch11-pf
                OBJECT-TYPE
                SYNTAX  INTEGER
                ACCESS  read-only
                STATUS  mandatory
                DESCRIPTION "BRANCH 11 PF"
                              ::= { panelboard2 911 }

pb2-branch12-pf
                OBJECT-TYPE
                SYNTAX  INTEGER
                ACCESS  read-only
                STATUS  mandatory
                DESCRIPTION "BRANCH 12 PF"
                              ::= { panelboard2 912 }

pb2-branch13-pf
                OBJECT-TYPE
                SYNTAX  INTEGER
                ACCESS  read-only
                STATUS  mandatory
                DESCRIPTION "BRANCH 13 PF"
                              ::= { panelboard2 913 }

pb2-branch14-pf
                OBJECT-TYPE
                SYNTAX  INTEGER
                ACCESS  read-only
                STATUS  mandatory
                DESCRIPTION "BRANCH 14 PF"
                              ::= { panelboard2 914 }

pb2-branch15-pf
                OBJECT-TYPE
                SYNTAX  INTEGER
                ACCESS  read-only
                STATUS  mandatory
                DESCRIPTION "BRANCH 15 PF"
                              ::= { panelboard2 915 }

pb2-branch16-pf
                OBJECT-TYPE
                SYNTAX  INTEGER
                ACCESS  read-only
                STATUS  mandatory
                DESCRIPTION "BRANCH 16 PF"
                              ::= { panelboard2 916 }

pb2-branch17-pf
                OBJECT-TYPE
                SYNTAX  INTEGER
                ACCESS  read-only
                STATUS  mandatory
                DESCRIPTION "BRANCH 17 PF"
                              ::= { panelboard2 917 }

pb2-branch18-pf
                OBJECT-TYPE
                SYNTAX  INTEGER
                ACCESS  read-only
                STATUS  mandatory
                DESCRIPTION "BRANCH 18 PF"
                              ::= { panelboard2 918 }

pb2-branch19-pf
                OBJECT-TYPE
                SYNTAX  INTEGER
                ACCESS  read-only
                STATUS  mandatory
                DESCRIPTION "BRANCH 19 PF"
                              ::= { panelboard2 919 }

pb2-branch20-pf
                OBJECT-TYPE
                SYNTAX  INTEGER
                ACCESS  read-only
                STATUS  mandatory
                DESCRIPTION "BRANCH 20 PF"
                              ::= { panelboard2 920 }

pb2-branch21-pf
                OBJECT-TYPE
                SYNTAX  INTEGER
                ACCESS  read-only
                STATUS  mandatory
                DESCRIPTION "BRANCH 21 PF"
                              ::= { panelboard2 921 }

pb2-branch22-pf
                OBJECT-TYPE
                SYNTAX  INTEGER
                ACCESS  read-only
                STATUS  mandatory
                DESCRIPTION "BRANCH 22 PF"
                              ::= { panelboard2 922 }

pb2-branch23-pf
                OBJECT-TYPE
                SYNTAX  INTEGER
                ACCESS  read-only
                STATUS  mandatory
                DESCRIPTION "BRANCH 23 PF"
                              ::= { panelboard2 923 }

pb2-branch24-pf
                OBJECT-TYPE
                SYNTAX  INTEGER
                ACCESS  read-only
                STATUS  mandatory
                DESCRIPTION "BRANCH 24 PF"
                              ::= { panelboard2 924 }

pb2-branch25-pf
                OBJECT-TYPE
                SYNTAX  INTEGER
                ACCESS  read-only
                STATUS  mandatory
                DESCRIPTION "BRANCH 25 PF"
                              ::= { panelboard2 925 }

pb2-branch26-pf
                OBJECT-TYPE
                SYNTAX  INTEGER
                ACCESS  read-only
                STATUS  mandatory
                DESCRIPTION "BRANCH 26 PF"
                              ::= { panelboard2 926 }

pb2-branch27-pf
                OBJECT-TYPE
                SYNTAX  INTEGER
                ACCESS  read-only
                STATUS  mandatory
                DESCRIPTION "BRANCH 27 PF"
                              ::= { panelboard2 927 }

pb2-branch28-pf
                OBJECT-TYPE
                SYNTAX  INTEGER
                ACCESS  read-only
                STATUS  mandatory
                DESCRIPTION "BRANCH 28 PF"
                              ::= { panelboard2 928 }

pb2-branch29-pf
                OBJECT-TYPE
                SYNTAX  INTEGER
                ACCESS  read-only
                STATUS  mandatory
                DESCRIPTION "BRANCH 29 PF"
                              ::= { panelboard2 929 }

pb2-branch30-pf
                OBJECT-TYPE
                SYNTAX  INTEGER
                ACCESS  read-only
                STATUS  mandatory
                DESCRIPTION "BRANCH 30 PF"
                              ::= { panelboard2 930 }

pb2-branch31-pf
                OBJECT-TYPE
                SYNTAX  INTEGER
                ACCESS  read-only
                STATUS  mandatory
                DESCRIPTION "BRANCH 31 PF"
                              ::= { panelboard2 931 }

pb2-branch32-pf
                OBJECT-TYPE
                SYNTAX  INTEGER
                ACCESS  read-only
                STATUS  mandatory
                DESCRIPTION "BRANCH 32 PF"
                              ::= { panelboard2 932 }

pb2-branch33-pf
                OBJECT-TYPE
                SYNTAX  INTEGER
                ACCESS  read-only
                STATUS  mandatory
                DESCRIPTION "BRANCH 33 PF"
                              ::= { panelboard2 933 }

pb2-branch34-pf
                OBJECT-TYPE
                SYNTAX  INTEGER
                ACCESS  read-only
                STATUS  mandatory
                DESCRIPTION "BRANCH 34 PF"
                              ::= { panelboard2 934 }

pb2-branch35-pf
                OBJECT-TYPE
                SYNTAX  INTEGER
                ACCESS  read-only
                STATUS  mandatory
                DESCRIPTION "BRANCH 35 PF"
                              ::= { panelboard2 935 }

pb2-branch36-pf
                OBJECT-TYPE
                SYNTAX  INTEGER
                ACCESS  read-only
                STATUS  mandatory
                DESCRIPTION "BRANCH 36 PF"
                              ::= { panelboard2 936 }

pb2-branch1-pf-sign
                OBJECT-TYPE
                SYNTAX  INTEGER
                ACCESS  read-only
                STATUS  mandatory
                DESCRIPTION "BRANCH 1 PF Sign
                                    Note for all PF sign: set = leading, reset = lagging"
                              ::= { panelboard2 1001 }

pb2-branch2-pf-sign
                OBJECT-TYPE
                SYNTAX  INTEGER
                ACCESS  read-only
                STATUS  mandatory
                DESCRIPTION "BRANCH 2 PF Sign"
                              ::= { panelboard2 1002 }

pb2-branch3-pf-sign
                OBJECT-TYPE
                SYNTAX  INTEGER
                ACCESS  read-only
                STATUS  mandatory
                DESCRIPTION "BRANCH 3 PF Sign"
                              ::= { panelboard2 1003 }

pb2-branch4-pf-sign
                OBJECT-TYPE
                SYNTAX  INTEGER
                ACCESS  read-only
                STATUS  mandatory
                DESCRIPTION "BRANCH 4 PF Sign"
                              ::= { panelboard2 1004 }

pb2-branch5-pf-sign
                OBJECT-TYPE
                SYNTAX  INTEGER
                ACCESS  read-only
                STATUS  mandatory
                DESCRIPTION "BRANCH 5 PF Sign"
                              ::= { panelboard2 1005 }

pb2-branch6-pf-sign
                OBJECT-TYPE
                SYNTAX  INTEGER
                ACCESS  read-only
                STATUS  mandatory
                DESCRIPTION "BRANCH 6 PF Sign"
                              ::= { panelboard2 1006 }

pb2-branch7-pf-sign
                OBJECT-TYPE
                SYNTAX  INTEGER
                ACCESS  read-only
                STATUS  mandatory
                DESCRIPTION "BRANCH 7 PF Sign"
                              ::= { panelboard2 1007 }

pb2-branch8-pf-sign
                OBJECT-TYPE
                SYNTAX  INTEGER
                ACCESS  read-only
                STATUS  mandatory
                DESCRIPTION "BRANCH 8 PF Sign"
                              ::= { panelboard2 1008 }

pb2-branch9-pf-sign
                OBJECT-TYPE
                SYNTAX  INTEGER
                ACCESS  read-only
                STATUS  mandatory
                DESCRIPTION "BRANCH 9 PF Sign"
                              ::= { panelboard2 1009 }

pb2-branch10-pf-sign
                OBJECT-TYPE
                SYNTAX  INTEGER
                ACCESS  read-only
                STATUS  mandatory
                DESCRIPTION "BRANCH 10 PF Sign"
                              ::= { panelboard2 1010 }

pb2-branch11-pf-sign
                OBJECT-TYPE
                SYNTAX  INTEGER
                ACCESS  read-only
                STATUS  mandatory
                DESCRIPTION "BRANCH 11 PF Sign"
                              ::= { panelboard2 1011 }

pb2-branch12-pf-sign
                OBJECT-TYPE
                SYNTAX  INTEGER
                ACCESS  read-only
                STATUS  mandatory
                DESCRIPTION "BRANCH 12 PF Sign"
                              ::= { panelboard2 1012 }

pb2-branch13-pf-sign
                OBJECT-TYPE
                SYNTAX  INTEGER
                ACCESS  read-only
                STATUS  mandatory
                DESCRIPTION "BRANCH 13 PF Sign"
                              ::= { panelboard2 1013 }

pb2-branch14-pf-sign
                OBJECT-TYPE
                SYNTAX  INTEGER
                ACCESS  read-only
                STATUS  mandatory
                DESCRIPTION "BRANCH 14 PF Sign"
                              ::= { panelboard2 1014 }

pb2-branch15-pf-sign
                OBJECT-TYPE
                SYNTAX  INTEGER
                ACCESS  read-only
                STATUS  mandatory
                DESCRIPTION "BRANCH 15 PF Sign"
                              ::= { panelboard2 1015 }

pb2-branch16-pf-sign
                OBJECT-TYPE
                SYNTAX  INTEGER
                ACCESS  read-only
                STATUS  mandatory
                DESCRIPTION "BRANCH 16 PF Sign"
                              ::= { panelboard2 1016 }

pb2-branch17-pf-sign
                OBJECT-TYPE
                SYNTAX  INTEGER
                ACCESS  read-only
                STATUS  mandatory
                DESCRIPTION "BRANCH 17 PF Sign"
                              ::= { panelboard2 1017 }

pb2-branch18-pf-sign
                OBJECT-TYPE
                SYNTAX  INTEGER
                ACCESS  read-only
                STATUS  mandatory
                DESCRIPTION "BRANCH 18 PF Sign"
                              ::= { panelboard2 1018 }

pb2-branch19-pf-sign
                OBJECT-TYPE
                SYNTAX  INTEGER
                ACCESS  read-only
                STATUS  mandatory
                DESCRIPTION "BRANCH 19 PF Sign"
                              ::= { panelboard2 1019 }

pb2-branch20-pf-sign
                OBJECT-TYPE
                SYNTAX  INTEGER
                ACCESS  read-only
                STATUS  mandatory
                DESCRIPTION "BRANCH 20 PF Sign"
                              ::= { panelboard2 1020 }

pb2-branch21-pf-sign
                OBJECT-TYPE
                SYNTAX  INTEGER
                ACCESS  read-only
                STATUS  mandatory
                DESCRIPTION "BRANCH 21 PF Sign"
                              ::= { panelboard2 1021 }

pb2-branch22-pf-sign
                OBJECT-TYPE
                SYNTAX  INTEGER
                ACCESS  read-only
                STATUS  mandatory
                DESCRIPTION "BRANCH 22 PF Sign"
                              ::= { panelboard2 1022 }

pb2-branch23-pf-sign
                OBJECT-TYPE
                SYNTAX  INTEGER
                ACCESS  read-only
                STATUS  mandatory
                DESCRIPTION "BRANCH 23 PF Sign"
                              ::= { panelboard2 1023 }

pb2-branch24-pf-sign
                OBJECT-TYPE
                SYNTAX  INTEGER
                ACCESS  read-only
                STATUS  mandatory
                DESCRIPTION "BRANCH 24 PF Sign"
                              ::= { panelboard2 1024 }

pb2-branch25-pf-sign
                OBJECT-TYPE
                SYNTAX  INTEGER
                ACCESS  read-only
                STATUS  mandatory
                DESCRIPTION "BRANCH 25 PF Sign"
                              ::= { panelboard2 1025 }

pb2-branch26-pf-sign
                OBJECT-TYPE
                SYNTAX  INTEGER
                ACCESS  read-only
                STATUS  mandatory
                DESCRIPTION "BRANCH 26 PF Sign"
                              ::= { panelboard2 1026 }

pb2-branch27-pf-sign
                OBJECT-TYPE
                SYNTAX  INTEGER
                ACCESS  read-only
                STATUS  mandatory
                DESCRIPTION "BRANCH 27 PF Sign"
                              ::= { panelboard2 1027 }

pb2-branch28-pf-sign
                OBJECT-TYPE
                SYNTAX  INTEGER
                ACCESS  read-only
                STATUS  mandatory
                DESCRIPTION "BRANCH 28 PF Sign"
                              ::= { panelboard2 1028 }

pb2-branch29-pf-sign
                OBJECT-TYPE
                SYNTAX  INTEGER
                ACCESS  read-only
                STATUS  mandatory
                DESCRIPTION "BRANCH 29 PF Sign"
                              ::= { panelboard2 1029 }

pb2-branch30-pf-sign
                OBJECT-TYPE
                SYNTAX  INTEGER
                ACCESS  read-only
                STATUS  mandatory
                DESCRIPTION "BRANCH 30 PF Sign"
                              ::= { panelboard2 1030 }

pb2-branch31-pf-sign
                OBJECT-TYPE
                SYNTAX  INTEGER
                ACCESS  read-only
                STATUS  mandatory
                DESCRIPTION "BRANCH 31 PF Sign"
                              ::= { panelboard2 1031 }

pb2-branch32-pf-sign
                OBJECT-TYPE
                SYNTAX  INTEGER
                ACCESS  read-only
                STATUS  mandatory
                DESCRIPTION "BRANCH 32 PF Sign"
                              ::= { panelboard2 1032 }

pb2-branch33-pf-sign
                OBJECT-TYPE
                SYNTAX  INTEGER
                ACCESS  read-only
                STATUS  mandatory
                DESCRIPTION "BRANCH 33 PF Sign"
                              ::= { panelboard2 1033 }

pb2-branch34-pf-sign
                OBJECT-TYPE
                SYNTAX  INTEGER
                ACCESS  read-only
                STATUS  mandatory
                DESCRIPTION "BRANCH 34 PF Sign"
                              ::= { panelboard2 1034 }

pb2-branch35-pf-sign
                OBJECT-TYPE
                SYNTAX  INTEGER
                ACCESS  read-only
                STATUS  mandatory
                DESCRIPTION "BRANCH 35 PF Sign"
                              ::= { panelboard2 1035 }

pb2-branch36-pf-sign
                OBJECT-TYPE
                SYNTAX  INTEGER
                ACCESS  read-only
                STATUS  mandatory
                DESCRIPTION "BRANCH 36 PF Sign"
                              ::= { panelboard2 1036 }

pb2-branch1-kwh-low
                OBJECT-TYPE
                SYNTAX  INTEGER
                ACCESS  read-write
                STATUS  mandatory
                DESCRIPTION "BRANCH 1 KWH Low
                                    Note for all KWH: 100 = 100 KWH
                Valus is 32 bits (High * 65536) + Low"
                              ::= { panelboard2 1101 }

pb2-branch1-kwh-high
                OBJECT-TYPE
                SYNTAX  INTEGER
                ACCESS  read-write
                STATUS  mandatory
                DESCRIPTION "BRANCH 1 KWH High"
                              ::= { panelboard2 1102 }

pb2-branch2-kwh-low
                OBJECT-TYPE
                SYNTAX  INTEGER
                ACCESS  read-write
                STATUS  mandatory
                DESCRIPTION "BRANCH 2 KWH Low"
                              ::= { panelboard2 1103 }

pb2-branch2-kwh-high
                OBJECT-TYPE
                SYNTAX  INTEGER
                ACCESS  read-write
                STATUS  mandatory
                DESCRIPTION "BRANCH 2 KWH High"
                              ::= { panelboard2 1104 }

pb2-branch3-kwh-low
                OBJECT-TYPE
                SYNTAX  INTEGER
                ACCESS  read-write
                STATUS  mandatory
                DESCRIPTION "BRANCH 3 KWH Low"
                              ::= { panelboard2 1105 }

pb2-branch3-kwh-high
                OBJECT-TYPE
                SYNTAX  INTEGER
                ACCESS  read-write
                STATUS  mandatory
                DESCRIPTION "BRANCH 3 KWH High"
                              ::= { panelboard2 1106 }

pb2-branch4-kwh-low
                OBJECT-TYPE
                SYNTAX  INTEGER
                ACCESS  read-write
                STATUS  mandatory
                DESCRIPTION "BRANCH 4 KWH Low"
                              ::= { panelboard2 1107 }

pb2-branch4-kwh-high
                OBJECT-TYPE
                SYNTAX  INTEGER
                ACCESS  read-write
                STATUS  mandatory
                DESCRIPTION "BRANCH 4 KWH High"
                              ::= { panelboard2 1108 }

pb2-branch5-kwh-low
                OBJECT-TYPE
                SYNTAX  INTEGER
                ACCESS  read-write
                STATUS  mandatory
                DESCRIPTION "BRANCH 5 KWH Low"
                              ::= { panelboard2 1109 }

pb2-branch5-kwh-high
                OBJECT-TYPE
                SYNTAX  INTEGER
                ACCESS  read-write
                STATUS  mandatory
                DESCRIPTION "BRANCH 5 KWH High"
                              ::= { panelboard2 1110 }

pb2-branch6-kwh-low
                OBJECT-TYPE
                SYNTAX  INTEGER
                ACCESS  read-write
                STATUS  mandatory
                DESCRIPTION "BRANCH 6 KWH Low"
                              ::= { panelboard2 1111 }

pb2-branch6-kwh-high
                OBJECT-TYPE
                SYNTAX  INTEGER
                ACCESS  read-write
                STATUS  mandatory
                DESCRIPTION "BRANCH 6 KWH High"
                              ::= { panelboard2 1112 }

pb2-branch7-kwh-low
                OBJECT-TYPE
                SYNTAX  INTEGER
                ACCESS  read-write
                STATUS  mandatory
                DESCRIPTION "BRANCH 7 KWH Low"
                              ::= { panelboard2 1113 }

pb2-branch7-kwh-high
                OBJECT-TYPE
                SYNTAX  INTEGER
                ACCESS  read-write
                STATUS  mandatory
                DESCRIPTION "BRANCH 7 KWH High"
                              ::= { panelboard2 1114 }

pb2-branch8-kwh-low
                OBJECT-TYPE
                SYNTAX  INTEGER
                ACCESS  read-write
                STATUS  mandatory
                DESCRIPTION "BRANCH 8 KWH Low"
                              ::= { panelboard2 1115 }

pb2-branch8-kwh-high
                OBJECT-TYPE
                SYNTAX  INTEGER
                ACCESS  read-write
                STATUS  mandatory
                DESCRIPTION "BRANCH 8 KWH High"
                              ::= { panelboard2 1116 }

pb2-branch9-kwh-low
                OBJECT-TYPE
                SYNTAX  INTEGER
                ACCESS  read-write
                STATUS  mandatory
                DESCRIPTION "BRANCH 9 KWH Low"
                              ::= { panelboard2 1117 }

pb2-branch9-kwh-high
                OBJECT-TYPE
                SYNTAX  INTEGER
                ACCESS  read-write
                STATUS  mandatory
                DESCRIPTION "BRANCH 9 KWH High"
                              ::= { panelboard2 1118 }

pb2-branch10-kwh-low
                OBJECT-TYPE
                SYNTAX  INTEGER
                ACCESS  read-write
                STATUS  mandatory
                DESCRIPTION "BRANCH 10 KWH Low"
                              ::= { panelboard2 1119 }

pb2-branch10-kwh-high
                OBJECT-TYPE
                SYNTAX  INTEGER
                ACCESS  read-write
                STATUS  mandatory
                DESCRIPTION "BRANCH 10 KWH High"
                              ::= { panelboard2 1120 }

pb2-branch11-kwh-low
                OBJECT-TYPE
                SYNTAX  INTEGER
                ACCESS  read-write
                STATUS  mandatory
                DESCRIPTION "BRANCH 11 KWH Low"
                              ::= { panelboard2 1121 }

pb2-branch11-kwh-high
                OBJECT-TYPE
                SYNTAX  INTEGER
                ACCESS  read-write
                STATUS  mandatory
                DESCRIPTION "BRANCH 11 KWH High"
                              ::= { panelboard2 1122 }

pb2-branch12-kwh-low
                OBJECT-TYPE
                SYNTAX  INTEGER
                ACCESS  read-write
                STATUS  mandatory
                DESCRIPTION "BRANCH 12 KWH Low"
                              ::= { panelboard2 1123 }

pb2-branch12-kwh-high
                OBJECT-TYPE
                SYNTAX  INTEGER
                ACCESS  read-write
                STATUS  mandatory
                DESCRIPTION "BRANCH 12 KWH High"
                              ::= { panelboard2 1124 }

pb2-branch13-kwh-low
                OBJECT-TYPE
                SYNTAX  INTEGER
                ACCESS  read-write
                STATUS  mandatory
                DESCRIPTION "BRANCH 13 KWH Low"
                              ::= { panelboard2 1125 }

pb2-branch13-kwh-high
                OBJECT-TYPE
                SYNTAX  INTEGER
                ACCESS  read-write
                STATUS  mandatory
                DESCRIPTION "BRANCH 13 KWH High"
                              ::= { panelboard2 1126 }

pb2-branch14-kwh-low
                OBJECT-TYPE
                SYNTAX  INTEGER
                ACCESS  read-write
                STATUS  mandatory
                DESCRIPTION "BRANCH 14 KWH Low"
                              ::= { panelboard2 1127 }

pb2-branch14-kwh-high
                OBJECT-TYPE
                SYNTAX  INTEGER
                ACCESS  read-write
                STATUS  mandatory
                DESCRIPTION "BRANCH 14 KWH High"
                              ::= { panelboard2 1128 }

pb2-branch15-kwh-low
                OBJECT-TYPE
                SYNTAX  INTEGER
                ACCESS  read-write
                STATUS  mandatory
                DESCRIPTION "BRANCH 15 KWH Low"
                              ::= { panelboard2 1129 }

pb2-branch15-kwh-high
                OBJECT-TYPE
                SYNTAX  INTEGER
                ACCESS  read-write
                STATUS  mandatory
                DESCRIPTION "BRANCH 15 KWH High"
                                ::= { panelboard2 1130 }

pb2-branch16-kwh-low
                OBJECT-TYPE
                SYNTAX  INTEGER
                ACCESS  read-write
                STATUS  mandatory
                DESCRIPTION "BRANCH 16 KWH Low"
                              ::= { panelboard2 1131 }

pb2-branch16-kwh-high
                OBJECT-TYPE
                SYNTAX  INTEGER
                ACCESS  read-write
                STATUS  mandatory
                DESCRIPTION "BRANCH 16 KWH High"
                              ::= { panelboard2 1132 }

pb2-branch17-kwh-low
                OBJECT-TYPE
                SYNTAX  INTEGER
                ACCESS  read-write
                STATUS  mandatory
                DESCRIPTION "BRANCH 17 KWH Low"
                              ::= { panelboard2 1133 }

pb2-branch17-kwh-high
                OBJECT-TYPE
                SYNTAX  INTEGER
                ACCESS  read-write
                STATUS  mandatory
                DESCRIPTION "BRANCH 17 KWH High"
                              ::= { panelboard2 1134 }

pb2-branch18-kwh-low
                OBJECT-TYPE
                SYNTAX  INTEGER
                ACCESS  read-write
                STATUS  mandatory
                DESCRIPTION "BRANCH 18 KWH Low"
                              ::= { panelboard2 1135 }

pb2-branch18-kwh-high
                OBJECT-TYPE
                SYNTAX  INTEGER
                ACCESS  read-write
                STATUS  mandatory
                DESCRIPTION "BRANCH 18 KWH High"
                              ::= { panelboard2 1136 }

pb2-branch19-kwh-low
                OBJECT-TYPE
                SYNTAX  INTEGER
                ACCESS  read-write
                STATUS  mandatory
                DESCRIPTION "BRANCH 19KWH Low"
                              ::= { panelboard2 1137 }

pb2-branch19-kwh-high
                OBJECT-TYPE
                SYNTAX  INTEGER
                ACCESS  read-write
                STATUS  mandatory
                DESCRIPTION "BRANCH 19 KWH High"
                              ::= { panelboard2 1138 }

pb2-branch20-kwh-low
                OBJECT-TYPE
                SYNTAX  INTEGER
                ACCESS  read-write
                STATUS  mandatory
                DESCRIPTION "BRANCH 20 KWH Low"
                              ::= { panelboard2 1139 }

pb2-branch20-kwh-high
                OBJECT-TYPE
                SYNTAX  INTEGER
                ACCESS  read-write
                STATUS  mandatory
                DESCRIPTION "BRANCH 20 KWH High"
                              ::= { panelboard2 1140 }

pb2-branch21-kwh-low
                OBJECT-TYPE
                SYNTAX  INTEGER
                ACCESS  read-write
                STATUS  mandatory
                DESCRIPTION "BRANCH 21 KWH Low"
                              ::= { panelboard2 1141 }

pb2-branch21-kwh-high
                OBJECT-TYPE
                SYNTAX  INTEGER
                ACCESS  read-write
                STATUS  mandatory
                DESCRIPTION "BRANCH 21 KWH High"
                              ::= { panelboard2 1142 }

pb2-branch22-kwh-low
                OBJECT-TYPE
                SYNTAX  INTEGER
                ACCESS  read-write
                STATUS  mandatory
                DESCRIPTION "BRANCH 22 KWH Low"
                              ::= { panelboard2 1143 }

pb2-branch22-kwh-high
                OBJECT-TYPE
                SYNTAX  INTEGER
                ACCESS  read-write
                STATUS  mandatory
                DESCRIPTION "BRANCH 22 KWH High"
                              ::= { panelboard2 1144 }

pb2-branch23-kwh-low
                OBJECT-TYPE
                SYNTAX  INTEGER
                ACCESS  read-write
                STATUS  mandatory
                DESCRIPTION "BRANCH 23 KWH Low"
                              ::= { panelboard2 1145 }

pb2-branch23-kwh-high
                OBJECT-TYPE
                SYNTAX  INTEGER
                ACCESS  read-write
                STATUS  mandatory
                DESCRIPTION "BRANCH 23 KWH High"
                              ::= { panelboard2 1146 }

pb2-branch24-kwh-low
                OBJECT-TYPE
                SYNTAX  INTEGER
                ACCESS  read-write
                STATUS  mandatory
                DESCRIPTION "BRANCH 24 KWH Low"
                              ::= { panelboard2 1147 }

pb2-branch24-kwh-high
                OBJECT-TYPE
                SYNTAX  INTEGER
                ACCESS  read-write
                STATUS  mandatory
                DESCRIPTION "BRANCH 24 KWH High"
                              ::= { panelboard2 1148 }

pb2-branch25-kwh-low
                OBJECT-TYPE
                SYNTAX  INTEGER
                ACCESS  read-write
                STATUS  mandatory
                DESCRIPTION "BRANCH 25 KWH Low"
                              ::= { panelboard2 1149 }

pb2-branch25-kwh-high
                OBJECT-TYPE
                SYNTAX  INTEGER
                ACCESS  read-write
                STATUS  mandatory
                DESCRIPTION "BRANCH 25 KWH High"
                              ::= { panelboard2 1150 }

pb2-branch26-kwh-low
                OBJECT-TYPE
                SYNTAX  INTEGER
                ACCESS  read-write
                STATUS  mandatory
                DESCRIPTION "BRANCH 26 KWH Low"
                              ::= { panelboard2 1151 }

pb2-branch26-kwh-high
                OBJECT-TYPE
                SYNTAX  INTEGER
                ACCESS  read-write
                STATUS  mandatory
                DESCRIPTION "BRANCH 26 KWH High"
                              ::= { panelboard2 1152 }

pb2-branch27-kwh-low
                OBJECT-TYPE
                SYNTAX  INTEGER
                ACCESS  read-write
                STATUS  mandatory
                DESCRIPTION "BRANCH 27 KWH Low"
                              ::= { panelboard2 1153 }

pb2-branch27-kwh-high
                OBJECT-TYPE
                SYNTAX  INTEGER
                ACCESS  read-write
                STATUS  mandatory
                DESCRIPTION "BRANCH 27 KWH High"
                              ::= { panelboard2 1154 }

pb2-branch28-kwh-low
                OBJECT-TYPE
                SYNTAX  INTEGER
                ACCESS  read-write
                STATUS  mandatory
                DESCRIPTION "BRANCH 28 KWH Low"
                              ::= { panelboard2 1155 }

pb2-branch28-kwh-high
                OBJECT-TYPE
                SYNTAX  INTEGER
                ACCESS  read-write
                STATUS  mandatory
                DESCRIPTION "BRANCH 28 KWH High"
                              ::= { panelboard2 1156 }

pb2-branch29-kwh-low
                OBJECT-TYPE
                SYNTAX  INTEGER
                ACCESS  read-write
                STATUS  mandatory
                DESCRIPTION "BRANCH 29 KWH Low"
                              ::= { panelboard2 1157 }

pb2-branch29-kwh-high
                OBJECT-TYPE
                SYNTAX  INTEGER
                ACCESS  read-write
                STATUS  mandatory
                DESCRIPTION "BRANCH 29 KWH High"
                              ::= { panelboard2 1158 }

pb2-branch30-kwh-low
                OBJECT-TYPE
                SYNTAX  INTEGER
                ACCESS  read-write
                STATUS  mandatory
                DESCRIPTION "BRANCH 30 KWH Low"
                              ::= { panelboard2 1159 }

pb2-branch30-kwh-high
                OBJECT-TYPE
                SYNTAX  INTEGER
                ACCESS  read-write
                STATUS  mandatory
                DESCRIPTION "BRANCH 30 KWH High"
                                ::= { panelboard2 1160 }

pb2-branch31-kwh-low
                OBJECT-TYPE
                SYNTAX  INTEGER
                ACCESS  read-write
                STATUS  mandatory
                DESCRIPTION "BRANCH 31 KWH Low"
                              ::= { panelboard2 1161 }

pb2-branch31-kwh-high
                OBJECT-TYPE
                SYNTAX  INTEGER
                ACCESS  read-write
                STATUS  mandatory
                DESCRIPTION "BRANCH 31 KWH High"
                              ::= { panelboard2 1162 }

pb2-branch32-kwh-low
                OBJECT-TYPE
                SYNTAX  INTEGER
                ACCESS  read-write
                STATUS  mandatory
                DESCRIPTION "BRANCH 32 KWH Low"
                              ::= { panelboard2 1163 }

pb2-branch32-kwh-high
                OBJECT-TYPE
                SYNTAX  INTEGER
                ACCESS  read-write
                STATUS  mandatory
                DESCRIPTION "BRANCH 32 KWH High"
                              ::= { panelboard2 1164 }

pb2-branch33-kwh-low
                OBJECT-TYPE
                SYNTAX  INTEGER
                ACCESS  read-write
                STATUS  mandatory
                DESCRIPTION "BRANCH 33 KWH Low"
                              ::= { panelboard2 1165 }

pb2-branch33-kwh-high
                OBJECT-TYPE
                SYNTAX  INTEGER
                ACCESS  read-write
                STATUS  mandatory
                DESCRIPTION "BRANCH 33 KWH High"
                              ::= { panelboard2 1166 }

pb2-branch34-kwh-low
                OBJECT-TYPE
                SYNTAX  INTEGER
                ACCESS  read-write
                STATUS  mandatory
                DESCRIPTION "BRANCH 34 KWH Low"
                              ::= { panelboard2 1167 }

pb2-branch34-kwh-high
                OBJECT-TYPE
                SYNTAX  INTEGER
                ACCESS  read-write
                STATUS  mandatory
                DESCRIPTION "BRANCH 34 KWH High"
                              ::= { panelboard2 1168 }

pb2-branch35-kwh-low
                OBJECT-TYPE
                SYNTAX  INTEGER
                ACCESS  read-write
                STATUS  mandatory
                DESCRIPTION "BRANCH 35 KWH Low"
                              ::= { panelboard2 1169 }

pb2-branch35-kwh-high
                OBJECT-TYPE
                SYNTAX  INTEGER
                ACCESS  read-write
                STATUS  mandatory
                DESCRIPTION "BRANCH 35 KWH High"
                                ::= { panelboard2 1170 }

pb2-branch36-kwh-low
                OBJECT-TYPE
                SYNTAX  INTEGER
                ACCESS  read-write
                STATUS  mandatory
                DESCRIPTION "BRANCH 36 KWH Low"
                              ::= { panelboard2 1171 }

pb2-branch36-kwh-high
                OBJECT-TYPE
                SYNTAX  INTEGER
                ACCESS  read-write
                STATUS  mandatory
                DESCRIPTION "BRANCH 36 KWH High"
                              ::= { panelboard2 1172 }


----------------------------------------------------------------
-- BCMS traps
----------------------------------------------------------------

pb1AlarmSummary
        TRAP-TYPE
                  ENTERPRISE        socomec
                  VARIABLES          { pb1-alarm-status-nonlatching }
                  DESCRIPTION      "PB1 Alarm Summary"
                  ::= 1

pb2AlarmSummary
        TRAP-TYPE
                  ENTERPRISE        socomec
                  VARIABLES          { pb2-alarm-status-nonlatching }
                  DESCRIPTION      "PB2 Alarm Summary"
                  ::= 2

END
