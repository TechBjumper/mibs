-- file automatically created


TELDAT-TRAP-SCFW-MIB DEFINITIONS ::= BEGIN


IMPORTS
	MODULE-IDENTITY,OBJECT-TYPE,OBJECT-IDENTITY,NOTIFICATION-TYPE,Integer32,IpAddress
		FROM SNMPv2-SMI
	DisplayString
		FROM SNMPv2-TC
	telEventTraps
		FROM TELDAT-MIB;


scfwTrapsMIB MODULE-IDENTITY
    LAST-UPDATED "201401200930Z"
    ORGANIZATION "Teldat, S.A."
    CONTACT-INFO 
        "Teldat, S.A.
        Customer Service

        Postal: Parque Tecnologico de Madrid
                Tres Cantos 28760
                Madrid, SPAIN

        Tel.: +34 918 076 565

        http://www.teldat.com"
    DESCRIPTION
        "This Module Information Base file is defined for managing received
        SNMP notifications generated by the SCFW event subsystem."
    REVISION "201401200930Z"
    DESCRIPTION "Initial implementation"
        ::= { telEventTraps 189 }


scfwEventsGroup	OBJECT IDENTIFIER	::= { scfwTrapsMIB 1 }

scfwNotifications	OBJECT IDENTIFIER	::= { scfwTrapsMIB 2 }
scfwNotificationsPrefix	OBJECT IDENTIFIER	::= { scfwNotifications 0 }

scfwEventObjects1 OBJECT-IDENTITY
    STATUS current
    DESCRIPTION
        "Event SCFW.1
        TCP listen for incoming RTU's connections has not been make."
    ::= { scfwEventsGroup 1 }

scfw1-tcp-port OBJECT-TYPE
    SYNTAX Integer32
    MAX-ACCESS accessible-for-notify
    STATUS current
    DESCRIPTION
        "Parameter 'tcp-port' in event SCFW.1"
    ::= { scfwEventObjects1 1 }

scfwEventObjects2 OBJECT-IDENTITY
    STATUS current
    DESCRIPTION
        "Event SCFW.2
        TCP listen for incoming Control Centers connections has not been make."
    ::= { scfwEventsGroup 2 }

scfw2-tcp-port OBJECT-TYPE
    SYNTAX Integer32
    MAX-ACCESS accessible-for-notify
    STATUS current
    DESCRIPTION
        "Parameter 'tcp-port' in event SCFW.2"
    ::= { scfwEventObjects2 1 }

scfwEventObjects3 OBJECT-IDENTITY
    STATUS current
    DESCRIPTION
        "Event SCFW.3
        A message with LRC/CRC error has been received from Control Center."
    ::= { scfwEventsGroup 3 }

scfw3-data-leng OBJECT-TYPE
    SYNTAX Integer32
    MAX-ACCESS accessible-for-notify
    STATUS current
    DESCRIPTION
        "Parameter 'data-leng' in event SCFW.3"
    ::= { scfwEventObjects3 1 }

scfw3-cent-ip OBJECT-TYPE
    SYNTAX IpAddress
    MAX-ACCESS accessible-for-notify
    STATUS current
    DESCRIPTION
        "Parameter 'cent-ip' in event SCFW.3"
    ::= { scfwEventObjects3 2 }

scfw3-cent-port OBJECT-TYPE
    SYNTAX Integer32
    MAX-ACCESS accessible-for-notify
    STATUS current
    DESCRIPTION
        "Parameter 'cent-port' in event SCFW.3"
    ::= { scfwEventObjects3 3 }

scfwEventObjects4 OBJECT-IDENTITY
    STATUS current
    DESCRIPTION
        "Event SCFW.4
        A message with LRC/CRC error has been received from RTU."
    ::= { scfwEventsGroup 4 }

scfw4-data-leng OBJECT-TYPE
    SYNTAX Integer32
    MAX-ACCESS accessible-for-notify
    STATUS current
    DESCRIPTION
        "Parameter 'data-leng' in event SCFW.4"
    ::= { scfwEventObjects4 1 }

scfw4-rtu-ip OBJECT-TYPE
    SYNTAX IpAddress
    MAX-ACCESS accessible-for-notify
    STATUS current
    DESCRIPTION
        "Parameter 'rtu-ip' in event SCFW.4"
    ::= { scfwEventObjects4 2 }

scfw4-rtu-port OBJECT-TYPE
    SYNTAX Integer32
    MAX-ACCESS accessible-for-notify
    STATUS current
    DESCRIPTION
        "Parameter 'rtu-port' in event SCFW.4"
    ::= { scfwEventObjects4 3 }

scfwEventObjects5 OBJECT-IDENTITY
    STATUS current
    DESCRIPTION
        "Event SCFW.5
        TCP session to direcction especified not found when an event occur."
    ::= { scfwEventsGroup 5 }

scfw5-directon OBJECT-TYPE
    SYNTAX DisplayString
    MAX-ACCESS accessible-for-notify
    STATUS current
    DESCRIPTION
        "Parameter 'directon' in event SCFW.5"
    ::= { scfwEventObjects5 1 }

scfw5-event-load OBJECT-TYPE
    SYNTAX Integer32
    MAX-ACCESS accessible-for-notify
    STATUS current
    DESCRIPTION
        "Parameter 'event-load' in event SCFW.5"
    ::= { scfwEventObjects5 2 }

scfwEventObjects6 OBJECT-IDENTITY
    STATUS current
    DESCRIPTION
        "Event SCFW.6
        Addres received from Control Center is not included in configuration
        registers list."
    ::= { scfwEventsGroup 6 }

scfw6-serial-address OBJECT-TYPE
    SYNTAX Integer32
    MAX-ACCESS accessible-for-notify
    STATUS current
    DESCRIPTION
        "Parameter 'serial-address' in event SCFW.6"
    ::= { scfwEventObjects6 1 }

scfw6-center-addr OBJECT-TYPE
    SYNTAX IpAddress
    MAX-ACCESS accessible-for-notify
    STATUS current
    DESCRIPTION
        "Parameter 'center-addr' in event SCFW.6"
    ::= { scfwEventObjects6 2 }

scfw6-tcp-port OBJECT-TYPE
    SYNTAX Integer32
    MAX-ACCESS accessible-for-notify
    STATUS current
    DESCRIPTION
        "Parameter 'tcp-port' in event SCFW.6"
    ::= { scfwEventObjects6 3 }

scfwEventObjects7 OBJECT-IDENTITY
    STATUS current
    DESCRIPTION
        "Event SCFW.7
        It's trying the connection against remote IP and P port."
    ::= { scfwEventsGroup 7 }

scfw7-serial-address OBJECT-TYPE
    SYNTAX Integer32
    MAX-ACCESS accessible-for-notify
    STATUS current
    DESCRIPTION
        "Parameter 'serial-address' in event SCFW.7"
    ::= { scfwEventObjects7 1 }

scfw7-rtu-ip-address OBJECT-TYPE
    SYNTAX IpAddress
    MAX-ACCESS accessible-for-notify
    STATUS current
    DESCRIPTION
        "Parameter 'rtu-ip-address' in event SCFW.7"
    ::= { scfwEventObjects7 2 }

scfw7-port OBJECT-TYPE
    SYNTAX Integer32
    MAX-ACCESS accessible-for-notify
    STATUS current
    DESCRIPTION
        "Parameter 'port' in event SCFW.7"
    ::= { scfwEventObjects7 3 }

scfwEventObjects8 OBJECT-IDENTITY
    STATUS current
    DESCRIPTION
        "Event SCFW.8
        Trying to send message to a RTU."
    ::= { scfwEventsGroup 8 }

scfw8-bytes OBJECT-TYPE
    SYNTAX Integer32
    MAX-ACCESS accessible-for-notify
    STATUS current
    DESCRIPTION
        "Parameter 'bytes' in event SCFW.8"
    ::= { scfwEventObjects8 1 }

scfw8-rem-ip-addr OBJECT-TYPE
    SYNTAX IpAddress
    MAX-ACCESS accessible-for-notify
    STATUS current
    DESCRIPTION
        "Parameter 'rem-ip-addr' in event SCFW.8"
    ::= { scfwEventObjects8 2 }

scfw8-rem-tcp-port OBJECT-TYPE
    SYNTAX Integer32
    MAX-ACCESS accessible-for-notify
    STATUS current
    DESCRIPTION
        "Parameter 'rem-tcp-port' in event SCFW.8"
    ::= { scfwEventObjects8 3 }

scfwEventObjects9 OBJECT-IDENTITY
    STATUS current
    DESCRIPTION
        "Event SCFW.9
        Trying to send message to Remote end."
    ::= { scfwEventsGroup 9 }

scfw9-bytes OBJECT-TYPE
    SYNTAX Integer32
    MAX-ACCESS accessible-for-notify
    STATUS current
    DESCRIPTION
        "Parameter 'bytes' in event SCFW.9"
    ::= { scfwEventObjects9 1 }

scfw9-rem-ip-addr OBJECT-TYPE
    SYNTAX IpAddress
    MAX-ACCESS accessible-for-notify
    STATUS current
    DESCRIPTION
        "Parameter 'rem-ip-addr' in event SCFW.9"
    ::= { scfwEventObjects9 2 }

scfw9-rem-tcp-port OBJECT-TYPE
    SYNTAX Integer32
    MAX-ACCESS accessible-for-notify
    STATUS current
    DESCRIPTION
        "Parameter 'rem-tcp-port' in event SCFW.9"
    ::= { scfwEventObjects9 3 }

scfwEventObjects10 OBJECT-IDENTITY
    STATUS current
    DESCRIPTION
        "Event SCFW.10
        A TCP Packet has been received from Control Center."
    ::= { scfwEventsGroup 10 }

scfw10-message-type OBJECT-TYPE
    SYNTAX DisplayString
    MAX-ACCESS accessible-for-notify
    STATUS current
    DESCRIPTION
        "Parameter 'message-type' in event SCFW.10"
    ::= { scfwEventObjects10 1 }

scfw10-bytes OBJECT-TYPE
    SYNTAX Integer32
    MAX-ACCESS accessible-for-notify
    STATUS current
    DESCRIPTION
        "Parameter 'bytes' in event SCFW.10"
    ::= { scfwEventObjects10 2 }

scfw10-foreign-host OBJECT-TYPE
    SYNTAX IpAddress
    MAX-ACCESS accessible-for-notify
    STATUS current
    DESCRIPTION
        "Parameter 'foreign-host' in event SCFW.10"
    ::= { scfwEventObjects10 3 }

scfw10-remote-port OBJECT-TYPE
    SYNTAX Integer32
    MAX-ACCESS accessible-for-notify
    STATUS current
    DESCRIPTION
        "Parameter 'remote-port' in event SCFW.10"
    ::= { scfwEventObjects10 4 }

scfwEventObjects11 OBJECT-IDENTITY
    STATUS current
    DESCRIPTION
        "Event SCFW.11
        A TCP Packet has been received from RTU."
    ::= { scfwEventsGroup 11 }

scfw11-message-type OBJECT-TYPE
    SYNTAX DisplayString
    MAX-ACCESS accessible-for-notify
    STATUS current
    DESCRIPTION
        "Parameter 'message-type' in event SCFW.11"
    ::= { scfwEventObjects11 1 }

scfw11-bytes OBJECT-TYPE
    SYNTAX Integer32
    MAX-ACCESS accessible-for-notify
    STATUS current
    DESCRIPTION
        "Parameter 'bytes' in event SCFW.11"
    ::= { scfwEventObjects11 2 }

scfw11-foreign-host OBJECT-TYPE
    SYNTAX IpAddress
    MAX-ACCESS accessible-for-notify
    STATUS current
    DESCRIPTION
        "Parameter 'foreign-host' in event SCFW.11"
    ::= { scfwEventObjects11 3 }

scfw11-remote-port OBJECT-TYPE
    SYNTAX Integer32
    MAX-ACCESS accessible-for-notify
    STATUS current
    DESCRIPTION
        "Parameter 'remote-port' in event SCFW.11"
    ::= { scfwEventObjects11 4 }

scfwEventObjects12 OBJECT-IDENTITY
    STATUS current
    DESCRIPTION
        "Event SCFW.12
        A TCP Packet has been received from RTU."
    ::= { scfwEventsGroup 12 }

scfw12-message-type OBJECT-TYPE
    SYNTAX DisplayString
    MAX-ACCESS accessible-for-notify
    STATUS current
    DESCRIPTION
        "Parameter 'message-type' in event SCFW.12"
    ::= { scfwEventObjects12 1 }

scfw12-bytes OBJECT-TYPE
    SYNTAX Integer32
    MAX-ACCESS accessible-for-notify
    STATUS current
    DESCRIPTION
        "Parameter 'bytes' in event SCFW.12"
    ::= { scfwEventObjects12 2 }

scfw12-foreign-host OBJECT-TYPE
    SYNTAX IpAddress
    MAX-ACCESS accessible-for-notify
    STATUS current
    DESCRIPTION
        "Parameter 'foreign-host' in event SCFW.12"
    ::= { scfwEventObjects12 3 }

scfw12-remote-port OBJECT-TYPE
    SYNTAX Integer32
    MAX-ACCESS accessible-for-notify
    STATUS current
    DESCRIPTION
        "Parameter 'remote-port' in event SCFW.12"
    ::= { scfwEventObjects12 4 }

scfwEventObjects13 OBJECT-IDENTITY
    STATUS current
    DESCRIPTION
        "Event SCFW.13
        The TCP session to RTU/Control Center has been closed."
    ::= { scfwEventsGroup 13 }

scfw13-type-host OBJECT-TYPE
    SYNTAX DisplayString
    MAX-ACCESS accessible-for-notify
    STATUS current
    DESCRIPTION
        "Parameter 'type-host' in event SCFW.13"
    ::= { scfwEventObjects13 1 }

scfw13-foreign-host OBJECT-TYPE
    SYNTAX IpAddress
    MAX-ACCESS accessible-for-notify
    STATUS current
    DESCRIPTION
        "Parameter 'foreign-host' in event SCFW.13"
    ::= { scfwEventObjects13 2 }

scfw13-remote-port OBJECT-TYPE
    SYNTAX Integer32
    MAX-ACCESS accessible-for-notify
    STATUS current
    DESCRIPTION
        "Parameter 'remote-port' in event SCFW.13"
    ::= { scfwEventObjects13 3 }

scfwEventObjects14 OBJECT-IDENTITY
    STATUS current
    DESCRIPTION
        "Event SCFW.14
        The TCP session has been closed by the Remote end."
    ::= { scfwEventsGroup 14 }

scfw14-foreign-host OBJECT-TYPE
    SYNTAX IpAddress
    MAX-ACCESS accessible-for-notify
    STATUS current
    DESCRIPTION
        "Parameter 'foreign-host' in event SCFW.14"
    ::= { scfwEventObjects14 1 }

scfw14-remote-port OBJECT-TYPE
    SYNTAX Integer32
    MAX-ACCESS accessible-for-notify
    STATUS current
    DESCRIPTION
        "Parameter 'remote-port' in event SCFW.14"
    ::= { scfwEventObjects14 2 }

scfwEventObjects15 OBJECT-IDENTITY
    STATUS current
    DESCRIPTION
        "Event SCFW.15
        The TCP session to RTU/Ctrl. Center has been opened."
    ::= { scfwEventsGroup 15 }

scfw15-type-host OBJECT-TYPE
    SYNTAX DisplayString
    MAX-ACCESS accessible-for-notify
    STATUS current
    DESCRIPTION
        "Parameter 'type-host' in event SCFW.15"
    ::= { scfwEventObjects15 1 }

scfw15-remote-ip OBJECT-TYPE
    SYNTAX IpAddress
    MAX-ACCESS accessible-for-notify
    STATUS current
    DESCRIPTION
        "Parameter 'remote-ip' in event SCFW.15"
    ::= { scfwEventObjects15 2 }

scfw15-remote-port OBJECT-TYPE
    SYNTAX Integer32
    MAX-ACCESS accessible-for-notify
    STATUS current
    DESCRIPTION
        "Parameter 'remote-port' in event SCFW.15"
    ::= { scfwEventObjects15 3 }

scfwEventObjects16 OBJECT-IDENTITY
    STATUS current
    DESCRIPTION
        "Event SCFW.16
        A packet was lost, due TCP Tx overrun error."
    ::= { scfwEventsGroup 16 }

scfw16-type-host OBJECT-TYPE
    SYNTAX DisplayString
    MAX-ACCESS accessible-for-notify
    STATUS current
    DESCRIPTION
        "Parameter 'type-host' in event SCFW.16"
    ::= { scfwEventObjects16 1 }

scfw16-rem-ip OBJECT-TYPE
    SYNTAX IpAddress
    MAX-ACCESS accessible-for-notify
    STATUS current
    DESCRIPTION
        "Parameter 'rem-ip' in event SCFW.16"
    ::= { scfwEventObjects16 2 }

scfw16-remp-tcp-port OBJECT-TYPE
    SYNTAX Integer32
    MAX-ACCESS accessible-for-notify
    STATUS current
    DESCRIPTION
        "Parameter 'remp-tcp-port' in event SCFW.16"
    ::= { scfwEventObjects16 3 }

scfwEventObjects17 OBJECT-IDENTITY
    STATUS current
    DESCRIPTION
        "Event SCFW.17
        TCP generic event was occurred."
    ::= { scfwEventsGroup 17 }

scfw17-event OBJECT-TYPE
    SYNTAX DisplayString
    MAX-ACCESS accessible-for-notify
    STATUS current
    DESCRIPTION
        "Parameter 'event' in event SCFW.17"
    ::= { scfwEventObjects17 1 }

scfw17-ip OBJECT-TYPE
    SYNTAX IpAddress
    MAX-ACCESS accessible-for-notify
    STATUS current
    DESCRIPTION
        "Parameter 'ip' in event SCFW.17"
    ::= { scfwEventObjects17 2 }

scfw17-port OBJECT-TYPE
    SYNTAX Integer32
    MAX-ACCESS accessible-for-notify
    STATUS current
    DESCRIPTION
        "Parameter 'port' in event SCFW.17"
    ::= { scfwEventObjects17 3 }

scfwEventObjects18 OBJECT-IDENTITY
    STATUS current
    DESCRIPTION
        "Event SCFW.18
        TCP Listen to Control Center has been closed, due max session number has been reached."
    ::= { scfwEventsGroup 18 }

scfw18-port OBJECT-TYPE
    SYNTAX Integer32
    MAX-ACCESS accessible-for-notify
    STATUS current
    DESCRIPTION
        "Parameter 'port' in event SCFW.18"
    ::= { scfwEventObjects18 1 }

scfwEventObjects19 OBJECT-IDENTITY
    STATUS current
    DESCRIPTION
        "Event SCFW.19
        TCP Listen to RTUs has been closed, due max session number has been reached."
    ::= { scfwEventsGroup 19 }

scfw19-port OBJECT-TYPE
    SYNTAX Integer32
    MAX-ACCESS accessible-for-notify
    STATUS current
    DESCRIPTION
        "Parameter 'port' in event SCFW.19"
    ::= { scfwEventObjects19 1 }

scfwEventObjects20 OBJECT-IDENTITY
    STATUS current
    DESCRIPTION
        "Event SCFW.20
        An input TCP session has been rejet."
    ::= { scfwEventsGroup 20 }

scfw20-event OBJECT-TYPE
    SYNTAX DisplayString
    MAX-ACCESS accessible-for-notify
    STATUS current
    DESCRIPTION
        "Parameter 'event' in event SCFW.20"
    ::= { scfwEventObjects20 1 }

scfw20-ip OBJECT-TYPE
    SYNTAX IpAddress
    MAX-ACCESS accessible-for-notify
    STATUS current
    DESCRIPTION
        "Parameter 'ip' in event SCFW.20"
    ::= { scfwEventObjects20 2 }

scfw20-port OBJECT-TYPE
    SYNTAX Integer32
    MAX-ACCESS accessible-for-notify
    STATUS current
    DESCRIPTION
        "Parameter 'port' in event SCFW.20"
    ::= { scfwEventObjects20 3 }


scfwNotification1 NOTIFICATION-TYPE
    OBJECTS { 
              scfw1-tcp-port 
            }
    STATUS current
    DESCRIPTION
        "Notification of Event SCFW.1

        Message: 'Can't open TCP listen for RTU's connections. Port $1'

        Parameters list:
              $1: scfw1-tcp-port

        TCP listen for incoming RTU's connections has not been make."
    ::= { scfwNotificationsPrefix 1 }

scfwNotification2 NOTIFICATION-TYPE
    OBJECTS { 
              scfw2-tcp-port 
            }
    STATUS current
    DESCRIPTION
        "Notification of Event SCFW.2

        Message: 'Can't make TCP listen for Control Centers connections. Port $1'

        Parameters list:
              $1: scfw2-tcp-port

        TCP listen for incoming Control Centers connections has not been make."
    ::= { scfwNotificationsPrefix 2 }

scfwNotification3 NOTIFICATION-TYPE
    OBJECTS { 
              scfw3-data-leng, 
              scfw3-cent-ip,
              scfw3-cent-port 
            }
    STATUS current
    DESCRIPTION
        "Notification of Event SCFW.3

        Message: 'A block with LRC/CRC error has been received from Control Center. Data length:$1, IP Address:$2, Port: $3'

        Parameters list:
              $1: scfw3-data-leng
              $2: scfw3-cent-ip
              $3: scfw3-cent-port

        A message with LRC/CRC error has been received from Control Center."
    ::= { scfwNotificationsPrefix 3 }

scfwNotification4 NOTIFICATION-TYPE
    OBJECTS { 
              scfw4-data-leng, 
              scfw4-rtu-ip,
              scfw4-rtu-port 
            }
    STATUS current
    DESCRIPTION
        "Notification of Event SCFW.4

        Message: 'A block with LRC/CRC error has been received from RTU, Data length:$1, IP Address:$2, Port: $3'

        Parameters list:
              $1: scfw4-data-leng
              $2: scfw4-rtu-ip
              $3: scfw4-rtu-port

        A message with LRC/CRC error has been received from RTU."
    ::= { scfwNotificationsPrefix 4 }

scfwNotification5 NOTIFICATION-TYPE
    OBJECTS { 
              scfw5-directon, 
              scfw5-event-load 
            }
    STATUS current
    DESCRIPTION
        "Notification of Event SCFW.5

        Message: 'TCP session to $1 not found for eve.:$2'

        Parameters list:
              $1: scfw5-directon
              $2: scfw5-event-load

        TCP session to direcction especified not found when an event occur."
    ::= { scfwNotificationsPrefix 5 }

scfwNotification6 NOTIFICATION-TYPE
    OBJECTS { 
              scfw6-serial-address, 
              scfw6-center-addr,
              scfw6-tcp-port 
            }
    STATUS current
    DESCRIPTION
        "Notification of Event SCFW.6

        Message: 'Address $1 received from Serial Terminal is not included in config. regiters. Ctrl Center IP address: $2, port: $3'

        Parameters list:
              $1: scfw6-serial-address
              $2: scfw6-center-addr
              $3: scfw6-tcp-port

        Addres received from Control Center is not included in configuration
        registers list."
    ::= { scfwNotificationsPrefix 6 }

scfwNotification7 NOTIFICATION-TYPE
    OBJECTS { 
              scfw7-serial-address, 
              scfw7-rtu-ip-address,
              scfw7-port 
            }
    STATUS current
    DESCRIPTION
        "Notification of Event SCFW.7

        Message: 'Address $1 is trying the connection against IP $2, Port $3'

        Parameters list:
              $1: scfw7-serial-address
              $2: scfw7-rtu-ip-address
              $3: scfw7-port

        It's trying the connection against remote IP and P port."
    ::= { scfwNotificationsPrefix 7 }

scfwNotification8 NOTIFICATION-TYPE
    OBJECTS { 
              scfw8-bytes, 
              scfw8-rem-ip-addr,
              scfw8-rem-tcp-port 
            }
    STATUS current
    DESCRIPTION
        "Notification of Event SCFW.8

        Message: 'Trying to send a message to RTU with $1 bytes. IP $2, Port $3'

        Parameters list:
              $1: scfw8-bytes
              $2: scfw8-rem-ip-addr
              $3: scfw8-rem-tcp-port

        Trying to send message to a RTU."
    ::= { scfwNotificationsPrefix 8 }

scfwNotification9 NOTIFICATION-TYPE
    OBJECTS { 
              scfw9-bytes, 
              scfw9-rem-ip-addr,
              scfw9-rem-tcp-port 
            }
    STATUS current
    DESCRIPTION
        "Notification of Event SCFW.9

        Message: 'Trying to send a message to Control Center with $1 bytes. IP $2, Port $3'

        Parameters list:
              $1: scfw9-bytes
              $2: scfw9-rem-ip-addr
              $3: scfw9-rem-tcp-port

        Trying to send message to Remote end."
    ::= { scfwNotificationsPrefix 9 }

scfwNotification10 NOTIFICATION-TYPE
    OBJECTS { 
              scfw10-message-type, 
              scfw10-bytes,
              scfw10-foreign-host,
              scfw10-remote-port 
            }
    STATUS current
    DESCRIPTION
        "Notification of Event SCFW.10

        Message: 'A TCP packet $1 has been received from Cntrl. Center, $2 bytes. rem. IP: $3, Port: $4'

        Parameters list:
              $1: scfw10-message-type
              $2: scfw10-bytes
              $3: scfw10-foreign-host
              $4: scfw10-remote-port

        A TCP Packet has been received from Control Center."
    ::= { scfwNotificationsPrefix 10 }

scfwNotification11 NOTIFICATION-TYPE
    OBJECTS { 
              scfw11-message-type, 
              scfw11-bytes,
              scfw11-foreign-host,
              scfw11-remote-port 
            }
    STATUS current
    DESCRIPTION
        "Notification of Event SCFW.11

        Message: 'A TCP packet $1 has been received from RTU, $2 bytes. rem. IP: $3, Port: $4'

        Parameters list:
              $1: scfw11-message-type
              $2: scfw11-bytes
              $3: scfw11-foreign-host
              $4: scfw11-remote-port

        A TCP Packet has been received from RTU."
    ::= { scfwNotificationsPrefix 11 }

scfwNotification12 NOTIFICATION-TYPE
    OBJECTS { 
              scfw12-message-type, 
              scfw12-bytes,
              scfw12-foreign-host,
              scfw12-remote-port 
            }
    STATUS current
    DESCRIPTION
        "Notification of Event SCFW.12

        Message: 'A TCP packet $1 has been received from RTU, $2 bytes. rem. IP: $3, Port: $4'

        Parameters list:
              $1: scfw12-message-type
              $2: scfw12-bytes
              $3: scfw12-foreign-host
              $4: scfw12-remote-port

        A TCP Packet has been received from RTU."
    ::= { scfwNotificationsPrefix 12 }

scfwNotification13 NOTIFICATION-TYPE
    OBJECTS { 
              scfw13-type-host, 
              scfw13-foreign-host,
              scfw13-remote-port 
            }
    STATUS current
    DESCRIPTION
        "Notification of Event SCFW.13

        Message: 'The TCP session to $1 has been closed. rem. IP: $2, Port: $3'

        Parameters list:
              $1: scfw13-type-host
              $2: scfw13-foreign-host
              $3: scfw13-remote-port

        The TCP session to RTU/Control Center has been closed."
    ::= { scfwNotificationsPrefix 13 }

scfwNotification14 NOTIFICATION-TYPE
    OBJECTS { 
              scfw14-foreign-host, 
              scfw14-remote-port 
            }
    STATUS current
    DESCRIPTION
        "Notification of Event SCFW.14

        Message: 'The TCP session has been closed by the Remote end. rem. IP: $1, Port: $2'

        Parameters list:
              $1: scfw14-foreign-host
              $2: scfw14-remote-port

        The TCP session has been closed by the Remote end."
    ::= { scfwNotificationsPrefix 14 }

scfwNotification15 NOTIFICATION-TYPE
    OBJECTS { 
              scfw15-type-host, 
              scfw15-remote-ip,
              scfw15-remote-port 
            }
    STATUS current
    DESCRIPTION
        "Notification of Event SCFW.15

        Message: 'The TCP session has been opened to $1. Remote IP:$2 , Port: $3'

        Parameters list:
              $1: scfw15-type-host
              $2: scfw15-remote-ip
              $3: scfw15-remote-port

        The TCP session to RTU/Ctrl. Center has been opened."
    ::= { scfwNotificationsPrefix 15 }

scfwNotification16 NOTIFICATION-TYPE
    OBJECTS { 
              scfw16-type-host, 
              scfw16-rem-ip,
              scfw16-remp-tcp-port 
            }
    STATUS current
    DESCRIPTION
        "Notification of Event SCFW.16

        Message: 'Packet lost due TCP Tx overrun error to $1: rem. IP $2, Port $3'

        Parameters list:
              $1: scfw16-type-host
              $2: scfw16-rem-ip
              $3: scfw16-remp-tcp-port

        A packet was lost, due TCP Tx overrun error."
    ::= { scfwNotificationsPrefix 16 }

scfwNotification17 NOTIFICATION-TYPE
    OBJECTS { 
              scfw17-event, 
              scfw17-ip,
              scfw17-port 
            }
    STATUS current
    DESCRIPTION
        "Notification of Event SCFW.17

        Message: 'The TCP event: $1 . Rem. IP: $2, Port: $3'

        Parameters list:
              $1: scfw17-event
              $2: scfw17-ip
              $3: scfw17-port

        TCP generic event was occurred."
    ::= { scfwNotificationsPrefix 17 }

scfwNotification18 NOTIFICATION-TYPE
    OBJECTS { 
              scfw18-port 
            }
    STATUS current
    DESCRIPTION
        "Notification of Event SCFW.18

        Message: 'Max sessions number has been reached to Control Centers, port $1'

        Parameters list:
              $1: scfw18-port

        TCP Listen to Control Center has been closed, due max session number has been reached."
    ::= { scfwNotificationsPrefix 18 }

scfwNotification19 NOTIFICATION-TYPE
    OBJECTS { 
              scfw19-port 
            }
    STATUS current
    DESCRIPTION
        "Notification of Event SCFW.19

        Message: 'Max sessions number has been reached to RTUs, port $1'

        Parameters list:
              $1: scfw19-port

        TCP Listen to RTUs has been closed, due max session number has been reached."
    ::= { scfwNotificationsPrefix 19 }

scfwNotification20 NOTIFICATION-TYPE
    OBJECTS { 
              scfw20-event, 
              scfw20-ip,
              scfw20-port 
            }
    STATUS current
    DESCRIPTION
        "Notification of Event SCFW.20

        Message: 'TCP inout session rejet: $1 . Rem. IP: $2, Port: $3'

        Parameters list:
              $1: scfw20-event
              $2: scfw20-ip
              $3: scfw20-port

        An input TCP session has been rejet."
    ::= { scfwNotificationsPrefix 20 }


END
