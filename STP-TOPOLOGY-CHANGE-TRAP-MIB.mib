STP-TOPOLOGY-CHANGE-TRAP-MIB DEFINITIONS ::= BEGIN

-- Centillion STP notification trap MIB release 1.0.0
-- Revision 04/13/2000  
 
-- Copyright 2000 Nortel Networks, Inc.
-- All rights reserved.
-- This Nortel Networks SNMP Management Information Base Specification
-- (Specification) embodies Nortel Networks' confidential and
-- proprietary intellectual property. Nortel Networks retains all
-- title and ownership in the Specification, including any
-- revisions.
 
-- This Specification is supplied "AS IS," and Nortel Networks makes
-- no warranty, either express or implied, as to the use,
-- operation, condition, or performance of the Specification.
 
 
-- Imports
  
IMPORTS
      TRAP-TYPE       FROM RFC-1215
      stpChangeTrap   FROM S5-ROOT-MIB
      bridgeGroupIdentifier  FROM CENTILLION-BRIDGEGROUP-MIB;
  
  
-- SECTION 2: Topology Change traps definitions
  
  
stpRxTopologyChg   TRAP-TYPE
     ENTERPRISE  stpChangeTrap
     VARIABLES   { bridgeGroupIdentifier }
--   STATUS      mandatory
     DESCRIPTION
         " This trap is sent when a spanning tree group receives a 
           topology change notification."

     ::= 1 

END

-- SECTION 1: Top Level Definitions
