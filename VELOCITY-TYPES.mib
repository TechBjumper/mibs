VELOCITY-TYPES DEFINITIONS ::= BEGIN

IMPORTS
  MODULE-IDENTITY, OBJECT-IDENTITY        FROM SNMPv2-SMI
  velocityMIBAdminInfo FROM VELOCITY-MIB;

velocityMibModule MODULE-IDENTITY
   LAST-UPDATED "200607310000Z"    -- 31 July 2006
   ORGANIZATION "Velocity Software Inc."
   CONTACT-INFO
       "Dennis Andrews
       Postal: Velocity Software, Inc.
               106-D Castro St.
               Mountain View, CA 94041
               USA
       Phone:  650-964-8867
       Fax:    650-964-9012
       Email:  dennis@velocitysoftware.com"
   DESCRIPTION
       "This MIB is an extension of the host MIB. This MIB currently
       only runs on linux. This is the original version."
   ::= { velocityMIBAdminInfo 4 }

END
