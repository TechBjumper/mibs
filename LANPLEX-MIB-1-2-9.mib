-- Copyright 1995 by 3Com Corporation.  All rights reserved.
-- MIB file name:  lanplex-mib
-- available in these 3Com devices:  Lanplex hubs
-- For support or more info, check 3Com's web page at http://www.3com.com


        --			LANplex Management Information Base
        --			Version 1.2.9
        -- 			12 April, 1994

        --			3Com Corporation
        --			85 Rangeway Road
        --			North Billerica, MA 01862
        --			(508) 670-9009
 
		--			Change History:
		--			 4/11/94	eah		Removed lpBridgePortAddressLearnedEvent and
		--								lpBridgePortAddressForgottenEvent traps
		--			 4/ 7/94	eah		Added lpBridgePortReceiveMulticastLimitExceededCount
		--			 6/30/93	eah		Added lpSystemSmtProxyEvents
		--			 6/15/93	eah		Added lpEthernetPortType
		--			 6/11/93	eah 	Added lpBridgeLocalIndex
		--			 5/29/93	eah		Deprecated lpSlot express attributes.
		--								lpFddiMacReceiveMulticastThreshold, and
		--								lpEthernetPortReceiveMulticastThreshold
		--								Added lpSlotBridgeFunctionCount,
		--								lpSlotBridgeFunctionBaseIndex,
		--								lpSystemSmtProxyTimeoutBase
		--			 3/ 9/93	eah		Added lpTrapEnterprise and lpTrapDest 
		--								groups
		--			 3/ 3/93	eah		Added enum for ESM to board type 
		--								objects
		--			 2/18/93	eah		Changed address threshold, address 
		--								learned, and address forgotten events 
		--								to use bridge attributes
		--			 2/ 2/93	eah		Created new group lpBridge
		--								Deprecated lpExpress,
		--								lpExpressFddiPort, 
		--								lpExpressEthernetPort, and
		--								lpExpressEthernetPortAddress groups
		--								Added lpSystemBridgeFunctionCount to
		--								the lpSystem group
		--								Deprecated 
		--								lpSystemExpressFunctionCount,
		--								lpSystemExpressFddiPortCount, and
		--								lpSystemExpressEthernetPortCount
		--		  	12/17/92	eah		Replaced lpPowerSupplyFailureType by
		--								lpPowerSupplyLastFailure which is
		--								read-only and includes a none value
		--								lpPowerSupplyFailureType was deprecated
		--								Changed lpPowerSupplyFailureEvent to
		--								use new object
		--			 3/ 1/92	jp		Added new groups using logical
		--								numbering scheme. Marked old groups
		--								as deprecated.
		--			 6/ 4/92	jp		Added lpFddiMacReceiveMulticastThreshold
		--								and lpEthernetPortReceiveMulticastThreshold
		--								objects.
		--			 6/15/92	jp		Added lpFddiMacBeaconHistory object.
		
-----------------------------------------------------------------------------------
		LANPLEX-MIB-1-2-9 DEFINITIONS ::= BEGIN

		IMPORTS
			enterprises, Counter,
				NetworkAddress					FROM RFC1155-SMI
			DisplayString						FROM RFC1213-MIB
			OBJECT-TYPE							FROM RFC-1212
			TRAP-TYPE							FROM RFC-1215;

		--  This MIB module uses the extended OBJECT-TYPE macro as
		--  defined in [9], and the TRAP-TYPE macro as defined in [10]

		synernetics		OBJECT IDENTIFIER ::= { enterprises 114 }
		lanplex			OBJECT IDENTIFIER ::= { synernetics 1 }

		-- this is the lanplex MIB module

		lanplexMib		OBJECT IDENTIFIER ::= { lanplex 1 }

		chassis			OBJECT IDENTIFIER ::= { lanplexMib 1 }
		slot			OBJECT IDENTIFIER ::= { lanplexMib 2 }
		spm				OBJECT IDENTIFIER ::= { lanplexMib 3 }
		feam			OBJECT IDENTIFIER ::= { lanplexMib 4 }
		fcm				OBJECT IDENTIFIER ::= { lanplexMib 5 }
		port			OBJECT IDENTIFIER ::= { lanplexMib 6 }
		eem				OBJECT IDENTIFIER ::= { lanplexMib 7 }
		eemFddiMAC		OBJECT IDENTIFIER ::= { lanplexMib 8 }
		eemEthernetPort	OBJECT IDENTIFIER ::= { lanplexMib 9 }
		eemMACAddress	OBJECT IDENTIFIER ::= { lanplexMib 10 }

		-- The following are new groups defined in this revision
		-- of the lanplex-mib. These groups contain all the functionality
		-- of the above named groups plus newly defined objects.

		lpSystem						OBJECT IDENTIFIER ::= { lanplexMib 11 }
		lpSlot							OBJECT IDENTIFIER ::= { lanplexMib 12 }
		lpFddiMac						OBJECT IDENTIFIER ::= { lanplexMib 13 }
		lpEthernetPort					OBJECT IDENTIFIER ::= { lanplexMib 14 }
		lpFddiPort						OBJECT IDENTIFIER ::= { lanplexMib 15 }
		lpExpress						OBJECT IDENTIFIER ::= { lanplexMib 16 }
		lpExpressFddiPort				OBJECT IDENTIFIER ::= { lanplexMib 17 }
		lpExpressEthernetPort			OBJECT IDENTIFIER ::= { lanplexMib 18 }
		lpExpressEthernetPortAddress	OBJECT IDENTIFIER ::= { lanplexMib 19 }
		lpPowerSupply					OBJECT IDENTIFIER ::= { lanplexMib 20 }

		-- New group for bridge support

		lpBridge						OBJECT IDENTIFIER ::= { lanplexMib 21 }

		-- New groups for controlling trap "filters"

		lpTrapEnterprise				OBJECT IDENTIFIER ::= { lanplexMib 22 }
		lpTrapDest						OBJECT IDENTIFIER ::= { lanplexMib 23 }

		-- The LANplex Chassis Group
		-- The Chassis Group contains all objects used to manage the LANplex chassis, 

		-- Note that this group has been marked as deprecated and is 
		-- included here for backward compatibilty. It will be removed 
		-- from the next revision of the lanplex MIB. The objects defined 
		-- in this table are now available via the lpSystem group."

		chassisId OBJECT-TYPE
			SYNTAX	INTEGER 
			ACCESS	read-only
			STATUS	deprecated
			DESCRIPTION
					"The unique identifier assigned to this station 
					during manufacturing."
			::= { chassis 1 }

		chassisType OBJECT-TYPE
			SYNTAX	INTEGER {
						other(1),
						tweleveSlot(2),
						fourSlot(3)
					}
			ACCESS	read-only
			STATUS	deprecated
			DESCRIPTION
					"The type of the LANplex chassis."
			::= { chassis 2 }

		chassisRevision OBJECT-TYPE
			SYNTAX	OCTET STRING (SIZE (1)) 
			ACCESS	read-only
			STATUS	deprecated
			DESCRIPTION
					"The revision number of the LANplex chassis."
			::= { chassis 3 }

		chassisName OBJECT-TYPE
			SYNTAX	DisplayString (SIZE (0..128))
			ACCESS	read-only
			STATUS	deprecated
			DESCRIPTION
					"The text string describing this chassis."
			::= { chassis 4 }

		chassisNameAbbrev OBJECT-TYPE
			SYNTAX	DisplayString (SIZE (0..128))
			ACCESS	read-only
			STATUS	deprecated
			DESCRIPTION
					"The text string describing the generic name for 
					this chassis."
			::= { chassis 5 }

		chassisManufacturer OBJECT-TYPE
			SYNTAX	DisplayString (SIZE (0..128))
			ACCESS	read-only
			STATUS	deprecated
			DESCRIPTION
					"The text string describing the manufacturer of 
					this chassis."
			::= { chassis 6 }

		chassisSlotCount OBJECT-TYPE
			SYNTAX	INTEGER
			ACCESS	read-only
			STATUS	deprecated
			DESCRIPTION
					"The number of slots in the LANplex chassis."
			::= { chassis 7 }

		chassisBuildTime OBJECT-TYPE
			SYNTAX	DisplayString (SIZE (0..128))
			ACCESS	read-only
			STATUS	deprecated
			DESCRIPTION
					"The build time of the LANplex system software."
			::= { chassis 8 }

		chassisSoftwareRevision OBJECT-TYPE
			SYNTAX	OCTET STRING (SIZE (4)) 
			ACCESS	read-only
			STATUS	deprecated
			DESCRIPTION
					"The revision number of the LANplex system software.
					Each byte indicates the following:
						byte 0:	major release number.
						byte 1:	minor release number.
						byte 2:	update number.
						byte 3:
							bits 7-6:	release type.
							bits 5-0:	supplemental idenrtifier."
			::= { chassis 9 }

		chassisControlPanelColumns OBJECT-TYPE
			SYNTAX	INTEGER 
			ACCESS	read-only
			STATUS	deprecated
			DESCRIPTION
					"The number of columns in the control panel 
					display."
			::= { chassis 10 }

		chassisControlPanelLines OBJECT-TYPE
			SYNTAX	INTEGER 
			ACCESS	read-only
			STATUS	deprecated
			DESCRIPTION
					"The number of lines in the control panel
					display."
			::= { chassis 11 }

		chassisControlPanelText OBJECT-TYPE
			SYNTAX	OCTET STRING (SIZE (0..128))
			ACCESS	read-only
			STATUS	deprecated
			DESCRIPTION
					"The currently displayed text in the control panel 
					display."
			::= { chassis 12 }

		chassisAction OBJECT-TYPE
			SYNTAX	INTEGER {
						other(1),
						reset(2)
					}
			ACCESS	read-write
			STATUS	deprecated
			DESCRIPTION
					"This object, when read, always returns the value other (1).
					The behavior of setting this object to each of the 
					acceptable values is as follows:

						reset:	resets the LANplex system."
			::= { chassis 13 }


		-- The lanplex Slot Table

		slotTable OBJECT-TYPE
			SYNTAX	SEQUENCE OF SlotEntry
			ACCESS	not-accessible
			STATUS	deprecated
			DESCRIPTION
					"A list of slot entries. A single instance of this 
					object exists for each slot in the LANplex chassis."
			::= { slot 1 }

		slotEntry OBJECT-TYPE
			SYNTAX	SlotEntry
			ACCESS	not-accessible
			STATUS	deprecated
			DESCRIPTION
					"A slot entry contains information common to a given slot 
					within a LANplex system

					Note that this object has been marked as deprecated and is 
					included here for backward compatibilty. It will be removed 
					from the next revision of the lanplex MIB. The objects defined 
					in this table are now available via the lpSlot table."
			INDEX	{ slotIndex }
			::= { slotTable 1 }

		SlotEntry ::=
			SEQUENCE {
				slotIndex
					INTEGER,
				slotBoardType
					INTEGER,
				slotBoardRevision
					OCTET STRING,
				slotBoardStatus
					INTEGER,
				slotBoardName
					DisplayString,
				slotBoardNameAbbrev
					DisplayString,
				slotBoardAction
					INTEGER
			}

		slotIndex OBJECT-TYPE
			SYNTAX	INTEGER
			ACCESS	read-only
			STATUS	deprecated
			DESCRIPTION
					"The physical slot number of this slot within the 
					LANplex chassis."
			::= { slotEntry 1 }

		slotBoardType OBJECT-TYPE
			SYNTAX	INTEGER {
						unknown(1),
						emptySlot(2),
						spm(3),
						feam(4),
						fcm(5), 
						eem(6),
						esm(7),
						fcm2(8)
					}
			ACCESS	read-only
			STATUS	deprecated
			DESCRIPTION
					"The type of board residing in this slot."
			::= { slotEntry 2 }
                
		slotBoardRevision OBJECT-TYPE
			SYNTAX	OCTET STRING (SIZE (1))
			ACCESS	read-only
			STATUS	deprecated
			DESCRIPTION
					"The revision number of the board in this slot."
			::= { slotEntry 3 }

		slotBoardStatus OBJECT-TYPE
			SYNTAX	INTEGER {
						notPresent(1),
						testing(2),
						offline(3),
						online(4)
					}
			ACCESS	read-only
			STATUS	deprecated
			DESCRIPTION
					"The status of the board in this slot."
			::= { slotEntry 4 }

		slotBoardName OBJECT-TYPE
			SYNTAX	DisplayString (SIZE (0..256))
			ACCESS	read-only
			STATUS	deprecated
			DESCRIPTION
					"The text string describing this board type."
			::= { slotEntry 5 }

		slotBoardNameAbbrev OBJECT-TYPE
			SYNTAX	DisplayString (SIZE (0..32))
			ACCESS	read-only
			STATUS	deprecated
			DESCRIPTION
					"The abbreviation used to describe this board type." 
			::= { slotEntry 6 }

		slotBoardAction OBJECT-TYPE
			SYNTAX	INTEGER {
						other(1),
						runDiagnostics(2)
					}
			ACCESS	read-write
			STATUS	deprecated
			DESCRIPTION
					"This object, when read, always returns the 
					value other (1). The behavior of setting this object 
					to each of the acceptable values is as follows:

						runDiagnostics:	runs the board's offline diagnostics."
			::= { slotEntry 7 }


    -- The lanplex SPM Table

		spmTable OBJECT-TYPE
			SYNTAX	SEQUENCE OF SPMEntry
			ACCESS	not-accessible
			STATUS	deprecated
			DESCRIPTION
					"A list of System Processor Module (SPM) entries. An entry 
					exists for each Slot Table Entry whose board type is SPM. 
					This table is indexed by the physical slot number of this 
					SPM within the LANplex chassis. The entries may not have
					consecutive Slot Indices.

					Note that this object has been marked as deprecated and is 
					included here for backward compatibilty. It will be removed 
					from the next revision of the lanplex MIB. The objects defined 
					in this table are now available via the lpSlot table."
			::= { spm 1 }

		spmEntry OBJECT-TYPE
			SYNTAX	SPMEntry
			ACCESS	not-accessible
			STATUS	deprecated
			DESCRIPTION
					"A SPM entry contains information common to a single System 
					Processor Module (SPM) within a LANplex system."
			INDEX	{ spmSlotIndex }
			::= { spmTable 1 }

		SPMEntry ::=
			SEQUENCE {
				spmSlotIndex
					INTEGER,
				spmEthernetPortCount
					INTEGER,
				spmBaseEthernetPortIndex
					INTEGER
			}

		spmSlotIndex OBJECT-TYPE
			SYNTAX	INTEGER
			ACCESS	read-only
			STATUS	deprecated
			DESCRIPTION
					"The physical slot number of this slot within the LANplex
					chassis."
			::= { spmEntry 1 }

		spmEthernetPortCount OBJECT-TYPE
			SYNTAX	INTEGER
			ACCESS	read-only
			STATUS	deprecated
			DESCRIPTION
					"The number of ethernet ports on this board."
			::= { spmEntry 2 }

		spmBaseEthernetPortIndex OBJECT-TYPE
			SYNTAX	INTEGER
			ACCESS	read-only
			STATUS	deprecated
			DESCRIPTION
					"The system-wide index for the first ethernet port
					 on this board."
			::= { spmEntry 3 }


		-- The lanplex FEAM Table

		feamTable OBJECT-TYPE
			SYNTAX	SEQUENCE OF FEAMEntry
			ACCESS	not-accessible
			STATUS	deprecated
			DESCRIPTION
					"A list of FDDI Enterprise Access Module (FEAM) entries. 
					An entry exists for each Slot Table Entry whose board type 
					is FEAM. This table is indexed by the physical slot number of
					this FEAM within the LANplex chassis. The entries may not 
					have consecutive Slot Indices.

					Note that this object has been marked as deprecated and is 
					included here for backward compatibilty. It will be removed 
					from the next revision of the lanplex MIB. The objects defined 
					in this table are now available via the lpSlot table."
			::= { feam 1 }

		feamEntry OBJECT-TYPE
			SYNTAX	FEAMEntry
			ACCESS	not-accessible
			STATUS	deprecated
			DESCRIPTION
					"A FEAM entry contains information common to a single FDDI 
					Enterprise Access Module (FEAM) within a LANplex system."
			INDEX	{ feamSlotIndex }
			::= { feamTable 1 }

		FEAMEntry ::=
                SEQUENCE {
					feamSlotIndex
						INTEGER,
					feamMACCount
						INTEGER,
					feamBaseMACIndex
						INTEGER,
					feamPortCount
						INTEGER,
					feamBasePortIndex
						INTEGER
			}

		feamSlotIndex OBJECT-TYPE
			SYNTAX	INTEGER
			ACCESS	read-only
			STATUS	deprecated
			DESCRIPTION
					"The physical slot number of this slot within the LANplex 
					chassis."
			::= { feamEntry 1 }

		feamMACCount OBJECT-TYPE
			SYNTAX	INTEGER
			ACCESS	read-only
			STATUS	deprecated
			DESCRIPTION
					"The number of FDDI MAC's present on this board."
			::= { feamEntry 2 }

		feamBaseMACIndex OBJECT-TYPE
			SYNTAX	INTEGER
			ACCESS	read-only
			STATUS	deprecated
			DESCRIPTION
					"The system-wide index of the first FDDI MAC on 
					this board. Additional MAC's on this board will have
					consecutively increasing MAC indices following 
					this index."
			::= { feamEntry 3 }

		feamPortCount OBJECT-TYPE
			SYNTAX	INTEGER
			ACCESS	read-only
			STATUS	deprecated
			DESCRIPTION
					"The number of FDDI ports present on this board."
			::= { feamEntry 4 }

		feamBasePortIndex OBJECT-TYPE
			SYNTAX	INTEGER
			ACCESS	read-only
			STATUS	deprecated
			DESCRIPTION
					"The system-wide index of the first FDDI port on 
					this board. Additional ports on this board will have
					consecutively increasing Port indices following 
					this index."
			::= { feamEntry 5 }


		-- The lanplex FCM Table

		fcmTable OBJECT-TYPE
			SYNTAX	SEQUENCE OF FCMEntry
			ACCESS	not-accessible
			STATUS deprecated
			DESCRIPTION
					"A list of FDDI Concentration Module (FCM) entries. An entry 
					exists for each Slot Table Entry whose board type is FCM. This 
					table is indexed by the physical slot number of this FCM 
					within the LANplex chassis. The entries may not have
					consecutive Slot Indices.

					Note that this object has been marked as deprecated and is 
					included here for backward compatibilty. It will be removed 
					from the next revision of the lanplex MIB. The objects defined 
					in this table are now available via the lpSlot table."
			::= { fcm 1 }

		fcmEntry OBJECT-TYPE
			SYNTAX FCMEntry
			ACCESS not-accessible
			STATUS deprecated
			DESCRIPTION
					"An FCM entry contains information common to a single FDDI 
					Concentration Module (FCM)  within a LANplex system."
			INDEX	{ fcmSlotIndex}
			::= { fcmTable 1 }

		FCMEntry ::=
			SEQUENCE {
				fcmSlotIndex
					INTEGER,
				fcmPortCount
					INTEGER,
				fcmBasePortIndex
					INTEGER
			}

		fcmSlotIndex OBJECT-TYPE
			SYNTAX	INTEGER
			ACCESS	read-only
			STATUS	deprecated
			DESCRIPTION
					"The physical slot number of this slot within the LANplex 
					chassis."
			::= { fcmEntry 1 }

		fcmPortCount OBJECT-TYPE
			SYNTAX	INTEGER
			ACCESS	read-only
			STATUS	deprecated
			DESCRIPTION
					"The number of FDDI ports present on this board."
			::= { fcmEntry 2 }

		fcmBasePortIndex OBJECT-TYPE
			SYNTAX	INTEGER
			ACCESS	read-only
			STATUS	deprecated
			DESCRIPTION
					"The system-wide index of the first FDDI port on 
					this board. Additional ports on this board will have
					consecutively increasing Port indices following 
					this index."
			::= { fcmEntry 3 }


 		-- The lanplex Port Table

		portTable OBJECT-TYPE
			SYNTAX	SEQUENCE OF PortEntry
			ACCESS	not-accessible
			STATUS	deprecated
			DESCRIPTION
					"A list of port entries. A single instance of this
					object exists for each port (excluding ethernet ports) 
					in the LANplex system.

					Note that this object has been marked as deprecated and is 
					included here for backward compatibilty. It will be removed 
					from the next revision of the lanplex MIB. The objects defined 
					in this table are now available either via the fddiPort group
					or the enetPort group."
			::= { port 1 }

		portEntry OBJECT-TYPE
			SYNTAX	PortEntry
			ACCESS	not-accessible
			STATUS	deprecated
			DESCRIPTION
					"A Port entry contains information common to a 
					particular port located on a particular board
					within the LANplex system."
			INDEX	{ portSlotIndex, portIndex }
			::= { portTable 1 }

		PortEntry ::=
			SEQUENCE {
				portSlotIndex
					INTEGER,
				portIndex
					INTEGER,
				portLabel
					DisplayString
			}

		portSlotIndex OBJECT-TYPE
			SYNTAX	INTEGER
			ACCESS	read-only
			STATUS	deprecated
			DESCRIPTION
					"The physical slot number of this slot within the 
					LANplex chassis."
			::= { portEntry 1 }

		portIndex OBJECT-TYPE
			SYNTAX	INTEGER
			ACCESS	read-only
			STATUS	deprecated
			DESCRIPTION
					"The index of the port on a particular slot."
			::= { portEntry 2 }

		portLabel OBJECT-TYPE
			SYNTAX	DisplayString (SIZE (0..32))
			ACCESS	read-write
			STATUS	deprecated
			DESCRIPTION
					"An ASCII text string describing this port."
			::= { portEntry 3 }


       -- The lanplex EEM Table

		eemTable OBJECT-TYPE
			SYNTAX	SEQUENCE OF EEMEntry
			ACCESS	not-accessible
			STATUS	deprecated
			DESCRIPTION
					"A list of Ethernet Express Module (EEM) entries. An entry 
					exists for each Slot Table Entry whose board type is EEM. This 
					table is indexed by the physical slot number of this EEM 
					within the LANplex chassis. The entries may not have
					consecutive Slot Indices.

					Note that this object has been marked as deprecated and is 
					included here for backward compatibilty. It will be removed 
					from the next revision of the lanplex MIB. The objects defined 
					in this table are now available either via the slot group or
					the express group."
			::= { eem 1 }

		eemEntry OBJECT-TYPE
			SYNTAX	EEMEntry
			ACCESS	not-accessible
			STATUS	deprecated
			DESCRIPTION
					"An EEM entry contains information common to a single Ethernet 
					Express Module (EEM) within a LANplex system."
			INDEX	{ eemSlotIndex }
			::= { eemTable 1 }

		EEMEntry ::=
			SEQUENCE {
				eemSlotIndex
					INTEGER,
				eemFddiMACCount
					INTEGER,
				eemBaseFddiMACIndex
					INTEGER,
				eemEthernetPortCount
					INTEGER,
				eemBaseEthernetPortIndex
					INTEGER,
				eemAddressThreshold
					INTEGER
			}

		eemSlotIndex OBJECT-TYPE
			SYNTAX	INTEGER
			ACCESS	read-only
			STATUS	deprecated
			DESCRIPTION
					"The physical slot number of this slot within the LANplex 
					chassis."
			::= { eemEntry 1 }

		eemFddiMACCount OBJECT-TYPE
			SYNTAX	INTEGER
			ACCESS	read-only
			STATUS	deprecated
			DESCRIPTION
					"The number of FDDI MAC's present on this board."
			::= { eemEntry 2 }

		eemBaseFddiMACIndex OBJECT-TYPE
			SYNTAX	INTEGER
			ACCESS	read-only
			STATUS	deprecated
			DESCRIPTION
					"The system-wide index of the first FDDI MAC on 
					this board. Additional FDDI MAC's on this board will 
					have consecutively increasing MAC indices following 
					this index."
			::= { eemEntry 3 }

		eemEthernetPortCount OBJECT-TYPE
			SYNTAX	INTEGER
			ACCESS	read-only
			STATUS	deprecated
			DESCRIPTION
					"The number of Ethernet ports present on this board."
			::= { eemEntry 4 }

		eemBaseEthernetPortIndex OBJECT-TYPE
			SYNTAX	INTEGER
			ACCESS	read-only
			STATUS	deprecated
			DESCRIPTION
					"The system-wide index of the first ethernet port on 
					this board. Additional ports on this board will have
					consecutively increasing Port indices following 
					this index."
			::= { eemEntry 5 }

		eemAddressThreshold OBJECT-TYPE
			SYNTAX	INTEGER 
			ACCESS	read-write
			STATUS	deprecated
			DESCRIPTION
					"A reporting threshold for the total number of Ethernet 
					Addresses known for this board. When this threshold 
					is reached the event eemAddressThresholdEvent is generated."
			::= { eemEntry 6 }


        -- The lanplex EEM FDDI MAC Table

		eemFddiMACTable OBJECT-TYPE
			SYNTAX	SEQUENCE OF EEMFddiMACEntry
			ACCESS	not-accessible
			STATUS	deprecated
			DESCRIPTION
					"A list of EEM FDDI MAC entries. The entries may not 
					have consecutive slot indices.

					Note that this object has been marked as deprecated and is 
					included here for backward compatibilty. It will be removed 
					from the next revision of the lanplex MIB. The objects defined 
					in this table are now available via the expressFddiPort group."
			::= { eemFddiMAC 1 }

		eemFddiMACEntry OBJECT-TYPE
			SYNTAX	EEMFddiMACEntry
			ACCESS	not-accessible
			STATUS	deprecated
			DESCRIPTION
					"An EEM FDDI MAC entry contains information common to an 
					FDDI MAC located on an EEM within a LANplex system."
			INDEX	{ eemFddiSlotIndex, eemFddiMACIndex}
			::= { eemFddiMACTable 1 }

		EEMFddiMACEntry ::=
			SEQUENCE {
				eemFddiSlotIndex
					INTEGER,
				eemFddiMACIndex
					INTEGER,
				eemFddiMACForwardedCts
					Counter,
				eemFddiMACDroppedCts
					Counter
			}

		eemFddiSlotIndex OBJECT-TYPE
			SYNTAX	INTEGER
			ACCESS	read-only
			STATUS	deprecated
			DESCRIPTION
					"The physical slot number of this board."
			::= { eemFddiMACEntry 1 }

		eemFddiMACIndex OBJECT-TYPE
			SYNTAX	INTEGER
			ACCESS	read-only
			STATUS	deprecated
			DESCRIPTION
					"A unique value for each FDDI MAC on this board."
			::= { eemFddiMACEntry 2 }

		eemFddiMACForwardedCts OBJECT-TYPE
			SYNTAX	Counter
			ACCESS	read-only
			STATUS	deprecated
			DESCRIPTION
					"A counter indicating the number of frames forwarded
					 by a MAC from an ethernet port to the FDDI network."
			::= { eemFddiMACEntry 3 }

		eemFddiMACDroppedCts OBJECT-TYPE
			SYNTAX	Counter
			ACCESS	read-only
			STATUS	deprecated
			DESCRIPTION
					"A counter indicating the number of frames that were
					dropped by a MAC due to local resource limitation or 
					unknown destination MAC address."
			::= { eemFddiMACEntry 4 }


        -- The lanplex EEM Ethernet Port Table

		eemEthernetPortTable OBJECT-TYPE
			SYNTAX	SEQUENCE OF EEMEthernetPortEntry
			ACCESS	not-accessible
			STATUS	deprecated
			DESCRIPTION
					"A list of EEM Ethernet Express Port entries. 
					The slot indices may not be consecutive. 
					The MAC indices will be consecutive.

					Note that this object has been marked as deprecated and is 
					included here for backward compatibilty. It will be removed 
					from the next revision of the lanplex MIB. The objects defined 
					in this table are now available via the expressEthernetPort group."
			::= { eemEthernetPort 1 }

		eemEthernetPortEntry OBJECT-TYPE
			SYNTAX	EEMEthernetPortEntry
			ACCESS	not-accessible
			STATUS	deprecated
			DESCRIPTION
					"An EEM Ethernet Express Port entry contains information 
					common to an Ethenet Port located on an Ethernet Express 
					Module (EEM) within a LANplex system."
			INDEX	{ eemEthernetPortSlotIndex, eemEthernetPortIndex }
			::= { eemEthernetPortTable 1 }

		EEMEthernetPortEntry ::=
			SEQUENCE {
				eemEthernetPortSlotIndex
					INTEGER,
				eemEthernetPortIndex
					INTEGER,
				eemEthernetPortLabel
					DisplayString,
				eemEthernetPortForwardedCts
					Counter,
				eemEthernetPortDroppedCts
					Counter,
				eemEthernetPortUTurnCts
					Counter,
				eemEthernetPortState
					INTEGER,
				eemEthernetPortAction
					INTEGER
			}
            
		eemEthernetPortSlotIndex OBJECT-TYPE
			SYNTAX	INTEGER
			ACCESS	read-only
			STATUS	deprecated
			DESCRIPTION
					"The physical slot number of the slot containing 
					this port within the LANplex chassis."
			::= { eemEthernetPortEntry 1 }

		eemEthernetPortIndex OBJECT-TYPE
			SYNTAX	INTEGER
			ACCESS	read-only
			STATUS	deprecated
			DESCRIPTION
					"The index of the port on a particular EEM board.
					This index ranges from 1 to eemEthernetPortCount."
			::= { eemEthernetPortEntry 2 }

		eemEthernetPortLabel OBJECT-TYPE
			SYNTAX	DisplayString (SIZE (0..32))
			ACCESS	read-write
			STATUS	deprecated
			DESCRIPTION
					"An ASCII text string describing this ethernet port."
			::= { eemEthernetPortEntry 3 }

		eemEthernetPortForwardedCts OBJECT-TYPE
			SYNTAX	Counter
			ACCESS	read-only
			STATUS	deprecated
			DESCRIPTION
					"A counter indicating the number of frames forwarded
					from this ethernet port on to the FDDI network."
			::= { eemEthernetPortEntry 4 }

		eemEthernetPortDroppedCts OBJECT-TYPE
			SYNTAX	Counter
			ACCESS	read-only
			STATUS	deprecated
			DESCRIPTION
					"A counter indicating the numer of frames received on 
					this port that were dropped due to the fact that the
					destination MAC address was determined to be on the
					same ethernet segment as the source MAC address.
					."
			::= { eemEthernetPortEntry 5 }

		eemEthernetPortUTurnCts OBJECT-TYPE
			SYNTAX	Counter
			ACCESS	read-only
			STATUS	deprecated
			DESCRIPTION
					"A counter indicating the number of frames received on this
					ethernet port and directed to another ethernet port."
			::= { eemEthernetPortEntry 6 }

		eemEthernetPortState OBJECT-TYPE
			SYNTAX	INTEGER {
						onlineActive(1),
						onlineInactive(2),
						offline(3)
					}
			ACCESS	read-only
			STATUS	deprecated
			DESCRIPTION
					"The state of the Ethernet Express port."
			::= { eemEthernetPortEntry 7 }

		eemEthernetPortAction OBJECT-TYPE
			SYNTAX	INTEGER {
						other(1),
						freezeAddress(2),
						flushAddress(3),
						flushDynamicAddress(4)
					}
			ACCESS	read-write
			STATUS	deprecated
			DESCRIPTION
					"This object, when read, always returns the value other (1).
					The behavior of setting this object to each of the 
					acceptable values is as follows:

						freezeAddress:	causes all the learned dynamic addresses 
										to be converted into static addresses.

						flushAddress:	causes all the addresses to be flushed 
										from a port's address list.

						flushDynamicAddress:	
										causes all the port's dynamic addresses 
										to be flushed from a port's address list."

			::= { eemEthernetPortEntry 8 }


        -- The lanplex EEM Ethernet MAC Address Table

		eemEthernetMACAddressTable OBJECT-TYPE
			SYNTAX	SEQUENCE OF EEMEthernetMACAddressEntry
			ACCESS	not-accessible
			STATUS	deprecated
			DESCRIPTION
					"A list of EEM Ethernet Express Remote MAC Address 
					entries. The slot indices may not be consecutive. 
					The port indices will be consecutive.

					Note that this object has been marked as deprecated and is 
					included here for backward compatibilty. It will be removed 
					from the next revision of the lanplex MIB. The objects defined 
					in this table are now available via the expressEthernetPort group."
			::= { eemMACAddress 1 }

		eemEthernetMACAddressEntry OBJECT-TYPE
			SYNTAX	EEMEthernetMACAddressEntry
			ACCESS	not-accessible
			STATUS	deprecated
			DESCRIPTION
					"A collection of information describing a remote Ethernet MAC 
					detected to be attached to an Ethernet Express port."
			INDEX	{ eemEthernetMACAddressSlotIndex, eemEthernetMACAddressPortIndex,
                        eemEthernetMACAddressIndex}
			::= { eemEthernetMACAddressTable 1 }

		EEMEthernetMACAddressEntry ::=
			SEQUENCE {
				eemEthernetMACAddressSlotIndex
					INTEGER,
				eemEthernetMACAddressPortIndex
					INTEGER,
				eemEthernetMACAddressIndex
					INTEGER,
				eemEthernetMACAddressType
					INTEGER,
				eemEthernetMACAddressRemoteAddress
					OCTET STRING,
				eemEthernetMACAddressIsStatic
					INTEGER,
				eemEthernetMACAddressStaticPort
					INTEGER,
				eemEthernetMACAddressAge
					INTEGER
			}

		eemEthernetMACAddressSlotIndex OBJECT-TYPE
			SYNTAX	INTEGER
			ACCESS	read-write
			STATUS	deprecated
			DESCRIPTION
					"The physical slot number of the slot containing this EEM
					within the LANplex chassis."
			::= { eemEthernetMACAddressEntry 1 }

		eemEthernetMACAddressPortIndex OBJECT-TYPE
			SYNTAX	INTEGER
			ACCESS	read-write
			STATUS	deprecated
			DESCRIPTION
					"The port index of this address entry within the table.
					This index ranges from 1 to eemEthernetPortCount."
			::= { eemEthernetMACAddressEntry 2 }

		eemEthernetMACAddressIndex OBJECT-TYPE
			SYNTAX	INTEGER
			ACCESS	read-write
			STATUS	deprecated
			DESCRIPTION
					"The index of this address entry within the table."
			::= { eemEthernetMACAddressEntry 3 }

		eemEthernetMACAddressType OBJECT-TYPE
			SYNTAX INTEGER {
						other(1),
						invalid(2)
					}
			ACCESS	read-write
			STATUS	deprecated
			DESCRIPTION
					"This object, when read, always returns the value other (1).
					Setting this object to invalid (2) will remove the 
					corresponding address entry from the table."
			::= { eemEthernetMACAddressEntry 4 }

		eemEthernetMACAddressRemoteAddress OBJECT-TYPE
			SYNTAX	OCTET STRING (SIZE (6))
			ACCESS	read-write
			STATUS	deprecated
			DESCRIPTION
					"The remote MAC address detected on this Ethernet Express 
					port."
			::= { eemEthernetMACAddressEntry 5 }

		eemEthernetMACAddressIsStatic OBJECT-TYPE
			SYNTAX	INTEGER {
						isStatic(1),
						isDynamic(2)
					}
			ACCESS	read-write
			STATUS	deprecated
			DESCRIPTION
					"A value indicating whether this MAC address was statically 
					configured or was dynamically learned on this port."
			::= { eemEthernetMACAddressEntry 6 }

		eemEthernetMACAddressStaticPort OBJECT-TYPE
			SYNTAX	INTEGER
			ACCESS	read-write
			STATUS	deprecated
			DESCRIPTION
					"If the object eemEthernetMACAddressIsStatic has 
					value isStatic(1), this object indicates the port for 
					which this MAC address was statically configured."
			::= { eemEthernetMACAddressEntry 7 }

		eemEthernetMACAddressAge OBJECT-TYPE
			SYNTAX	INTEGER
			ACCESS	read-write
			STATUS	deprecated
			DESCRIPTION
					"This object indicates the time elapsed since this MAC address
					was added to this port's address table."
			::= { eemEthernetMACAddressEntry 8 }


		-- XXX NEW GROUPS
		-- The lanplex system Group

		lpSystemId OBJECT-TYPE
			SYNTAX	INTEGER 
			ACCESS	read-only
			STATUS	mandatory
			DESCRIPTION
					"The unique identifier assigned to this system 
					during manufacturing."
			::= { lpSystem 1 }

		lpSystemType OBJECT-TYPE
			SYNTAX	INTEGER {
						other(1),
						tweleveSlot(2),
						fourSlot(3)
					}
			ACCESS	read-only
			STATUS	mandatory
			DESCRIPTION
					"The type of the LANplex system."
			::= { lpSystem 2 }

		lpSystemName OBJECT-TYPE
			SYNTAX	DisplayString (SIZE (0..128))
			ACCESS	read-only
			STATUS	mandatory
			DESCRIPTION
					"The text string describing this system."
			::= { lpSystem 3 }

		lpSystemManufacturer OBJECT-TYPE
			SYNTAX	DisplayString (SIZE (0..128))
			ACCESS	read-only
			STATUS	mandatory
			DESCRIPTION
					"The text string describing the manufacturer of 
					this system."
			::= { lpSystem 4 }

		lpSystemBackplaneRevision OBJECT-TYPE
			SYNTAX	OCTET STRING (SIZE (1)) 
			ACCESS	read-only
			STATUS	mandatory
			DESCRIPTION
					"The revision level of the system backplane. 
					Bits 6 and 7 indicate the artwork revision.
					Bits 0 through 5 indicate the rework level."
			::= { lpSystem 5 }

		lpSystemSlotCount OBJECT-TYPE
			SYNTAX	INTEGER
			ACCESS	read-only
			STATUS	mandatory
			DESCRIPTION
					"The number of slots in the system."
			::= { lpSystem 6 }

		lpSystemMemorySize OBJECT-TYPE
			SYNTAX	INTEGER 
			ACCESS	read-only
			STATUS	mandatory
			DESCRIPTION
					"The amount of memory (RAM), in bytes, present
					on the system processor board." 
			::= { lpSystem 7 }

		lpSystemFlashMemorySize OBJECT-TYPE
			SYNTAX	INTEGER 
			ACCESS	read-only
			STATUS	mandatory
			DESCRIPTION
					"The amount of flash memory, in bytes, present
					on the system processor board."
			::= { lpSystem 8 }

		lpSystemNvMemorySize OBJECT-TYPE
			SYNTAX	INTEGER 
			ACCESS	read-only
			STATUS	mandatory
			DESCRIPTION
					"The amount of non-volatile memory, in bytes, 
					present on the system processor board." 
			::= { lpSystem 9 }

		lpSystemSoftwareRevision OBJECT-TYPE
			SYNTAX	OCTET STRING (SIZE (4)) 
			ACCESS	read-only
			STATUS	mandatory
			DESCRIPTION
					"The revision number of the LANplex system software.
					Each byte indicates the following:
						byte 0:	major release number.
						byte 1:	minor release number.
						byte 2:	update number.
						byte 3:
							bits 7-6:	release type.
							bits 5-0:	supplemental identifier."
			::= { lpSystem 10 }

		lpSystemBuildTime OBJECT-TYPE
			SYNTAX	DisplayString (SIZE (0..128))
			ACCESS	read-only
			STATUS	mandatory
			DESCRIPTION
					"The build time of the system software."
			::= { lpSystem 11 }

		lpSystemControlPanelHardwareRevision OBJECT-TYPE
			SYNTAX	OCTET STRING (SIZE (1)) 
			ACCESS	read-only
			STATUS	mandatory
			DESCRIPTION
					"An 8-bit value specifying the revision level of 
					the control panel hardware."
			::= { lpSystem 12 }

		lpSystemControlPanelSoftwareRevision OBJECT-TYPE
			SYNTAX	OCTET STRING (SIZE (1)) 
			ACCESS	read-only
			STATUS	mandatory
			DESCRIPTION
					"An 8-bit value specifying the revision level of 
					the control panel software."
			::= { lpSystem 13 }

		lpSystemControlPanelLines OBJECT-TYPE
			SYNTAX	INTEGER 
			ACCESS	read-only
			STATUS	mandatory
			DESCRIPTION
					"The number of lines in the control panel
					display."
			::= { lpSystem 14 }

		lpSystemControlPanelColumns OBJECT-TYPE
			SYNTAX	INTEGER 
			ACCESS	read-only
			STATUS	mandatory
			DESCRIPTION
					"The number of columns in the control panel 
					display."
			::= { lpSystem 15 }

		lpSystemControlPanelText OBJECT-TYPE
			SYNTAX	OCTET STRING (SIZE (0..128))
			ACCESS	read-only
			STATUS	mandatory
			DESCRIPTION
					"The currently displayed text in the control panel 
					display."
			::= { lpSystem 16 }

		lpSystemFddiMacCount OBJECT-TYPE
			SYNTAX	INTEGER 
			ACCESS	read-only
			STATUS	mandatory
			DESCRIPTION
					"The number of FDDI MAC's present in the system." 
			::= { lpSystem 17 }

		lpSystemFddiPortCount OBJECT-TYPE
			SYNTAX	INTEGER 
			ACCESS	read-only
			STATUS	mandatory
			DESCRIPTION
					"The number of FDDI ports present in the system." 
			::= { lpSystem 18 }

		lpSystemEthernetPortCount OBJECT-TYPE
			SYNTAX	INTEGER 
			ACCESS	read-only
			STATUS	mandatory
			DESCRIPTION
					"The number of ethernet ports present in the system." 
			::= { lpSystem 19 }

		lpSystemExpressFunctionCount OBJECT-TYPE
			SYNTAX	INTEGER 
			ACCESS	read-only
			STATUS	deprecated
			DESCRIPTION
					"The number of Ethernet Express functions present in 
					the system. Curently this value is equal to the number
					of Express boards present in the system." 
			::= { lpSystem 20 }

		lpSystemExpressFddiPortCount OBJECT-TYPE
			SYNTAX	INTEGER 
			ACCESS	read-only
			STATUS	deprecated
			DESCRIPTION
					"The number of Ethernet Express FDDI ports present 
					in the system." 
			::= { lpSystem 21 }

		lpSystemExpressEthernetPortCount OBJECT-TYPE
			SYNTAX	INTEGER 
			ACCESS	read-only
			STATUS	deprecated
			DESCRIPTION
					"The number of Ethernet Express ethernet ports 
					present in the system." 
			::= { lpSystem 22 }

		lpSystemPowerSupplyCount OBJECT-TYPE
			SYNTAX	INTEGER 
			ACCESS	read-only
			STATUS	mandatory
			DESCRIPTION
					"The number of power supply units present in the system." 
			::= { lpSystem 23 }

		lpSystemAction OBJECT-TYPE
			SYNTAX	INTEGER {
						other(1),
						reset(2)
					}
			ACCESS	read-write
			STATUS	mandatory
			DESCRIPTION
					"This object, when read, always returns the value other (1).
					The behavior of setting this object to each of the 
					acceptable values is as follows:

						reset:	resets the LANplex system."
			::= { lpSystem 24 }

		lpSystemBridgeFunctionCount OBJECT-TYPE
			SYNTAX	INTEGER 
			ACCESS	read-only
			STATUS	mandatory
			DESCRIPTION
					"The number of bridge functions present in 
					the system. Curently this value is equal to the sum of
					the number of Express and Switching modules in the system."
			::= { lpSystem 25 }

		lpSystemSmtProxyTimeoutBase OBJECT-TYPE
			SYNTAX	INTEGER (1..10)
			ACCESS	read-write
			STATUS	mandatory
			DESCRIPTION
					"The initial timeout value, in seconds, before the SMT 
					proxy attempts to backoff and retry.  Since the SMT proxy
					will attempt three retries before determining that the
					proxied station is not answering, with the timeout
					doubling for each retry, the total time for a request to
					time out is equal to seven times the base timeout value."
			::= { lpSystem 26 }

		lpSystemSmtProxyEvents OBJECT-TYPE
			SYNTAX	INTEGER {
						enable(1),
						disable(2)
					}
			ACCESS	read-write
			STATUS	mandatory
			DESCRIPTION
					"This object determines if the SMT proxy will generate
					traps for SMT events occuring at other stations.  If
					enabled, the SMT proxy will generate traps for all SMT
					events, those that occur locally, and those that occur
					at other stations.  If disabled, the SMT proxy will only
					generate traps for events which occur locally.  The
					default value for this object is enabled(1)."
			::= { lpSystem 27 }


		-- The lanplex Slot Table

		lpSlotTable OBJECT-TYPE
			SYNTAX	SEQUENCE OF LpSlotEntry
			ACCESS	not-accessible
			STATUS	mandatory
			DESCRIPTION
					"A list of slot entries. A single instance of this 
					object exists for each slot in the LANplex system."
			::= { lpSlot 1 }

		lpSlotEntry OBJECT-TYPE
			SYNTAX	LpSlotEntry
			ACCESS	not-accessible
			STATUS	mandatory
			DESCRIPTION
					"A slot entry contains information common to a given 
					slot within a LANplex system."
			INDEX	{ lpSlotIndex }
			::= { lpSlotTable 1 }

		LpSlotEntry ::=
			SEQUENCE {
				lpSlotIndex
					INTEGER,
				lpSlotBoardType
					INTEGER,
				lpSlotBoardRevision
					OCTET STRING,
				lpSlotBoardStatus
					INTEGER,
				lpSlotBoardName
					DisplayString,
				lpSlotBoardNameAbbrev
					DisplayString,
				lpSlotFddiMacCount
					INTEGER,
				lpSlotFddiMacBaseIndex
					INTEGER,
				lpSlotFddiPortCount
					INTEGER,
				lpSlotFddiPortBaseIndex
					INTEGER,
				lpSlotEthernetPortCount
					INTEGER,
				lpSlotEthernetPortBaseIndex
					INTEGER,
				lpSlotExpressFunctionCount
					INTEGER,
				lpSlotExpressFunctionBaseIndex
					INTEGER,
				lpSlotExpressFddiPortCount
					INTEGER,
				lpSlotExpressFddiPortBaseIndex
					INTEGER,
				lpSlotExpressEthernetPortCount
					INTEGER,
				lpSlotExpressEthernetPortBaseIndex
					INTEGER,
				lpSlotBoardAction
					INTEGER,
		 		lpSlotBridgeFunctionCount
					INTEGER,
				lpSlotBridgeFunctionBaseIndex
					INTEGER
			}

		lpSlotIndex OBJECT-TYPE
			SYNTAX	INTEGER
			ACCESS	read-only
			STATUS	mandatory
			DESCRIPTION
					"The physical slot number of this slot within the 
					 system."
			::= { lpSlotEntry 1 }

		lpSlotBoardType OBJECT-TYPE
			SYNTAX	INTEGER {
						unknown(1),
						emptySlot(2),
						spm(3),
						feam(4),
						fcm(5), 
						eem(6),
						esm(7),
						fcm2(8)
					}
			ACCESS	read-only
			STATUS	mandatory
			DESCRIPTION
					"The type of board residing in this slot."
			::= { lpSlotEntry 2 }
                
		lpSlotBoardRevision OBJECT-TYPE
			SYNTAX	OCTET STRING (SIZE (1))
			ACCESS	read-only
			STATUS	mandatory
			DESCRIPTION
					"The revision number of the board in this slot."
			::= { lpSlotEntry 3 }

		lpSlotBoardStatus OBJECT-TYPE
			SYNTAX	INTEGER {
						notPresent(1),
						testing(2),
						offline(3),
						online(4)
					}
			ACCESS	read-only
			STATUS	mandatory
			DESCRIPTION
					"The status of the board in this slot."
			::= { lpSlotEntry 4 }

		lpSlotBoardName OBJECT-TYPE
			SYNTAX	DisplayString (SIZE (0..256))
			ACCESS	read-only
			STATUS	mandatory
			DESCRIPTION
					"The text string describing this board."
			::= { lpSlotEntry 5 }

		lpSlotBoardNameAbbrev OBJECT-TYPE
			SYNTAX	DisplayString (SIZE (0..32))
			ACCESS	read-only
			STATUS	mandatory
			DESCRIPTION
					"The abbreviation used to describe this board." 
			::= { lpSlotEntry 6 }

		lpSlotFddiMacCount OBJECT-TYPE
			SYNTAX	INTEGER
			ACCESS	read-only
			STATUS	mandatory
			DESCRIPTION
					"The number of FDDI MAC's present in this slot."
			::= { lpSlotEntry 7 }

 		lpSlotFddiMacBaseIndex OBJECT-TYPE
			SYNTAX	INTEGER
			ACCESS	read-only
			STATUS	mandatory
			DESCRIPTION
					"The index of the first FDDI MAC in this slot."
			::= { lpSlotEntry 8 }

 		lpSlotFddiPortCount OBJECT-TYPE
			SYNTAX	INTEGER
			ACCESS	read-only
			STATUS	mandatory
			DESCRIPTION
					"The number of FDDI ports present in this slot."
			::= { lpSlotEntry 9 }

 		lpSlotFddiPortBaseIndex OBJECT-TYPE
			SYNTAX	INTEGER
			ACCESS	read-only
			STATUS	mandatory
			DESCRIPTION
					"The index of the first FDDI port in this slot."
			::= { lpSlotEntry 10 }

 		lpSlotEthernetPortCount OBJECT-TYPE
			SYNTAX	INTEGER
			ACCESS	read-only
			STATUS	mandatory
			DESCRIPTION
					"The number of ethernet ports present in this slot."
			::= { lpSlotEntry 11 }

 		lpSlotEthernetPortBaseIndex OBJECT-TYPE
			SYNTAX	INTEGER
			ACCESS	read-only
			STATUS	mandatory
			DESCRIPTION
					"The index of the first ethernet port in this slot."
			::= { lpSlotEntry 12 }

 		lpSlotExpressFunctionCount OBJECT-TYPE
			SYNTAX	INTEGER
			ACCESS	read-only
			STATUS	deprecated
			DESCRIPTION
					"The number of Express functions present in this slot."
			::= { lpSlotEntry 13 }

 		lpSlotExpressFunctionBaseIndex OBJECT-TYPE
			SYNTAX	INTEGER
			ACCESS	read-only
			STATUS	deprecated
			DESCRIPTION
					"The index of the first Express function in this slot."
			::= { lpSlotEntry 14 }

 		lpSlotExpressFddiPortCount OBJECT-TYPE
			SYNTAX	INTEGER
			ACCESS	read-only
			STATUS	deprecated
			DESCRIPTION
					"The number of Express FDDI ports present in this slot."
			::= { lpSlotEntry 15 }

 		lpSlotExpressFddiPortBaseIndex OBJECT-TYPE
			SYNTAX	INTEGER
			ACCESS	read-only
			STATUS	deprecated
			DESCRIPTION
					"The index of the first Express FDDI port in this slot."
			::= { lpSlotEntry 16 }

  		lpSlotExpressEthernetPortCount OBJECT-TYPE
			SYNTAX	INTEGER
			ACCESS	read-only
			STATUS	deprecated
			DESCRIPTION
					"The number of Express ethernet ports present 
					in this slot."
			::= { lpSlotEntry 17 }

 		lpSlotExpressEthernetPortBaseIndex OBJECT-TYPE
			SYNTAX	INTEGER
			ACCESS	read-only
			STATUS	deprecated
			DESCRIPTION
					"The index of the first Express ethernet port 
					in this slot."
			::= { lpSlotEntry 18 }

		lpSlotBoardAction OBJECT-TYPE
			SYNTAX	INTEGER {
						other(1),
						runDiagnostics(2)
					}
			ACCESS	read-write
			STATUS	mandatory
			DESCRIPTION
					"This object, when read, always returns the 
					value other (1). The behavior of setting this object 
					to each of the acceptable values is as follows:

						runDiagnostics:	runs the board's offline diagnostics."
			::= { lpSlotEntry 19 }

 		lpSlotBridgeFunctionCount OBJECT-TYPE
			SYNTAX	INTEGER
			ACCESS	read-only
			STATUS	mandatory
			DESCRIPTION
					"The number of bridge functions present in this slot."
			::= { lpSlotEntry 20 }

 		lpSlotBridgeFunctionBaseIndex OBJECT-TYPE
			SYNTAX	INTEGER
			ACCESS	read-only
			STATUS	mandatory
			DESCRIPTION
					"The index of the first bridge function in this slot."
			::= { lpSlotEntry 21 }


 		-- FDDI MAC group

		lpFddiMacTable OBJECT-TYPE
			SYNTAX	SEQUENCE OF LpFddiMacEntry
			ACCESS	not-accessible
			STATUS	mandatory
			DESCRIPTION
					"A list of FDDI MAC entries. A single instance of
					this object exists for each FDDI MAC present 
					in the system."
			::= { lpFddiMac 1 }

		lpFddiMacEntry OBJECT-TYPE
			SYNTAX	LpFddiMacEntry
			ACCESS	not-accessible
			STATUS	mandatory
			DESCRIPTION
					"An FDDI MAC entry contains information common to a 
					particular FDDI MAC within the system."
			INDEX	{ lpFddiMacIndex }
			::= { lpFddiMacTable 1 }

		LpFddiMacEntry ::=
			SEQUENCE {
				lpFddiMacIndex
					INTEGER,
				lpFddiMacSlotIndex
					INTEGER,
				lpFddiMacLocalIndex
					INTEGER,
				lpFddiMacByteReceiveRate
					INTEGER,
				lpFddiMacPeakByteReceiveRate
					INTEGER,
				lpFddiMacFrameReceiveRate
					INTEGER,
				lpFddiMacPeakFrameReceiveRate
					INTEGER,
				lpFddiMacByteTransmitRate
					INTEGER,
				lpFddiMacPeakByteTransmitRate
					INTEGER,
				lpFddiMacFrameTransmitRate
					INTEGER,
				lpFddiMacPeakFrameTransmitRate
					INTEGER,
				lpFddiMacReceiveMulticastThreshold
					INTEGER,
				lpFddiMacBeaconHistory
					OCTET STRING
			}

		lpFddiMacIndex OBJECT-TYPE
			SYNTAX	INTEGER
			ACCESS	read-only
			STATUS	mandatory
			DESCRIPTION
					"A unique value for each FDDI MAC in the system.
					The MAC identified by a particular value of this 
					index is the same MAC as identified by the same 
					value of ifIndex."
			::= { lpFddiMacEntry 1 }

		lpFddiMacSlotIndex OBJECT-TYPE
			SYNTAX	INTEGER
			ACCESS	read-only
			STATUS	mandatory
			DESCRIPTION
					"The slot number corresponding to the physical location
					of this MAC."
			::= { lpFddiMacEntry 2 }

		lpFddiMacLocalIndex OBJECT-TYPE
			SYNTAX	INTEGER
			ACCESS	read-only
			STATUS	mandatory
			DESCRIPTION
					"The index of this MAC relative to the slot on which it
					is physically present."
			::= { lpFddiMacEntry 3 }

		lpFddiMacByteReceiveRate OBJECT-TYPE
			SYNTAX	INTEGER
			ACCESS	read-only
			STATUS	mandatory
			DESCRIPTION
					"The average number of bytes received per second by this
					MAC during the most recent sampling period."
			::= { lpFddiMacEntry 4 }

		lpFddiMacPeakByteReceiveRate OBJECT-TYPE
			SYNTAX	INTEGER
			ACCESS	read-only
			STATUS	mandatory
			DESCRIPTION
					"The peak value of lpFddiMacByteReceiveRate for
					this MAC since the system was last initialized."
			::= { lpFddiMacEntry 5 }

		lpFddiMacFrameReceiveRate OBJECT-TYPE
			SYNTAX	INTEGER
			ACCESS	read-only
			STATUS	mandatory
			DESCRIPTION
					"The average number of frames received per second by this
					MAC during the most recent sampling period."
			::= { lpFddiMacEntry 6 }

		lpFddiMacPeakFrameReceiveRate OBJECT-TYPE
			SYNTAX	INTEGER
			ACCESS	read-only
			STATUS	mandatory
			DESCRIPTION
					"The peak value of lpFddiMacFrameReceiveRate for
					this MAC since the system was last initialized."
			::= { lpFddiMacEntry 7 }

		lpFddiMacByteTransmitRate OBJECT-TYPE
			SYNTAX	INTEGER
			ACCESS	read-only
			STATUS	mandatory
			DESCRIPTION
					"The average number of bytes transmitted per second by
					this MAC during the most recent sampling period."
			::= { lpFddiMacEntry 8 }

		lpFddiMacPeakByteTransmitRate OBJECT-TYPE
			SYNTAX	INTEGER
			ACCESS	read-only
			STATUS	mandatory
			DESCRIPTION
					"The peak value of lpFddiMacByteTransmitRate for
					this MAC since the system was last initialized."
			::= { lpFddiMacEntry 9 }

		lpFddiMacFrameTransmitRate OBJECT-TYPE
			SYNTAX	INTEGER
			ACCESS	read-only
			STATUS	mandatory
			DESCRIPTION
					"The average number of frames transmitted per second by 
					this MAC during the most recent sampling period."
			::= { lpFddiMacEntry 10 }

		lpFddiMacPeakFrameTransmitRate OBJECT-TYPE
			SYNTAX	INTEGER
			ACCESS	read-only
			STATUS	mandatory
			DESCRIPTION
					"The peak value of lpFddiMacFrameTransmitRate for
					this MAC since the system was last initialized."
			::= { lpFddiMacEntry 11 }

		lpFddiMacReceiveMulticastThreshold OBJECT-TYPE
			SYNTAX	INTEGER
			ACCESS	read-write
			STATUS	deprecated
			DESCRIPTION
					"The maximum number of multicast frames per second
					that can be received in the sample interval. The
					sample interval is one second. The default value
					for this object is zero which implies an infinite rate."
			::= { lpFddiMacEntry 12 }

		lpFddiMacBeaconHistory OBJECT-TYPE
			SYNTAX	OCTET STRING (SIZE (0..256))
			ACCESS	read-only
			STATUS	mandatory
			DESCRIPTION
					"This object gives a history of the most recent beacon
					information received on this MAC. It can contain up to
					a maximum of eight records. Each record is of the form:
						source MAC:				6 bytes
						beacon data length:		2 bytes.
						beacon data:			0-16 bytes."
			::= { lpFddiMacEntry 13 }


		-- Ethernet Port group

		lpEthernetPortTable OBJECT-TYPE
			SYNTAX	SEQUENCE OF LpEthernetPortEntry
			ACCESS	not-accessible
			STATUS	mandatory
			DESCRIPTION
					"A list of ethernet port entries. A single instance 
					of this object exists for each ethernet port present
					in the system."
			::= { lpEthernetPort 1 }

		lpEthernetPortEntry OBJECT-TYPE
			SYNTAX	LpEthernetPortEntry
			ACCESS	not-accessible
			STATUS	mandatory
			DESCRIPTION
					"An ethernet port entry contains information common to a 
					particular ethernet port within the system."
			INDEX	{ lpEthernetPortIndex }
			::= { lpEthernetPortTable 1 }

		LpEthernetPortEntry ::=
			SEQUENCE {
				lpEthernetPortIndex
					INTEGER,
				lpEthernetPortSlotIndex
					INTEGER,
				lpEthernetPortLocalIndex
					INTEGER,
				lpEthernetPortLabel
					DisplayString,
				lpEthernetPortChipsetType
					INTEGER,
				lpEthernetPortLinkStatus
					INTEGER,
				lpEthernetPortByteReceiveRate
					INTEGER,
				lpEthernetPortPeakByteReceiveRate
					INTEGER,
				lpEthernetPortFrameReceiveRate
					INTEGER,
				lpEthernetPortPeakFrameReceiveRate
					INTEGER,
				lpEthernetPortByteTransmitRate
					INTEGER,
				lpEthernetPortPeakByteTransmitRate
					INTEGER,
				lpEthernetPortFrameTransmitRate
					INTEGER,
				lpEthernetPortPeakFrameTransmitRate
					INTEGER,
				lpEthernetPortReceiveMulticastThreshold
					INTEGER,
				lpEthernetPortType
					INTEGER
			}

		lpEthernetPortIndex OBJECT-TYPE
			SYNTAX	INTEGER
			ACCESS	read-only
			STATUS	mandatory
			DESCRIPTION
					"A unique value for each ethernet port in the system.
					The port identified by a particular value of this 
					index is the same port as identified by the same 
					value of ifIndex."
			::= { lpEthernetPortEntry 1 }

		lpEthernetPortSlotIndex OBJECT-TYPE
			SYNTAX	INTEGER
			ACCESS	read-only
			STATUS	mandatory
			DESCRIPTION
					"The slot number corresponding to the physical location
					of this port."
			::= { lpEthernetPortEntry 2 }

		lpEthernetPortLocalIndex OBJECT-TYPE
			SYNTAX	INTEGER
			ACCESS	read-only
			STATUS	mandatory
			DESCRIPTION
					"The index of this port relative to the slot on which it
					is physically present."
			::= { lpEthernetPortEntry 3 }

		lpEthernetPortLabel OBJECT-TYPE
			SYNTAX	DisplayString (SIZE (0..32))
			ACCESS	read-write
			STATUS	mandatory
			DESCRIPTION
					"An ASCII text string describing this port."
			::= { lpEthernetPortEntry 4 }

		lpEthernetPortChipsetType OBJECT-TYPE
			SYNTAX	INTEGER {
						other(1),
						chipsetAMD79900(2),
						chipsetIntel82586(3),
						chipsetIntel82596(4),
						chipsetSEEQ8003(5),
						chipsetNational8390(6),
						chipsetNationalSonic(7),
						chipsetFujitsu86950(8)
					}
			ACCESS	read-only
			STATUS	mandatory
			DESCRIPTION
					"The type of chipset used to implement this port."
			::= { lpEthernetPortEntry 5 }

		lpEthernetPortLinkStatus OBJECT-TYPE
			SYNTAX	INTEGER {
						active(1),
						inActive(2)
					}
			ACCESS	read-only
			STATUS	mandatory
			DESCRIPTION
					"The current value of the link status for this port."
			::= { lpEthernetPortEntry 6 }

		lpEthernetPortByteReceiveRate OBJECT-TYPE
			SYNTAX	INTEGER
			ACCESS	read-only
			STATUS	mandatory
			DESCRIPTION
					"The average number of bytes received per second by this
					port during the most recent sampling period."
			::= { lpEthernetPortEntry 7 }

		lpEthernetPortPeakByteReceiveRate OBJECT-TYPE
			SYNTAX	INTEGER
			ACCESS	read-only
			STATUS	mandatory
			DESCRIPTION
					"The peak value of lpEthernetPortByteReceiveRate for
					this port since the system was last initialized."
			::= { lpEthernetPortEntry 8 }

		lpEthernetPortFrameReceiveRate OBJECT-TYPE
			SYNTAX	INTEGER
			ACCESS	read-only
			STATUS	mandatory
			DESCRIPTION
					"The average number of frames received per second by this
					port during the most recent sampling period."
			::= { lpEthernetPortEntry 9 }

		lpEthernetPortPeakFrameReceiveRate OBJECT-TYPE
			SYNTAX	INTEGER
			ACCESS	read-only
			STATUS	mandatory
			DESCRIPTION
					"The peak value of lpEthernetPortFrameReceiveRate for
					this port since the system was last initialized."
			::= { lpEthernetPortEntry 10 }

		lpEthernetPortByteTransmitRate OBJECT-TYPE
			SYNTAX	INTEGER
			ACCESS	read-only
			STATUS	mandatory
			DESCRIPTION
					"The average number of bytes transmitted per second by
					this port during the most recent sampling period."
			::= { lpEthernetPortEntry 11 }

		lpEthernetPortPeakByteTransmitRate OBJECT-TYPE
			SYNTAX	INTEGER
			ACCESS	read-only
			STATUS	mandatory
			DESCRIPTION
					"The peak value of lpEthernetPortByteTransmitRate for
					this port since the system was last initialized."
			::= { lpEthernetPortEntry 12 }

		lpEthernetPortFrameTransmitRate OBJECT-TYPE
			SYNTAX	INTEGER
			ACCESS	read-only
			STATUS	mandatory
			DESCRIPTION
					"The average number of frames transmitted per second by 
					this port during the most recent sampling period."
			::= { lpEthernetPortEntry 13 }

		lpEthernetPortPeakFrameTransmitRate OBJECT-TYPE
			SYNTAX	INTEGER
			ACCESS	read-only
			STATUS	mandatory
			DESCRIPTION
					"The peak value of lpEthernetPortFrameTransmitRate for
					this port since the system was last initialized."
			::= { lpEthernetPortEntry 14 }

		lpEthernetPortReceiveMulticastThreshold OBJECT-TYPE
			SYNTAX	INTEGER
			ACCESS	read-write
			STATUS	deprecated
			DESCRIPTION
					"The maximum number of multicast frames per second
					that can be received in the sample interval. The
					sample interval is four seconds. The default value
					for this object is zero which implies an infinite rate."
			::= { lpEthernetPortEntry 15 }

		lpEthernetPortType OBJECT-TYPE
			SYNTAX	INTEGER {
						telco10BaseT(1),
						rj4510BaseT(2),
						foirl(3),
						aui(4),
						other(5)
					}
			ACCESS	read-write
			STATUS	mandatory
			DESCRIPTION
					"Specific description of this port's type."
			::= { lpEthernetPortEntry 16 }


 		-- FDDI port group

		lpFddiPortTable OBJECT-TYPE
			SYNTAX	SEQUENCE OF LpFddiPortEntry
			ACCESS	not-accessible
			STATUS	mandatory
			DESCRIPTION
					"A list of FDDI port entries. A single instance of this
					object exists for each FDDI port in the system."
			::= { lpFddiPort 1 }

		lpFddiPortEntry OBJECT-TYPE
			SYNTAX	LpFddiPortEntry
			ACCESS	not-accessible
			STATUS	mandatory
			DESCRIPTION
					"A Port entry contains information common to a 
					particular FDDI port in the system."
			INDEX	{ lpFddiPortIndex }
			::= { lpFddiPortTable 1 }

		LpFddiPortEntry ::=
			SEQUENCE {
				lpFddiPortIndex
					INTEGER,
				lpFddiPortSlotIndex
					INTEGER,
				lpFddiPortLocalIndex
					INTEGER,
				lpFddiPortLabel
					DisplayString
			}

		lpFddiPortIndex OBJECT-TYPE
			SYNTAX	INTEGER
			ACCESS	read-only
			STATUS	mandatory
			DESCRIPTION
					"A unique value for each FDDI port in the system. 
					It's value ranges between 1 and the value of 
					lpSystemFddiPortCount."
			::= { lpFddiPortEntry 1 }

		lpFddiPortSlotIndex OBJECT-TYPE
			SYNTAX	INTEGER
			ACCESS	read-only
			STATUS	mandatory
			DESCRIPTION
					"The slot number corresponding to the physical location
					of this port."
			::= { lpFddiPortEntry 2 }

		lpFddiPortLocalIndex OBJECT-TYPE
			SYNTAX	INTEGER
			ACCESS	read-only
			STATUS	mandatory
			DESCRIPTION
					"The index of this port relative to the slot on which it
					is physically present."
			::= { lpFddiPortEntry 3 }

		lpFddiPortLabel OBJECT-TYPE
			SYNTAX	DisplayString (SIZE (0..32))
			ACCESS	read-write
			STATUS	mandatory
			DESCRIPTION
					"An ASCII text string describing this port."
			::= { lpFddiPortEntry 4 }


 		-- Express Function group

		lpExpressTable OBJECT-TYPE
			SYNTAX	SEQUENCE OF LpExpressEntry
			ACCESS	not-accessible
			STATUS	deprecated
			DESCRIPTION
					"A list of Express function entries."
			::= { lpExpress 1 }

		lpExpressEntry OBJECT-TYPE
			SYNTAX	LpExpressEntry
			ACCESS	not-accessible
			STATUS	deprecated
			DESCRIPTION
					"An Express entry contains information common to a 
					particular Express function in a given system."
			INDEX	{ lpExpressIndex }
			::= { lpExpressTable 1 }

		LpExpressEntry ::=
			SEQUENCE {
				lpExpressIndex
					INTEGER,
				lpExpressSlotIndex
					INTEGER,
				lpExpressLocalIndex
					INTEGER,
				lpExpressAddressThreshold
					INTEGER
			}

		lpExpressIndex OBJECT-TYPE
			SYNTAX	INTEGER
			ACCESS	read-only
			STATUS	deprecated
			DESCRIPTION
					"A unique value for each Express function in the system.
					It's value ranges between 1 and the value of
					lpSystemExpressFunctionCount."
			::= { lpExpressEntry 1 }

		lpExpressSlotIndex OBJECT-TYPE
			SYNTAX	INTEGER
			ACCESS	read-only
			STATUS	deprecated
			DESCRIPTION
					"The slot number corresponding to the physical location
					of this function."
			::= { lpExpressEntry 2 }

		lpExpressLocalIndex OBJECT-TYPE
			SYNTAX	INTEGER
			ACCESS	read-only
			STATUS	deprecated
			DESCRIPTION
					"The index of this function relative to the slot on which it
					is physically present."
			::= { lpExpressEntry 3 }

		lpExpressAddressThreshold OBJECT-TYPE
			SYNTAX	INTEGER 
			ACCESS	read-write
			STATUS	deprecated
			DESCRIPTION
					"A reporting threshold for the total number of Ethernet 
					Addresses known for this board. When this threshold 
					is reached, the event lpEemAddressThresholdEvent is 
					generated."
			::= { lpExpressEntry 4 }


  		-- Express FDDI Port group

		lpExpressFddiPortTable OBJECT-TYPE
			SYNTAX	SEQUENCE OF LpExpressFddiPortEntry
			ACCESS	not-accessible
			STATUS	deprecated
			DESCRIPTION
					"A list of Express FDDI port entries."
			::= { lpExpressFddiPort 1 }

		lpExpressFddiPortEntry OBJECT-TYPE
			SYNTAX	LpExpressFddiPortEntry
			ACCESS	not-accessible
			STATUS	deprecated
			DESCRIPTION
					"A Port entry contains information for a particular 
					Express FDDI port in a given system."
			INDEX	{ lpExpressFddiPortIndex }
			::= { lpExpressFddiPortTable 1 }

		LpExpressFddiPortEntry ::=
			SEQUENCE {
				lpExpressFddiPortIndex
					INTEGER,
				lpExpressFddiPortSlotIndex
					INTEGER,
				lpExpressFddiPortLocalIndex
					INTEGER,
				lpExpressFddiPortForwardedCts
					Counter,
				lpExpressFddiPortDroppedCts
					Counter
			}

		lpExpressFddiPortIndex OBJECT-TYPE
			SYNTAX	INTEGER
			ACCESS	read-only
			STATUS	deprecated
			DESCRIPTION
					"A unique value for each Express port in the system.
					It's value ranges between 1 and the value of
					lpSystemExpressFddiPortCount."
			::= { lpExpressFddiPortEntry 1 }

		lpExpressFddiPortSlotIndex OBJECT-TYPE
			SYNTAX	INTEGER
			ACCESS	read-only
			STATUS	deprecated
			DESCRIPTION
					"The slot number corresponding to the physical location
					of this port."
			::= { lpExpressFddiPortEntry 2 }

		lpExpressFddiPortLocalIndex OBJECT-TYPE
			SYNTAX	INTEGER
			ACCESS	read-only
			STATUS	deprecated
			DESCRIPTION
					"The index of this port relative to the slot on which it
					is physically present."
			::= { lpExpressFddiPortEntry 3 }

		lpExpressFddiPortForwardedCts OBJECT-TYPE
			SYNTAX	Counter
			ACCESS	read-only
			STATUS	deprecated
			DESCRIPTION
					"The number of frames forwarded by this MAC from
					 an ethernet port to the FDDI network."
			::= { lpExpressFddiPortEntry 4 }

		lpExpressFddiPortDroppedCts OBJECT-TYPE
			SYNTAX	Counter
			ACCESS	read-only
			STATUS	deprecated
			DESCRIPTION
					"The number of frames received by this MAC that
					 were not forwarded."
			::= { lpExpressFddiPortEntry 5 }


  		-- Express Ethernet Port group

		lpExpressEthernetPortTable OBJECT-TYPE
			SYNTAX	SEQUENCE OF LpExpressEthernetPortEntry
			ACCESS	not-accessible
			STATUS	deprecated
			DESCRIPTION
					"A list of Express ethernet port entries."
			::= { lpExpressEthernetPort 1 }

		lpExpressEthernetPortEntry OBJECT-TYPE
			SYNTAX	LpExpressEthernetPortEntry
			ACCESS	not-accessible
			STATUS	deprecated
			DESCRIPTION
					"An Expres ethernet port entry contains information
					common to a particular Express ethernet port located
					in the system."
			INDEX	{ lpExpressEthernetPortIndex }
			::= { lpExpressEthernetPortTable 1 }

		LpExpressEthernetPortEntry ::=
			SEQUENCE {
				lpExpressEthernetPortIndex
					INTEGER,
				lpExpressEthernetPortSlotIndex
					INTEGER,
				lpExpressEthernetPortLocalIndex
					INTEGER,
				lpExpressEthernetPortForwardedCts
					Counter,
				lpExpressEthernetPortDroppedCts
					Counter,
				lpExpressEthernetPortUTurnCts
					Counter,
				lpExpressEthernetPortAction
					INTEGER
			}

		lpExpressEthernetPortIndex OBJECT-TYPE
			SYNTAX	INTEGER
			ACCESS	read-only
			STATUS	deprecated
			DESCRIPTION
					"A unique value for each Express ethernet port in the 
					system. It's value ranges between 1 and the value of
					lpSystemExpressEthernetPortCount."
			::= { lpExpressEthernetPortEntry 1 }

		lpExpressEthernetPortSlotIndex OBJECT-TYPE
			SYNTAX	INTEGER
			ACCESS	read-only
			STATUS	deprecated
			DESCRIPTION
					"The slot number corresponding to the physical location
					of this port."
			::= { lpExpressEthernetPortEntry 2 }

		lpExpressEthernetPortLocalIndex OBJECT-TYPE
			SYNTAX	INTEGER
			ACCESS	read-only
			STATUS	deprecated
			DESCRIPTION
					"The index of this port relative to the slot on which it
					is physically present."
			::= { lpExpressEthernetPortEntry 3 }

		lpExpressEthernetPortForwardedCts OBJECT-TYPE
			SYNTAX	Counter
			ACCESS	read-only
			STATUS	deprecated
			DESCRIPTION
					"The number of frames forwarded from this ethernet
					 port to the FDDI network."
			::= { lpExpressEthernetPortEntry 4 }

		lpExpressEthernetPortDroppedCts OBJECT-TYPE
			SYNTAX	Counter
			ACCESS	read-only
			STATUS	deprecated
			DESCRIPTION
					"The number of frames received by this ethernet
					 port that were not forwarded or u-turned."
			::= { lpExpressEthernetPortEntry 5 }

		lpExpressEthernetPortUTurnCts OBJECT-TYPE
			SYNTAX	Counter
			ACCESS	read-only
			STATUS	deprecated
			DESCRIPTION
					"The number of frames received by this ethernet
					 port that were directed to another ethernet port."
			::= { lpExpressEthernetPortEntry 6 }

		lpExpressEthernetPortAction OBJECT-TYPE
			SYNTAX	INTEGER {
						other(1),
						freezeAddress(2),
						flushAddress(3),
						flushDynamicAddress(4)
					}
			ACCESS	read-write
			STATUS	deprecated
			DESCRIPTION
					"This object, when read, always returns the value other (1).
					The behavior of setting this object to each of the 
					acceptable values is as follows:

						freezeAddress:	causes all the learned dynamic addresses 
										to be converted into static addresses.

						flushAddress:	causes all the addresses to be flushed 
										from a port's address list.

						flushDynamicAddress:	
										causes all the port's dynamic addresses 
										to be flushed from a port's address list."

			::= { lpExpressEthernetPortEntry 7 }

  
      -- Express Ethernet port Address Table

		lpExpressEthernetPortAddressTable OBJECT-TYPE
			SYNTAX	SEQUENCE OF LpExpressEthernetPortAddressEntry
			ACCESS	not-accessible
			STATUS	deprecated
			DESCRIPTION
					"A list of Express Remote MAC Address entries."
			::= { lpExpressEthernetPortAddress 1 }

		lpExpressEthernetPortAddressEntry OBJECT-TYPE
			SYNTAX	LpExpressEthernetPortAddressEntry
			ACCESS	not-accessible
			STATUS	deprecated
			DESCRIPTION
					"An entry contains information describing a remote Ethernet 
					MAC detected to be attached to an Express port."
			INDEX	{ lpExpressEthernetPortAddressPortIndex, 
						lpExpressEthernetPortAddressIndex }
			::= { lpExpressEthernetPortAddressTable 1 }

		LpExpressEthernetPortAddressEntry ::=
			SEQUENCE {
				lpExpressEthernetPortAddressPortIndex
					INTEGER,
				lpExpressEthernetPortAddressIndex
					INTEGER,
				lpExpressEthernetPortAddressSlotIndex
					INTEGER,
				lpExpressEthernetPortAddressType
					INTEGER,
				lpExpressEthernetPortAddressRemoteAddress
					OCTET STRING,
				lpExpressEthernetPortAddressIsStatic
					INTEGER,
				lpExpressEthernetPortAddressStaticPort
					INTEGER,
				lpExpressEthernetPortAddressAge
					INTEGER
			}

		lpExpressEthernetPortAddressPortIndex OBJECT-TYPE
			SYNTAX	INTEGER
			ACCESS	read-write
			STATUS	deprecated
			DESCRIPTION
					"A unique value for each Express ethernet port in the
					 system. It's value ranges between 1 and the value of
					lpSystemExpressEthernetPortCount."
			::= { lpExpressEthernetPortAddressEntry 1 }

		lpExpressEthernetPortAddressIndex OBJECT-TYPE
			SYNTAX	INTEGER
			ACCESS	read-write
			STATUS	deprecated
			DESCRIPTION
					"The index of this address entry within the address table." 
			::= { lpExpressEthernetPortAddressEntry 2 }

		lpExpressEthernetPortAddressSlotIndex OBJECT-TYPE
			SYNTAX	INTEGER
			ACCESS	read-write
			STATUS	deprecated
			DESCRIPTION
					"The slot number corresponding to the physical location
					of this port."
			::= { lpExpressEthernetPortAddressEntry 3 }

		lpExpressEthernetPortAddressType OBJECT-TYPE
			SYNTAX INTEGER {
						other(1),
						invalid(2)
					}
			ACCESS	read-write
			STATUS	deprecated
			DESCRIPTION
					"This object, when read, always returns the value other (1).
					Setting this object to invalid (2) will remove the 
					corresponding address entry from the table."
			::= { lpExpressEthernetPortAddressEntry 4 }

		lpExpressEthernetPortAddressRemoteAddress OBJECT-TYPE
			SYNTAX	OCTET STRING (SIZE (6))
			ACCESS	read-write
			STATUS	deprecated
			DESCRIPTION
					"The remote MAC address detected on this port."
			::= { lpExpressEthernetPortAddressEntry 5 }

		lpExpressEthernetPortAddressIsStatic OBJECT-TYPE
			SYNTAX	INTEGER {
						isStatic(1),
						isDynamic(2)
					}
			ACCESS	read-write
			STATUS	deprecated
			DESCRIPTION
					"A value indicating whether this MAC address was statically 
					configured or was dynamically learned on this port."
			::= { lpExpressEthernetPortAddressEntry 6 }

		lpExpressEthernetPortAddressStaticPort OBJECT-TYPE
			SYNTAX	INTEGER
			ACCESS	read-write
			STATUS	deprecated
			DESCRIPTION
					"If the object lpExpressEthernetPortAddressIsStatic has 
					value isStatic(1), this object indicates the port for 
					which this MAC address was statically configured."
			::= { lpExpressEthernetPortAddressEntry 7 }

		lpExpressEthernetPortAddressAge OBJECT-TYPE
			SYNTAX	INTEGER
			ACCESS	read-write
			STATUS	deprecated
			DESCRIPTION
					"This object indicates the time, in seconds, elapsed since 
					this MAC address was added to this port's address table."
			::= { lpExpressEthernetPortAddressEntry 8 }


 		-- Power Supply group

		lpPowerSupplyTable OBJECT-TYPE
			SYNTAX	SEQUENCE OF LpPowerSupplyEntry
			ACCESS	not-accessible
			STATUS	mandatory
			DESCRIPTION
					"A list of power supply entries."
			::= { lpPowerSupply 1 }

		lpPowerSupplyEntry OBJECT-TYPE
			SYNTAX	LpPowerSupplyEntry
			ACCESS	not-accessible
			STATUS	mandatory
			DESCRIPTION
					"A power supply entry contains information common for
					a particular power supply unit in the system."
			INDEX	{ lpPowerSupplyIndex }
			::= { lpPowerSupplyTable 1 }

		LpPowerSupplyEntry ::=
			SEQUENCE {
				lpPowerSupplyIndex
					INTEGER,
				lpPowerSupplyLocation
					INTEGER,
				lpPowerSupplyStatus
					INTEGER,
				lpPowerSupplyFailureType
					INTEGER,
				lpPowerSupplyLastFailure
					INTEGER
			}

		lpPowerSupplyIndex OBJECT-TYPE
			SYNTAX	INTEGER
			ACCESS	read-only
			STATUS	mandatory
			DESCRIPTION
					"A unique value for each power supply in the system.
					It's value ranges between 1 and the value of
					lpSystemPowerSupplyCount."
			::= { lpPowerSupplyEntry 1 }

		lpPowerSupplyLocation OBJECT-TYPE
			SYNTAX	INTEGER
			ACCESS	read-only
			STATUS	mandatory
			DESCRIPTION
					"The physical slot in which this power supply unit 
					resides in the system."
			::= { lpPowerSupplyEntry 2 }

		lpPowerSupplyStatus OBJECT-TYPE
			SYNTAX INTEGER
			ACCESS	read-only
			STATUS	mandatory
			DESCRIPTION
					"The status of the power supply. A value of 0 indicates
					a working unit. A non-zero value represents a bit mask of
					the possible failure types. Each set bit indicates the
					following failure type:
						bit0:	systemAcFailure
						bit1:	systemPlus5Failure
						bit2:	systemPlus12Failure
						bit3:	systemOverTemperatureFailure."
			::= { lpPowerSupplyEntry 3 }

		lpPowerSupplyFailureType OBJECT-TYPE
			SYNTAX INTEGER {
						systemAcFailure(1),
						systemPlus5Failure(2),
						systemPlus12Failure(3),
						systemOverTemperatureFailure(4)
					}
			ACCESS	not-accessible
			STATUS	deprecated
			DESCRIPTION
					"This object is sent in the varlist when the 
					lpPowerSupplyFailureEvent trap is generated. It 
					indicates the particular failure type that caused
					this trap to be generated."
			::= { lpPowerSupplyEntry 4 }

		lpPowerSupplyLastFailure OBJECT-TYPE
			SYNTAX INTEGER {
						systemAcFailure(1),
						systemPlus5Failure(2),
						systemPlus12Failure(3),
						systemOverTemperatureFailure(4),
						none(5)
					}
			ACCESS	read-only
			STATUS	mandatory
			DESCRIPTION
					"This object represents the most recent power
					supply failure type.  If no failure has occured,
					the value of this object is none.  This object is
					included in the varlist when the lpPowerSupplyFailureEvent 
					trap is generated.  It indicates the failure type that 
					caused the trap to be generated."
			::= { lpPowerSupplyEntry 5 }


 		-- Bridge Function Group

		lpBridgeTable OBJECT-TYPE
			SYNTAX	SEQUENCE OF LpBridgeEntry
			ACCESS	not-accessible
			STATUS	mandatory
			DESCRIPTION
					"A list of bridge function entries."
			::= { lpBridge 1 }

		lpBridgeEntry OBJECT-TYPE
			SYNTAX	LpBridgeEntry
			ACCESS	not-accessible
			STATUS	mandatory
			DESCRIPTION
					"A bridge entry contains information common to a 
					particular bridge function in a given system."
			INDEX	{ lpBridgeIndex }
			::= { lpBridgeTable 1 }

		LpBridgeEntry ::=
			SEQUENCE {
				lpBridgeIndex
					INTEGER,
				lpBridgeBaseSlotIndex
					INTEGER,
				lpBridgePortCount
					INTEGER,
				lpBridgeAddressTableSize
					INTEGER,
				lpBridgeAddressThreshold
					INTEGER,
				lpBridgeMode
					INTEGER,
				lpBridgeLocalIndex
					INTEGER
			}

		lpBridgeIndex OBJECT-TYPE
			SYNTAX	INTEGER
			ACCESS	read-only
			STATUS	mandatory
			DESCRIPTION
					"A unique value for each bridge function in the system.
					It's value ranges between 1 and the value of
					lpSystemBridgeFunctionCount."
			::= { lpBridgeEntry 1 }

		lpBridgeBaseSlotIndex OBJECT-TYPE
			SYNTAX	INTEGER
			ACCESS	read-only
			STATUS	mandatory
			DESCRIPTION
					"The slot number of the lowest numbered slot which 
					contains a physical port that this bridge function 
					controls."
			::= { lpBridgeEntry 2 }

		lpBridgePortCount OBJECT-TYPE
			SYNTAX	INTEGER
			ACCESS	read-only
			STATUS	mandatory
			DESCRIPTION
					"The number of ports that this bridge function controls."
			::= { lpBridgeEntry 3 }

		lpBridgeAddressTableSize OBJECT-TYPE
			SYNTAX	INTEGER 
			ACCESS	read-only
			STATUS	mandatory
			DESCRIPTION
					"The size of the address table for this bridge function."
			::= { lpBridgeEntry 4 }

		lpBridgeAddressThreshold OBJECT-TYPE
			SYNTAX	INTEGER 
			ACCESS	read-write
			STATUS	mandatory
			DESCRIPTION
					"A reporting threshold for the total number of 
					addresses known for this board. When this threshold 
					is reached, the event lpBridgeAddressThresholdEvent is 
					generated.  The range of valid values for setting this 
					object is between 1 and the value reported by 
					lpBridgeAddressTableSize + 1 (Note that this range
					applies to values issued in set requests.  The current
					value may be outside this range, for example if the value
					of lpBridgeMode is changed).  Setting this object to one
					greater than the address table size disables the generation
					of lpBridgeAddressThresholdEvents since the limit will 
					never be reached."
			::= { lpBridgeEntry 5 }

		lpBridgeMode OBJECT-TYPE
			SYNTAX	INTEGER {
						expressMode(1),
						ieee8021dBridgeMode(2),
						notSupported(3)
					}
			ACCESS	read-write
			STATUS	mandatory
			DESCRIPTION
					"The operational mode of this bridge function.  Note that
					bridges which report notSupported(3) will not support sets
					of this object, and that the value notSupported(3) is not
					a valid value for a set operation."
			::= { lpBridgeEntry 6 }

		lpBridgeLocalIndex OBJECT-TYPE
			SYNTAX	INTEGER
			ACCESS	read-only
			STATUS	mandatory
			DESCRIPTION
					"The index of this bridge function relative to the slot 
					on which it is physically present."
			::= { lpBridgeEntry 7 }


  		-- Bridge Port Table

		lpBridgePortTable OBJECT-TYPE
			SYNTAX	SEQUENCE OF LpBridgePortEntry
			ACCESS	not-accessible
			STATUS	mandatory
			DESCRIPTION
					"A list of bridge port entries."
			::= { lpBridge 2 }

		lpBridgePortEntry OBJECT-TYPE
			SYNTAX	LpBridgePortEntry
			ACCESS	not-accessible
			STATUS	mandatory
			DESCRIPTION
					"A Port entry contains information for a particular 
					bridge port in a given system."
			INDEX	{ lpBridgePortBridgeIndex, lpBridgePortIndex }
			::= { lpBridgePortTable 1 }

		LpBridgePortEntry ::=
			SEQUENCE {
				lpBridgePortBridgeIndex
					INTEGER,
				lpBridgePortIndex
					INTEGER,
				lpBridgePortSlotIndex
					INTEGER,
				lpBridgePortLocalIndex
					INTEGER,
				lpBridgePortType
					INTEGER,
				lpBridgePortIpFragmentationEnabled
					INTEGER,
				lpBridgePortReceiveMulticastLimit
					INTEGER,
				lpBridgePortAddressAction
					INTEGER,
				lpBridgePortTotalForwardedCts
					Counter,
				lpBridgePortManagementFramesReceived
					Counter,
				lpBridgePortTotalDiscards
					Counter,
				lpBridgePortReceiveBlockedDiscards
					Counter,
				lpBridgePortReceiveMulticastLimitExceededs
					Counter,
				lpBridgePortReceiveSecurityDiscards
					Counter,
				lpBridgePortReceiveUnknownDiscards
					Counter,
				lpBridgePortReceiveOtherDiscards
					Counter,
				lpBridgePortReceiveErrorDiscards
					Counter,
				lpBridgePortSameSegmentDiscards
					Counter,
				lpBridgePortTransmitBlockedDiscards
					Counter,
				lpBridgePortTotalFiltered
					Counter,
				lpBridgePortReceiveUnicastFiltered
					Counter,
				lpBridgePortReceiveMulticastFiltered
					Counter,
				lpBridgePortTransmitUnicastFiltered
					Counter,
				lpBridgePortTransmitMulticastFiltered
					Counter,
				lpBridgePortReceiveMulticastLimitExceededCount
					Counter
			}

		lpBridgePortBridgeIndex OBJECT-TYPE
			SYNTAX	INTEGER
			ACCESS	read-only
			STATUS	mandatory
			DESCRIPTION
					"A unique value for each bridge function in the system.
					It's value ranges between 1 and the value of
					lpSystemBridgeFunctionCount."
			::= { lpBridgePortEntry 1 }

		lpBridgePortIndex OBJECT-TYPE
			SYNTAX	INTEGER
			ACCESS	read-only
			STATUS	mandatory
			DESCRIPTION
					"A unique value for each bridge port controlled by a given
					bridge function.  It's value ranges between 1 and the 
					value of lpBridgePortCount for the bridge function
					which this entry references."
			::= { lpBridgePortEntry 2 }

		lpBridgePortSlotIndex OBJECT-TYPE
			SYNTAX	INTEGER
			ACCESS	read-only
			STATUS	mandatory
			DESCRIPTION
					"The slot number corresponding to the physical location
					of this port."
			::= { lpBridgePortEntry 3 }

		lpBridgePortLocalIndex OBJECT-TYPE
			SYNTAX	INTEGER
			ACCESS	read-only
			STATUS	mandatory
			DESCRIPTION
					"The index of this port relative to the slot on which it
					is physically present and its port type.  For example
					FDDI ports in a slot are identified with local indices from
					1 to the number of FDDI ports in that slot, and the Ethernet
					ports in the same slot are identified with local indices from
					1 to the number of Ethernet ports in that slot."
			::= { lpBridgePortEntry 4 }

		lpBridgePortType OBJECT-TYPE
			SYNTAX  INTEGER {
						ethernet(1),
						fddi(2),
						other(3)
					}
			ACCESS  read-only
			STATUS  mandatory
			DESCRIPTION
					"The type of this port."
			::= { lpBridgePortEntry 5 }

		lpBridgePortIpFragmentationEnabled OBJECT-TYPE
			SYNTAX	INTEGER {
						true(1),
						false(2),
						notSupported(3)
					}
			ACCESS	read-write
			STATUS	mandatory
			DESCRIPTION
					"A flag indicating whether or not IP fragmentation is
					enabled on this bridge port.  Note that bridges which 
					report notSupported(3) will not support sets of this
					object, and that the value notSupported(3) is not
					a valid value for a set operation."
			::= { lpBridgePortEntry 6 }

		lpBridgePortReceiveMulticastLimit OBJECT-TYPE
			SYNTAX	INTEGER (0..65535)
			ACCESS	read-write
			STATUS	mandatory
			DESCRIPTION
					"The maximum number of multicast frames per second
					that can be received in the sample interval. The
					sample interval is one second. The default value
					for this object is zero which implies an infinite rate."
			::= { lpBridgePortEntry 7 }

		lpBridgePortAddressAction OBJECT-TYPE
			SYNTAX	INTEGER {
						other(1),
						freezeAddress(2),
						flushAddress(3),
						flushDynamicAddress(4)
					}
			ACCESS	read-write
			STATUS	mandatory
			DESCRIPTION
					"This object, when read, always returns the value other (1).
					The behavior of setting this object to each of the 
					acceptable values is as follows:

						freezeAddress:	causes all the learned dynamic addresses 
										to be converted into static addresses.

						flushAddress:	causes all the addresses to be flushed 
										from the port's address list.

						flushDynamicAddress:	
										causes all dynamic addresses to be
										flushed from the port's address list."
			::= { lpBridgePortEntry 8 }

		lpBridgePortTotalForwardedCts OBJECT-TYPE
			SYNTAX	Counter
			ACCESS	read-only
			STATUS	mandatory
			DESCRIPTION
					"The total number of frames forwarded from this port to
					all other ports of this bridge.  Note that the total forwarded
					count is NOT equal to the receive count minus the discard
					count, as a single received multicast/broadcast frame can
					be forwarded to multiple bridge ports.  Also frames which
					are 'flooded' because of unknown destination addresses
					account for multiple forwarding as well.  The total 
					forwarding count is the instantaneous sumation of the 
					'forwarded to' counts to all other ports of the bridge."
			::= { lpBridgePortEntry 9 }

		lpBridgePortManagementFramesReceived OBJECT-TYPE
			SYNTAX	Counter
			ACCESS	read-only
			STATUS	mandatory
			DESCRIPTION
					"The number of bridge management frames received by this
					port."
			::= { lpBridgePortEntry 10 }

		lpBridgePortTotalDiscards OBJECT-TYPE
			SYNTAX	Counter
			ACCESS	read-only
			STATUS	mandatory
			DESCRIPTION
					"The total number of frames discarded by this port."
			::= { lpBridgePortEntry 11 }

		lpBridgePortReceiveBlockedDiscards OBJECT-TYPE
			SYNTAX	Counter
			ACCESS	read-only
			STATUS	mandatory
			DESCRIPTION
					"The number of frames discarded by this port because the
					the receiving bridge port was not in the 'forwarding'
					state."
			::= { lpBridgePortEntry 12 }

		lpBridgePortReceiveMulticastLimitExceededs OBJECT-TYPE
			SYNTAX	Counter
			ACCESS	read-only
			STATUS	mandatory
			DESCRIPTION
					"The number of multicast/broadcast frames discarded by 
					this port because the lpBridgePortReceiveMulticastLimit
					was exceeded."
			::= { lpBridgePortEntry 13 }

		lpBridgePortReceiveSecurityDiscards OBJECT-TYPE
			SYNTAX	Counter
			ACCESS	read-only
			STATUS	mandatory
			DESCRIPTION
					"The number of frames discarded by this port because they
					contained source addresses which were statically configured
					on another bridge port.  A statically configured address
					(station), which is not allowed to move, appears to have
					moved."
			::= { lpBridgePortEntry 14 }

		lpBridgePortReceiveUnknownDiscards OBJECT-TYPE
			SYNTAX	Counter
			ACCESS	read-only
			STATUS	mandatory
			DESCRIPTION
					"The number of frames discarded by this port because the
					destination address was unknown.  Note that this counter
					is only valid for FDDI ports, and only when the bridge is an
					EEM, or an ESM operating in express mode."
			::= { lpBridgePortEntry 15 }

		lpBridgePortReceiveOtherDiscards OBJECT-TYPE
			SYNTAX	Counter
			ACCESS	read-only
			STATUS	mandatory
			DESCRIPTION
					"The number of frames discarded by this port because they
					contained either invalid (group) source addresses or
					source addresses belonging to this bridge (indicative of
					network loops)."
			::= { lpBridgePortEntry 16 }

		lpBridgePortReceiveErrorDiscards OBJECT-TYPE
			SYNTAX	Counter
			ACCESS	read-only
			STATUS	mandatory
			DESCRIPTION
					"The number of frames discarded by this port because of
					internal bridge system errors (e.g., hardware and 
					software address table discrepencies)."
			::= { lpBridgePortEntry 17 }

		lpBridgePortSameSegmentDiscards OBJECT-TYPE
			SYNTAX	Counter
			ACCESS	read-only
			STATUS	mandatory
			DESCRIPTION
					"The number of frames discarded by this port because the
					destination address is known on the same network segment
					as the source address, i.e., the frame does not need to 
					be bridged."
			::= { lpBridgePortEntry 18 }

		lpBridgePortTransmitBlockedDiscards OBJECT-TYPE
			SYNTAX	Counter
			ACCESS	read-only
			STATUS	mandatory
			DESCRIPTION
					"The number of frames discarded by this port because the
					the transmitting bridge port was not in the 'forwarding'
					state."
			::= { lpBridgePortEntry 19 }

		lpBridgePortTotalFiltered OBJECT-TYPE
			SYNTAX	Counter
			ACCESS	read-only
			STATUS	mandatory
			DESCRIPTION
					"The total number of frames discarded by this port due to
					user defined filters."
			::= { lpBridgePortEntry 20 }

		lpBridgePortReceiveUnicastFiltered OBJECT-TYPE
			SYNTAX	Counter
			ACCESS	read-only
			STATUS	mandatory
			DESCRIPTION
					"The number of frames discarded by this port due to user
					defined receive path filters."
			::= { lpBridgePortEntry 21 }

		lpBridgePortReceiveMulticastFiltered OBJECT-TYPE
			SYNTAX	Counter
			ACCESS	read-only
			STATUS	mandatory
			DESCRIPTION
					"The number of frames discarded by this port due to user
					defined receive multicast path filters."
			::= { lpBridgePortEntry 22 }

		lpBridgePortTransmitUnicastFiltered OBJECT-TYPE
			SYNTAX	Counter
			ACCESS	read-only
			STATUS	mandatory
			DESCRIPTION
					"The number of frames discarded by this port due to user
					defined transmit path filters."
			::= { lpBridgePortEntry 23 }

		lpBridgePortTransmitMulticastFiltered OBJECT-TYPE
			SYNTAX	Counter
			ACCESS	read-only
			STATUS	mandatory
			DESCRIPTION
					"The number of frames discarded by this port due to user
					defined transmit multicast path filters."
			::= { lpBridgePortEntry 24 }

		lpBridgePortReceiveMulticastLimitExceededCount OBJECT-TYPE
			SYNTAX	Counter
			ACCESS	read-only
			STATUS	mandatory
			DESCRIPTION
					"The number of times the lpBridgePortReceiveMulticastLimit was
					exceeded."
			::= { lpBridgePortEntry 25 }


		-- Bridge Port Forwarded-To Table

		lpBridgePortForwardedToTable OBJECT-TYPE
			SYNTAX  SEQUENCE OF LpBridgePortForwardedToEntry
			ACCESS  not-accessible
			STATUS  mandatory
			DESCRIPTION
					"A list of port forwarding count information."
			::= { lpBridge 3 }

		lpBridgePortForwardedToEntry OBJECT-TYPE
			SYNTAX  LpBridgePortForwardedToEntry
			ACCESS  not-accessible
			STATUS  mandatory
			DESCRIPTION
					"A bridge port forwarded-to entry contains information on the
					count of frames forwarded from the receiving port indicated
					by the corresponding lpBridgePortForwardedToReceivePortIndex,
					to the destination port indicated by the corresponding
					lpBridgePortForwardedToDstPortIndex.  Note that no entries
					exist which are indexed with the same values for both the
					lpBridgePortForwardedToReceivePortIndex and the
					lpBridgePortForwardedToDstPortIndex objects."
			INDEX	{ lpBridgePortForwardedToBridgeIndex,
					lpBridgePortForwardedToReceivePortIndex,
					lpBridgePortForwardedToDstPortIndex }
			::= { lpBridgePortForwardedToTable 1 }

		LpBridgePortForwardedToEntry ::=
			SEQUENCE {
				lpBridgePortForwardedToBridgeIndex
					INTEGER,
				lpBridgePortForwardedToReceivePortIndex
					INTEGER,
				lpBridgePortForwardedToDstPortIndex
					INTEGER,
				lpBridgePortForwardedToCount
					Counter
			}

		lpBridgePortForwardedToBridgeIndex OBJECT-TYPE
			SYNTAX	INTEGER
			ACCESS	read-only
			STATUS	mandatory
			DESCRIPTION
					"A unique value for each bridge function in the system.
					It's value ranges between 1 and the value of
					lpSystemBridgeFunctionCount."
			::= { lpBridgePortForwardedToEntry 1 }

		lpBridgePortForwardedToReceivePortIndex OBJECT-TYPE
			SYNTAX	INTEGER
			ACCESS	read-only
			STATUS	mandatory
			DESCRIPTION
					"A unique value for each bridge port controlled by a given
					bridge function.  It's value ranges between 1 and the 
					value of lpBridgePortCount for the bridge function
					which this entry references.  This port index refers to the
					receiving port which is forwarding frames."
			::= { lpBridgePortForwardedToEntry 2 }

		lpBridgePortForwardedToDstPortIndex OBJECT-TYPE
			SYNTAX	INTEGER
			ACCESS	read-only
			STATUS	mandatory
			DESCRIPTION
					"A unique value for each bridge port controlled by a given
					bridge function.  It's value ranges between 1 and the 
					value of lpBridgePortCount for the bridge function
					which this entry references.  This port index refers to
					the destination port to which frames are being forwarded."
			::= { lpBridgePortForwardedToEntry 3 }

		lpBridgePortForwardedToCount OBJECT-TYPE
			SYNTAX	Counter
			ACCESS	read-only
			STATUS	mandatory
			DESCRIPTION
					"The count of frames forwarded from the receiving port to
					the destination port."
			::= { lpBridgePortForwardedToEntry 4 }


		-- Bridge Port Filtered-To Table

		lpBridgePortFilteredToTable OBJECT-TYPE
			SYNTAX  SEQUENCE OF LpBridgePortFilteredToEntry
			ACCESS  not-accessible
			STATUS  mandatory
			DESCRIPTION
					"A list of port filtering count information."
			::= { lpBridge 4 }

		lpBridgePortFilteredToEntry OBJECT-TYPE
			SYNTAX  LpBridgePortFilteredToEntry
			ACCESS  not-accessible
			STATUS  mandatory
			DESCRIPTION
					"A bridge port filtered-to entry contains information on the
					count of frames filtered from the receiving port indicated
					by the corresponding lpBridgePortFilteredToReceivePortIndex,
					to the destination port indicated by the corresponding
					lpBridgePortFilteredToDstPortIndex.  Note that no entries
					exist which are indexed with the same values for both the
					lpBridgePortFilteredToReceivePortIndex and the
					lpBridgePortFilteredToDstPortIndex objects."
			INDEX	{ lpBridgePortFilteredToBridgeIndex,
					lpBridgePortFilteredToReceivePortIndex,
					lpBridgePortFilteredToDstPortIndex }
			::= { lpBridgePortFilteredToTable 1 }

		LpBridgePortFilteredToEntry ::=
			SEQUENCE {
				lpBridgePortFilteredToBridgeIndex
					INTEGER,
				lpBridgePortFilteredToReceivePortIndex
					INTEGER,
				lpBridgePortFilteredToDstPortIndex
					INTEGER,
				lpBridgePortFilteredToCount
					Counter
			}

		lpBridgePortFilteredToBridgeIndex OBJECT-TYPE
			SYNTAX	INTEGER
			ACCESS	read-only
			STATUS	mandatory
			DESCRIPTION
					"A unique value for each bridge function in the system.
					It's value ranges between 1 and the value of
					lpSystemBridgeFunctionCount."
			::= { lpBridgePortFilteredToEntry 1 }

		lpBridgePortFilteredToReceivePortIndex OBJECT-TYPE
			SYNTAX	INTEGER
			ACCESS	read-only
			STATUS	mandatory
			DESCRIPTION
					"A unique value for each bridge port controlled by a given
					bridge function.  It's value ranges between 1 and the 
					value of lpBridgePortCount for the bridge function
					which this entry references.  This port index refers to the
					receiving port which is filtering frames."
			::= { lpBridgePortFilteredToEntry 2 }

		lpBridgePortFilteredToDstPortIndex OBJECT-TYPE
			SYNTAX	INTEGER
			ACCESS	read-only
			STATUS	mandatory
			DESCRIPTION
					"A unique value for each bridge port controlled by a given
					bridge function.  It's value ranges between 1 and the 
					value of lpBridgePortCount for the bridge function
					which this entry references.  This port index refers to
					the destination port to which frames are being filtered."
			::= { lpBridgePortFilteredToEntry 3 }

		lpBridgePortFilteredToCount OBJECT-TYPE
			SYNTAX	Counter
			ACCESS	read-only
			STATUS	mandatory
			DESCRIPTION
					"The count of frames filtered from the receiving port to
					the destination port."
			::= { lpBridgePortFilteredToEntry 4 }


		-- Bridge Port AddressTable

		lpBridgePortAddressTable OBJECT-TYPE
			SYNTAX	SEQUENCE OF LpBridgePortAddressEntry
			ACCESS	not-accessible
			STATUS	mandatory
			DESCRIPTION
					"A list of bridge port address entries."
			::= { lpBridge 5 }

		lpBridgePortAddressEntry OBJECT-TYPE
			SYNTAX	LpBridgePortAddressEntry
			ACCESS	not-accessible
			STATUS	mandatory
			DESCRIPTION
					"An bridge port address entry contains information about
					particular bridge port address in a given system."
			INDEX	{ lpBridgePortAddressBridgeIndex, 
					lpBridgePortAddressPortIndex, 
					lpBridgePortAddressIndex }
			::= { lpBridgePortAddressTable 1 }

		LpBridgePortAddressEntry ::=
			SEQUENCE {
				lpBridgePortAddressBridgeIndex
					INTEGER,
				lpBridgePortAddressPortIndex
					INTEGER,
				lpBridgePortAddressIndex
					INTEGER,
				lpBridgePortAddressRemoteAddress
					OCTET STRING,
				lpBridgePortAddressType
					INTEGER,
				lpBridgePortAddressIsStatic
					INTEGER,
				lpBridgePortAddressStaticPort
					INTEGER,
				lpBridgePortAddressAge
					INTEGER
			}

		lpBridgePortAddressBridgeIndex OBJECT-TYPE
			SYNTAX	INTEGER
			ACCESS	read-only
			STATUS	mandatory
			DESCRIPTION
					"A unique value for each bridge function in the system.
					It's value ranges between 1 and the value of
					lpSystemBridgeFunctionCount."
			::= { lpBridgePortAddressEntry 1 }

		lpBridgePortAddressPortIndex OBJECT-TYPE
			SYNTAX	INTEGER
			ACCESS	read-only
			STATUS	mandatory
			DESCRIPTION
					"A unique value for each bridge port controlled by a given
					bridge function.  It's value ranges between 1 and the 
					value of lpBridgePortCount for the bridge function
					which this entry references."
			::= { lpBridgePortAddressEntry 2 }

		lpBridgePortAddressIndex OBJECT-TYPE
			SYNTAX	INTEGER
			ACCESS	read-only
			STATUS	mandatory
			DESCRIPTION
					"The index of this address entry within the bridge address 
					table." 
			::= { lpBridgePortAddressEntry 3 }

		lpBridgePortAddressRemoteAddress OBJECT-TYPE
			SYNTAX	OCTET STRING (SIZE (6))
			ACCESS	read-write
			STATUS	mandatory
			DESCRIPTION
					"The remote MAC address detected on the port corresponding
					to this entry.  Setting this object attempts to create a
					new entry in the table.  Since the value of 
					lpBridgePortAddressIndex is determined automatically internal
					to the bridge, a set is only successful if the index value
					specified for lpBridgePortAddressIndex is zero.  A get-next
					using the values of lpBridgePortAddressBridgeIndex and 
					lpBridgePortAddressPortIndex can be used to determine the
					address index assigned to the newly added address entry."
			::= { lpBridgePortAddressEntry 4 }

		lpBridgePortAddressType OBJECT-TYPE
			SYNTAX INTEGER {
						other(1),
						invalid(2)
					}
			ACCESS	read-write
			STATUS	mandatory
			DESCRIPTION
					"This object, when read, always returns the value other (1).
					Setting this object to invalid (2) will remove the 
					corresponding address entry from the table."
			::= { lpBridgePortAddressEntry 5 }

		lpBridgePortAddressIsStatic OBJECT-TYPE
			SYNTAX	INTEGER {
						isStatic(1),
						isDynamic(2)
					}
			ACCESS	read-write
			STATUS	mandatory
			DESCRIPTION
					"A value indicating whether this MAC address was statically 
					configured or was dynamically learned."
			::= { lpBridgePortAddressEntry 6 }

		lpBridgePortAddressStaticPort OBJECT-TYPE
			SYNTAX	INTEGER
			ACCESS	read-only
			STATUS	mandatory
			DESCRIPTION
					"If the object lpBridgePortAddressIsStatic has 
					value isStatic(1), this object indicates the local port
					index (as reported by lpBridgePortLocalIndex) for 
					which this MAC address was statically configured.  If
					the object lpBridgePortAddressIsStatic has the value
					isDynamic(2), the value of this object is 0."
			::= { lpBridgePortAddressEntry 7 }

		lpBridgePortAddressAge OBJECT-TYPE
			SYNTAX	INTEGER
			ACCESS	read-only
			STATUS	mandatory
			DESCRIPTION
					"This object indicates the time, in seconds, elapsed since 
					a packet containing this address as a source was last seen
					on the port corresponding to this entry."
			::= { lpBridgePortAddressEntry 8 }


		-- Trap Enterprise Table

		lpTrapEnterpriseTable OBJECT-TYPE
			SYNTAX	SEQUENCE OF LpTrapEnterpriseTableEntry
			ACCESS	not-accessible
			STATUS	mandatory
			DESCRIPTION
					"This table contains a listing of enterprises under which
					various traps are defined.  In all cases except for the 
					MIB-II generic traps, the enterprise under which a trap 
					is defined is the same as that appearing in the ENTERPRISE 
					portion of the trap.  Associated with each trap enterprise
					is a trap enterprise index."
			::= { lpTrapEnterprise 1 }

		lpTrapEnterpriseTableEntry OBJECT-TYPE
			SYNTAX	LpTrapEnterpriseTableEntry
			ACCESS	not-accessible
			STATUS	mandatory
			DESCRIPTION
					"Information relating a specific trap enterprise OID with
					a trap enterprise index."
			INDEX	{ lpTrapEnterpriseIndex }
			::= { lpTrapEnterpriseTable 1 }

		LpTrapEnterpriseTableEntry ::=
			SEQUENCE {
				lpTrapEnterpriseIndex
					INTEGER,
				lpTrapEnterpriseOID
					OBJECT IDENTIFIER
			}

		lpTrapEnterpriseIndex OBJECT-TYPE
			SYNTAX	INTEGER
			ACCESS	read-only
			STATUS	mandatory
			DESCRIPTION
					"A unique index corresponding to a particular enterprise
					OID under which traps are defined.  This value of this 
					object corresponding to a particular enterprise OID will
					remain constant accross system resets."
			::= { lpTrapEnterpriseTableEntry 1 }

		lpTrapEnterpriseOID OBJECT-TYPE
			SYNTAX	OBJECT IDENTIFIER
			ACCESS	read-only
			STATUS	mandatory
			DESCRIPTION
					"An enterpise OID under which traps are defined."
			::= { lpTrapEnterpriseTableEntry 2 }


		-- Trap Destination Table
					
		lpTrapDestTable OBJECT-TYPE
			SYNTAX	SEQUENCE OF LpTrapDestTableEntry
			ACCESS	not-accessible
			STATUS	mandatory
			DESCRIPTION
					"This table contains information specifying which traps
					will be transmitted by the LANplex to a given destination 
					address.  The table is indexed by the destination address, 
					the index of the enterprise which generates the trap, and
					the trap number.  Each entry in the table with a status 
					of valid identifies a trap which, when generated, will be 
					transmitted to the corresponding destination address 
					listed in that entry."
			::= { lpTrapDest 1 }

		lpTrapDestTableEntry OBJECT-TYPE
			SYNTAX	LpTrapDestTableEntry
			ACCESS	not-accessible
			STATUS	mandatory
			DESCRIPTION
					"Information relating a trap with a destination address
					to which the trap will be sent when it is generated."
			INDEX { lpTrapDestAddr, 
					lpTrapDestEnterpriseIndex, 
					lpTrapNumber }
			::= { lpTrapDestTable 1 }

		LpTrapDestTableEntry ::=
			SEQUENCE {
				lpTrapDestAddr
					NetworkAddress,
				lpTrapDestEnterpriseIndex
					INTEGER,
				lpTrapNumber
					INTEGER,
				lpTrapEntryStatus
					INTEGER
			}

		lpTrapDestAddr OBJECT-TYPE
			SYNTAX	NetworkAddress
			ACCESS	read-only
			STATUS	mandatory
			DESCRIPTION
					"The network address to which the trap identified by
					this entry is to be transmitted."
			::= { lpTrapDestTableEntry 1 }

		lpTrapDestEnterpriseIndex OBJECT-TYPE
			SYNTAX	INTEGER
			ACCESS	read-only
			STATUS	mandatory
			DESCRIPTION
					"The enterprise index of the enterprise identified in this
					entry.  The value of this object is the same as the
					lpTrapEnterpriseIndex value for a given enterprise."
			::= { lpTrapDestTableEntry 2 }

		lpTrapNumber OBJECT-TYPE
			SYNTAX	INTEGER
			ACCESS	read-only
			STATUS	mandatory
			DESCRIPTION
					"The number of the trap within the corresponding
					enterprise for this entry."
			::= { lpTrapDestTableEntry 3 }

		lpTrapEntryStatus OBJECT-TYPE
			SYNTAX	INTEGER {
						valid(1),
						invalid(2)
					}
			ACCESS	read-write
			STATUS	mandatory
			DESCRIPTION
					"The status of the trap destination table entry.  Setting
					this object to valid has the effect of attempting to add
					the row corresponding to the instance specified.  If the
					instance already exists, the set is successful (with no
					new entry added).  If the instance specified is invalid,
					the set fails, otherwise the set succeeds and results in
					a new entry being added to the table.  Setting this object
					to invalid has the effect of removing the corresponding 
					entry from the table."
			::= { lpTrapDestTableEntry 4 }


        -- lanplex MIB traps

		lpSlotInsertEvent TRAP-TYPE
			ENTERPRISE	lanplexMib
			VARIABLES	{ lpSlotIndex, lpSlotBoardType, lpSlotBoardRevision }
			DESCRIPTION
					"The SNMP trap that is generated when a board is inserted
					into a particular slot in the chassis."
			::= 1

		lpSlotExtractEvent TRAP-TYPE
			ENTERPRISE	lanplexMib
			VARIABLES	{ lpSlotIndex }
			DESCRIPTION
					"The SNMP trap that is generated when a board is extracted
					from a particular slot in the chassis."
			::= 2

		lpBridgeAddressThresholdEvent TRAP-TYPE
			ENTERPRISE	lanplexMib
			VARIABLES	{ lpBridgeIndex,
						lpBridgeBaseSlotIndex }
			DESCRIPTION
					"The SNMP trap that is generated when the number of
					addresses stored in the bridge reaches 
					lpBridgeAddressThreshold."
			::= 3

		-- The lpBridgePortAddressLearnedEvent and the lpBridgePortAddressForgottenEvent
		-- traps are obsolete and are no longer supported.

		lpSystemOverTemperatureEvent TRAP-TYPE
			ENTERPRISE	lanplexMib
			DESCRIPTION
					"The SNMP trap that is generated when the system 
					temperature exceeds a certain threshold."
			::= 6

		lpSlotOverTemperatureEvent TRAP-TYPE
			ENTERPRISE	lanplexMib
			VARIABLES	{ lpSlotIndex,
						lpSlotBoardType,
						lpSlotBoardRevision,
						lpSlotBoardStatus }
			DESCRIPTION
					"The SNMP trap that is generated when the temperature of
					a board in a particular slot exceeds a certain threshold."
			::= 7

		lpPowerSupplyFailureEvent TRAP-TYPE
			ENTERPRISE	lanplexMib
			VARIABLES	{ lpPowerSupplyIndex,
						lpPowerSupplyLocation,
						lpPowerSupplyLastFailure,
						 lpSystemPowerSupplyCount}
			DESCRIPTION
					"The SNMP trap that is generated when a power supply
					unit fails in the system."
			::= 8

	END
