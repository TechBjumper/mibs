ChrComIfOpticsOTS-SRC-MIB

--FORCE-INCLUDE	<mib.h>
--FORCE-INCLUDE	<snmpdefs.h>
--FORCE-INCLUDE	"mibhand.h"

	DEFINITIONS  ::=  BEGIN

IMPORTS
	OBJECT-TYPE, Counter32			FROM  SNMPv2-SMI
	Integer32, Unsigned32			FROM  SNMPv2-SMI
	chrComIfOptics				FROM  Chromatis-MIB
	chrComIfifIndex					FROM  ChrComIfifTable-MIB;

-- chrComIfOpticsOTS-SRC Table

chrComIfOpticsOTS-SRCTable		OBJECT-TYPE
	SYNTAX		SEQUENCE OF ChrComIfOpticsOTS-SRCEntry
	MAX-ACCESS	not-accessible
	STATUS		current
	DESCRIPTION
	"1. The OTS-SRC is managed only for the Ring side of the Metropolis Network (not for the Trib side).
2. When post-OPA exists, the preceding ADOM/OMDM does NOT have an OTS-SRC layer This layer should be grayed and not accessible to the user
"
	::= { chrComIfOptics 2}

chrComIfOpticsOTS-SRCEntry		OBJECT-TYPE
	SYNTAX		ChrComIfOpticsOTS-SRCEntry
	MAX-ACCESS	not-accessible
	STATUS		current
	DESCRIPTION
	""
	INDEX  {  chrComIfifIndex }

--DEFAULT  get-function-async  MNIL_GetRoutine
--DEFAULT  set-function-async  MNIL_SetRoutine
--DEFAULT  next-function-async MNIL_NextRoutine
--DEFAULT  test-function-async MNIL_TestRoutine
--DEFAULT  cookie "OTS-SRC"
	::= { chrComIfOpticsOTS-SRCTable  1 }

ChrComIfOpticsOTS-SRCEntry  ::=
	SEQUENCE  {
	chrComIfOpticsOtsSrcOutPower		Integer32	(-501..300),
	chrComIfOpticsOtsSrcLOOPThr		Integer32	(-501..300),
	chrComIfOpticsOtsSrcSafetyThr		Integer32	(-501..300),
	chrComIfOpticsAlarmVector		Unsigned32	(0..4294967295),
	chrComIfOpticsAlarmSeverityProfileIndex Unsigned32	(0..4294967295)
}

chrComIfOpticsOtsSrcOutPower 	OBJECT-TYPE
	SYNTAX		Integer32	(-501..300)
	MAX-ACCESS 	read-only
	STATUS 		current
	DESCRIPTION
	"Total Optical Power Monitored at the output of the ADOM/OMDM/post-OPA/in-line-OPA. "
	::= { chrComIfOpticsOTS-SRCEntry  1 }

chrComIfOpticsOtsSrcLOOPThr 	OBJECT-TYPE
	SYNTAX		Integer32	(-501..300)
	MAX-ACCESS 	read-write
	STATUS 		current
	DESCRIPTION
	"This is a threshold on OTS-SRC total output Power indicating the existence of light energy emitted into the Ring."
	::= { chrComIfOpticsOTS-SRCEntry  2 }

chrComIfOpticsOtsSrcSafetyThr 	OBJECT-TYPE
	SYNTAX		Integer32	(-501..300)
	MAX-ACCESS 	read-write
	STATUS 		current
	DESCRIPTION
	"This is a threshold on OTS-SRC total output Power indicating that the light energy emitted into the Ring exceeds the safety threshold"
	::= { chrComIfOpticsOTS-SRCEntry  3 }

chrComIfOpticsAlarmVector 	OBJECT-TYPE
	SYNTAX		Unsigned32	(0..4294967295)
	MAX-ACCESS 	read-only
	STATUS 		current
	DESCRIPTION
	"16 bit field. The following are bits relative positions (0=LSB), and the trap ID associated to each alarm state. 

8. Ring-out loss of Optical power 
metropolisOTS-SRCLoop
9. Ring-out Optical Power output Safety Limit Crossing 
metropolisOTS-SRCSafety
"
	::= { chrComIfOpticsOTS-SRCEntry  4 }

chrComIfOpticsAlarmSeverityProfileIndex 	OBJECT-TYPE
	SYNTAX		Unsigned32	(0..4294967295)
	MAX-ACCESS 	read-write
	STATUS 		current
	DESCRIPTION
	""
	::= { chrComIfOpticsOTS-SRCEntry  5 }


END
