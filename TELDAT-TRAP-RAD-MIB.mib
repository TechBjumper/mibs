-- file automatically created


TELDAT-TRAP-RAD-MIB DEFINITIONS ::= BEGIN


IMPORTS
	MODULE-IDENTITY,OBJECT-TYPE,OBJECT-IDENTITY,NOTIFICATION-TYPE,Integer32,IpAddress
		FROM SNMPv2-SMI
	DisplayString
		FROM SNMPv2-TC
	telEventTraps
		FROM TELDAT-MIB;


radTrapsMIB MODULE-IDENTITY
    LAST-UPDATED "201401200930Z"
    ORGANIZATION "Teldat, S.A."
    CONTACT-INFO 
        "Teldat, S.A.
        Customer Service

        Postal: Parque Tecnologico de Madrid
                Tres Cantos 28760
                Madrid, SPAIN

        Tel.: +34 918 076 565

        http://www.teldat.com"
    DESCRIPTION
        "This Module Information Base file is defined for managing received
        SNMP notifications generated by the RAD event subsystem."
    REVISION "201401200930Z"
    DESCRIPTION "Initial implementation"
        ::= { telEventTraps 130 }


radEventsGroup	OBJECT IDENTIFIER	::= { radTrapsMIB 1 }

radNotifications	OBJECT IDENTIFIER	::= { radTrapsMIB 2 }
radNotificationsPrefix	OBJECT IDENTIFIER	::= { radNotifications 0 }

radEventObjects1 OBJECT-IDENTITY
    STATUS current
    DESCRIPTION
        "Event RAD.1
        This message is generated when an ACCESS REQUEST packet is sent to
        RADIUS server, if a new PAP or CHAP authentication arrives."
    ::= { radEventsGroup 1 }

rad1-addr-rad-serv OBJECT-TYPE
    SYNTAX IpAddress
    MAX-ACCESS accessible-for-notify
    STATUS current
    DESCRIPTION
        "Parameter 'addr-rad-serv' in event RAD.1"
    ::= { radEventObjects1 1 }

rad1-id OBJECT-TYPE
    SYNTAX Integer32
    MAX-ACCESS accessible-for-notify
    STATUS current
    DESCRIPTION
        "Parameter 'id' in event RAD.1"
    ::= { radEventObjects1 2 }

rad1-servc OBJECT-TYPE
    SYNTAX DisplayString
    MAX-ACCESS accessible-for-notify
    STATUS current
    DESCRIPTION
        "Parameter 'servc' in event RAD.1"
    ::= { radEventObjects1 3 }

rad1-interface OBJECT-TYPE
    SYNTAX DisplayString
    MAX-ACCESS accessible-for-notify
    STATUS current
    DESCRIPTION
        "Parameter 'interface' in event RAD.1"
    ::= { radEventObjects1 4 }

radEventObjects2 OBJECT-IDENTITY
    STATUS current
    DESCRIPTION
        "Event RAD.2
        This message is generated when an ACCESS ACCEPT packet is received,
        which is sent by the RADIUS server if the RADIUS request
        is authenticated (PAP or CHAP)."
    ::= { radEventsGroup 2 }

rad2-addr-rad-serv OBJECT-TYPE
    SYNTAX IpAddress
    MAX-ACCESS accessible-for-notify
    STATUS current
    DESCRIPTION
        "Parameter 'addr-rad-serv' in event RAD.2"
    ::= { radEventObjects2 1 }

rad2-id OBJECT-TYPE
    SYNTAX Integer32
    MAX-ACCESS accessible-for-notify
    STATUS current
    DESCRIPTION
        "Parameter 'id' in event RAD.2"
    ::= { radEventObjects2 2 }

rad2-servc OBJECT-TYPE
    SYNTAX DisplayString
    MAX-ACCESS accessible-for-notify
    STATUS current
    DESCRIPTION
        "Parameter 'servc' in event RAD.2"
    ::= { radEventObjects2 3 }

rad2-interface OBJECT-TYPE
    SYNTAX DisplayString
    MAX-ACCESS accessible-for-notify
    STATUS current
    DESCRIPTION
        "Parameter 'interface' in event RAD.2"
    ::= { radEventObjects2 4 }

radEventObjects3 OBJECT-IDENTITY
    STATUS current
    DESCRIPTION
        "Event RAD.3
        This message is generated when an ACCESS REJECT packet is received,
        which is sent by the RADIUS server if the RADIUS request is rejected
        (PAP or CHAP)."
    ::= { radEventsGroup 3 }

rad3-addr-rad-serv OBJECT-TYPE
    SYNTAX IpAddress
    MAX-ACCESS accessible-for-notify
    STATUS current
    DESCRIPTION
        "Parameter 'addr-rad-serv' in event RAD.3"
    ::= { radEventObjects3 1 }

rad3-id OBJECT-TYPE
    SYNTAX Integer32
    MAX-ACCESS accessible-for-notify
    STATUS current
    DESCRIPTION
        "Parameter 'id' in event RAD.3"
    ::= { radEventObjects3 2 }

rad3-servc OBJECT-TYPE
    SYNTAX DisplayString
    MAX-ACCESS accessible-for-notify
    STATUS current
    DESCRIPTION
        "Parameter 'servc' in event RAD.3"
    ::= { radEventObjects3 3 }

rad3-interface OBJECT-TYPE
    SYNTAX DisplayString
    MAX-ACCESS accessible-for-notify
    STATUS current
    DESCRIPTION
        "Parameter 'interface' in event RAD.3"
    ::= { radEventObjects3 4 }

radEventObjects4 OBJECT-IDENTITY
    STATUS current
    DESCRIPTION
        "Event RAD.4
        This message is generated when an ACCESS CHALLENGE packet is received,
        which is sent by the RADIUS server to ask for a new
        ACCESS REQUEST packet (PAP or CHAP)."
    ::= { radEventsGroup 4 }

rad4-addr-rad-serv OBJECT-TYPE
    SYNTAX IpAddress
    MAX-ACCESS accessible-for-notify
    STATUS current
    DESCRIPTION
        "Parameter 'addr-rad-serv' in event RAD.4"
    ::= { radEventObjects4 1 }

rad4-id OBJECT-TYPE
    SYNTAX Integer32
    MAX-ACCESS accessible-for-notify
    STATUS current
    DESCRIPTION
        "Parameter 'id' in event RAD.4"
    ::= { radEventObjects4 2 }

rad4-servc OBJECT-TYPE
    SYNTAX DisplayString
    MAX-ACCESS accessible-for-notify
    STATUS current
    DESCRIPTION
        "Parameter 'servc' in event RAD.4"
    ::= { radEventObjects4 3 }

rad4-interface OBJECT-TYPE
    SYNTAX DisplayString
    MAX-ACCESS accessible-for-notify
    STATUS current
    DESCRIPTION
        "Parameter 'interface' in event RAD.4"
    ::= { radEventObjects4 4 }

radEventObjects5 OBJECT-IDENTITY
    STATUS current
    DESCRIPTION
        "Event RAD.5
        This message is generated when an ACCESS REQUEST packet is retransmitted
        by the client if the RADIUS server response is not received
        in the expected time (PAP or CHAP)."
    ::= { radEventsGroup 5 }

rad5-addr-rad-serv OBJECT-TYPE
    SYNTAX IpAddress
    MAX-ACCESS accessible-for-notify
    STATUS current
    DESCRIPTION
        "Parameter 'addr-rad-serv' in event RAD.5"
    ::= { radEventObjects5 1 }

rad5-id OBJECT-TYPE
    SYNTAX Integer32
    MAX-ACCESS accessible-for-notify
    STATUS current
    DESCRIPTION
        "Parameter 'id' in event RAD.5"
    ::= { radEventObjects5 2 }

rad5-servc OBJECT-TYPE
    SYNTAX DisplayString
    MAX-ACCESS accessible-for-notify
    STATUS current
    DESCRIPTION
        "Parameter 'servc' in event RAD.5"
    ::= { radEventObjects5 3 }

rad5-interface OBJECT-TYPE
    SYNTAX DisplayString
    MAX-ACCESS accessible-for-notify
    STATUS current
    DESCRIPTION
        "Parameter 'interface' in event RAD.5"
    ::= { radEventObjects5 4 }

radEventObjects6 OBJECT-IDENTITY
    STATUS current
    DESCRIPTION
        "Event RAD.6
        This message is generated when an authentication request is rejected
        if a RADIUS server response is not received or nets to RADIUS servers
        are down and the number of possible attempts is over (PAP or CHAP)."
    ::= { radEventsGroup 6 }

rad6-servc OBJECT-TYPE
    SYNTAX DisplayString
    MAX-ACCESS accessible-for-notify
    STATUS current
    DESCRIPTION
        "Parameter 'servc' in event RAD.6"
    ::= { radEventObjects6 1 }

rad6-interface OBJECT-TYPE
    SYNTAX DisplayString
    MAX-ACCESS accessible-for-notify
    STATUS current
    DESCRIPTION
        "Parameter 'interface' in event RAD.6"
    ::= { radEventObjects6 2 }

radEventObjects7 OBJECT-IDENTITY
    STATUS current
    DESCRIPTION
        "Event RAD.7
        This message is generated when it is tried to send a packet to
        a RADIUS server and outgoing net is no UP (PAP or CHAP)."
    ::= { radEventsGroup 7 }

rad7-addr-rad-serv OBJECT-TYPE
    SYNTAX IpAddress
    MAX-ACCESS accessible-for-notify
    STATUS current
    DESCRIPTION
        "Parameter 'addr-rad-serv' in event RAD.7"
    ::= { radEventObjects7 1 }

rad7-servc OBJECT-TYPE
    SYNTAX DisplayString
    MAX-ACCESS accessible-for-notify
    STATUS current
    DESCRIPTION
        "Parameter 'servc' in event RAD.7"
    ::= { radEventObjects7 2 }

rad7-interface OBJECT-TYPE
    SYNTAX DisplayString
    MAX-ACCESS accessible-for-notify
    STATUS current
    DESCRIPTION
        "Parameter 'interface' in event RAD.7"
    ::= { radEventObjects7 3 }

radEventObjects8 OBJECT-IDENTITY
    STATUS current
    DESCRIPTION
        "Event RAD.8
        This message is generated when an ACCESS ACCEPT packet is received
        with an attribute with invalid length from the RADIUS Server
        (PAP or CHAP)."
    ::= { radEventsGroup 8 }

rad8-addr-rad-serv OBJECT-TYPE
    SYNTAX IpAddress
    MAX-ACCESS accessible-for-notify
    STATUS current
    DESCRIPTION
        "Parameter 'addr-rad-serv' in event RAD.8"
    ::= { radEventObjects8 1 }

rad8-id OBJECT-TYPE
    SYNTAX Integer32
    MAX-ACCESS accessible-for-notify
    STATUS current
    DESCRIPTION
        "Parameter 'id' in event RAD.8"
    ::= { radEventObjects8 2 }

rad8-typ OBJECT-TYPE
    SYNTAX Integer32
    MAX-ACCESS accessible-for-notify
    STATUS current
    DESCRIPTION
        "Parameter 'typ' in event RAD.8"
    ::= { radEventObjects8 3 }

rad8-servc OBJECT-TYPE
    SYNTAX DisplayString
    MAX-ACCESS accessible-for-notify
    STATUS current
    DESCRIPTION
        "Parameter 'servc' in event RAD.8"
    ::= { radEventObjects8 4 }

rad8-interface OBJECT-TYPE
    SYNTAX DisplayString
    MAX-ACCESS accessible-for-notify
    STATUS current
    DESCRIPTION
        "Parameter 'interface' in event RAD.8"
    ::= { radEventObjects8 5 }

radEventObjects9 OBJECT-IDENTITY
    STATUS current
    DESCRIPTION
        "Event RAD.9
        This message is generated when an ACCESS ACCEPT packet is received
        with an attribute with an invalid content from the RADIUS Server
        (PAP or CHAP)."
    ::= { radEventsGroup 9 }

rad9-addr-rad-serv OBJECT-TYPE
    SYNTAX IpAddress
    MAX-ACCESS accessible-for-notify
    STATUS current
    DESCRIPTION
        "Parameter 'addr-rad-serv' in event RAD.9"
    ::= { radEventObjects9 1 }

rad9-id OBJECT-TYPE
    SYNTAX Integer32
    MAX-ACCESS accessible-for-notify
    STATUS current
    DESCRIPTION
        "Parameter 'id' in event RAD.9"
    ::= { radEventObjects9 2 }

rad9-typ OBJECT-TYPE
    SYNTAX Integer32
    MAX-ACCESS accessible-for-notify
    STATUS current
    DESCRIPTION
        "Parameter 'typ' in event RAD.9"
    ::= { radEventObjects9 3 }

rad9-servc OBJECT-TYPE
    SYNTAX DisplayString
    MAX-ACCESS accessible-for-notify
    STATUS current
    DESCRIPTION
        "Parameter 'servc' in event RAD.9"
    ::= { radEventObjects9 4 }

rad9-interface OBJECT-TYPE
    SYNTAX DisplayString
    MAX-ACCESS accessible-for-notify
    STATUS current
    DESCRIPTION
        "Parameter 'interface' in event RAD.9"
    ::= { radEventObjects9 5 }

radEventObjects10 OBJECT-IDENTITY
    STATUS current
    DESCRIPTION
        "Event RAD.10
        This message is generated when an ACCESS ACCEPT packet is received
        with an excessive number of attributes with the same type from
        the RADIUS Server (PAP or CHAP)."
    ::= { radEventsGroup 10 }

rad10-addr-rad-serv OBJECT-TYPE
    SYNTAX IpAddress
    MAX-ACCESS accessible-for-notify
    STATUS current
    DESCRIPTION
        "Parameter 'addr-rad-serv' in event RAD.10"
    ::= { radEventObjects10 1 }

rad10-id OBJECT-TYPE
    SYNTAX Integer32
    MAX-ACCESS accessible-for-notify
    STATUS current
    DESCRIPTION
        "Parameter 'id' in event RAD.10"
    ::= { radEventObjects10 2 }

rad10-typ OBJECT-TYPE
    SYNTAX Integer32
    MAX-ACCESS accessible-for-notify
    STATUS current
    DESCRIPTION
        "Parameter 'typ' in event RAD.10"
    ::= { radEventObjects10 3 }

rad10-servc OBJECT-TYPE
    SYNTAX DisplayString
    MAX-ACCESS accessible-for-notify
    STATUS current
    DESCRIPTION
        "Parameter 'servc' in event RAD.10"
    ::= { radEventObjects10 4 }

rad10-interface OBJECT-TYPE
    SYNTAX DisplayString
    MAX-ACCESS accessible-for-notify
    STATUS current
    DESCRIPTION
        "Parameter 'interface' in event RAD.10"
    ::= { radEventObjects10 5 }

radEventObjects11 OBJECT-IDENTITY
    STATUS current
    DESCRIPTION
        "Event RAD.11
        This message is generated when an ACCESS ACCEPT packet is received
        with an invalid attribute for the offered service from the RADIUS
        Server (PAP or CHAP)."
    ::= { radEventsGroup 11 }

rad11-addr-rad-serv OBJECT-TYPE
    SYNTAX IpAddress
    MAX-ACCESS accessible-for-notify
    STATUS current
    DESCRIPTION
        "Parameter 'addr-rad-serv' in event RAD.11"
    ::= { radEventObjects11 1 }

rad11-id OBJECT-TYPE
    SYNTAX Integer32
    MAX-ACCESS accessible-for-notify
    STATUS current
    DESCRIPTION
        "Parameter 'id' in event RAD.11"
    ::= { radEventObjects11 2 }

rad11-typ OBJECT-TYPE
    SYNTAX Integer32
    MAX-ACCESS accessible-for-notify
    STATUS current
    DESCRIPTION
        "Parameter 'typ' in event RAD.11"
    ::= { radEventObjects11 3 }

rad11-servc OBJECT-TYPE
    SYNTAX DisplayString
    MAX-ACCESS accessible-for-notify
    STATUS current
    DESCRIPTION
        "Parameter 'servc' in event RAD.11"
    ::= { radEventObjects11 4 }

rad11-interface OBJECT-TYPE
    SYNTAX DisplayString
    MAX-ACCESS accessible-for-notify
    STATUS current
    DESCRIPTION
        "Parameter 'interface' in event RAD.11"
    ::= { radEventObjects11 5 }

radEventObjects12 OBJECT-IDENTITY
    STATUS current
    DESCRIPTION
        "Event RAD.12
        This message is generated when a RADIUS server response is received
        with an invalid length (PAP or CHAP)."
    ::= { radEventsGroup 12 }

rad12-addr-rad-serv OBJECT-TYPE
    SYNTAX IpAddress
    MAX-ACCESS accessible-for-notify
    STATUS current
    DESCRIPTION
        "Parameter 'addr-rad-serv' in event RAD.12"
    ::= { radEventObjects12 1 }

rad12-id OBJECT-TYPE
    SYNTAX Integer32
    MAX-ACCESS accessible-for-notify
    STATUS current
    DESCRIPTION
        "Parameter 'id' in event RAD.12"
    ::= { radEventObjects12 2 }

rad12-servc OBJECT-TYPE
    SYNTAX DisplayString
    MAX-ACCESS accessible-for-notify
    STATUS current
    DESCRIPTION
        "Parameter 'servc' in event RAD.12"
    ::= { radEventObjects12 3 }

rad12-interface OBJECT-TYPE
    SYNTAX DisplayString
    MAX-ACCESS accessible-for-notify
    STATUS current
    DESCRIPTION
        "Parameter 'interface' in event RAD.12"
    ::= { radEventObjects12 4 }

radEventObjects13 OBJECT-IDENTITY
    STATUS current
    DESCRIPTION
        "Event RAD.13
        This message is generated when an ACCESS REQUEST packet is sent to
        RADIUS server, if a new CONSOLE authentication arrives."
    ::= { radEventsGroup 13 }

rad13-addr-rad-serv OBJECT-TYPE
    SYNTAX IpAddress
    MAX-ACCESS accessible-for-notify
    STATUS current
    DESCRIPTION
        "Parameter 'addr-rad-serv' in event RAD.13"
    ::= { radEventObjects13 1 }

rad13-id OBJECT-TYPE
    SYNTAX Integer32
    MAX-ACCESS accessible-for-notify
    STATUS current
    DESCRIPTION
        "Parameter 'id' in event RAD.13"
    ::= { radEventObjects13 2 }

radEventObjects14 OBJECT-IDENTITY
    STATUS current
    DESCRIPTION
        "Event RAD.14
        This message is generated when an ACCESS ACCEPT packet is received,
        which is sent by the RADIUS server if the RADIUS request is
        authenticated (CONSOLE)."
    ::= { radEventsGroup 14 }

rad14-addr-rad-serv OBJECT-TYPE
    SYNTAX IpAddress
    MAX-ACCESS accessible-for-notify
    STATUS current
    DESCRIPTION
        "Parameter 'addr-rad-serv' in event RAD.14"
    ::= { radEventObjects14 1 }

rad14-id OBJECT-TYPE
    SYNTAX Integer32
    MAX-ACCESS accessible-for-notify
    STATUS current
    DESCRIPTION
        "Parameter 'id' in event RAD.14"
    ::= { radEventObjects14 2 }

radEventObjects15 OBJECT-IDENTITY
    STATUS current
    DESCRIPTION
        "Event RAD.15
        This message is generated when an ACCESS REJECT packet is received,
        which is sent by the RADIUS server if the RADIUS request is rejected
        (CONSOLE)."
    ::= { radEventsGroup 15 }

rad15-addr-rad-serv OBJECT-TYPE
    SYNTAX IpAddress
    MAX-ACCESS accessible-for-notify
    STATUS current
    DESCRIPTION
        "Parameter 'addr-rad-serv' in event RAD.15"
    ::= { radEventObjects15 1 }

rad15-id OBJECT-TYPE
    SYNTAX Integer32
    MAX-ACCESS accessible-for-notify
    STATUS current
    DESCRIPTION
        "Parameter 'id' in event RAD.15"
    ::= { radEventObjects15 2 }

radEventObjects16 OBJECT-IDENTITY
    STATUS current
    DESCRIPTION
        "Event RAD.16
        This message is generated when an ACCESS CHALLENGE packet is received,
        which is sent by the RADIUS server to ask for a new ACCESS REQUEST
        packet (CONSOLE)."
    ::= { radEventsGroup 16 }

rad16-addr-rad-serv OBJECT-TYPE
    SYNTAX IpAddress
    MAX-ACCESS accessible-for-notify
    STATUS current
    DESCRIPTION
        "Parameter 'addr-rad-serv' in event RAD.16"
    ::= { radEventObjects16 1 }

rad16-id OBJECT-TYPE
    SYNTAX Integer32
    MAX-ACCESS accessible-for-notify
    STATUS current
    DESCRIPTION
        "Parameter 'id' in event RAD.16"
    ::= { radEventObjects16 2 }

radEventObjects17 OBJECT-IDENTITY
    STATUS current
    DESCRIPTION
        "Event RAD.17
        This message is generated when an ACCESS REQUEST packet is retransmitted
        by the client if the RADIUS server response is not received
        in the expected time (CONSOLE)."
    ::= { radEventsGroup 17 }

rad17-addr-rad-serv OBJECT-TYPE
    SYNTAX IpAddress
    MAX-ACCESS accessible-for-notify
    STATUS current
    DESCRIPTION
        "Parameter 'addr-rad-serv' in event RAD.17"
    ::= { radEventObjects17 1 }

rad17-id OBJECT-TYPE
    SYNTAX Integer32
    MAX-ACCESS accessible-for-notify
    STATUS current
    DESCRIPTION
        "Parameter 'id' in event RAD.17"
    ::= { radEventObjects17 2 }

radEventObjects19 OBJECT-IDENTITY
    STATUS current
    DESCRIPTION
        "Event RAD.19
        This message is generated when it is tried to send a packet to a
        RADIUS server and outgoing net is not UP (CONSOLE)."
    ::= { radEventsGroup 19 }

rad19-addr-rad-serv OBJECT-TYPE
    SYNTAX IpAddress
    MAX-ACCESS accessible-for-notify
    STATUS current
    DESCRIPTION
        "Parameter 'addr-rad-serv' in event RAD.19"
    ::= { radEventObjects19 1 }

radEventObjects20 OBJECT-IDENTITY
    STATUS current
    DESCRIPTION
        "Event RAD.20
        This message is generated when an ACCESS ACCEPT packet is received
        with an attribute with invalid length from the RADIUS Server (CONSOLE)."
    ::= { radEventsGroup 20 }

rad20-addr-rad-serv OBJECT-TYPE
    SYNTAX IpAddress
    MAX-ACCESS accessible-for-notify
    STATUS current
    DESCRIPTION
        "Parameter 'addr-rad-serv' in event RAD.20"
    ::= { radEventObjects20 1 }

rad20-id OBJECT-TYPE
    SYNTAX Integer32
    MAX-ACCESS accessible-for-notify
    STATUS current
    DESCRIPTION
        "Parameter 'id' in event RAD.20"
    ::= { radEventObjects20 2 }

rad20-typ OBJECT-TYPE
    SYNTAX Integer32
    MAX-ACCESS accessible-for-notify
    STATUS current
    DESCRIPTION
        "Parameter 'typ' in event RAD.20"
    ::= { radEventObjects20 3 }

radEventObjects21 OBJECT-IDENTITY
    STATUS current
    DESCRIPTION
        "Event RAD.21
        This message is generated when an ACCESS ACCEPT packet is received
        with an attribute with an invalid content from the RADIUS Server
        (CONSOLE)."
    ::= { radEventsGroup 21 }

rad21-addr-rad-serv OBJECT-TYPE
    SYNTAX IpAddress
    MAX-ACCESS accessible-for-notify
    STATUS current
    DESCRIPTION
        "Parameter 'addr-rad-serv' in event RAD.21"
    ::= { radEventObjects21 1 }

rad21-id OBJECT-TYPE
    SYNTAX Integer32
    MAX-ACCESS accessible-for-notify
    STATUS current
    DESCRIPTION
        "Parameter 'id' in event RAD.21"
    ::= { radEventObjects21 2 }

rad21-typ OBJECT-TYPE
    SYNTAX Integer32
    MAX-ACCESS accessible-for-notify
    STATUS current
    DESCRIPTION
        "Parameter 'typ' in event RAD.21"
    ::= { radEventObjects21 3 }

radEventObjects22 OBJECT-IDENTITY
    STATUS current
    DESCRIPTION
        "Event RAD.22
        This message is generated when an ACCESS ACCEPT packet is received
        with a excessive number of attributes with the same type
        from the RADIUS Server (CONSOLE)."
    ::= { radEventsGroup 22 }

rad22-addr-rad-serv OBJECT-TYPE
    SYNTAX IpAddress
    MAX-ACCESS accessible-for-notify
    STATUS current
    DESCRIPTION
        "Parameter 'addr-rad-serv' in event RAD.22"
    ::= { radEventObjects22 1 }

rad22-id OBJECT-TYPE
    SYNTAX Integer32
    MAX-ACCESS accessible-for-notify
    STATUS current
    DESCRIPTION
        "Parameter 'id' in event RAD.22"
    ::= { radEventObjects22 2 }

rad22-typ OBJECT-TYPE
    SYNTAX Integer32
    MAX-ACCESS accessible-for-notify
    STATUS current
    DESCRIPTION
        "Parameter 'typ' in event RAD.22"
    ::= { radEventObjects22 3 }

radEventObjects23 OBJECT-IDENTITY
    STATUS current
    DESCRIPTION
        "Event RAD.23
        This message is generated when an ACCESS ACCEPT packet is received
        with an invalid attribute for the offered service from the RADIUS
        Server (CONSOLE)."
    ::= { radEventsGroup 23 }

rad23-addr-rad-serv OBJECT-TYPE
    SYNTAX IpAddress
    MAX-ACCESS accessible-for-notify
    STATUS current
    DESCRIPTION
        "Parameter 'addr-rad-serv' in event RAD.23"
    ::= { radEventObjects23 1 }

rad23-id OBJECT-TYPE
    SYNTAX Integer32
    MAX-ACCESS accessible-for-notify
    STATUS current
    DESCRIPTION
        "Parameter 'id' in event RAD.23"
    ::= { radEventObjects23 2 }

rad23-typ OBJECT-TYPE
    SYNTAX Integer32
    MAX-ACCESS accessible-for-notify
    STATUS current
    DESCRIPTION
        "Parameter 'typ' in event RAD.23"
    ::= { radEventObjects23 3 }

radEventObjects24 OBJECT-IDENTITY
    STATUS current
    DESCRIPTION
        "Event RAD.24
        This message is generated when a RADIUS server response is received
        with an invalid length (CONSOLE)."
    ::= { radEventsGroup 24 }

rad24-addr-rad-serv OBJECT-TYPE
    SYNTAX IpAddress
    MAX-ACCESS accessible-for-notify
    STATUS current
    DESCRIPTION
        "Parameter 'addr-rad-serv' in event RAD.24"
    ::= { radEventObjects24 1 }

rad24-id OBJECT-TYPE
    SYNTAX Integer32
    MAX-ACCESS accessible-for-notify
    STATUS current
    DESCRIPTION
        "Parameter 'id' in event RAD.24"
    ::= { radEventObjects24 2 }

radEventObjects25 OBJECT-IDENTITY
    STATUS current
    DESCRIPTION
        "Event RAD.25
        This message is generated when an ACCESS REQUEST packet is sent to the
        RADIUS server, if a new TELNET or FTP authentication arrives."
    ::= { radEventsGroup 25 }

rad25-addr-rad-serv OBJECT-TYPE
    SYNTAX IpAddress
    MAX-ACCESS accessible-for-notify
    STATUS current
    DESCRIPTION
        "Parameter 'addr-rad-serv' in event RAD.25"
    ::= { radEventObjects25 1 }

rad25-id OBJECT-TYPE
    SYNTAX Integer32
    MAX-ACCESS accessible-for-notify
    STATUS current
    DESCRIPTION
        "Parameter 'id' in event RAD.25"
    ::= { radEventObjects25 2 }

rad25-servc OBJECT-TYPE
    SYNTAX DisplayString
    MAX-ACCESS accessible-for-notify
    STATUS current
    DESCRIPTION
        "Parameter 'servc' in event RAD.25"
    ::= { radEventObjects25 3 }

rad25-lcl-addr OBJECT-TYPE
    SYNTAX IpAddress
    MAX-ACCESS accessible-for-notify
    STATUS current
    DESCRIPTION
        "Parameter 'lcl-addr' in event RAD.25"
    ::= { radEventObjects25 4 }

rad25-lcl-prt OBJECT-TYPE
    SYNTAX Integer32
    MAX-ACCESS accessible-for-notify
    STATUS current
    DESCRIPTION
        "Parameter 'lcl-prt' in event RAD.25"
    ::= { radEventObjects25 5 }

rad25-rmt-addr OBJECT-TYPE
    SYNTAX IpAddress
    MAX-ACCESS accessible-for-notify
    STATUS current
    DESCRIPTION
        "Parameter 'rmt-addr' in event RAD.25"
    ::= { radEventObjects25 6 }

rad25-rmt-prt OBJECT-TYPE
    SYNTAX Integer32
    MAX-ACCESS accessible-for-notify
    STATUS current
    DESCRIPTION
        "Parameter 'rmt-prt' in event RAD.25"
    ::= { radEventObjects25 7 }

radEventObjects26 OBJECT-IDENTITY
    STATUS current
    DESCRIPTION
        "Event RAD.26
        This message is generated when an ACCESS ACCEPT packet is received,
        which is sent by the RADIUS server if the RADIUS request is
        authenticated (TELNET or FTP)."
    ::= { radEventsGroup 26 }

rad26-addr-rad-serv OBJECT-TYPE
    SYNTAX IpAddress
    MAX-ACCESS accessible-for-notify
    STATUS current
    DESCRIPTION
        "Parameter 'addr-rad-serv' in event RAD.26"
    ::= { radEventObjects26 1 }

rad26-id OBJECT-TYPE
    SYNTAX Integer32
    MAX-ACCESS accessible-for-notify
    STATUS current
    DESCRIPTION
        "Parameter 'id' in event RAD.26"
    ::= { radEventObjects26 2 }

rad26-servc OBJECT-TYPE
    SYNTAX DisplayString
    MAX-ACCESS accessible-for-notify
    STATUS current
    DESCRIPTION
        "Parameter 'servc' in event RAD.26"
    ::= { radEventObjects26 3 }

rad26-lcl-addr OBJECT-TYPE
    SYNTAX IpAddress
    MAX-ACCESS accessible-for-notify
    STATUS current
    DESCRIPTION
        "Parameter 'lcl-addr' in event RAD.26"
    ::= { radEventObjects26 4 }

rad26-lcl-prt OBJECT-TYPE
    SYNTAX Integer32
    MAX-ACCESS accessible-for-notify
    STATUS current
    DESCRIPTION
        "Parameter 'lcl-prt' in event RAD.26"
    ::= { radEventObjects26 5 }

rad26-rmt-addr OBJECT-TYPE
    SYNTAX IpAddress
    MAX-ACCESS accessible-for-notify
    STATUS current
    DESCRIPTION
        "Parameter 'rmt-addr' in event RAD.26"
    ::= { radEventObjects26 6 }

rad26-rmt-prt OBJECT-TYPE
    SYNTAX Integer32
    MAX-ACCESS accessible-for-notify
    STATUS current
    DESCRIPTION
        "Parameter 'rmt-prt' in event RAD.26"
    ::= { radEventObjects26 7 }

radEventObjects27 OBJECT-IDENTITY
    STATUS current
    DESCRIPTION
        "Event RAD.27
        This message is generated when an ACCESS REJECT packet is received,
        which is sent by the RADIUS server if the RADIUS request is rejected
        (TELNET or FTP)."
    ::= { radEventsGroup 27 }

rad27-addr-rad-serv OBJECT-TYPE
    SYNTAX IpAddress
    MAX-ACCESS accessible-for-notify
    STATUS current
    DESCRIPTION
        "Parameter 'addr-rad-serv' in event RAD.27"
    ::= { radEventObjects27 1 }

rad27-id OBJECT-TYPE
    SYNTAX Integer32
    MAX-ACCESS accessible-for-notify
    STATUS current
    DESCRIPTION
        "Parameter 'id' in event RAD.27"
    ::= { radEventObjects27 2 }

rad27-servc OBJECT-TYPE
    SYNTAX DisplayString
    MAX-ACCESS accessible-for-notify
    STATUS current
    DESCRIPTION
        "Parameter 'servc' in event RAD.27"
    ::= { radEventObjects27 3 }

rad27-lcl-addr OBJECT-TYPE
    SYNTAX IpAddress
    MAX-ACCESS accessible-for-notify
    STATUS current
    DESCRIPTION
        "Parameter 'lcl-addr' in event RAD.27"
    ::= { radEventObjects27 4 }

rad27-lcl-prt OBJECT-TYPE
    SYNTAX Integer32
    MAX-ACCESS accessible-for-notify
    STATUS current
    DESCRIPTION
        "Parameter 'lcl-prt' in event RAD.27"
    ::= { radEventObjects27 5 }

rad27-rmt-addr OBJECT-TYPE
    SYNTAX IpAddress
    MAX-ACCESS accessible-for-notify
    STATUS current
    DESCRIPTION
        "Parameter 'rmt-addr' in event RAD.27"
    ::= { radEventObjects27 6 }

rad27-rmt-prt OBJECT-TYPE
    SYNTAX Integer32
    MAX-ACCESS accessible-for-notify
    STATUS current
    DESCRIPTION
        "Parameter 'rmt-prt' in event RAD.27"
    ::= { radEventObjects27 7 }

radEventObjects28 OBJECT-IDENTITY
    STATUS current
    DESCRIPTION
        "Event RAD.28
        This message is generated when an ACCESS CHALLENGE packet is received,
        which is sent by the RADIUS server to ask for a new ACCESS REQUEST
        packet (TELNET or FTP)."
    ::= { radEventsGroup 28 }

rad28-addr-rad-serv OBJECT-TYPE
    SYNTAX IpAddress
    MAX-ACCESS accessible-for-notify
    STATUS current
    DESCRIPTION
        "Parameter 'addr-rad-serv' in event RAD.28"
    ::= { radEventObjects28 1 }

rad28-id OBJECT-TYPE
    SYNTAX Integer32
    MAX-ACCESS accessible-for-notify
    STATUS current
    DESCRIPTION
        "Parameter 'id' in event RAD.28"
    ::= { radEventObjects28 2 }

rad28-servc OBJECT-TYPE
    SYNTAX DisplayString
    MAX-ACCESS accessible-for-notify
    STATUS current
    DESCRIPTION
        "Parameter 'servc' in event RAD.28"
    ::= { radEventObjects28 3 }

rad28-lcl-addr OBJECT-TYPE
    SYNTAX IpAddress
    MAX-ACCESS accessible-for-notify
    STATUS current
    DESCRIPTION
        "Parameter 'lcl-addr' in event RAD.28"
    ::= { radEventObjects28 4 }

rad28-lcl-prt OBJECT-TYPE
    SYNTAX Integer32
    MAX-ACCESS accessible-for-notify
    STATUS current
    DESCRIPTION
        "Parameter 'lcl-prt' in event RAD.28"
    ::= { radEventObjects28 5 }

rad28-rmt-addr OBJECT-TYPE
    SYNTAX IpAddress
    MAX-ACCESS accessible-for-notify
    STATUS current
    DESCRIPTION
        "Parameter 'rmt-addr' in event RAD.28"
    ::= { radEventObjects28 6 }

rad28-rmt-prt OBJECT-TYPE
    SYNTAX Integer32
    MAX-ACCESS accessible-for-notify
    STATUS current
    DESCRIPTION
        "Parameter 'rmt-prt' in event RAD.28"
    ::= { radEventObjects28 7 }

radEventObjects29 OBJECT-IDENTITY
    STATUS current
    DESCRIPTION
        "Event RAD.29
        This message is generated when an ACCESS REQUEST packet is retransmitted
        by the client if the RADIUS server response is not received
        in the expected time (TELNET or FTP)."
    ::= { radEventsGroup 29 }

rad29-addr-rad-serv OBJECT-TYPE
    SYNTAX IpAddress
    MAX-ACCESS accessible-for-notify
    STATUS current
    DESCRIPTION
        "Parameter 'addr-rad-serv' in event RAD.29"
    ::= { radEventObjects29 1 }

rad29-id OBJECT-TYPE
    SYNTAX Integer32
    MAX-ACCESS accessible-for-notify
    STATUS current
    DESCRIPTION
        "Parameter 'id' in event RAD.29"
    ::= { radEventObjects29 2 }

rad29-servc OBJECT-TYPE
    SYNTAX DisplayString
    MAX-ACCESS accessible-for-notify
    STATUS current
    DESCRIPTION
        "Parameter 'servc' in event RAD.29"
    ::= { radEventObjects29 3 }

rad29-lcl-addr OBJECT-TYPE
    SYNTAX IpAddress
    MAX-ACCESS accessible-for-notify
    STATUS current
    DESCRIPTION
        "Parameter 'lcl-addr' in event RAD.29"
    ::= { radEventObjects29 4 }

rad29-lcl-prt OBJECT-TYPE
    SYNTAX Integer32
    MAX-ACCESS accessible-for-notify
    STATUS current
    DESCRIPTION
        "Parameter 'lcl-prt' in event RAD.29"
    ::= { radEventObjects29 5 }

rad29-rmt-addr OBJECT-TYPE
    SYNTAX IpAddress
    MAX-ACCESS accessible-for-notify
    STATUS current
    DESCRIPTION
        "Parameter 'rmt-addr' in event RAD.29"
    ::= { radEventObjects29 6 }

rad29-rmt-prt OBJECT-TYPE
    SYNTAX Integer32
    MAX-ACCESS accessible-for-notify
    STATUS current
    DESCRIPTION
        "Parameter 'rmt-prt' in event RAD.29"
    ::= { radEventObjects29 7 }

radEventObjects30 OBJECT-IDENTITY
    STATUS current
    DESCRIPTION
        "Event RAD.30
        This message is generated when an authentication request is rejected
        if a RADIUS server response is not received or nets to RADIUS servers
        are down and the number of possible attempts is over (TELNET or FTP)."
    ::= { radEventsGroup 30 }

rad30-servc OBJECT-TYPE
    SYNTAX DisplayString
    MAX-ACCESS accessible-for-notify
    STATUS current
    DESCRIPTION
        "Parameter 'servc' in event RAD.30"
    ::= { radEventObjects30 1 }

rad30-lcl-addr OBJECT-TYPE
    SYNTAX IpAddress
    MAX-ACCESS accessible-for-notify
    STATUS current
    DESCRIPTION
        "Parameter 'lcl-addr' in event RAD.30"
    ::= { radEventObjects30 2 }

rad30-lcl-prt OBJECT-TYPE
    SYNTAX Integer32
    MAX-ACCESS accessible-for-notify
    STATUS current
    DESCRIPTION
        "Parameter 'lcl-prt' in event RAD.30"
    ::= { radEventObjects30 3 }

rad30-rmt-addr OBJECT-TYPE
    SYNTAX IpAddress
    MAX-ACCESS accessible-for-notify
    STATUS current
    DESCRIPTION
        "Parameter 'rmt-addr' in event RAD.30"
    ::= { radEventObjects30 4 }

rad30-rmt-prt OBJECT-TYPE
    SYNTAX Integer32
    MAX-ACCESS accessible-for-notify
    STATUS current
    DESCRIPTION
        "Parameter 'rmt-prt' in event RAD.30"
    ::= { radEventObjects30 5 }

radEventObjects31 OBJECT-IDENTITY
    STATUS current
    DESCRIPTION
        "Event RAD.31
        This message is generated when it is tried to send a packet to
        a RADIUS server and outgoing net is not UP (TELNET or FTP)."
    ::= { radEventsGroup 31 }

rad31-addr-rad-serv OBJECT-TYPE
    SYNTAX IpAddress
    MAX-ACCESS accessible-for-notify
    STATUS current
    DESCRIPTION
        "Parameter 'addr-rad-serv' in event RAD.31"
    ::= { radEventObjects31 1 }

rad31-servc OBJECT-TYPE
    SYNTAX DisplayString
    MAX-ACCESS accessible-for-notify
    STATUS current
    DESCRIPTION
        "Parameter 'servc' in event RAD.31"
    ::= { radEventObjects31 2 }

rad31-lcl-addr OBJECT-TYPE
    SYNTAX IpAddress
    MAX-ACCESS accessible-for-notify
    STATUS current
    DESCRIPTION
        "Parameter 'lcl-addr' in event RAD.31"
    ::= { radEventObjects31 3 }

rad31-lcl-prt OBJECT-TYPE
    SYNTAX Integer32
    MAX-ACCESS accessible-for-notify
    STATUS current
    DESCRIPTION
        "Parameter 'lcl-prt' in event RAD.31"
    ::= { radEventObjects31 4 }

rad31-rmt-addr OBJECT-TYPE
    SYNTAX IpAddress
    MAX-ACCESS accessible-for-notify
    STATUS current
    DESCRIPTION
        "Parameter 'rmt-addr' in event RAD.31"
    ::= { radEventObjects31 5 }

rad31-rmt-prt OBJECT-TYPE
    SYNTAX Integer32
    MAX-ACCESS accessible-for-notify
    STATUS current
    DESCRIPTION
        "Parameter 'rmt-prt' in event RAD.31"
    ::= { radEventObjects31 6 }

radEventObjects32 OBJECT-IDENTITY
    STATUS current
    DESCRIPTION
        "Event RAD.32
        This message is generated when an ACCESS ACCEPT packet is received
        with an attribute with invalid length from the RADIUS Server
        (TELNET or FTP)."
    ::= { radEventsGroup 32 }

rad32-addr-rad-serv OBJECT-TYPE
    SYNTAX IpAddress
    MAX-ACCESS accessible-for-notify
    STATUS current
    DESCRIPTION
        "Parameter 'addr-rad-serv' in event RAD.32"
    ::= { radEventObjects32 1 }

rad32-id OBJECT-TYPE
    SYNTAX Integer32
    MAX-ACCESS accessible-for-notify
    STATUS current
    DESCRIPTION
        "Parameter 'id' in event RAD.32"
    ::= { radEventObjects32 2 }

rad32-typ OBJECT-TYPE
    SYNTAX Integer32
    MAX-ACCESS accessible-for-notify
    STATUS current
    DESCRIPTION
        "Parameter 'typ' in event RAD.32"
    ::= { radEventObjects32 3 }

rad32-servc OBJECT-TYPE
    SYNTAX DisplayString
    MAX-ACCESS accessible-for-notify
    STATUS current
    DESCRIPTION
        "Parameter 'servc' in event RAD.32"
    ::= { radEventObjects32 4 }

rad32-lcl-addr OBJECT-TYPE
    SYNTAX IpAddress
    MAX-ACCESS accessible-for-notify
    STATUS current
    DESCRIPTION
        "Parameter 'lcl-addr' in event RAD.32"
    ::= { radEventObjects32 5 }

rad32-lcl-prt OBJECT-TYPE
    SYNTAX Integer32
    MAX-ACCESS accessible-for-notify
    STATUS current
    DESCRIPTION
        "Parameter 'lcl-prt' in event RAD.32"
    ::= { radEventObjects32 6 }

rad32-rmt-addr OBJECT-TYPE
    SYNTAX IpAddress
    MAX-ACCESS accessible-for-notify
    STATUS current
    DESCRIPTION
        "Parameter 'rmt-addr' in event RAD.32"
    ::= { radEventObjects32 7 }

rad32-rmt-prt OBJECT-TYPE
    SYNTAX Integer32
    MAX-ACCESS accessible-for-notify
    STATUS current
    DESCRIPTION
        "Parameter 'rmt-prt' in event RAD.32"
    ::= { radEventObjects32 8 }

radEventObjects33 OBJECT-IDENTITY
    STATUS current
    DESCRIPTION
        "Event RAD.33
        This message is generated when an ACCESS ACCEPT packet is received
        with an attribute with an invalid content from the RADIUS Server
        (TELNET or FTP)."
    ::= { radEventsGroup 33 }

rad33-addr-rad-serv OBJECT-TYPE
    SYNTAX IpAddress
    MAX-ACCESS accessible-for-notify
    STATUS current
    DESCRIPTION
        "Parameter 'addr-rad-serv' in event RAD.33"
    ::= { radEventObjects33 1 }

rad33-id OBJECT-TYPE
    SYNTAX Integer32
    MAX-ACCESS accessible-for-notify
    STATUS current
    DESCRIPTION
        "Parameter 'id' in event RAD.33"
    ::= { radEventObjects33 2 }

rad33-typ OBJECT-TYPE
    SYNTAX Integer32
    MAX-ACCESS accessible-for-notify
    STATUS current
    DESCRIPTION
        "Parameter 'typ' in event RAD.33"
    ::= { radEventObjects33 3 }

rad33-servc OBJECT-TYPE
    SYNTAX DisplayString
    MAX-ACCESS accessible-for-notify
    STATUS current
    DESCRIPTION
        "Parameter 'servc' in event RAD.33"
    ::= { radEventObjects33 4 }

rad33-lcl-addr OBJECT-TYPE
    SYNTAX IpAddress
    MAX-ACCESS accessible-for-notify
    STATUS current
    DESCRIPTION
        "Parameter 'lcl-addr' in event RAD.33"
    ::= { radEventObjects33 5 }

rad33-lcl-prt OBJECT-TYPE
    SYNTAX Integer32
    MAX-ACCESS accessible-for-notify
    STATUS current
    DESCRIPTION
        "Parameter 'lcl-prt' in event RAD.33"
    ::= { radEventObjects33 6 }

rad33-rmt-addr OBJECT-TYPE
    SYNTAX IpAddress
    MAX-ACCESS accessible-for-notify
    STATUS current
    DESCRIPTION
        "Parameter 'rmt-addr' in event RAD.33"
    ::= { radEventObjects33 7 }

rad33-rmt-prt OBJECT-TYPE
    SYNTAX Integer32
    MAX-ACCESS accessible-for-notify
    STATUS current
    DESCRIPTION
        "Parameter 'rmt-prt' in event RAD.33"
    ::= { radEventObjects33 8 }

radEventObjects34 OBJECT-IDENTITY
    STATUS current
    DESCRIPTION
        "Event RAD.34
        This message is generated when an ACCESS ACCEPT packet is received
        with an excessive number of attributes with the same type from
        the RADIUS Server (TELNET or FTP)."
    ::= { radEventsGroup 34 }

rad34-addr-rad-serv OBJECT-TYPE
    SYNTAX IpAddress
    MAX-ACCESS accessible-for-notify
    STATUS current
    DESCRIPTION
        "Parameter 'addr-rad-serv' in event RAD.34"
    ::= { radEventObjects34 1 }

rad34-id OBJECT-TYPE
    SYNTAX Integer32
    MAX-ACCESS accessible-for-notify
    STATUS current
    DESCRIPTION
        "Parameter 'id' in event RAD.34"
    ::= { radEventObjects34 2 }

rad34-typ OBJECT-TYPE
    SYNTAX Integer32
    MAX-ACCESS accessible-for-notify
    STATUS current
    DESCRIPTION
        "Parameter 'typ' in event RAD.34"
    ::= { radEventObjects34 3 }

rad34-servc OBJECT-TYPE
    SYNTAX DisplayString
    MAX-ACCESS accessible-for-notify
    STATUS current
    DESCRIPTION
        "Parameter 'servc' in event RAD.34"
    ::= { radEventObjects34 4 }

rad34-lcl-addr OBJECT-TYPE
    SYNTAX IpAddress
    MAX-ACCESS accessible-for-notify
    STATUS current
    DESCRIPTION
        "Parameter 'lcl-addr' in event RAD.34"
    ::= { radEventObjects34 5 }

rad34-lcl-prt OBJECT-TYPE
    SYNTAX Integer32
    MAX-ACCESS accessible-for-notify
    STATUS current
    DESCRIPTION
        "Parameter 'lcl-prt' in event RAD.34"
    ::= { radEventObjects34 6 }

rad34-rmt-addr OBJECT-TYPE
    SYNTAX IpAddress
    MAX-ACCESS accessible-for-notify
    STATUS current
    DESCRIPTION
        "Parameter 'rmt-addr' in event RAD.34"
    ::= { radEventObjects34 7 }

rad34-rmt-prt OBJECT-TYPE
    SYNTAX Integer32
    MAX-ACCESS accessible-for-notify
    STATUS current
    DESCRIPTION
        "Parameter 'rmt-prt' in event RAD.34"
    ::= { radEventObjects34 8 }

radEventObjects35 OBJECT-IDENTITY
    STATUS current
    DESCRIPTION
        "Event RAD.35
        This message is generated when an ACCESS ACCEPT packet is received
        with an invalid attribute for the offered service from the RADIUS
        Server (TELNET or FTP)."
    ::= { radEventsGroup 35 }

rad35-addr-rad-serv OBJECT-TYPE
    SYNTAX IpAddress
    MAX-ACCESS accessible-for-notify
    STATUS current
    DESCRIPTION
        "Parameter 'addr-rad-serv' in event RAD.35"
    ::= { radEventObjects35 1 }

rad35-id OBJECT-TYPE
    SYNTAX Integer32
    MAX-ACCESS accessible-for-notify
    STATUS current
    DESCRIPTION
        "Parameter 'id' in event RAD.35"
    ::= { radEventObjects35 2 }

rad35-typ OBJECT-TYPE
    SYNTAX Integer32
    MAX-ACCESS accessible-for-notify
    STATUS current
    DESCRIPTION
        "Parameter 'typ' in event RAD.35"
    ::= { radEventObjects35 3 }

rad35-servc OBJECT-TYPE
    SYNTAX DisplayString
    MAX-ACCESS accessible-for-notify
    STATUS current
    DESCRIPTION
        "Parameter 'servc' in event RAD.35"
    ::= { radEventObjects35 4 }

rad35-lcl-addr OBJECT-TYPE
    SYNTAX IpAddress
    MAX-ACCESS accessible-for-notify
    STATUS current
    DESCRIPTION
        "Parameter 'lcl-addr' in event RAD.35"
    ::= { radEventObjects35 5 }

rad35-lcl-prt OBJECT-TYPE
    SYNTAX Integer32
    MAX-ACCESS accessible-for-notify
    STATUS current
    DESCRIPTION
        "Parameter 'lcl-prt' in event RAD.35"
    ::= { radEventObjects35 6 }

rad35-rmt-addr OBJECT-TYPE
    SYNTAX IpAddress
    MAX-ACCESS accessible-for-notify
    STATUS current
    DESCRIPTION
        "Parameter 'rmt-addr' in event RAD.35"
    ::= { radEventObjects35 7 }

rad35-rmt-prt OBJECT-TYPE
    SYNTAX Integer32
    MAX-ACCESS accessible-for-notify
    STATUS current
    DESCRIPTION
        "Parameter 'rmt-prt' in event RAD.35"
    ::= { radEventObjects35 8 }

radEventObjects36 OBJECT-IDENTITY
    STATUS current
    DESCRIPTION
        "Event RAD.36
        This message is generated when a RADIUS server response is received
        with an invalid length (TELNET or FTP)."
    ::= { radEventsGroup 36 }

rad36-addr-rad-serv OBJECT-TYPE
    SYNTAX IpAddress
    MAX-ACCESS accessible-for-notify
    STATUS current
    DESCRIPTION
        "Parameter 'addr-rad-serv' in event RAD.36"
    ::= { radEventObjects36 1 }

rad36-id OBJECT-TYPE
    SYNTAX Integer32
    MAX-ACCESS accessible-for-notify
    STATUS current
    DESCRIPTION
        "Parameter 'id' in event RAD.36"
    ::= { radEventObjects36 2 }

rad36-servc OBJECT-TYPE
    SYNTAX DisplayString
    MAX-ACCESS accessible-for-notify
    STATUS current
    DESCRIPTION
        "Parameter 'servc' in event RAD.36"
    ::= { radEventObjects36 3 }

rad36-lcl-addr OBJECT-TYPE
    SYNTAX IpAddress
    MAX-ACCESS accessible-for-notify
    STATUS current
    DESCRIPTION
        "Parameter 'lcl-addr' in event RAD.36"
    ::= { radEventObjects36 4 }

rad36-lcl-prt OBJECT-TYPE
    SYNTAX Integer32
    MAX-ACCESS accessible-for-notify
    STATUS current
    DESCRIPTION
        "Parameter 'lcl-prt' in event RAD.36"
    ::= { radEventObjects36 5 }

rad36-rmt-addr OBJECT-TYPE
    SYNTAX IpAddress
    MAX-ACCESS accessible-for-notify
    STATUS current
    DESCRIPTION
        "Parameter 'rmt-addr' in event RAD.36"
    ::= { radEventObjects36 6 }

rad36-rmt-prt OBJECT-TYPE
    SYNTAX Integer32
    MAX-ACCESS accessible-for-notify
    STATUS current
    DESCRIPTION
        "Parameter 'rmt-prt' in event RAD.36"
    ::= { radEventObjects36 7 }

radEventObjects37 OBJECT-IDENTITY
    STATUS current
    DESCRIPTION
        "Event RAD.37
        This message is generated when a RADIUS server response is received and
        there is not any pending request corresponding to that packet or rhe
        packet contains errors."
    ::= { radEventsGroup 37 }

rad37-addr-rad-serv OBJECT-TYPE
    SYNTAX IpAddress
    MAX-ACCESS accessible-for-notify
    STATUS current
    DESCRIPTION
        "Parameter 'addr-rad-serv' in event RAD.37"
    ::= { radEventObjects37 1 }

rad37-id OBJECT-TYPE
    SYNTAX Integer32
    MAX-ACCESS accessible-for-notify
    STATUS current
    DESCRIPTION
        "Parameter 'id' in event RAD.37"
    ::= { radEventObjects37 2 }

radEventObjects38 OBJECT-IDENTITY
    STATUS current
    DESCRIPTION
        "Event RAD.38
        This message is generated when a response is received from an unknown
        RADIUS server."
    ::= { radEventsGroup 38 }

rad38-addr-rad-serv OBJECT-TYPE
    SYNTAX IpAddress
    MAX-ACCESS accessible-for-notify
    STATUS current
    DESCRIPTION
        "Parameter 'addr-rad-serv' in event RAD.38"
    ::= { radEventObjects38 1 }

rad38-id OBJECT-TYPE
    SYNTAX Integer32
    MAX-ACCESS accessible-for-notify
    STATUS current
    DESCRIPTION
        "Parameter 'id' in event RAD.38"
    ::= { radEventObjects38 2 }

rad38-src-prt OBJECT-TYPE
    SYNTAX Integer32
    MAX-ACCESS accessible-for-notify
    STATUS current
    DESCRIPTION
        "Parameter 'src-prt' in event RAD.38"
    ::= { radEventObjects38 3 }

rad38-dst-prt OBJECT-TYPE
    SYNTAX Integer32
    MAX-ACCESS accessible-for-notify
    STATUS current
    DESCRIPTION
        "Parameter 'dst-prt' in event RAD.38"
    ::= { radEventObjects38 4 }

radEventObjects39 OBJECT-IDENTITY
    STATUS current
    DESCRIPTION
        "Event RAD.39
        This message is generated when a RADIUS packet is received
        with an unknown type."
    ::= { radEventsGroup 39 }

rad39-addr-rad-serv OBJECT-TYPE
    SYNTAX IpAddress
    MAX-ACCESS accessible-for-notify
    STATUS current
    DESCRIPTION
        "Parameter 'addr-rad-serv' in event RAD.39"
    ::= { radEventObjects39 1 }

rad39-id OBJECT-TYPE
    SYNTAX Integer32
    MAX-ACCESS accessible-for-notify
    STATUS current
    DESCRIPTION
        "Parameter 'id' in event RAD.39"
    ::= { radEventObjects39 2 }

rad39-typ OBJECT-TYPE
    SYNTAX Integer32
    MAX-ACCESS accessible-for-notify
    STATUS current
    DESCRIPTION
        "Parameter 'typ' in event RAD.39"
    ::= { radEventObjects39 3 }

radEventObjects40 OBJECT-IDENTITY
    STATUS current
    DESCRIPTION
        "Event RAD.40
        This message is generated when a RADIUS server response is received
        with an invalid length."
    ::= { radEventsGroup 40 }

rad40-addr-rad-serv OBJECT-TYPE
    SYNTAX IpAddress
    MAX-ACCESS accessible-for-notify
    STATUS current
    DESCRIPTION
        "Parameter 'addr-rad-serv' in event RAD.40"
    ::= { radEventObjects40 1 }

rad40-id OBJECT-TYPE
    SYNTAX Integer32
    MAX-ACCESS accessible-for-notify
    STATUS current
    DESCRIPTION
        "Parameter 'id' in event RAD.40"
    ::= { radEventObjects40 2 }

radEventObjects41 OBJECT-IDENTITY
    STATUS current
    DESCRIPTION
        "Event RAD.41
        Generic internal error event."
    ::= { radEventsGroup 41 }

rad41-error-string OBJECT-TYPE
    SYNTAX DisplayString
    MAX-ACCESS accessible-for-notify
    STATUS current
    DESCRIPTION
        "Parameter 'error-string' in event RAD.41"
    ::= { radEventObjects41 1 }

radEventObjects42 OBJECT-IDENTITY
    STATUS current
    DESCRIPTION
        "Event RAD.42
        Attribute sent in a Radius request."
    ::= { radEventsGroup 42 }

rad42-name OBJECT-TYPE
    SYNTAX DisplayString
    MAX-ACCESS accessible-for-notify
    STATUS current
    DESCRIPTION
        "Parameter 'name' in event RAD.42"
    ::= { radEventObjects42 1 }

rad42-length OBJECT-TYPE
    SYNTAX Integer32
    MAX-ACCESS accessible-for-notify
    STATUS current
    DESCRIPTION
        "Parameter 'length' in event RAD.42"
    ::= { radEventObjects42 2 }

rad42-value OBJECT-TYPE
    SYNTAX DisplayString
    MAX-ACCESS accessible-for-notify
    STATUS current
    DESCRIPTION
        "Parameter 'value' in event RAD.42"
    ::= { radEventObjects42 3 }

radEventObjects43 OBJECT-IDENTITY
    STATUS current
    DESCRIPTION
        "Event RAD.43
        Attribute received in a Radius response."
    ::= { radEventsGroup 43 }

rad43-name OBJECT-TYPE
    SYNTAX DisplayString
    MAX-ACCESS accessible-for-notify
    STATUS current
    DESCRIPTION
        "Parameter 'name' in event RAD.43"
    ::= { radEventObjects43 1 }

rad43-length OBJECT-TYPE
    SYNTAX Integer32
    MAX-ACCESS accessible-for-notify
    STATUS current
    DESCRIPTION
        "Parameter 'length' in event RAD.43"
    ::= { radEventObjects43 2 }

rad43-value OBJECT-TYPE
    SYNTAX DisplayString
    MAX-ACCESS accessible-for-notify
    STATUS current
    DESCRIPTION
        "Parameter 'value' in event RAD.43"
    ::= { radEventObjects43 3 }

radEventObjects44 OBJECT-IDENTITY
    STATUS current
    DESCRIPTION
        "Event RAD.44
        This message is generated when a packet is sent to a RADIUS server."
    ::= { radEventsGroup 44 }

rad44-packet-type OBJECT-TYPE
    SYNTAX DisplayString
    MAX-ACCESS accessible-for-notify
    STATUS current
    DESCRIPTION
        "Parameter 'packet-type' in event RAD.44"
    ::= { radEventObjects44 1 }

rad44-length OBJECT-TYPE
    SYNTAX Integer32
    MAX-ACCESS accessible-for-notify
    STATUS current
    DESCRIPTION
        "Parameter 'length' in event RAD.44"
    ::= { radEventObjects44 2 }

rad44-server-address OBJECT-TYPE
    SYNTAX IpAddress
    MAX-ACCESS accessible-for-notify
    STATUS current
    DESCRIPTION
        "Parameter 'server-address' in event RAD.44"
    ::= { radEventObjects44 3 }

rad44-server-port OBJECT-TYPE
    SYNTAX Integer32
    MAX-ACCESS accessible-for-notify
    STATUS current
    DESCRIPTION
        "Parameter 'server-port' in event RAD.44"
    ::= { radEventObjects44 4 }

rad44-identifier OBJECT-TYPE
    SYNTAX Integer32
    MAX-ACCESS accessible-for-notify
    STATUS current
    DESCRIPTION
        "Parameter 'identifier' in event RAD.44"
    ::= { radEventObjects44 5 }

rad44-service OBJECT-TYPE
    SYNTAX DisplayString
    MAX-ACCESS accessible-for-notify
    STATUS current
    DESCRIPTION
        "Parameter 'service' in event RAD.44"
    ::= { radEventObjects44 6 }

radEventObjects45 OBJECT-IDENTITY
    STATUS current
    DESCRIPTION
        "Event RAD.45
        This message is generated when a packet is sent to a RADIUS server."
    ::= { radEventsGroup 45 }

rad45-packet-type OBJECT-TYPE
    SYNTAX DisplayString
    MAX-ACCESS accessible-for-notify
    STATUS current
    DESCRIPTION
        "Parameter 'packet-type' in event RAD.45"
    ::= { radEventObjects45 1 }

rad45-length OBJECT-TYPE
    SYNTAX Integer32
    MAX-ACCESS accessible-for-notify
    STATUS current
    DESCRIPTION
        "Parameter 'length' in event RAD.45"
    ::= { radEventObjects45 2 }

rad45-server-address OBJECT-TYPE
    SYNTAX IpAddress
    MAX-ACCESS accessible-for-notify
    STATUS current
    DESCRIPTION
        "Parameter 'server-address' in event RAD.45"
    ::= { radEventObjects45 3 }

rad45-server-port OBJECT-TYPE
    SYNTAX Integer32
    MAX-ACCESS accessible-for-notify
    STATUS current
    DESCRIPTION
        "Parameter 'server-port' in event RAD.45"
    ::= { radEventObjects45 4 }

rad45-identifier OBJECT-TYPE
    SYNTAX Integer32
    MAX-ACCESS accessible-for-notify
    STATUS current
    DESCRIPTION
        "Parameter 'identifier' in event RAD.45"
    ::= { radEventObjects45 5 }

rad45-service OBJECT-TYPE
    SYNTAX DisplayString
    MAX-ACCESS accessible-for-notify
    STATUS current
    DESCRIPTION
        "Parameter 'service' in event RAD.45"
    ::= { radEventObjects45 6 }

radEventObjects46 OBJECT-IDENTITY
    STATUS current
    DESCRIPTION
        "Event RAD.46
        This message is generated when a packet is retransmitted to a RADIUS server."
    ::= { radEventsGroup 46 }

rad46-packet-type OBJECT-TYPE
    SYNTAX DisplayString
    MAX-ACCESS accessible-for-notify
    STATUS current
    DESCRIPTION
        "Parameter 'packet-type' in event RAD.46"
    ::= { radEventObjects46 1 }

rad46-length OBJECT-TYPE
    SYNTAX Integer32
    MAX-ACCESS accessible-for-notify
    STATUS current
    DESCRIPTION
        "Parameter 'length' in event RAD.46"
    ::= { radEventObjects46 2 }

rad46-server-address OBJECT-TYPE
    SYNTAX IpAddress
    MAX-ACCESS accessible-for-notify
    STATUS current
    DESCRIPTION
        "Parameter 'server-address' in event RAD.46"
    ::= { radEventObjects46 3 }

rad46-server-port OBJECT-TYPE
    SYNTAX Integer32
    MAX-ACCESS accessible-for-notify
    STATUS current
    DESCRIPTION
        "Parameter 'server-port' in event RAD.46"
    ::= { radEventObjects46 4 }

rad46-identifier OBJECT-TYPE
    SYNTAX Integer32
    MAX-ACCESS accessible-for-notify
    STATUS current
    DESCRIPTION
        "Parameter 'identifier' in event RAD.46"
    ::= { radEventObjects46 5 }

rad46-service OBJECT-TYPE
    SYNTAX DisplayString
    MAX-ACCESS accessible-for-notify
    STATUS current
    DESCRIPTION
        "Parameter 'service' in event RAD.46"
    ::= { radEventObjects46 6 }

radEventObjects47 OBJECT-IDENTITY
    STATUS current
    DESCRIPTION
        "Event RAD.47
        Generic comment on usual information message."
    ::= { radEventsGroup 47 }

rad47-info-string OBJECT-TYPE
    SYNTAX DisplayString
    MAX-ACCESS accessible-for-notify
    STATUS current
    DESCRIPTION
        "Parameter 'info-string' in event RAD.47"
    ::= { radEventObjects47 1 }

radEventObjects48 OBJECT-IDENTITY
    STATUS current
    DESCRIPTION
        "Event RAD.48
        This message is generated when an authentication request is rejected
        if a RADIUS server response is not received or nets to RADIUS servers
        are down and the number of possible attempts is over."
    ::= { radEventsGroup 48 }

rad48-service OBJECT-TYPE
    SYNTAX DisplayString
    MAX-ACCESS accessible-for-notify
    STATUS current
    DESCRIPTION
        "Parameter 'service' in event RAD.48"
    ::= { radEventObjects48 1 }

radEventObjects49 OBJECT-IDENTITY
    STATUS current
    DESCRIPTION
        "Event RAD.49
        This message is generated when it is tried to send a packet to a
        RADIUS server and outgoing net is not UP."
    ::= { radEventsGroup 49 }

rad49-addr-rad-serv OBJECT-TYPE
    SYNTAX IpAddress
    MAX-ACCESS accessible-for-notify
    STATUS current
    DESCRIPTION
        "Parameter 'addr-rad-serv' in event RAD.49"
    ::= { radEventObjects49 1 }

rad49-service OBJECT-TYPE
    SYNTAX DisplayString
    MAX-ACCESS accessible-for-notify
    STATUS current
    DESCRIPTION
        "Parameter 'service' in event RAD.49"
    ::= { radEventObjects49 2 }

radEventObjects50 OBJECT-IDENTITY
    STATUS current
    DESCRIPTION
        "Event RAD.50
        This message is generated when an ACCESS REQUEST packet is sent to
        RADIUS server, if a new authentication arrives."
    ::= { radEventsGroup 50 }

rad50-addr-rad-serv OBJECT-TYPE
    SYNTAX IpAddress
    MAX-ACCESS accessible-for-notify
    STATUS current
    DESCRIPTION
        "Parameter 'addr-rad-serv' in event RAD.50"
    ::= { radEventObjects50 1 }

rad50-id OBJECT-TYPE
    SYNTAX Integer32
    MAX-ACCESS accessible-for-notify
    STATUS current
    DESCRIPTION
        "Parameter 'id' in event RAD.50"
    ::= { radEventObjects50 2 }

rad50-service OBJECT-TYPE
    SYNTAX DisplayString
    MAX-ACCESS accessible-for-notify
    STATUS current
    DESCRIPTION
        "Parameter 'service' in event RAD.50"
    ::= { radEventObjects50 3 }

radEventObjects51 OBJECT-IDENTITY
    STATUS current
    DESCRIPTION
        "Event RAD.51
        This message is generated when an ACCESS REQUEST packet is retransmitted
        by the client if the RADIUS server response is not received
        in the expected time."
    ::= { radEventsGroup 51 }

rad51-addr-rad-serv OBJECT-TYPE
    SYNTAX IpAddress
    MAX-ACCESS accessible-for-notify
    STATUS current
    DESCRIPTION
        "Parameter 'addr-rad-serv' in event RAD.51"
    ::= { radEventObjects51 1 }

rad51-id OBJECT-TYPE
    SYNTAX Integer32
    MAX-ACCESS accessible-for-notify
    STATUS current
    DESCRIPTION
        "Parameter 'id' in event RAD.51"
    ::= { radEventObjects51 2 }

rad51-service OBJECT-TYPE
    SYNTAX DisplayString
    MAX-ACCESS accessible-for-notify
    STATUS current
    DESCRIPTION
        "Parameter 'service' in event RAD.51"
    ::= { radEventObjects51 3 }

radEventObjects52 OBJECT-IDENTITY
    STATUS current
    DESCRIPTION
        "Event RAD.52
        This message is generated when an ACCESS ACCEPT packet is received,
        which is sent by the RADIUS server if the RADIUS request is
        authenticated."
    ::= { radEventsGroup 52 }

rad52-addr-rad-serv OBJECT-TYPE
    SYNTAX IpAddress
    MAX-ACCESS accessible-for-notify
    STATUS current
    DESCRIPTION
        "Parameter 'addr-rad-serv' in event RAD.52"
    ::= { radEventObjects52 1 }

rad52-id OBJECT-TYPE
    SYNTAX Integer32
    MAX-ACCESS accessible-for-notify
    STATUS current
    DESCRIPTION
        "Parameter 'id' in event RAD.52"
    ::= { radEventObjects52 2 }

rad52-service OBJECT-TYPE
    SYNTAX DisplayString
    MAX-ACCESS accessible-for-notify
    STATUS current
    DESCRIPTION
        "Parameter 'service' in event RAD.52"
    ::= { radEventObjects52 3 }

radEventObjects53 OBJECT-IDENTITY
    STATUS current
    DESCRIPTION
        "Event RAD.53
        This message is generated when an ACCESS REJECT packet is received,
        which is sent by the RADIUS server if the RADIUS request is rejected."
    ::= { radEventsGroup 53 }

rad53-addr-rad-serv OBJECT-TYPE
    SYNTAX IpAddress
    MAX-ACCESS accessible-for-notify
    STATUS current
    DESCRIPTION
        "Parameter 'addr-rad-serv' in event RAD.53"
    ::= { radEventObjects53 1 }

rad53-id OBJECT-TYPE
    SYNTAX Integer32
    MAX-ACCESS accessible-for-notify
    STATUS current
    DESCRIPTION
        "Parameter 'id' in event RAD.53"
    ::= { radEventObjects53 2 }

rad53-service OBJECT-TYPE
    SYNTAX DisplayString
    MAX-ACCESS accessible-for-notify
    STATUS current
    DESCRIPTION
        "Parameter 'service' in event RAD.53"
    ::= { radEventObjects53 3 }

radEventObjects54 OBJECT-IDENTITY
    STATUS current
    DESCRIPTION
        "Event RAD.54
        This message is generated when an ACCESS CHALLENGE packet is received,
        which is sent by the RADIUS server to ask for a new ACCESS REQUEST
        packet."
    ::= { radEventsGroup 54 }

rad54-addr-rad-serv OBJECT-TYPE
    SYNTAX IpAddress
    MAX-ACCESS accessible-for-notify
    STATUS current
    DESCRIPTION
        "Parameter 'addr-rad-serv' in event RAD.54"
    ::= { radEventObjects54 1 }

rad54-id OBJECT-TYPE
    SYNTAX Integer32
    MAX-ACCESS accessible-for-notify
    STATUS current
    DESCRIPTION
        "Parameter 'id' in event RAD.54"
    ::= { radEventObjects54 2 }

rad54-service OBJECT-TYPE
    SYNTAX DisplayString
    MAX-ACCESS accessible-for-notify
    STATUS current
    DESCRIPTION
        "Parameter 'service' in event RAD.54"
    ::= { radEventObjects54 3 }

radEventObjects55 OBJECT-IDENTITY
    STATUS current
    DESCRIPTION
        "Event RAD.55
        This message is generated when an ACCESS ACCEPT packet is received
        with an attribute with invalid length from the RADIUS Server."
    ::= { radEventsGroup 55 }

rad55-addr-rad-serv OBJECT-TYPE
    SYNTAX IpAddress
    MAX-ACCESS accessible-for-notify
    STATUS current
    DESCRIPTION
        "Parameter 'addr-rad-serv' in event RAD.55"
    ::= { radEventObjects55 1 }

rad55-id OBJECT-TYPE
    SYNTAX Integer32
    MAX-ACCESS accessible-for-notify
    STATUS current
    DESCRIPTION
        "Parameter 'id' in event RAD.55"
    ::= { radEventObjects55 2 }

rad55-typ OBJECT-TYPE
    SYNTAX Integer32
    MAX-ACCESS accessible-for-notify
    STATUS current
    DESCRIPTION
        "Parameter 'typ' in event RAD.55"
    ::= { radEventObjects55 3 }

rad55-service OBJECT-TYPE
    SYNTAX DisplayString
    MAX-ACCESS accessible-for-notify
    STATUS current
    DESCRIPTION
        "Parameter 'service' in event RAD.55"
    ::= { radEventObjects55 4 }

radEventObjects56 OBJECT-IDENTITY
    STATUS current
    DESCRIPTION
        "Event RAD.56
        This message is generated when an ACCESS ACCEPT packet is received
        with an attribute with an invalid content from the RADIUS Server."
    ::= { radEventsGroup 56 }

rad56-addr-rad-serv OBJECT-TYPE
    SYNTAX IpAddress
    MAX-ACCESS accessible-for-notify
    STATUS current
    DESCRIPTION
        "Parameter 'addr-rad-serv' in event RAD.56"
    ::= { radEventObjects56 1 }

rad56-id OBJECT-TYPE
    SYNTAX Integer32
    MAX-ACCESS accessible-for-notify
    STATUS current
    DESCRIPTION
        "Parameter 'id' in event RAD.56"
    ::= { radEventObjects56 2 }

rad56-typ OBJECT-TYPE
    SYNTAX Integer32
    MAX-ACCESS accessible-for-notify
    STATUS current
    DESCRIPTION
        "Parameter 'typ' in event RAD.56"
    ::= { radEventObjects56 3 }

rad56-service OBJECT-TYPE
    SYNTAX DisplayString
    MAX-ACCESS accessible-for-notify
    STATUS current
    DESCRIPTION
        "Parameter 'service' in event RAD.56"
    ::= { radEventObjects56 4 }

radEventObjects57 OBJECT-IDENTITY
    STATUS current
    DESCRIPTION
        "Event RAD.57
        This message is generated when an ACCESS ACCEPT packet is received
        with a excessive number of attributes with the same type
        from the RADIUS Server."
    ::= { radEventsGroup 57 }

rad57-addr-rad-serv OBJECT-TYPE
    SYNTAX IpAddress
    MAX-ACCESS accessible-for-notify
    STATUS current
    DESCRIPTION
        "Parameter 'addr-rad-serv' in event RAD.57"
    ::= { radEventObjects57 1 }

rad57-id OBJECT-TYPE
    SYNTAX Integer32
    MAX-ACCESS accessible-for-notify
    STATUS current
    DESCRIPTION
        "Parameter 'id' in event RAD.57"
    ::= { radEventObjects57 2 }

rad57-typ OBJECT-TYPE
    SYNTAX Integer32
    MAX-ACCESS accessible-for-notify
    STATUS current
    DESCRIPTION
        "Parameter 'typ' in event RAD.57"
    ::= { radEventObjects57 3 }

rad57-service OBJECT-TYPE
    SYNTAX DisplayString
    MAX-ACCESS accessible-for-notify
    STATUS current
    DESCRIPTION
        "Parameter 'service' in event RAD.57"
    ::= { radEventObjects57 4 }

radEventObjects58 OBJECT-IDENTITY
    STATUS current
    DESCRIPTION
        "Event RAD.58
        This message is generated when an ACCESS ACCEPT packet is received
        with an invalid attribute for the offered service from the RADIUS
        Server."
    ::= { radEventsGroup 58 }

rad58-addr-rad-serv OBJECT-TYPE
    SYNTAX IpAddress
    MAX-ACCESS accessible-for-notify
    STATUS current
    DESCRIPTION
        "Parameter 'addr-rad-serv' in event RAD.58"
    ::= { radEventObjects58 1 }

rad58-id OBJECT-TYPE
    SYNTAX Integer32
    MAX-ACCESS accessible-for-notify
    STATUS current
    DESCRIPTION
        "Parameter 'id' in event RAD.58"
    ::= { radEventObjects58 2 }

rad58-typ OBJECT-TYPE
    SYNTAX Integer32
    MAX-ACCESS accessible-for-notify
    STATUS current
    DESCRIPTION
        "Parameter 'typ' in event RAD.58"
    ::= { radEventObjects58 3 }

rad58-service OBJECT-TYPE
    SYNTAX DisplayString
    MAX-ACCESS accessible-for-notify
    STATUS current
    DESCRIPTION
        "Parameter 'service' in event RAD.58"
    ::= { radEventObjects58 4 }

radEventObjects59 OBJECT-IDENTITY
    STATUS current
    DESCRIPTION
        "Event RAD.59
        This message is generated when a RADIUS server response is received
        with an invalid length."
    ::= { radEventsGroup 59 }

rad59-addr-rad-serv OBJECT-TYPE
    SYNTAX IpAddress
    MAX-ACCESS accessible-for-notify
    STATUS current
    DESCRIPTION
        "Parameter 'addr-rad-serv' in event RAD.59"
    ::= { radEventObjects59 1 }

rad59-id OBJECT-TYPE
    SYNTAX Integer32
    MAX-ACCESS accessible-for-notify
    STATUS current
    DESCRIPTION
        "Parameter 'id' in event RAD.59"
    ::= { radEventObjects59 2 }

rad59-service OBJECT-TYPE
    SYNTAX DisplayString
    MAX-ACCESS accessible-for-notify
    STATUS current
    DESCRIPTION
        "Parameter 'service' in event RAD.59"
    ::= { radEventObjects59 3 }


radNotification1 NOTIFICATION-TYPE
    OBJECTS { 
              rad1-addr-rad-serv, 
              rad1-id,
              rad1-servc,
              rad1-interface 
            }
    STATUS current
    DESCRIPTION
        "Notification of Event RAD.1

        Message: 'send an ACCESS REQUEST packet to RADIUS server $1, identifier $2, for service $3 on interface $4'

        Parameters list:
              $1: rad1-addr-rad-serv
              $2: rad1-id
              $3: rad1-servc
              $4: rad1-interface

        This message is generated when an ACCESS REQUEST packet is sent to
        RADIUS server, if a new PAP or CHAP authentication arrives."
    ::= { radNotificationsPrefix 1 }

radNotification2 NOTIFICATION-TYPE
    OBJECTS { 
              rad2-addr-rad-serv, 
              rad2-id,
              rad2-servc,
              rad2-interface 
            }
    STATUS current
    DESCRIPTION
        "Notification of Event RAD.2

        Message: 'receive an ACCESS ACCEPT packet from RADIUS server $1, identifier $2, for service $3 on interface $4'

        Parameters list:
              $1: rad2-addr-rad-serv
              $2: rad2-id
              $3: rad2-servc
              $4: rad2-interface

        This message is generated when an ACCESS ACCEPT packet is received,
        which is sent by the RADIUS server if the RADIUS request
        is authenticated (PAP or CHAP)."
    ::= { radNotificationsPrefix 2 }

radNotification3 NOTIFICATION-TYPE
    OBJECTS { 
              rad3-addr-rad-serv, 
              rad3-id,
              rad3-servc,
              rad3-interface 
            }
    STATUS current
    DESCRIPTION
        "Notification of Event RAD.3

        Message: 'receive an ACCESS REJECT packet from RADIUS server $1, identifier $2, for service $3 on interface $4'

        Parameters list:
              $1: rad3-addr-rad-serv
              $2: rad3-id
              $3: rad3-servc
              $4: rad3-interface

        This message is generated when an ACCESS REJECT packet is received,
        which is sent by the RADIUS server if the RADIUS request is rejected
        (PAP or CHAP)."
    ::= { radNotificationsPrefix 3 }

radNotification4 NOTIFICATION-TYPE
    OBJECTS { 
              rad4-addr-rad-serv, 
              rad4-id,
              rad4-servc,
              rad4-interface 
            }
    STATUS current
    DESCRIPTION
        "Notification of Event RAD.4

        Message: 'receive an ACCESS CHALLENGE packet from RADIUS server $1, identifier $2, for service $3 on interface $4'

        Parameters list:
              $1: rad4-addr-rad-serv
              $2: rad4-id
              $3: rad4-servc
              $4: rad4-interface

        This message is generated when an ACCESS CHALLENGE packet is received,
        which is sent by the RADIUS server to ask for a new
        ACCESS REQUEST packet (PAP or CHAP)."
    ::= { radNotificationsPrefix 4 }

radNotification5 NOTIFICATION-TYPE
    OBJECTS { 
              rad5-addr-rad-serv, 
              rad5-id,
              rad5-servc,
              rad5-interface 
            }
    STATUS current
    DESCRIPTION
        "Notification of Event RAD.5

        Message: 'retransmit ACCESS REQUEST packet to RADIUS server $1, identifier $2, for service $3 on interface $4'

        Parameters list:
              $1: rad5-addr-rad-serv
              $2: rad5-id
              $3: rad5-servc
              $4: rad5-interface

        This message is generated when an ACCESS REQUEST packet is retransmitted
        by the client if the RADIUS server response is not received
        in the expected time (PAP or CHAP)."
    ::= { radNotificationsPrefix 5 }

radNotification6 NOTIFICATION-TYPE
    OBJECTS { 
              rad6-servc, 
              rad6-interface 
            }
    STATUS current
    DESCRIPTION
        "Notification of Event RAD.6

        Message: 'fail authentication due to no communication with RADIUS servers, for service $1 on interface $2'

        Parameters list:
              $1: rad6-servc
              $2: rad6-interface

        This message is generated when an authentication request is rejected
        if a RADIUS server response is not received or nets to RADIUS servers
        are down and the number of possible attempts is over (PAP or CHAP)."
    ::= { radNotificationsPrefix 6 }

radNotification7 NOTIFICATION-TYPE
    OBJECTS { 
              rad7-addr-rad-serv, 
              rad7-servc,
              rad7-interface 
            }
    STATUS current
    DESCRIPTION
        "Notification of Event RAD.7

        Message: 'net to servidor RADIUS $1 is not UP, for service $2 on interface $3'

        Parameters list:
              $1: rad7-addr-rad-serv
              $2: rad7-servc
              $3: rad7-interface

        This message is generated when it is tried to send a packet to
        a RADIUS server and outgoing net is no UP (PAP or CHAP)."
    ::= { radNotificationsPrefix 7 }

radNotification8 NOTIFICATION-TYPE
    OBJECTS { 
              rad8-addr-rad-serv, 
              rad8-id,
              rad8-typ,
              rad8-servc,
              rad8-interface 
            }
    STATUS current
    DESCRIPTION
        "Notification of Event RAD.8

        Message: 'receive an ACCESS ACCEPT packet from RADIUS server $1, identifier $2, with attribute type $3 with invalid length, for service $4 on interface $5'

        Parameters list:
              $1: rad8-addr-rad-serv
              $2: rad8-id
              $3: rad8-typ
              $4: rad8-servc
              $5: rad8-interface

        This message is generated when an ACCESS ACCEPT packet is received
        with an attribute with invalid length from the RADIUS Server
        (PAP or CHAP)."
    ::= { radNotificationsPrefix 8 }

radNotification9 NOTIFICATION-TYPE
    OBJECTS { 
              rad9-addr-rad-serv, 
              rad9-id,
              rad9-typ,
              rad9-servc,
              rad9-interface 
            }
    STATUS current
    DESCRIPTION
        "Notification of Event RAD.9

        Message: 'receive an ACCESS ACCEPT packet from RADIUS server $1, identifier $2, with attribute type $3 with invalid content, for service $4 on interface $5'

        Parameters list:
              $1: rad9-addr-rad-serv
              $2: rad9-id
              $3: rad9-typ
              $4: rad9-servc
              $5: rad9-interface

        This message is generated when an ACCESS ACCEPT packet is received
        with an attribute with an invalid content from the RADIUS Server
        (PAP or CHAP)."
    ::= { radNotificationsPrefix 9 }

radNotification10 NOTIFICATION-TYPE
    OBJECTS { 
              rad10-addr-rad-serv, 
              rad10-id,
              rad10-typ,
              rad10-servc,
              rad10-interface 
            }
    STATUS current
    DESCRIPTION
        "Notification of Event RAD.10

        Message: 'receive an ACCESS ACCEPT packet from RADIUS server $1, identifier $2, with extra attribute type $3, for service $4 on interface $5'

        Parameters list:
              $1: rad10-addr-rad-serv
              $2: rad10-id
              $3: rad10-typ
              $4: rad10-servc
              $5: rad10-interface

        This message is generated when an ACCESS ACCEPT packet is received
        with an excessive number of attributes with the same type from
        the RADIUS Server (PAP or CHAP)."
    ::= { radNotificationsPrefix 10 }

radNotification11 NOTIFICATION-TYPE
    OBJECTS { 
              rad11-addr-rad-serv, 
              rad11-id,
              rad11-typ,
              rad11-servc,
              rad11-interface 
            }
    STATUS current
    DESCRIPTION
        "Notification of Event RAD.11

        Message: 'receive an ACCESS ACCEPT packet from RADIUS server $1, identifier $2, with invalid attribute type $3, for service $4 on interface $5'

        Parameters list:
              $1: rad11-addr-rad-serv
              $2: rad11-id
              $3: rad11-typ
              $4: rad11-servc
              $5: rad11-interface

        This message is generated when an ACCESS ACCEPT packet is received
        with an invalid attribute for the offered service from the RADIUS
        Server (PAP or CHAP)."
    ::= { radNotificationsPrefix 11 }

radNotification12 NOTIFICATION-TYPE
    OBJECTS { 
              rad12-addr-rad-serv, 
              rad12-id,
              rad12-servc,
              rad12-interface 
            }
    STATUS current
    DESCRIPTION
        "Notification of Event RAD.12

        Message: 'receive an ACCESS RESPONSE packet from RADIUS server $1, identifier $2, with invalid length, for service $3 on interface $4'

        Parameters list:
              $1: rad12-addr-rad-serv
              $2: rad12-id
              $3: rad12-servc
              $4: rad12-interface

        This message is generated when a RADIUS server response is received
        with an invalid length (PAP or CHAP)."
    ::= { radNotificationsPrefix 12 }

radNotification13 NOTIFICATION-TYPE
    OBJECTS { 
              rad13-addr-rad-serv, 
              rad13-id 
            }
    STATUS current
    DESCRIPTION
        "Notification of Event RAD.13

        Message: 'send an ACCESS REQUEST packet to RADIUS server $1, identifier $2, for service CONSOLE'

        Parameters list:
              $1: rad13-addr-rad-serv
              $2: rad13-id

        This message is generated when an ACCESS REQUEST packet is sent to
        RADIUS server, if a new CONSOLE authentication arrives."
    ::= { radNotificationsPrefix 13 }

radNotification14 NOTIFICATION-TYPE
    OBJECTS { 
              rad14-addr-rad-serv, 
              rad14-id 
            }
    STATUS current
    DESCRIPTION
        "Notification of Event RAD.14

        Message: 'receive an ACCESS ACCEPT packet from RADIUS server $1, identifier $2, for service CONSOLE'

        Parameters list:
              $1: rad14-addr-rad-serv
              $2: rad14-id

        This message is generated when an ACCESS ACCEPT packet is received,
        which is sent by the RADIUS server if the RADIUS request is
        authenticated (CONSOLE)."
    ::= { radNotificationsPrefix 14 }

radNotification15 NOTIFICATION-TYPE
    OBJECTS { 
              rad15-addr-rad-serv, 
              rad15-id 
            }
    STATUS current
    DESCRIPTION
        "Notification of Event RAD.15

        Message: 'receive an ACCESS REJECT packet from RADIUS server $1, identifier $2, for service CONSOLE'

        Parameters list:
              $1: rad15-addr-rad-serv
              $2: rad15-id

        This message is generated when an ACCESS REJECT packet is received,
        which is sent by the RADIUS server if the RADIUS request is rejected
        (CONSOLE)."
    ::= { radNotificationsPrefix 15 }

radNotification16 NOTIFICATION-TYPE
    OBJECTS { 
              rad16-addr-rad-serv, 
              rad16-id 
            }
    STATUS current
    DESCRIPTION
        "Notification of Event RAD.16

        Message: 'receive an ACCESS CHALLENGE packet from RADIUS server $1, identifier $2, for service CONSOLE'

        Parameters list:
              $1: rad16-addr-rad-serv
              $2: rad16-id

        This message is generated when an ACCESS CHALLENGE packet is received,
        which is sent by the RADIUS server to ask for a new ACCESS REQUEST
        packet (CONSOLE)."
    ::= { radNotificationsPrefix 16 }

radNotification17 NOTIFICATION-TYPE
    OBJECTS { 
              rad17-addr-rad-serv, 
              rad17-id 
            }
    STATUS current
    DESCRIPTION
        "Notification of Event RAD.17

        Message: 'retransmit ACCESS REQUEST packet to RADIUS server $1, identifier $2, for service CONSOLE'

        Parameters list:
              $1: rad17-addr-rad-serv
              $2: rad17-id

        This message is generated when an ACCESS REQUEST packet is retransmitted
        by the client if the RADIUS server response is not received
        in the expected time (CONSOLE)."
    ::= { radNotificationsPrefix 17 }

radNotification18 NOTIFICATION-TYPE
    STATUS current
    DESCRIPTION
        "Notification of Event RAD.18

        Message: 'fail authentication due to no communication with RADIUS servers, for service CONSOLE'

        This message is generated when an authentication request is rejected
        if a RADIUS server response is not received or nets to RADIUS servers
        are down and the number of possible attempts is over (CONSOLE)."
    ::= { radNotificationsPrefix 18 }

radNotification19 NOTIFICATION-TYPE
    OBJECTS { 
              rad19-addr-rad-serv 
            }
    STATUS current
    DESCRIPTION
        "Notification of Event RAD.19

        Message: 'net to servidor RADIUS $1 is not UP, for service CONSOLE'

        Parameters list:
              $1: rad19-addr-rad-serv

        This message is generated when it is tried to send a packet to a
        RADIUS server and outgoing net is not UP (CONSOLE)."
    ::= { radNotificationsPrefix 19 }

radNotification20 NOTIFICATION-TYPE
    OBJECTS { 
              rad20-addr-rad-serv, 
              rad20-id,
              rad20-typ 
            }
    STATUS current
    DESCRIPTION
        "Notification of Event RAD.20

        Message: 'receive an ACCESS ACCEPT packet from RADIUS server $1, identifier $2, with attribute type $3 with invalid length, for service CONSOLE'

        Parameters list:
              $1: rad20-addr-rad-serv
              $2: rad20-id
              $3: rad20-typ

        This message is generated when an ACCESS ACCEPT packet is received
        with an attribute with invalid length from the RADIUS Server (CONSOLE)."
    ::= { radNotificationsPrefix 20 }

radNotification21 NOTIFICATION-TYPE
    OBJECTS { 
              rad21-addr-rad-serv, 
              rad21-id,
              rad21-typ 
            }
    STATUS current
    DESCRIPTION
        "Notification of Event RAD.21

        Message: 'receive an ACCESS ACCEPT packet from RADIUS server $1, identifier $2, with attribute type $3 with invalid content, for service CONSOLE'

        Parameters list:
              $1: rad21-addr-rad-serv
              $2: rad21-id
              $3: rad21-typ

        This message is generated when an ACCESS ACCEPT packet is received
        with an attribute with an invalid content from the RADIUS Server
        (CONSOLE)."
    ::= { radNotificationsPrefix 21 }

radNotification22 NOTIFICATION-TYPE
    OBJECTS { 
              rad22-addr-rad-serv, 
              rad22-id,
              rad22-typ 
            }
    STATUS current
    DESCRIPTION
        "Notification of Event RAD.22

        Message: 'receive an ACCESS ACCEPT packet from RADIUS server $1, identifier $2, with extra attribute type $3, for service CONSOLE'

        Parameters list:
              $1: rad22-addr-rad-serv
              $2: rad22-id
              $3: rad22-typ

        This message is generated when an ACCESS ACCEPT packet is received
        with a excessive number of attributes with the same type
        from the RADIUS Server (CONSOLE)."
    ::= { radNotificationsPrefix 22 }

radNotification23 NOTIFICATION-TYPE
    OBJECTS { 
              rad23-addr-rad-serv, 
              rad23-id,
              rad23-typ 
            }
    STATUS current
    DESCRIPTION
        "Notification of Event RAD.23

        Message: 'receive an ACCESS ACCEPT packet from RADIUS server $1, identifier $2, with invalid attribute type $3, for service CONSOLE'

        Parameters list:
              $1: rad23-addr-rad-serv
              $2: rad23-id
              $3: rad23-typ

        This message is generated when an ACCESS ACCEPT packet is received
        with an invalid attribute for the offered service from the RADIUS
        Server (CONSOLE)."
    ::= { radNotificationsPrefix 23 }

radNotification24 NOTIFICATION-TYPE
    OBJECTS { 
              rad24-addr-rad-serv, 
              rad24-id 
            }
    STATUS current
    DESCRIPTION
        "Notification of Event RAD.24

        Message: 'receive an ACCESS RESPONSE packet from RADIUS server $1, identifier $2, with invalid length, for service CONSOLE'

        Parameters list:
              $1: rad24-addr-rad-serv
              $2: rad24-id

        This message is generated when a RADIUS server response is received
        with an invalid length (CONSOLE)."
    ::= { radNotificationsPrefix 24 }

radNotification25 NOTIFICATION-TYPE
    OBJECTS { 
              rad25-addr-rad-serv, 
              rad25-id,
              rad25-servc,
              rad25-lcl-addr,
              rad25-lcl-prt,
              rad25-rmt-addr,
              rad25-rmt-prt 
            }
    STATUS current
    DESCRIPTION
        "Notification of Event RAD.25

        Message: 'send an ACCESS REQUEST packet to RADIUS server $1, identifier $2, for service $3, local address $4, local port $5, remote address $6, remote port $7'

        Parameters list:
              $1: rad25-addr-rad-serv
              $2: rad25-id
              $3: rad25-servc
              $4: rad25-lcl-addr
              $5: rad25-lcl-prt
              $6: rad25-rmt-addr
              $7: rad25-rmt-prt

        This message is generated when an ACCESS REQUEST packet is sent to the
        RADIUS server, if a new TELNET or FTP authentication arrives."
    ::= { radNotificationsPrefix 25 }

radNotification26 NOTIFICATION-TYPE
    OBJECTS { 
              rad26-addr-rad-serv, 
              rad26-id,
              rad26-servc,
              rad26-lcl-addr,
              rad26-lcl-prt,
              rad26-rmt-addr,
              rad26-rmt-prt 
            }
    STATUS current
    DESCRIPTION
        "Notification of Event RAD.26

        Message: 'receive an ACCESS ACCEPT packet from RADIUS server $1, identifier $2, for service $3, local address $4, local port $5, remote address $6, remote port $7'

        Parameters list:
              $1: rad26-addr-rad-serv
              $2: rad26-id
              $3: rad26-servc
              $4: rad26-lcl-addr
              $5: rad26-lcl-prt
              $6: rad26-rmt-addr
              $7: rad26-rmt-prt

        This message is generated when an ACCESS ACCEPT packet is received,
        which is sent by the RADIUS server if the RADIUS request is
        authenticated (TELNET or FTP)."
    ::= { radNotificationsPrefix 26 }

radNotification27 NOTIFICATION-TYPE
    OBJECTS { 
              rad27-addr-rad-serv, 
              rad27-id,
              rad27-servc,
              rad27-lcl-addr,
              rad27-lcl-prt,
              rad27-rmt-addr,
              rad27-rmt-prt 
            }
    STATUS current
    DESCRIPTION
        "Notification of Event RAD.27

        Message: 'receive an ACCESS REJECT packet from RADIUS server $1, identifier $2, for service $3, local address $4, local port $5, remote address $6, remote port $7'

        Parameters list:
              $1: rad27-addr-rad-serv
              $2: rad27-id
              $3: rad27-servc
              $4: rad27-lcl-addr
              $5: rad27-lcl-prt
              $6: rad27-rmt-addr
              $7: rad27-rmt-prt

        This message is generated when an ACCESS REJECT packet is received,
        which is sent by the RADIUS server if the RADIUS request is rejected
        (TELNET or FTP)."
    ::= { radNotificationsPrefix 27 }

radNotification28 NOTIFICATION-TYPE
    OBJECTS { 
              rad28-addr-rad-serv, 
              rad28-id,
              rad28-servc,
              rad28-lcl-addr,
              rad28-lcl-prt,
              rad28-rmt-addr,
              rad28-rmt-prt 
            }
    STATUS current
    DESCRIPTION
        "Notification of Event RAD.28

        Message: 'receive an ACCESS CHALLENGE packet from RADIUS server $1, identifier $2, for service $3, local address $4, local port $5, remote address $6, remote port $7'

        Parameters list:
              $1: rad28-addr-rad-serv
              $2: rad28-id
              $3: rad28-servc
              $4: rad28-lcl-addr
              $5: rad28-lcl-prt
              $6: rad28-rmt-addr
              $7: rad28-rmt-prt

        This message is generated when an ACCESS CHALLENGE packet is received,
        which is sent by the RADIUS server to ask for a new ACCESS REQUEST
        packet (TELNET or FTP)."
    ::= { radNotificationsPrefix 28 }

radNotification29 NOTIFICATION-TYPE
    OBJECTS { 
              rad29-addr-rad-serv, 
              rad29-id,
              rad29-servc,
              rad29-lcl-addr,
              rad29-lcl-prt,
              rad29-rmt-addr,
              rad29-rmt-prt 
            }
    STATUS current
    DESCRIPTION
        "Notification of Event RAD.29

        Message: 'retransmit ACCESS REQUEST packet to RADIUS server $1, identifier $2, for service $3, local address $4, local port $5, remote address $6, remote port $7'

        Parameters list:
              $1: rad29-addr-rad-serv
              $2: rad29-id
              $3: rad29-servc
              $4: rad29-lcl-addr
              $5: rad29-lcl-prt
              $6: rad29-rmt-addr
              $7: rad29-rmt-prt

        This message is generated when an ACCESS REQUEST packet is retransmitted
        by the client if the RADIUS server response is not received
        in the expected time (TELNET or FTP)."
    ::= { radNotificationsPrefix 29 }

radNotification30 NOTIFICATION-TYPE
    OBJECTS { 
              rad30-servc, 
              rad30-lcl-addr,
              rad30-lcl-prt,
              rad30-rmt-addr,
              rad30-rmt-prt 
            }
    STATUS current
    DESCRIPTION
        "Notification of Event RAD.30

        Message: 'fail authentication due to no communication with RADIUS servers, for service $1, local address $2, local port $3, remote address $4, remote port $5'

        Parameters list:
              $1: rad30-servc
              $2: rad30-lcl-addr
              $3: rad30-lcl-prt
              $4: rad30-rmt-addr
              $5: rad30-rmt-prt

        This message is generated when an authentication request is rejected
        if a RADIUS server response is not received or nets to RADIUS servers
        are down and the number of possible attempts is over (TELNET or FTP)."
    ::= { radNotificationsPrefix 30 }

radNotification31 NOTIFICATION-TYPE
    OBJECTS { 
              rad31-addr-rad-serv, 
              rad31-servc,
              rad31-lcl-addr,
              rad31-lcl-prt,
              rad31-rmt-addr,
              rad31-rmt-prt 
            }
    STATUS current
    DESCRIPTION
        "Notification of Event RAD.31

        Message: 'net to servidor RADIUS $1 is not UP, for service $2, local address $3, local port $4, remote address $5, remote port $6'

        Parameters list:
              $1: rad31-addr-rad-serv
              $2: rad31-servc
              $3: rad31-lcl-addr
              $4: rad31-lcl-prt
              $5: rad31-rmt-addr
              $6: rad31-rmt-prt

        This message is generated when it is tried to send a packet to
        a RADIUS server and outgoing net is not UP (TELNET or FTP)."
    ::= { radNotificationsPrefix 31 }

radNotification32 NOTIFICATION-TYPE
    OBJECTS { 
              rad32-addr-rad-serv, 
              rad32-id,
              rad32-typ,
              rad32-servc,
              rad32-lcl-addr,
              rad32-lcl-prt,
              rad32-rmt-addr,
              rad32-rmt-prt 
            }
    STATUS current
    DESCRIPTION
        "Notification of Event RAD.32

        Message: 'receive an ACCESS ACCEPT packet from RADIUS server $1, identifier $2, with attribute type $3 with invalid length, for service $4, local address $5, local port $6, remote address $7, remote port $8'

        Parameters list:
              $1: rad32-addr-rad-serv
              $2: rad32-id
              $3: rad32-typ
              $4: rad32-servc
              $5: rad32-lcl-addr
              $6: rad32-lcl-prt
              $7: rad32-rmt-addr
              $8: rad32-rmt-prt

        This message is generated when an ACCESS ACCEPT packet is received
        with an attribute with invalid length from the RADIUS Server
        (TELNET or FTP)."
    ::= { radNotificationsPrefix 32 }

radNotification33 NOTIFICATION-TYPE
    OBJECTS { 
              rad33-addr-rad-serv, 
              rad33-id,
              rad33-typ,
              rad33-servc,
              rad33-lcl-addr,
              rad33-lcl-prt,
              rad33-rmt-addr,
              rad33-rmt-prt 
            }
    STATUS current
    DESCRIPTION
        "Notification of Event RAD.33

        Message: 'receive an ACCESS ACCEPT packet from RADIUS server $1, identifier $2, with attribute type $3 with invalid content, for service $4, local address $5, local port $6, remote address $7, remote port $8'

        Parameters list:
              $1: rad33-addr-rad-serv
              $2: rad33-id
              $3: rad33-typ
              $4: rad33-servc
              $5: rad33-lcl-addr
              $6: rad33-lcl-prt
              $7: rad33-rmt-addr
              $8: rad33-rmt-prt

        This message is generated when an ACCESS ACCEPT packet is received
        with an attribute with an invalid content from the RADIUS Server
        (TELNET or FTP)."
    ::= { radNotificationsPrefix 33 }

radNotification34 NOTIFICATION-TYPE
    OBJECTS { 
              rad34-addr-rad-serv, 
              rad34-id,
              rad34-typ,
              rad34-servc,
              rad34-lcl-addr,
              rad34-lcl-prt,
              rad34-rmt-addr,
              rad34-rmt-prt 
            }
    STATUS current
    DESCRIPTION
        "Notification of Event RAD.34

        Message: 'receive an ACCESS ACCEPT packet from RADIUS server $1, identifier $2, with extra attribute type $3, for service $4, local address $5, local port $6, remote address $7, remote port $8'

        Parameters list:
              $1: rad34-addr-rad-serv
              $2: rad34-id
              $3: rad34-typ
              $4: rad34-servc
              $5: rad34-lcl-addr
              $6: rad34-lcl-prt
              $7: rad34-rmt-addr
              $8: rad34-rmt-prt

        This message is generated when an ACCESS ACCEPT packet is received
        with an excessive number of attributes with the same type from
        the RADIUS Server (TELNET or FTP)."
    ::= { radNotificationsPrefix 34 }

radNotification35 NOTIFICATION-TYPE
    OBJECTS { 
              rad35-addr-rad-serv, 
              rad35-id,
              rad35-typ,
              rad35-servc,
              rad35-lcl-addr,
              rad35-lcl-prt,
              rad35-rmt-addr,
              rad35-rmt-prt 
            }
    STATUS current
    DESCRIPTION
        "Notification of Event RAD.35

        Message: 'receive an ACCESS ACCEPT packet from RADIUS server $1, identifier $2, with invalid attribute type $3, for service $4, local address $5, local port $6, remote address $7, remote port $8'

        Parameters list:
              $1: rad35-addr-rad-serv
              $2: rad35-id
              $3: rad35-typ
              $4: rad35-servc
              $5: rad35-lcl-addr
              $6: rad35-lcl-prt
              $7: rad35-rmt-addr
              $8: rad35-rmt-prt

        This message is generated when an ACCESS ACCEPT packet is received
        with an invalid attribute for the offered service from the RADIUS
        Server (TELNET or FTP)."
    ::= { radNotificationsPrefix 35 }

radNotification36 NOTIFICATION-TYPE
    OBJECTS { 
              rad36-addr-rad-serv, 
              rad36-id,
              rad36-servc,
              rad36-lcl-addr,
              rad36-lcl-prt,
              rad36-rmt-addr,
              rad36-rmt-prt 
            }
    STATUS current
    DESCRIPTION
        "Notification of Event RAD.36

        Message: 'receive an ACCESS RESPONSE packet from RADIUS server $1, identifier $2, with invalid length, for service $3, local address $4, local port $5, remote address $6, remote port $7'

        Parameters list:
              $1: rad36-addr-rad-serv
              $2: rad36-id
              $3: rad36-servc
              $4: rad36-lcl-addr
              $5: rad36-lcl-prt
              $6: rad36-rmt-addr
              $7: rad36-rmt-prt

        This message is generated when a RADIUS server response is received
        with an invalid length (TELNET or FTP)."
    ::= { radNotificationsPrefix 36 }

radNotification37 NOTIFICATION-TYPE
    OBJECTS { 
              rad37-addr-rad-serv, 
              rad37-id 
            }
    STATUS current
    DESCRIPTION
        "Notification of Event RAD.37

        Message: 'discard packet from RADIUS server $1, identifier $2'

        Parameters list:
              $1: rad37-addr-rad-serv
              $2: rad37-id

        This message is generated when a RADIUS server response is received and
        there is not any pending request corresponding to that packet or rhe
        packet contains errors."
    ::= { radNotificationsPrefix 37 }

radNotification38 NOTIFICATION-TYPE
    OBJECTS { 
              rad38-addr-rad-serv, 
              rad38-id,
              rad38-src-prt,
              rad38-dst-prt 
            }
    STATUS current
    DESCRIPTION
        "Notification of Event RAD.38

        Message: 'receive an ACCESS RESPONSE packet from unknown RADIUS server $1, identifier $2, source port $3, destination port $4'

        Parameters list:
              $1: rad38-addr-rad-serv
              $2: rad38-id
              $3: rad38-src-prt
              $4: rad38-dst-prt

        This message is generated when a response is received from an unknown
        RADIUS server."
    ::= { radNotificationsPrefix 38 }

radNotification39 NOTIFICATION-TYPE
    OBJECTS { 
              rad39-addr-rad-serv, 
              rad39-id,
              rad39-typ 
            }
    STATUS current
    DESCRIPTION
        "Notification of Event RAD.39

        Message: 'received a RADIUS packet from RADIUS server $1, identifier $2, with unknown type $3'

        Parameters list:
              $1: rad39-addr-rad-serv
              $2: rad39-id
              $3: rad39-typ

        This message is generated when a RADIUS packet is received
        with an unknown type."
    ::= { radNotificationsPrefix 39 }

radNotification40 NOTIFICATION-TYPE
    OBJECTS { 
              rad40-addr-rad-serv, 
              rad40-id 
            }
    STATUS current
    DESCRIPTION
        "Notification of Event RAD.40

        Message: 'receive an ACCESS RESPONSE packet from RADIUS server $1, identifier $2, with invalid length'

        Parameters list:
              $1: rad40-addr-rad-serv
              $2: rad40-id

        This message is generated when a RADIUS server response is received
        with an invalid length."
    ::= { radNotificationsPrefix 40 }

radNotification41 NOTIFICATION-TYPE
    OBJECTS { 
              rad41-error-string 
            }
    STATUS current
    DESCRIPTION
        "Notification of Event RAD.41

        Message: '$1'

        Parameters list:
              $1: rad41-error-string

        Generic internal error event."
    ::= { radNotificationsPrefix 41 }

radNotification42 NOTIFICATION-TYPE
    OBJECTS { 
              rad42-name, 
              rad42-length,
              rad42-value 
            }
    STATUS current
    DESCRIPTION
        "Notification of Event RAD.42

        Message: 'send attribute $1, length $2: $3'

        Parameters list:
              $1: rad42-name
              $2: rad42-length
              $3: rad42-value

        Attribute sent in a Radius request."
    ::= { radNotificationsPrefix 42 }

radNotification43 NOTIFICATION-TYPE
    OBJECTS { 
              rad43-name, 
              rad43-length,
              rad43-value 
            }
    STATUS current
    DESCRIPTION
        "Notification of Event RAD.43

        Message: 'receive attribute $1, length $2: $3'

        Parameters list:
              $1: rad43-name
              $2: rad43-length
              $3: rad43-value

        Attribute received in a Radius response."
    ::= { radNotificationsPrefix 43 }

radNotification44 NOTIFICATION-TYPE
    OBJECTS { 
              rad44-packet-type, 
              rad44-length,
              rad44-server-address,
              rad44-server-port,
              rad44-identifier,
              rad44-service 
            }
    STATUS current
    DESCRIPTION
        "Notification of Event RAD.44

        Message: 'send $1 packet length $2, to RADIUS server $3:$4, identifier $5, for service $6'

        Parameters list:
              $1: rad44-packet-type
              $2: rad44-length
              $3: rad44-server-address
              $4: rad44-server-port
              $5: rad44-identifier
              $6: rad44-service

        This message is generated when a packet is sent to a RADIUS server."
    ::= { radNotificationsPrefix 44 }

radNotification45 NOTIFICATION-TYPE
    OBJECTS { 
              rad45-packet-type, 
              rad45-length,
              rad45-server-address,
              rad45-server-port,
              rad45-identifier,
              rad45-service 
            }
    STATUS current
    DESCRIPTION
        "Notification of Event RAD.45

        Message: 'receive $1 packet length $2, from RADIUS server $3:$4, identifier $5, for service $6'

        Parameters list:
              $1: rad45-packet-type
              $2: rad45-length
              $3: rad45-server-address
              $4: rad45-server-port
              $5: rad45-identifier
              $6: rad45-service

        This message is generated when a packet is sent to a RADIUS server."
    ::= { radNotificationsPrefix 45 }

radNotification46 NOTIFICATION-TYPE
    OBJECTS { 
              rad46-packet-type, 
              rad46-length,
              rad46-server-address,
              rad46-server-port,
              rad46-identifier,
              rad46-service 
            }
    STATUS current
    DESCRIPTION
        "Notification of Event RAD.46

        Message: 'retransmit $1 packet length $2, to RADIUS server $3:$4, identifier $5, for service $6'

        Parameters list:
              $1: rad46-packet-type
              $2: rad46-length
              $3: rad46-server-address
              $4: rad46-server-port
              $5: rad46-identifier
              $6: rad46-service

        This message is generated when a packet is retransmitted to a RADIUS server."
    ::= { radNotificationsPrefix 46 }

radNotification47 NOTIFICATION-TYPE
    OBJECTS { 
              rad47-info-string 
            }
    STATUS current
    DESCRIPTION
        "Notification of Event RAD.47

        Message: '$1'

        Parameters list:
              $1: rad47-info-string

        Generic comment on usual information message."
    ::= { radNotificationsPrefix 47 }

radNotification48 NOTIFICATION-TYPE
    OBJECTS { 
              rad48-service 
            }
    STATUS current
    DESCRIPTION
        "Notification of Event RAD.48

        Message: 'fail authentication due to no communication with RADIUS servers, for service $1'

        Parameters list:
              $1: rad48-service

        This message is generated when an authentication request is rejected
        if a RADIUS server response is not received or nets to RADIUS servers
        are down and the number of possible attempts is over."
    ::= { radNotificationsPrefix 48 }

radNotification49 NOTIFICATION-TYPE
    OBJECTS { 
              rad49-addr-rad-serv, 
              rad49-service 
            }
    STATUS current
    DESCRIPTION
        "Notification of Event RAD.49

        Message: 'net to servidor RADIUS $1 is not UP, for service $2'

        Parameters list:
              $1: rad49-addr-rad-serv
              $2: rad49-service

        This message is generated when it is tried to send a packet to a
        RADIUS server and outgoing net is not UP."
    ::= { radNotificationsPrefix 49 }

radNotification50 NOTIFICATION-TYPE
    OBJECTS { 
              rad50-addr-rad-serv, 
              rad50-id,
              rad50-service 
            }
    STATUS current
    DESCRIPTION
        "Notification of Event RAD.50

        Message: 'send an ACCESS REQUEST packet to RADIUS server $1, identifier $2, for service $3'

        Parameters list:
              $1: rad50-addr-rad-serv
              $2: rad50-id
              $3: rad50-service

        This message is generated when an ACCESS REQUEST packet is sent to
        RADIUS server, if a new authentication arrives."
    ::= { radNotificationsPrefix 50 }

radNotification51 NOTIFICATION-TYPE
    OBJECTS { 
              rad51-addr-rad-serv, 
              rad51-id,
              rad51-service 
            }
    STATUS current
    DESCRIPTION
        "Notification of Event RAD.51

        Message: 'retransmit ACCESS REQUEST packet to RADIUS server $1, identifier $2, for service $3'

        Parameters list:
              $1: rad51-addr-rad-serv
              $2: rad51-id
              $3: rad51-service

        This message is generated when an ACCESS REQUEST packet is retransmitted
        by the client if the RADIUS server response is not received
        in the expected time."
    ::= { radNotificationsPrefix 51 }

radNotification52 NOTIFICATION-TYPE
    OBJECTS { 
              rad52-addr-rad-serv, 
              rad52-id,
              rad52-service 
            }
    STATUS current
    DESCRIPTION
        "Notification of Event RAD.52

        Message: 'receive an ACCESS ACCEPT packet from RADIUS server $1, identifier $2, for service $3'

        Parameters list:
              $1: rad52-addr-rad-serv
              $2: rad52-id
              $3: rad52-service

        This message is generated when an ACCESS ACCEPT packet is received,
        which is sent by the RADIUS server if the RADIUS request is
        authenticated."
    ::= { radNotificationsPrefix 52 }

radNotification53 NOTIFICATION-TYPE
    OBJECTS { 
              rad53-addr-rad-serv, 
              rad53-id,
              rad53-service 
            }
    STATUS current
    DESCRIPTION
        "Notification of Event RAD.53

        Message: 'receive an ACCESS REJECT packet from RADIUS server $1, identifier $2, for service $3'

        Parameters list:
              $1: rad53-addr-rad-serv
              $2: rad53-id
              $3: rad53-service

        This message is generated when an ACCESS REJECT packet is received,
        which is sent by the RADIUS server if the RADIUS request is rejected."
    ::= { radNotificationsPrefix 53 }

radNotification54 NOTIFICATION-TYPE
    OBJECTS { 
              rad54-addr-rad-serv, 
              rad54-id,
              rad54-service 
            }
    STATUS current
    DESCRIPTION
        "Notification of Event RAD.54

        Message: 'receive an ACCESS CHALLENGE packet from RADIUS server $1, identifier $2, for service $3'

        Parameters list:
              $1: rad54-addr-rad-serv
              $2: rad54-id
              $3: rad54-service

        This message is generated when an ACCESS CHALLENGE packet is received,
        which is sent by the RADIUS server to ask for a new ACCESS REQUEST
        packet."
    ::= { radNotificationsPrefix 54 }

radNotification55 NOTIFICATION-TYPE
    OBJECTS { 
              rad55-addr-rad-serv, 
              rad55-id,
              rad55-typ,
              rad55-service 
            }
    STATUS current
    DESCRIPTION
        "Notification of Event RAD.55

        Message: 'receive an ACCESS ACCEPT packet from RADIUS server $1, identifier $2, with attribute type $3 with invalid length, for service $4'

        Parameters list:
              $1: rad55-addr-rad-serv
              $2: rad55-id
              $3: rad55-typ
              $4: rad55-service

        This message is generated when an ACCESS ACCEPT packet is received
        with an attribute with invalid length from the RADIUS Server."
    ::= { radNotificationsPrefix 55 }

radNotification56 NOTIFICATION-TYPE
    OBJECTS { 
              rad56-addr-rad-serv, 
              rad56-id,
              rad56-typ,
              rad56-service 
            }
    STATUS current
    DESCRIPTION
        "Notification of Event RAD.56

        Message: 'receive an ACCESS ACCEPT packet from RADIUS server $1, identifier $2, with attribute type $3 with invalid content, for service $4'

        Parameters list:
              $1: rad56-addr-rad-serv
              $2: rad56-id
              $3: rad56-typ
              $4: rad56-service

        This message is generated when an ACCESS ACCEPT packet is received
        with an attribute with an invalid content from the RADIUS Server."
    ::= { radNotificationsPrefix 56 }

radNotification57 NOTIFICATION-TYPE
    OBJECTS { 
              rad57-addr-rad-serv, 
              rad57-id,
              rad57-typ,
              rad57-service 
            }
    STATUS current
    DESCRIPTION
        "Notification of Event RAD.57

        Message: 'receive an ACCESS ACCEPT packet from RADIUS server $1, identifier $2, with extra attribute type $3, for service $4'

        Parameters list:
              $1: rad57-addr-rad-serv
              $2: rad57-id
              $3: rad57-typ
              $4: rad57-service

        This message is generated when an ACCESS ACCEPT packet is received
        with a excessive number of attributes with the same type
        from the RADIUS Server."
    ::= { radNotificationsPrefix 57 }

radNotification58 NOTIFICATION-TYPE
    OBJECTS { 
              rad58-addr-rad-serv, 
              rad58-id,
              rad58-typ,
              rad58-service 
            }
    STATUS current
    DESCRIPTION
        "Notification of Event RAD.58

        Message: 'receive an ACCESS ACCEPT packet from RADIUS server $1, identifier $2, with invalid attribute type $3, for service $4'

        Parameters list:
              $1: rad58-addr-rad-serv
              $2: rad58-id
              $3: rad58-typ
              $4: rad58-service

        This message is generated when an ACCESS ACCEPT packet is received
        with an invalid attribute for the offered service from the RADIUS
        Server."
    ::= { radNotificationsPrefix 58 }

radNotification59 NOTIFICATION-TYPE
    OBJECTS { 
              rad59-addr-rad-serv, 
              rad59-id,
              rad59-service 
            }
    STATUS current
    DESCRIPTION
        "Notification of Event RAD.59

        Message: 'receive an ACCESS RESPONSE packet from RADIUS server $1, identifier $2, with invalid length, for service $3'

        Parameters list:
              $1: rad59-addr-rad-serv
              $2: rad59-id
              $3: rad59-service

        This message is generated when a RADIUS server response is received
        with an invalid length."
    ::= { radNotificationsPrefix 59 }


END
