--
--
-- NOTE:
--
--
-- This is the DS24  NPI MIB.
--
--
--
-- February 9, 1998
--
--
--
-- ==================================================================
--
-- 

-- ----------------------------------------------------------------
-- Copyright (c) 1996, 1997 Network Peripherals Inc.
-- All rights reserved.

-- This SNMP Management Information Specification embodies
-- Network Peripherals Inc.'s (NPI) confidential and
-- proprietary intellectual property.  NPI retains all title
-- and ownership in the Specification, including any revisions.

-- This Specification is supplied "AS IS", and NPI
-- makes no warranty, either expressed or implied,
-- as to the use, operation, condition, or performance of the
-- Specification.

-- -----------------
-- Revised History :
-- -----------------
-- ==================================================================


Npi-NuSwitch-COMMON-MIB DEFINITIONS ::= BEGIN

IMPORTS
     mgmt, NetworkAddress, IpAddress, Counter, Gauge,
     TimeTicks                                          FROM RFC1155-SMI
     DisplayString                                      FROM RFC1213-MIB
     TRAP-TYPE                                          FROM RFC-1215
     OBJECT-TYPE, internet                                        FROM RFC-1212;


mgmt            OBJECT IDENTIFIER ::= { iso org(3) dod(6) internet(1) mgmt(2) }
directory       OBJECT IDENTIFIER ::= { internet 1 }
experimental    OBJECT IDENTIFIER ::= { internet 3 }
private         OBJECT IDENTIFIER ::= { internet 4 }
enterprises     OBJECT IDENTIFIER ::= { private 1 }


MacAddress ::= OCTET STRING (SIZE (6))    -- a 6 octet address in


-- (1.3.6.1.4.1.1101)
npi      OBJECT IDENTIFIER ::= { enterprises 1101 }

-- (1.3.6.1.4.1.1101.2)
npi-Switching-MIB  OBJECT IDENTIFIER ::= { npi 2 }

-- (1.3.6.1.4.1.1101.2.13)
switch-DS24 OBJECT IDENTIFIER ::= { npi-Switching-MIB 13 }

-- =======================================================================


-- 1 =======================================================================
-- (1.3.6.1.4.1.1101.2.13.1)
-- basic hub information, mandatory

   switchBasicHubInfo OBJECT IDENTIFIER ::= { switch-DS24 1 }

   switchHubMibVersion  OBJECT-TYPE
       SYNTAX  INTEGER
       ACCESS  read-only
       STATUS  mandatory
       DESCRIPTION
               " MIB version, 1 1   1   10000 -> 0.00.60 "
       ::= { switchBasicHubInfo 1 }

   switchHubHwAgingSwitch  OBJECT-TYPE
       SYNTAX  INTEGER
               {   enable (1),
                   disable (2)
               }
       ACCESS  read-write
       STATUS  mandatory
       DESCRIPTION
               "Enable the HW aging or not. If enabled the default Aging
				 will be 300 secs "
       ::= { switchBasicHubInfo 2 }


   switchHubLed  OBJECT-TYPE
       SYNTAX  OCTET STRING
       ACCESS  read-only
       STATUS  mandatory
       DESCRIPTION
               " The object indicates Hub's LED current status."
       ::= { switchBasicHubInfo 4 }

--
-- [DS24]
-- struct {
--     u-char pwr;              1:Ok, 0:Fail
--     u-char rdn-pwr;          1:Ok, 0:Fail
--     u-char console;          1:Ok, 0:Off
--     struct {
--              u-char speed100;        1: on, 0: off
--              u-char link;        	1: on, 0: off
--              u-char full-duplex;     1: full-duplex , 0: half-duplex
--     } port [24];
-- }
--

   switchAddrSpanningTreefunction  OBJECT-TYPE
       SYNTAX  INTEGER
               {   support (1),
                   noSupport (2)
               }
       ACCESS  read-only
       STATUS  mandatory
       DESCRIPTION
               " The object indicates that the spanning tree function
                 supports or not."
       ::= { switchBasicHubInfo 5 }

   switchAddrSecurityfunction  OBJECT-TYPE
       SYNTAX  INTEGER
               {   support (1),
                   noSupport (2)
               }
       ACCESS  read-only
       STATUS  mandatory
       DESCRIPTION
               " The object indicates the security function supports or not."
       ::= { switchBasicHubInfo 6 }

   basicSwitchPortMonitoringfunction  OBJECT-TYPE
       SYNTAX  INTEGER
               {   support (1),
                   noSupport (2)
               }
       ACCESS  read-only
       STATUS  mandatory
       DESCRIPTION
               " The object indicates the port monitor function supports or not."
       ::= { switchBasicHubInfo 7 }

   basicSwitchVirtualLANfunction  OBJECT-TYPE
       SYNTAX  INTEGER
               {   support (1),
                   noSupport (2)
               }
       ACCESS  read-only
       STATUS  mandatory
       DESCRIPTION
               " The object indicates the Virtual LAN function supports or not."
       ::= { switchBasicHubInfo 8 }


   basicSwitchHubClearStats  OBJECT-TYPE
       SYNTAX  INTEGER
               {   noClear(1),
                   clear(2)
               }
       ACCESS  read-write
       STATUS  mandatory
       DESCRIPTION
               " Clear switching hub's counters:
                 1. Bridge MIB (1.3.6.1.2.1.17.)
                    dot1dStpTopChange (.2.4.0)

                 2. Repeater MIB (1.3.6.1.2.1.22.)

                    !!! Only clear switching hub (unit=1) !!!

                    rptrMonitorGroupTotalFrames (.2.2.1.2)
                    rptrMonitorGroupTotalOctets (.2.2.1.3)
                    rptrMonitorGroupTotalErrors (.2.2.1.4)

                 3. Switch common MIB (1.3.6.1.4.1.1101.2.1.)
                    switchmonUnitCollision (.11.1)
               "
       ::= { switchBasicHubInfo 11 }


   basicSwitchRMONMIBfunction  OBJECT-TYPE
       SYNTAX  INTEGER
               {   support (1),
                   noSupport (2)
               }
       ACCESS  read-only
       STATUS  mandatory
       DESCRIPTION
               " The object indicates the RMON MIB function supports or not."
       ::= { switchBasicHubInfo 12 }




-- 2 =======================================================================
--
-- (1.3.6.1.4.1.1101.2.13.2)
-- basic port information, mandatory

   switchBasicPortInfo OBJECT IDENTIFIER ::= { switch-DS24 2 }

   switchPortTable  OBJECT-TYPE
       SYNTAX  SEQUENCE OF SwitchPortEntry
       ACCESS  not-accessible
       STATUS  mandatory
       DESCRIPTION
               " Basic information for each port."
       ::= { switchBasicPortInfo  1 }

   switchPortEntry  OBJECT-TYPE
       SYNTAX  SwitchPortEntry
       ACCESS  not-accessible
       STATUS  mandatory
       DESCRIPTION
               " Port information entry."
       INDEX   { switchPortIndex }
       ::= { switchPortTable  1 }

   SwitchPortEntry ::=
       SEQUENCE {
           switchPortIndex
               INTEGER,
           switchPortType
               INTEGER,
           switchPortLink
               INTEGER,
           switchPortEnable
               INTEGER,
           switchPortFullDuplex
               INTEGER,
           switchPortFlowControl
               INTEGER,
           switchPortVirtualLanModeStatus
               INTEGER,
           switchPortSpeed
               INTEGER,
           switchPortAutoNegotiationFunction
               INTEGER,
           switchPortAutoNegotiation
               INTEGER
       }

   switchPortIndex  OBJECT-TYPE
       SYNTAX  INTEGER
       ACCESS  read-only
       STATUS  mandatory
       DESCRIPTION
               " port number :
                 DS24    : ( 1 .. 24)
                 FE-1200 : ( 1 .. 12)
                 FE210 : ( 1 .. 12)
                 FE224: ( 1 .. 6)
               "
       ::= { switchPortEntry 1 }

   switchPortType  OBJECT-TYPE
       SYNTAX  INTEGER
               {   other(1),
                   tenBaseT(2),
                   tenBase2(3),
                   tenBase5(4),
                   tenBaseF(5),
                   hundredBaseTX(11),
-- MDA Present 
                   hundredBaseFX(12)
               }
       ACCESS  read-only
       STATUS  mandatory
       DESCRIPTION
               " The type of each port."
       ::= { switchPortEntry 3 }

   switchPortLink  OBJECT-TYPE
       SYNTAX  INTEGER
               {   up(1),
                   down(2)
               }
       ACCESS  read-only
       STATUS  mandatory
       DESCRIPTION
               " This object indicates the link status of each port is
                 up or down."
       ::= { switchPortEntry 4 }

   switchPortEnable  OBJECT-TYPE
       SYNTAX  INTEGER
               {   enable (1),
                   disable (2)
               }
       ACCESS  read-write
       STATUS  mandatory
       DESCRIPTION
               " Enable/disable status of the port,
                 default = enable(1).
               "
       ::= { switchPortEntry 5 }

   switchPortFullDuplex  OBJECT-TYPE
       SYNTAX  INTEGER
               {   enable (1),
                   disable (2)
               }
       ACCESS  read-write
       STATUS  mandatory
       DESCRIPTION
               " Full/half duplex,  default = disable(2),
                 Conditional Write: this object can be written only when
                 switchPortAutoNegotiation is disable and port is enabled.
               "
       ::= { switchPortEntry 6 }


   switchPortVirtualLanModeStatus  OBJECT-TYPE
       SYNTAX  INTEGER
               {   on (1),
                   off (2)
               }
       ACCESS  read-only
       STATUS  mandatory
       DESCRIPTION
               " The object indicates whether the port is in Virtual LAN mode."
       ::= { switchPortEntry 8 }

   switchPortSpeed  OBJECT-TYPE
       SYNTAX  INTEGER
               {   tenMb    (2),
                   hundredMb   (3)
               }
       ACCESS  read-write
       STATUS  mandatory
       DESCRIPTION
               "Port data rate, this object can be writen only when
                switchPortAutoNegotiation is set disable .
               "
       ::= { switchPortEntry 9 }

   switchPortAutoNegotiationFunction  OBJECT-TYPE
       SYNTAX  INTEGER
               {   support (1),
                   noSupport (2)
               }
       ACCESS  read-only
       STATUS  mandatory
       DESCRIPTION
               " The object indicates that the auto-negotiation function of
                 the port supports or not,
                 default = support(1).
               "
       ::= { switchPortEntry 10 }

   switchPortAutoNegotiation  OBJECT-TYPE
       SYNTAX  INTEGER
               {   enable (1),
                   disable (2)
               }
       ACCESS  read-write
       STATUS  mandatory
       DESCRIPTION
               " Enable/disable the function of the port auto-negotiation,
                 default = enable (1).
               "
       ::= { switchPortEntry 11 }



-- 7 ======================================================
-- (1.3.6.1.4.1.1101.2.13.7)
-- Port Monitor information, optional

   switchPortMonitorInfo  OBJECT IDENTIFIER ::= { switch-DS24 7 }

   switchPortMonitorswitch  OBJECT-TYPE
       SYNTAX  INTEGER
               {   on(1),
                   off(2)
               }
       ACCESS  read-write
       STATUS  mandatory
       DESCRIPTION
               " A state to present whether the port monitor function is
                 ON or OF in the hub.
                 The default is OFF.
               "
       ::= { switchPortMonitorInfo 1 }

   switchPortMonitorMaxCount  OBJECT-TYPE
       SYNTAX  INTEGER
       ACCESS  read-only
       STATUS  mandatory
       DESCRIPTION
               " Max. monitor count in this hub
				 DS24    = 23
               "
       ::= { switchPortMonitorInfo 2 }

   switchPortMonitorActiveCount  OBJECT-TYPE
       SYNTAX  INTEGER
       ACCESS  read-only
       STATUS  mandatory
       DESCRIPTION
               " Current active monitor count in this hub."
       ::= { switchPortMonitorInfo 3 }


   switchPortMonitoringOperation  OBJECT-TYPE
       SYNTAX  OCTET STRING
       ACCESS  read-write
       STATUS  mandatory
       DESCRIPTION
               " Operation information."
       ::= { switchPortMonitorInfo 4 }

--
-- struct PM-CNTL  {
--    u-char status[PORT-NUM - 1];      1: on,  !=1 off
-- } ;
--

   switchPortMonitorMessageStatus  OBJECT-TYPE
       SYNTAX  INTEGER
               {   ok (1),
                   switch-is-off (2),
                   not-active (3),
                   bad-monitoring-port (4),
                   bad-monitored-port (5)
               }
       ACCESS  read-only
       STATUS  mandatory
       DESCRIPTION
               " The new operation message."
       ::= { switchPortMonitorInfo 5 }


-- 8 ======================================================
-- (1.3.6.1.4.1.1101.2.13.8)
-- virtual LAN information, optional

   switchVirtualLanInfo    OBJECT IDENTIFIER ::= { switch-DS24 8 }

   switchVirtualLanSwitch  OBJECT-TYPE
       SYNTAX  INTEGER
               {   on(1),
                   off(2)
               }
       ACCESS  read-write
       STATUS  mandatory
       DESCRIPTION
               " A state to present whether the virtul LAN function is
                 ON or OFF in the hub.
                 To OFF the switch must write by the original manager.
                 The default value is OFF.
               "
       ::= { switchVirtualLanInfo 1 }

   switchVirtualLanOperation  OBJECT-TYPE
       SYNTAX  OCTET STRING
       ACCESS  read-write
       STATUS  mandatory
       DESCRIPTION
               " Operation information for Virtual LAN."
       ::= { switchVirtualLanInfo 2 }

--
--    struct {
--       u-char  vlan-id[PORT-NUM]; 
--    } ;
--
--    #define PORT-NUM
--	  DS24 = 24
--


   switchVirtualLanMessage  OBJECT-TYPE
       SYNTAX  INTEGER
               {   ok (1),
                   switch-is-off (2)
               }
       ACCESS  read-only
       STATUS  mandatory
       DESCRIPTION
               " the operation message."
       ::= { switchVirtualLanInfo 5 }


-- (1.3.6.1.4.1.1101.2.13.10)
-- port statistic information, mandatory

   switchStatisticInfo  OBJECT IDENTIFIER ::= { switch-DS24 10 }

   switchStatisticPortTable  OBJECT-TYPE
       SYNTAX  SEQUENCE OF SwitchStatisticPortEntry
       ACCESS  not-accessible
       STATUS  mandatory
       DESCRIPTION
               "A table that contains information about every
               port that is associated with this transparent
               bridge."
       ::= { switchStatisticInfo 1 }

   switchStatisticPortEntry OBJECT-TYPE
       SYNTAX  SwitchStatisticPortEntry
       ACCESS  not-accessible
       STATUS  mandatory
       DESCRIPTION
               "A list of information for each port of a
               transparent bridge."
       INDEX   { switchStatisticPort }
       ::= { switchStatisticPortTable 1 }

   SwitchStatisticPortEntry ::=
       SEQUENCE {
           switchStatisticPort
               INTEGER,
           switchStatisticPortInFrames
               Counter,
           switchStatisticPortOutFrames
               Counter,
           switchStatisticPortInDiscards
               Counter,
           switchStatisticPortInKBytes
               Counter,
           switchStatisticPortOutKBytes
               Counter,
           switchStatisticPortRxFCSError
               Counter,
           switchStatisticPortRxAllignError
               Counter,
           switchStatisticPortRxRUNTError
               Counter,
           switchStatisticPortRxFrameLongError
               Counter,
           switchStatisticPortOutDiscards
               Counter,
           switchStatisticPortNetCollision
               Counter,
           switchStatisticPortHashCollision
               Counter,
           switchStatisticPortLossPacket
               Counter
       }

   switchStatisticPort OBJECT-TYPE
       SYNTAX  INTEGER
       ACCESS  read-only
       STATUS  mandatory
       DESCRIPTION
               " The port number of the port for which this entry
                 contains Transparent bridging management
                 information.
                 FE-1200 : ( 1 .. 12)
                 FE-210  : ( 1 .. 12)
                 FE-224  : ( 1 .. 6)
               "
       ::= { switchStatisticPortEntry 1 }

--
-- counters defined in Bridge MIB (RFC 1493)

   switchStatisticPortInFrames  OBJECT-TYPE
       SYNTAX  Counter
       ACCESS  read-only
       STATUS  mandatory
       DESCRIPTION
               " The number of frames that have been received by
                 this port from its segment. Note that a frame
                 received on the interface corresponding to this
                 port is only counted by this object if and only if
                 it is for a protocol being processed by the local
                 bridging function, including bridge management
                 frames."
       ::= { switchStatisticPortEntry 2 }

   switchStatisticPortOutFrames  OBJECT-TYPE
       SYNTAX  Counter
       ACCESS  read-only
       STATUS  mandatory
       DESCRIPTION
               " The number of frames that have been transmitted
                 by this port to its segment.  Note that a frame
                 transmitted on the interface corresponding to this
                 port is only counted by this object if and only if
                 it is for a protocol being processed by the local
                 bridging function, including bridge management
                 frames."
       ::= { switchStatisticPortEntry 3 }

   switchStatisticPortInDiscards  OBJECT-TYPE
       SYNTAX  Counter
       ACCESS  read-only
       STATUS  mandatory
       DESCRIPTION
               " Count of valid frames received which were
                 discarded (i.e., filtered) by the Forwarding
                 Process."
       ::= { switchStatisticPortEntry 4 }

--
-- counters defined for byte count

   switchStatisticPortInKBytes  OBJECT-TYPE
       SYNTAX  Counter
       ACCESS  read-only
       STATUS  mandatory
       DESCRIPTION
               " The number of k-bytes of switchStatisticPortInFrame"
       ::= { switchStatisticPortEntry 5 }

   switchStatisticPortOutKBytes  OBJECT-TYPE
       SYNTAX  Counter
       ACCESS  read-only
       STATUS  mandatory
       DESCRIPTION
               " The number of k-bytes of switchStatisticPortOutFrame"
       ::= { switchStatisticPortEntry 6 }

--
-- Rx error count

   switchStatisticPortRxFCSError  OBJECT-TYPE
       SYNTAX  Counter
       ACCESS  read-only
       STATUS  mandatory
       DESCRIPTION
               " The number of received FCS error packet count "
       ::= { switchStatisticPortEntry 7 }

   switchStatisticPortRxAllignError  OBJECT-TYPE
       SYNTAX  Counter
       ACCESS  read-only
       STATUS  mandatory
       DESCRIPTION
               " The number of received allignment error packet count "
       ::= { switchStatisticPortEntry 8 }

   switchStatisticPortRxRUNTError  OBJECT-TYPE
       SYNTAX  Counter
       ACCESS  read-only
       STATUS  mandatory
       DESCRIPTION
               " The number of received RUNT error packet count "
       ::= { switchStatisticPortEntry 9 }

   switchStatisticPortRxFrameLongError  OBJECT-TYPE
       SYNTAX  Counter
       ACCESS  read-only
       STATUS  mandatory
       DESCRIPTION
               " The number of received farme too long error packet count "
       ::= { switchStatisticPortEntry 10 }

--
-- Tx discard count

   switchStatisticPortOutDiscards  OBJECT-TYPE
       SYNTAX   Counter
       ACCESS   read-only
       STATUS   mandatory
       DESCRIPTION
               " Count of valid frames received which were
                 discarded (i.e., filtered) by the outgoing Forwarding
                 Process."
       ::= { switchStatisticPortEntry 11 }

--
-- other count

   switchStatisticPortNetCollision  OBJECT-TYPE
       SYNTAX  Counter
       ACCESS  read-only
       STATUS  mandatory
       DESCRIPTION
               " The number of nework collision count "
       ::= { switchStatisticPortEntry 12 }

   switchStatisticPortHashCollision  OBJECT-TYPE
       SYNTAX  Counter
       ACCESS  read-only
       STATUS  mandatory
       DESCRIPTION
               " The number of forward collision count "
       ::= { switchStatisticPortEntry 13 }

   switchStatisticPortLossPacket  OBJECT-TYPE
       SYNTAX  Counter
       ACCESS  read-only
       STATUS  mandatory
       DESCRIPTION
               " The number of loss packets after the input buffer full "
       ::= { switchStatisticPortEntry 14 }



-- 11  ======================================================
-- (1.3.6.1.4.1.1101.2.13.11)
-- switch unit statistic information, mandatory

   switchMonUnitInfo  OBJECT IDENTIFIER ::= { switch-DS24 11 }

   switchmonUnitCollision  OBJECT-TYPE
       SYNTAX  Counter
       ACCESS  read-only
       STATUS  mandatory
       DESCRIPTION
               " 11 1"
       ::= { switchMonUnitInfo 1 }

-- 14  ======================================================
-- (1.3.6.1.4.1.1101.2.13.14)
-- spanning tree information, optional

   switchSpanningTreeInfo  OBJECT IDENTIFIER ::= { switch-DS24 14 }

   switchSpanningTreeSwitch  OBJECT-TYPE
       SYNTAX  INTEGER
               {   on(1),
                   off(2)
               }
       ACCESS  read-write
       STATUS  mandatory
       DESCRIPTION
               " A switch to select whether the spanning tree is ON or OFF.
                 The default is ON.  If the value is changed, the system need
                 to be restarted."
       ::= { switchSpanningTreeInfo 1 }

-- 15  ======================================================
-- (1.3.6.1.4.1.1101.2.13.15)
-- SNMP Host Config

   switchSnmpManagerTable         OBJECT-TYPE
          SYNTAX    SEQUENCE OF SwitchSnmpManagerEntry    
          ACCESS    not-accessible
          STATUS    mandatory
          DESCRIPTION
              " This table contains the information needed
                for SNMP Management. "
          ::= { switch-DS24 15 }

   switchSnmpManagerEntry         OBJECT-TYPE
          SYNTAX    SwitchSnmpManagerEntry
          ACCESS    not-accessible
          STATUS    mandatory
DESCRIPTION ""
          ::=  { switchSnmpManagerTable 1}

   SwitchSnmpManagerEntry  ::=
        SEQUENCE {
			switchSnmpManagerIndex
                  INTEGER,
            switchSnmpManagerHostname
                  DisplayString,
            switchSnmpManagerIpAddr
                  IpAddress,
            switchSnmpManagerComm
                  DisplayString
       }

   switchSnmpManagerIndex     OBJECT-TYPE
          SYNTAX    INTEGER
          ACCESS    read-only
          STATUS    mandatory
DESCRIPTION ""
          ::= { switchSnmpManagerEntry 1}

   switchSnmpManagerHostname          OBJECT-TYPE
          SYNTAX    DisplayString (SIZE(1..16))
          ACCESS    read-write
          STATUS    mandatory
          DESCRIPTION
               " The host name of the management station which
                 has the SNMP access ."
           ::= { switchSnmpManagerEntry 2 }

   switchSnmpManagerIpAddr     OBJECT-TYPE
          SYNTAX    IpAddress
          ACCESS    read-write
          STATUS    mandatory
          DESCRIPTION
               " The Internet address of the management station which
                 has the SNMP access ."
          ::= { switchSnmpManagerEntry 3}

   switchSnmpManagerComm          OBJECT-TYPE
          SYNTAX    DisplayString (SIZE(1..16))
          ACCESS    read-write
          STATUS    mandatory
          DESCRIPTION
              "  Community name used for SNMP management for
                 this station"
           ::= { switchSnmpManagerEntry 4 }

-- 16  ======================================================
-- (1.3.6.1.4.1.1101.2.13.16)
-- Community Configuration

   switchCommManagerTable         OBJECT-TYPE
          SYNTAX    SEQUENCE OF SwitchCommManagerEntry    
          ACCESS    not-accessible
          STATUS    mandatory
          DESCRIPTION
              " This table contains the information needed
                for access permissions for community "
          ::= { switch-DS24 16 }

   switchCommManagerEntry         OBJECT-TYPE
          SYNTAX    SwitchCommManagerEntry
          ACCESS    not-accessible
          STATUS    mandatory
DESCRIPTION ""
          ::=  { switchCommManagerTable 1}

   SwitchCommManagerEntry  ::=
        SEQUENCE {
			switchCommManagerIndex
                  INTEGER,
            switchCommManagerComm
                  DisplayString,
            switchCommManagerGet
                  INTEGER,
            switchCommManagerSet
                  INTEGER,
            switchCommManagerTrap
                  INTEGER
       }

   switchCommManagerIndex     OBJECT-TYPE
          SYNTAX    INTEGER
          ACCESS    read-only
          STATUS    mandatory
DESCRIPTION ""
          ::= { switchCommManagerEntry 1}


   switchCommManagerComm          OBJECT-TYPE
          SYNTAX    DisplayString (SIZE(1..16))
          ACCESS    read-write
          STATUS    mandatory
          DESCRIPTION
              "  Community name used for SNMP management for
                 this station"
           ::= { switchCommManagerEntry 2 }

   switchCommManagerGet  OBJECT-TYPE
       SYNTAX  INTEGER
               {   on (1),
                   off (2)
               }
       ACCESS  read-write
       STATUS  mandatory
       DESCRIPTION
               " The object indicates whether this comminuty has
                 SNMP Get access or not. "
       ::= { switchCommManagerEntry 3 }

   switchCommManagerSet  OBJECT-TYPE
       SYNTAX  INTEGER
               {   on (1),
                   off (2)
               }
       ACCESS  read-write
       STATUS  mandatory
       DESCRIPTION
               " The object indicates whether this comminuty has
                 SNMP Set access or not. "
       ::= { switchCommManagerEntry 4 }

   switchCommManagerTrap  OBJECT-TYPE
       SYNTAX  INTEGER
               {   on (1),
                   off (2)
               }
       ACCESS  read-write
       STATUS  mandatory
       DESCRIPTION
               " The object indicates whether trap is set to this
                 comminuty or not. "
       ::= { switchCommManagerEntry 5 }

END

-- EOF
