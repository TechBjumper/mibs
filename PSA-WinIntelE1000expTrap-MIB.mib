PSA-WinIntelE1000expTrap-MIB DEFINITIONS ::= BEGIN

--PRIMEQUEST system management MIB for Partition
--
--
--$Copyright$
--Copyright Fujitsu Limited 2009
--All rights reserved
--
--
--MIB Revision: 02000001
--

IMPORTS
	OBJECT-TYPE								FROM RFC-1212
	TRAP-TYPE								FROM RFC-1215
	mib-2, DisplayString					FROM RFC1213-MIB
	TimeTicks, Counter, Gauge, IpAddress	FROM RFC1155-SMI
	mgmt, enterprises						FROM RFC1155-SMI;

--enterprises	OBJECT IDENTIFIER ::={ iso org(3) dod(6) internet(1) private(4) 1 }
--
--PRIMEQUEST system management MIB nodes
--fujitsu:                    1.3.6.1.4.1.211
-- products:                  1.3.6.1.4.1.211.1
--  iaServer:                 1.3.6.1.4.1.211.1.31
--   primequest:              1.3.6.1.4.1.211.1.31.1
--    partition:	           1.3.6.1.4.1.211.1.31.1.2
--
--Trap enterprise is "psaWinIntelE1000expTrap"

--FUJITSU PRIMEQUEST system management MIB nodes for Partition
  fujitsu        OBJECT IDENTIFIER  ::={ enterprises 211 }
  products       OBJECT IDENTIFIER  ::={ fujitsu 1 }
  iaServer       OBJECT IDENTIFIER  ::={ products 31 }
  primequest     OBJECT IDENTIFIER  ::={ iaServer 1 }
   partition     OBJECT IDENTIFIER  ::={ primequest 2 }
    parititonVariables	OBJECT IDENTIFIER	::={ partition	200 }
    partitionEnterprise      OBJECT IDENTIFIER  ::={ partition 201 }
     psaComTrap              OBJECT IDENTIFIER  ::={ partitionEnterprise 1 }
     psaWinIntelE100Trap     OBJECT IDENTIFIER  ::={ partitionEnterprise 51 }
     psaWinIntelE1000Trap    OBJECT IDENTIFIER  ::={ partitionEnterprise 52 }
     psaWinBcm5700Trap       OBJECT IDENTIFIER  ::={ partitionEnterprise 53 }
     psaWinEmulexTrap        OBJECT IDENTIFIER  ::={ partitionEnterprise 54 }
     psaWinLsiLogicTrap      OBJECT IDENTIFIER  ::={ partitionEnterprise 55 }
     psaWinDiskTrap          OBJECT IDENTIFIER  ::={ partitionEnterprise 56 }
     psaWinGrmpdTrap         OBJECT IDENTIFIER  ::={ partitionEnterprise 57 }
     psaWinDiskMirrorTrap    OBJECT IDENTIFIER  ::={ partitionEnterprise 58 }
     psaWinXframe2Trap       OBJECT IDENTIFIER  ::={ partitionEnterprise 59 }
     psaWinIntelE1000expTrap OBJECT IDENTIFIER  ::={ partitionEnterprise 60 }
     psaWinSvsRaidTrap       OBJECT IDENTIFIER  ::={ partitionEnterprise 61 }
     psaWinMpdTrap           OBJECT IDENTIFIER  ::={ partitionEnterprise 62 }
     psaWinGlsTrap           OBJECT IDENTIFIER  ::={ partitionEnterprise 63 }

--***************************************************************************************
--
--FUJITSU PRIMEQUEST system management trap parameter variables for Partition
--	They aren't directly accessibles(can't use snmp get/set command), but sent with trap
--
--***************************************************************************************

     trapVarComInfo	OBJECT IDENTIFIER	::={ parititonVariables 1 }

trapPartitionName OBJECT-TYPE
   SYNTAX   DisplayString
   ACCESS   not-accessible
   STATUS   mandatory
   DESCRIPTION "Partition name which trap is generated."
   ::= { trapVarComInfo 1 }

trapPartitionId OBJECT-TYPE
   SYNTAX   INTEGER
   ACCESS   not-accessible
   STATUS   mandatory
   DESCRIPTION "Paritition identifier which trap is generated."
   ::= { trapVarComInfo 2 }

trapEventLevel OBJECT-TYPE
   SYNTAX   DisplayString
   ACCESS   not-accessible
   STATUS   mandatory
   DESCRIPTION "Event level"
   ::= { trapVarComInfo 3 }

trapEventId OBJECT-TYPE
   SYNTAX   INTEGER
   ACCESS   not-accessible
   STATUS   mandatory
   DESCRIPTION "Event Identifier"
   ::= { trapVarComInfo 4 }

trapUnitName OBJECT-TYPE
   SYNTAX   DisplayString
   ACCESS   not-accessible
   STATUS   mandatory
   DESCRIPTION "Unit name which trap is generated."
   ::= { trapVarComInfo 5 }

trapMmbVip OBJECT-TYPE
   SYNTAX   DisplayString
   ACCESS   not-accessible
   STATUS   mandatory
   DESCRIPTION "Management board vertual IP address."
   ::= { trapVarComInfo 6 }

     trapVarDivInfo	OBJECT IDENTIFIER	::={ parititonVariables 2 }

trapPartNo OBJECT-TYPE
   SYNTAX   DisplayString
   ACCESS   not-accessible
   STATUS   mandatory
   DESCRIPTION "Parts number of trap source."
   ::= { trapVarDivInfo 1 }

trapStepping OBJECT-TYPE
   SYNTAX   DisplayString
   ACCESS   not-accessible
   STATUS   mandatory
   DESCRIPTION " "
   ::= { trapVarDivInfo 2 }

trapSerialNo OBJECT-TYPE
   SYNTAX   DisplayString
   ACCESS   not-accessible
   STATUS   mandatory
   DESCRIPTION "Serial number of trap source. "
   ::= { trapVarDivInfo 3 }

trapModelNo OBJECT-TYPE
   SYNTAX   DisplayString
   ACCESS   not-accessible
   STATUS   mandatory
   DESCRIPTION "Model number of trap source."
   ::= { trapVarDivInfo 4 }

trapSuspect OBJECT-TYPE
   SYNTAX   DisplayString
   ACCESS   not-accessible
   STATUS   mandatory
   DESCRIPTION "Logical name or pci bus number of trap source."
   ::= { trapVarDivInfo 5 }

trapVendorId OBJECT-TYPE
   SYNTAX   DisplayString
   ACCESS   not-accessible
   STATUS   mandatory
   DESCRIPTION "Vendor identifier of trap source."
   ::= { trapVarDivInfo 6 }

trapDeviceId OBJECT-TYPE
   SYNTAX   DisplayString
   ACCESS   not-accessible
   STATUS   mandatory
   DESCRIPTION "Device identifier of trap source."
   ::= { trapVarDivInfo 7 }

trapRevision OBJECT-TYPE
   SYNTAX   DisplayString
   ACCESS   not-accessible
   STATUS   mandatory
   DESCRIPTION "Revision of trap source."
   ::= { trapVarDivInfo 8 }

trapCardName OBJECT-TYPE
   SYNTAX   DisplayString
   ACCESS   not-accessible
   STATUS   mandatory
   DESCRIPTION "Device name of trap source."
   ::= { trapVarDivInfo 9 }

trapErrDetail OBJECT-TYPE
   SYNTAX   DisplayString
   ACCESS   not-accessible
   STATUS   mandatory
   DESCRIPTION " "
   ::= { trapVarDivInfo 10 }

trapErrCode OBJECT-TYPE
   SYNTAX   DisplayString
   ACCESS   not-accessible
   STATUS   mandatory
   DESCRIPTION " "
   ::= { trapVarDivInfo 11 }

trapIrpCode OBJECT-TYPE
   SYNTAX   DisplayString
   ACCESS   not-accessible
   STATUS   mandatory
   DESCRIPTION " "
   ::= { trapVarDivInfo 12 }

trapHbaNo OBJECT-TYPE
   SYNTAX   INTEGER
   ACCESS   not-accessible
   STATUS   mandatory
   DESCRIPTION " "
   ::= { trapVarDivInfo 13 }

trapErrCause OBJECT-TYPE
   SYNTAX   DisplayString
   ACCESS   not-accessible
   STATUS   mandatory
   DESCRIPTION " "
   ::= { trapVarDivInfo 14 }

trapPathNo OBJECT-TYPE
   SYNTAX   INTEGER
   ACCESS   not-accessible
   STATUS   mandatory
   DESCRIPTION " "
   ::= { trapVarDivInfo 15 }

trapDiskId OBJECT-TYPE
   SYNTAX   DisplayString
   ACCESS   not-accessible
   STATUS   mandatory
   DESCRIPTION " "
   ::= { trapVarDivInfo 16 }

trapFmrDiskId OBJECT-TYPE
   SYNTAX   DisplayString
   ACCESS   not-accessible
   STATUS   mandatory
   DESCRIPTION " "
   ::= { trapVarDivInfo 17 }

trapCurDiskId OBJECT-TYPE
   SYNTAX   DisplayString
   ACCESS   not-accessible
   STATUS   mandatory
   DESCRIPTION " "
   ::= { trapVarDivInfo 18 }

trapPathId OBJECT-TYPE
   SYNTAX   DisplayString
   ACCESS   not-accessible
   STATUS   mandatory
   DESCRIPTION " "
   ::= { trapVarDivInfo 19 }

trapPhysIf OBJECT-TYPE
   SYNTAX   DisplayString
   ACCESS   not-accessible
   STATUS   mandatory
   DESCRIPTION " "
   ::= { trapVarDivInfo 20 }

trapVirtualIf OBJECT-TYPE
   SYNTAX   DisplayString
   ACCESS   not-accessible
   STATUS   mandatory
   DESCRIPTION " "
   ::= { trapVarDivInfo 21 }

trapLogicalIp OBJECT-TYPE
   SYNTAX   DisplayString
   ACCESS   not-accessible
   STATUS   mandatory
   DESCRIPTION " "
   ::= { trapVarDivInfo 22 }

trapWatchIp OBJECT-TYPE
   SYNTAX   DisplayString
   ACCESS   not-accessible
   STATUS   mandatory
   DESCRIPTION " "
   ::= { trapVarDivInfo 23 }

trapInterface OBJECT-TYPE
   SYNTAX   DisplayString
   ACCESS   not-accessible
   STATUS   mandatory
   DESCRIPTION " "
   ::= { trapVarDivInfo 24 }

trapSourceIp OBJECT-TYPE
   SYNTAX   DisplayString
   ACCESS   not-accessible
   STATUS   mandatory
   DESCRIPTION " "
   ::= { trapVarDivInfo 25 }

trapDestIp OBJECT-TYPE
   SYNTAX   DisplayString
   ACCESS   not-accessible
   STATUS   mandatory
   DESCRIPTION " "
   ::= { trapVarDivInfo 26 }

trapModelName OBJECT-TYPE
   SYNTAX   DisplayString
   ACCESS   not-accessible
   STATUS   mandatory
   DESCRIPTION "Model name of trap source."
   ::= { trapVarDivInfo 27 }

--***************************************************************************************
--
--FUJITSU PRIMEQUEST system management TRAP definition for Partition
--	Trap enterprise:	psaWinIntelE1000expTrap (.1.3.6.1.4.1.211.1.31.1.2.201.60)
--
--***************************************************************************************

e1000expWinEvent0 TRAP-TYPE
   ENTERPRISE   psaWinIntelE1000expTrap
   VARIABLES {
      trapPartitionName,
      trapPartitionId,
      trapEventLevel,
      trapEventId,
      trapUnitName,
      trapSuspect,
      trapMmbVip
   }
   DESCRIPTION "e1000_express: Adapter or Software error (Adapter not found)"
   --#TYPE			"E1000exp Win Event 0"
   --#SUMMARY		"%s(PID=%d) %s %d %s e1000_express:%s Adapter or Software error (Adapter not found)"
   --#ARGUMENTS		{ 0, 1, 2, 3, 4, 5 }
   --#SEVERITY		MINOR
   ::= 21700

e1000expWinEvent1 TRAP-TYPE
   ENTERPRISE   psaWinIntelE1000expTrap
   VARIABLES {
      trapPartitionName,
      trapPartitionId,
      trapEventLevel,
      trapEventId,
      trapUnitName,
      trapSuspect,
      trapMmbVip
   }
   DESCRIPTION "e1000_express: Adapter or Software error (Driver load error)"
   --#TYPE			"E1000exp Win Event 1"
   --#SUMMARY		"%s(PID=%d) %s %d %s e1000_express:%s Adapter or Software error (Driver load error)"
   --#ARGUMENTS		{ 0, 1, 2, 3, 4, 5 }
   --#SEVERITY		MAJOR
   ::= 21701

e1000expWinEvent2 TRAP-TYPE
   ENTERPRISE   psaWinIntelE1000expTrap
   VARIABLES {
      trapPartitionName,
      trapPartitionId,
      trapEventLevel,
      trapEventId,
      trapUnitName,
      trapSuspect,
      trapMmbVip
   }
   DESCRIPTION "e1000_express: Software error (Could not allocate The MAP REGISTRES)"
   --#TYPE			"E1000exp Win Event 2"
   --#SUMMARY		"%s(PID=%d) %s %d %s e1000_express:%s Software error (Could not allocate The MAP REGISTRES)"
   --#ARGUMENTS		{ 0, 1, 2, 3, 4, 5 }
   --#SEVERITY		MINOR
   ::= 21702

e1000expWinEvent3 TRAP-TYPE
   ENTERPRISE   psaWinIntelE1000expTrap
   VARIABLES {
      trapPartitionName,
      trapPartitionId,
      trapEventLevel,
      trapEventId,
      trapUnitName,
      trapSuspect,
      trapMmbVip
   }
   DESCRIPTION "e1000_express: Software error (Could not assign an interrupt)"
   --#TYPE			"E1000exp Win Event 3"
   --#SUMMARY		"%s(PID=%d) %s %d %s e1000_express:%s Software error (Could not assign an interrupt)"
   --#ARGUMENTS		{ 0, 1, 2, 3, 4, 5 }
   --#SEVERITY		MAJOR
   ::= 21703

e1000expWinEvent4 TRAP-TYPE
   ENTERPRISE   psaWinIntelE1000expTrap
   VARIABLES {
      trapPartitionName,
      trapPartitionId,
      trapEventLevel,
      trapEventId,
      trapUnitName,
      trapSuspect,
      trapMmbVip
   }
   DESCRIPTION "e1000_express: Software error (Could not allocate memory)"
   --#TYPE			"E1000exp Win Event 4"
   --#SUMMARY		"%s(PID=%d) %s %d %s e1000_express:%s Software error (Could not allocate memory)"
   --#ARGUMENTS		{ 0, 1, 2, 3, 4, 5 }
   --#SEVERITY		MAJOR
   ::= 21704

e1000expWinEvent5 TRAP-TYPE
   ENTERPRISE   psaWinIntelE1000expTrap
   VARIABLES {
      trapPartitionName,
      trapPartitionId,
      trapEventLevel,
      trapEventId,
      trapUnitName,
      trapSuspect,
      trapMmbVip
   }
   DESCRIPTION "e1000_express: Software error (Could not allocate shared memory)"
   --#TYPE			"E1000exp Win Event 5"
   --#SUMMARY		"%s(PID=%d) %s %d %s e1000_express:%s Software error (Could not allocate shared memory)"
   --#ARGUMENTS		{ 0, 1, 2, 3, 4, 5 }
   --#SEVERITY		MINOR
   ::= 21705

e1000expWinEvent6 TRAP-TYPE
   ENTERPRISE   psaWinIntelE1000expTrap
   VARIABLES {
      trapPartitionName,
      trapPartitionId,
      trapEventLevel,
      trapEventId,
      trapUnitName,
      trapSuspect,
      trapMmbVip
   }
   DESCRIPTION "e1000_express: Software error (Could not allocate memory)"
   --#TYPE			"E1000exp Win Event 6"
   --#SUMMARY		"%s(PID=%d) %s %d %s e1000_express:%s Software error (Could not allocate memory)"
   --#ARGUMENTS		{ 0, 1, 2, 3, 4, 5 }
   --#SEVERITY		MINOR
   ::= 21706

e1000expWinEvent7 TRAP-TYPE
   ENTERPRISE   psaWinIntelE1000expTrap
   VARIABLES {
      trapPartitionName,
      trapPartitionId,
      trapEventLevel,
      trapEventId,
      trapUnitName,
      trapSuspect,
      trapMmbVip
   }
   DESCRIPTION "e1000_express: Software error (Could not allocate memory)"
   --#TYPE			"E1000exp Win Event 7"
   --#SUMMARY		"%s(PID=%d) %s %d %s e1000_express:%s Software error (Could not allocate memory)"
   --#ARGUMENTS		{ 0, 1, 2, 3, 4, 5 }
   --#SEVERITY		MINOR
   ::= 21707

e1000expWinEvent8 TRAP-TYPE
   ENTERPRISE   psaWinIntelE1000expTrap
   VARIABLES {
      trapPartitionName,
      trapPartitionId,
      trapEventLevel,
      trapEventId,
      trapUnitName,
      trapSuspect,
      trapMmbVip
   }
   DESCRIPTION "e1000_express: Software error (Could not allocate memory)"
   --#TYPE			"E1000exp Win Event 8"
   --#SUMMARY		"%s(PID=%d) %s %d %s e1000_express:%s Software error (Could not allocate memory)"
   --#ARGUMENTS		{ 0, 1, 2, 3, 4, 5 }
   --#SEVERITY		MINOR
   ::= 21708

e1000expWinEvent9 TRAP-TYPE
   ENTERPRISE   psaWinIntelE1000expTrap
   VARIABLES {
      trapPartitionName,
      trapPartitionId,
      trapEventLevel,
      trapEventId,
      trapUnitName,
      trapSuspect,
      trapVendorId,
      trapDeviceId,
      trapRevision,
      trapMmbVip
   }
   DESCRIPTION "e1000_express: Adapter error (Could not establish link)"
   --#TYPE			"E1000exp Win Event 9"
   --#SUMMARY		"%s(PID=%d) %s %d %s e1000_express:%s Adapter error (Could not establish link) vendor-id=%s device-id=%s revision=%s"
   --#ARGUMENTS		{ 0, 1, 2, 3, 4, 5, 6, 7, 8 }
   --#SEVERITY		MINOR
   ::= 21709

e1000expWinEvent10 TRAP-TYPE
   ENTERPRISE   psaWinIntelE1000expTrap
   VARIABLES {
      trapPartitionName,
      trapPartitionId,
      trapEventLevel,
      trapEventId,
      trapUnitName,
      trapSuspect,
      trapVendorId,
      trapDeviceId,
      trapRevision,
      trapMmbVip
   }
   DESCRIPTION "e1000_express: Adapter error (NOT properly configured)"
   --#TYPE			"E1000exp Win Event 10"
   --#SUMMARY		"%s(PID=%d) %s %d %s e1000_express:%s Adapter error (NOT properly configured) vendor-id=%s device-id=%s revision=%s"
   --#ARGUMENTS		{ 0, 1, 2, 3, 4, 5, 6, 7, 8 }
   --#SEVERITY		MAJOR
   ::= 21710

e1000expWinEvent11 TRAP-TYPE
   ENTERPRISE   psaWinIntelE1000expTrap
   VARIABLES {
      trapPartitionName,
      trapPartitionId,
      trapEventLevel,
      trapEventId,
      trapUnitName,
      trapSuspect,
      trapVendorId,
      trapDeviceId,
      trapRevision,
      trapMmbVip
   }
   DESCRIPTION "e1000_express: Adapter error (Not configured for bus mastering)"
   --#TYPE			"E1000exp Win Event 11"
   --#SUMMARY		"%s(PID=%d) %s %d %s e1000_express:%s Adapter error (Not configured for bus mastering) vendor-id=%s device-id=%s revision=%s"
   --#ARGUMENTS		{ 0, 1, 2, 3, 4, 5, 6, 7, 8 }
   --#SEVERITY		MAJOR
   ::= 21711

e1000expWinEvent12 TRAP-TYPE
   ENTERPRISE   psaWinIntelE1000expTrap
   VARIABLES {
      trapPartitionName,
      trapPartitionId,
      trapEventLevel,
      trapEventId,
      trapUnitName,
      trapSuspect,
      trapMmbVip
   }
   DESCRIPTION "e1000_express: Software error (Could not allocate the NDIS receive packets)"
   --#TYPE			"E1000exp Win Event 12"
   --#SUMMARY		"%s(PID=%d) %s %d %s e1000_express:%s Software error (Could not allocate the NDIS receive packets)"
   --#ARGUMENTS		{ 0, 1, 2, 3, 4, 5 }
   --#SEVERITY		MINOR
   ::= 21712

e1000expWinEvent13 TRAP-TYPE
   ENTERPRISE   psaWinIntelE1000expTrap
   VARIABLES {
      trapPartitionName,
      trapPartitionId,
      trapEventLevel,
      trapEventId,
      trapUnitName,
      trapSuspect,
      trapMmbVip
   }
   DESCRIPTION "e1000_express: Software error (Could not allocate the NDIS receive buffers)"
   --#TYPE			"E1000exp Win Event 13"
   --#SUMMARY		"%s(PID=%d) %s %d %s e1000_express:%s Software error (Could not allocate the NDIS receive buffers)"
   --#ARGUMENTS		{ 0, 1, 2, 3, 4, 5 }
   --#SEVERITY		MINOR
   ::= 21713

e1000expWinEvent14 TRAP-TYPE
   ENTERPRISE   psaWinIntelE1000expTrap
   VARIABLES {
      trapPartitionName,
      trapPartitionId,
      trapEventLevel,
      trapEventId,
      trapUnitName,
      trapSuspect,
      trapMmbVip
   }
   DESCRIPTION "e1000_express: Software error (unable to assign PCI resources)"
   --#TYPE			"E1000exp Win Event 14"
   --#SUMMARY		"%s(PID=%d) %s %d %s e1000_express:%s Software error (unable to assign PCI resources)"
   --#ARGUMENTS		{ 0, 1, 2, 3, 4, 5 }
   --#SEVERITY		MINOR
   ::= 21714

e1000expWinEvent15 TRAP-TYPE
   ENTERPRISE   psaWinIntelE1000expTrap
   VARIABLES {
      trapPartitionName,
      trapPartitionId,
      trapEventLevel,
      trapEventId,
      trapUnitName,
      trapSuspect,
      trapMmbVip
   }
   DESCRIPTION "e1000_express: Software error (unable to claim PCI resources)"
   --#TYPE			"E1000exp Win Event 15"
   --#SUMMARY		"%s(PID=%d) %s %d %s e1000_express:%s Software error (unable to claim PCI resources)"
   --#ARGUMENTS		{ 0, 1, 2, 3, 4, 5 }
   --#SEVERITY		MINOR
   ::= 21715

e1000expWinEvent16 TRAP-TYPE
   ENTERPRISE   psaWinIntelE1000expTrap
   VARIABLES {
      trapPartitionName,
      trapPartitionId,
      trapEventLevel,
      trapEventId,
      trapUnitName,
      trapSuspect,
      trapVendorId,
      trapDeviceId,
      trapRevision,
      trapMmbVip
   }
   DESCRIPTION "e1000_express: Adapter error (EEPROM error)"
   --#TYPE			"E1000exp Win Event 16"
   --#SUMMARY		"%s(PID=%d) %s %d %s e1000_express:%s Adapter error (EEPROM error) vendor-id=%s device-id=%s revision=%s"
   --#ARGUMENTS		{ 0, 1, 2, 3, 4, 5, 6, 7, 8 }
   --#SEVERITY		MAJOR
   ::= 21716

e1000expWinEvent17 TRAP-TYPE
   ENTERPRISE   psaWinIntelE1000expTrap
   VARIABLES {
      trapPartitionName,
      trapPartitionId,
      trapEventLevel,
      trapEventId,
      trapUnitName,
      trapSuspect,
      trapMmbVip
   }
   DESCRIPTION "e1000_express: Software error (Could not start)"
   --#TYPE			"E1000exp Win Event 17"
   --#SUMMARY		"%s(PID=%d) %s %d %s e1000_express:%s Software error (Could not start)"
   --#ARGUMENTS		{ 0, 1, 2, 3, 4, 5 }
   --#SEVERITY		MINOR
   ::= 21717

e1000expWinEvent18 TRAP-TYPE
   ENTERPRISE   psaWinIntelE1000expTrap
   VARIABLES {
      trapPartitionName,
      trapPartitionId,
      trapEventLevel,
      trapEventId,
      trapUnitName,
      trapSuspect,
      trapMmbVip
   }
   DESCRIPTION "e1000_express: Software error (MDIX setting conflict with the AutoNeg Settings)"
   --#TYPE			"E1000exp Win Event 18"
   --#SUMMARY		"%s(PID=%d) %s %d %s e1000_express:%s Software error (MDIX setting conflict with the AutoNeg Settings)"
   --#ARGUMENTS		{ 0, 1, 2, 3, 4, 5 }
   --#SEVERITY		MINOR
   ::= 21718

e1000expWinEvent19 TRAP-TYPE
   ENTERPRISE   psaWinIntelE1000expTrap
   VARIABLES {
      trapPartitionName,
      trapPartitionId,
      trapEventLevel,
      trapEventId,
      trapUnitName,
      trapSuspect,
      trapVendorId,
      trapDeviceId,
      trapRevision,
      trapMmbVip
   }
   DESCRIPTION "e1000_express: Adapter error (Could not start)"
   --#TYPE			"E1000exp Win Event 19"
   --#SUMMARY		"%s(PID=%d) %s %d %s e1000_express:%s Adapter error (Could not start) vendor-id=%s device-id=%s revision=%s"
   --#ARGUMENTS		{ 0, 1, 2, 3, 4, 5, 6, 7, 8 }
   --#SEVERITY		MINOR
   ::= 21719

e1000expWinEvent20 TRAP-TYPE
   ENTERPRISE   psaWinIntelE1000expTrap
   VARIABLES {
      trapPartitionName,
      trapPartitionId,
      trapEventLevel,
      trapEventId,
      trapUnitName,
      trapSuspect,
      trapMmbVip
   }
   DESCRIPTION "e1000_express: Software error (Could not allocate all resources)"
   --#TYPE			"E1000exp Win Event 20"
   --#SUMMARY		"%s(PID=%d) %s %d %s e1000_express:%s Software error (Could not allocate all resources)"
   --#ARGUMENTS		{ 0, 1, 2, 3, 4, 5 }
   --#SEVERITY		MINOR
   ::= 21720

e1000expWinEvent21 TRAP-TYPE
   ENTERPRISE   psaWinIntelE1000expTrap
   VARIABLES {
      trapPartitionName,
      trapPartitionId,
      trapEventLevel,
      trapEventId,
      trapUnitName,
      trapSuspect,
      trapMmbVip
   }
   DESCRIPTION "e1000_express: Software error (failed to initialize properly)"
   --#TYPE			"E1000exp Win Event 21"
   --#SUMMARY		"%s(PID=%d) %s %d %s e1000_express:%s Software error (failed to initialize properly)"
   --#ARGUMENTS		{ 0, 1, 2, 3, 4, 5 }
   --#SEVERITY		MINOR
   ::= 21721

e1000expWinEvent22 TRAP-TYPE
   ENTERPRISE   psaWinIntelE1000expTrap
   VARIABLES {
      trapPartitionName,
      trapPartitionId,
      trapEventLevel,
      trapEventId,
      trapUnitName,
      trapSuspect,
      trapMmbVip
   }
   DESCRIPTION "e1000_express: Software error (Could not find a supported gigabit network connection)"
   --#TYPE			"E1000exp Win Event 22"
   --#SUMMARY		"%s(PID=%d) %s %d %s e1000_express:%s Software error (Could not find a supported gigabit network connection)"
   --#ARGUMENTS		{ 0, 1, 2, 3, 4, 5 }
   --#SEVERITY		MINOR
   ::= 21722

e1000expWinEvent23 TRAP-TYPE
   ENTERPRISE   psaWinIntelE1000expTrap
   VARIABLES {
      trapPartitionName,
      trapPartitionId,
      trapEventLevel,
      trapEventId,
      trapUnitName,
      trapSuspect,
      trapMmbVip
   }
   DESCRIPTION "e1000_express: Adapter or Software error (Driver load error)"
   --#TYPE			"E1000exp Win Event 23"
   --#SUMMARY		"%s(PID=%d) %s %d %s e1000_express:%s Adapter or Software error (Driver load error)"
   --#ARGUMENTS		{ 0, 1, 2, 3, 4, 5 }
   --#SEVERITY		MINOR
   ::= 21723

e1000expWinEvent24 TRAP-TYPE
   ENTERPRISE   psaWinIntelE1000expTrap
   VARIABLES {
      trapPartitionName,
      trapPartitionId,
      trapEventLevel,
      trapEventId,
      trapUnitName,
      trapSuspect,
      trapMmbVip
   }
   DESCRIPTION "e1000_express: Software error (Could not assign an interrupt)"
   --#TYPE			"E1000exp Win Event 24"
   --#SUMMARY		"%s(PID=%d) %s %d %s e1000_express:%s Software error (Could not assign an interrupt)"
   --#ARGUMENTS		{ 0, 1, 2, 3, 4, 5 }
   --#SEVERITY		MINOR
   ::= 21724

e1000expWinEvent25 TRAP-TYPE
   ENTERPRISE   psaWinIntelE1000expTrap
   VARIABLES {
      trapPartitionName,
      trapPartitionId,
      trapEventLevel,
      trapEventId,
      trapUnitName,
      trapSuspect,
      trapVendorId,
      trapDeviceId,
      trapRevision,
      trapMmbVip
   }
   DESCRIPTION "e1000_express: Adapter error (NOT properly configured)"
   --#TYPE			"E1000exp Win Event 25"
   --#SUMMARY		"%s(PID=%d) %s %d %s e1000_express:%s Adapter error (NOT properly configured) vendor-id=%s device-id=%s revision=%s"
   --#ARGUMENTS		{ 0, 1, 2, 3, 4, 5, 6, 7, 8 }
   --#SEVERITY		MAJOR
   ::= 21725

e1000expWinEvent26 TRAP-TYPE
   ENTERPRISE   psaWinIntelE1000expTrap
   VARIABLES {
      trapPartitionName,
      trapPartitionId,
      trapEventLevel,
      trapEventId,
      trapUnitName,
      trapSuspect,
      trapVendorId,
      trapDeviceId,
      trapRevision,
      trapMmbVip
   }
   DESCRIPTION "e1000_express: Adapter error (Not configured for bus mastering)"
   --#TYPE			"E1000exp Win Event 26"
   --#SUMMARY		"%s(PID=%d) %s %d %s e1000_express:%s Adapter error (Not configured for bus mastering) vendor-id=%s device-id=%s revision=%s"
   --#ARGUMENTS		{ 0, 1, 2, 3, 4, 5, 6, 7, 8 }
   --#SEVERITY		MAJOR
   ::= 21726

e1000expWinEvent27 TRAP-TYPE
   ENTERPRISE   psaWinIntelE1000expTrap
   VARIABLES {
      trapPartitionName,
      trapPartitionId,
      trapEventLevel,
      trapEventId,
      trapUnitName,
      trapSuspect,
      trapMmbVip
   }
   DESCRIPTION "e1000_express: Software error (unable to assign PCI resources)"
   --#TYPE			"E1000exp Win Event 27"
   --#SUMMARY		"%s(PID=%d) %s %d %s e1000_express:%s Software error (unable to assign PCI resources)"
   --#ARGUMENTS		{ 0, 1, 2, 3, 4, 5 }
   --#SEVERITY		MINOR
   ::= 21727

e1000expWinEvent28 TRAP-TYPE
   ENTERPRISE   psaWinIntelE1000expTrap
   VARIABLES {
      trapPartitionName,
      trapPartitionId,
      trapEventLevel,
      trapEventId,
      trapUnitName,
      trapSuspect,
      trapMmbVip
   }
   DESCRIPTION "e1000_express: Software error (unable to claim PCI resources)"
   --#TYPE			"E1000exp Win Event 28"
   --#SUMMARY		"%s(PID=%d) %s %d %s e1000_express:%s Software error (unable to claim PCI resources)"
   --#ARGUMENTS		{ 0, 1, 2, 3, 4, 5 }
   --#SEVERITY		MINOR
   ::= 21728

e1000expWinEvent29 TRAP-TYPE
   ENTERPRISE   psaWinIntelE1000expTrap
   VARIABLES {
      trapPartitionName,
      trapPartitionId,
      trapEventLevel,
      trapEventId,
      trapUnitName,
      trapSuspect,
      trapVendorId,
      trapDeviceId,
      trapRevision,
      trapMmbVip
   }
   DESCRIPTION "e1000_express: Adapter error (EEPROM error)"
   --#TYPE			"E1000exp Win Event 29"
   --#SUMMARY		"%s(PID=%d) %s %d %s e1000_express:%s Adapter error (EEPROM error) vendor-id=%s device-id=%s revision=%s"
   --#ARGUMENTS		{ 0, 1, 2, 3, 4, 5, 6, 7, 8 }
   --#SEVERITY		MAJOR
   ::= 21729

e1000expWinEvent30 TRAP-TYPE
   ENTERPRISE   psaWinIntelE1000expTrap
   VARIABLES {
      trapPartitionName,
      trapPartitionId,
      trapEventLevel,
      trapEventId,
      trapUnitName,
      trapSuspect,
      trapMmbVip
   }
   DESCRIPTION "e1000_express: Software error (Could not start)"
   --#TYPE			"E1000exp Win Event 30"
   --#SUMMARY		"%s(PID=%d) %s %d %s e1000_express:%s Software error (Could not start)"
   --#ARGUMENTS		{ 0, 1, 2, 3, 4, 5 }
   --#SEVERITY		MINOR
   ::= 21730

END
