--*********************************
-- MIB table for TH2E sensor
--
-- by Miroslav Steiger
-- www.papouch.com - Copyright (c) 2009
--
--*********************************

The-v01-MIB DEFINITIONS ::= BEGIN

IMPORTS  
--	MODULE-IDENTITY,
--	OBJECT-TYPE,
--	NOTIFICATION-TYPE,     
		enterprises,
		IpAddress,
		Counter,
		Gauge,
		TimeTicks
    	FROM RFC1155-SMI
    OBJECT-TYPE
		FROM RFC-1212    
	DisplayString
		FROM RFC1213-MIB
	TRAP-TYPE
		FROM RFC-1215
    ;
    		
papouchProjekt	   OBJECT IDENTIFIER ::= { enterprises 18248 }	
the		       OBJECT IDENTIFIER ::= { papouchProjekt 20 }	
version1            OBJECT IDENTIFIER ::= { the 1 }            

device-var         OBJECT IDENTIFIER ::= { version1 1 }
table-channel      OBJECT IDENTIFIER ::= { version1 2 } 
table-watchValue   OBJECT IDENTIFIER ::= { version1 3 }
--
-- Type Definitions
--

PositiveInteger ::= INTEGER (0..65535)
---
--- TABULKA PRO PARAMETRY pro cteni a zapis
---
 channelTable OBJECT-TYPE
	SYNTAX  SEQUENCE OF ChannelEntry
	ACCESS  not-accessible
	STATUS  current
	DESCRIPTION	""
 ::= { table-channel 1 }
 channelEntry OBJECT-TYPE
	SYNTAX  ChannelEntry
	ACCESS  not-accessible
	STATUS  current
	DESCRIPTION	""
	INDEX   { index }
 ::= { channelTable 1 }
 ChannelEntry ::=
    SEQUENCE { 
        inChStatus
            INTEGER,
        inChValue
            INTEGER,  
        inChUnits
            INTEGER
            
    }
    
--
-- parametry pro cteni status mode
--
--
-- OID 1.3.6.1.4.1.18248.20.1.2.1.1.1.1 - 3  
-- Status kanalu
--  
inChStatus  OBJECT-TYPE
	SYNTAX  	INTEGER
	ACCESS		read-only
	STATUS		current
	DESCRIPTION	"0 = OK,1 = Not available,2 = over-flow,3 = under-flow,4=ERR"
::= { channelEntry 1 }         
--
-- OID 1.3.6.1.4.1.18248.20.1.2.1.1.2.1 - 3  
-- Namioena hodnota
--
inChValue  OBJECT-TYPE
	SYNTAX  	INTEGER
	ACCESS		read-only
	STATUS		current
	DESCRIPTION	""
::= { channelEntry 2 } 
--
-- OID 1.3.6.1.4.1.18248.20.1.2.1.1.3.1 - 3  
-- Jednotka (pro teplotu nebo vlhkost)
--
inChUnits  OBJECT-TYPE
	SYNTAX  	INTEGER
	ACCESS		read-only
	STATUS		current
	DESCRIPTION	"0 = Celsius, 1 = Fahrenfeit, 2 = Kelvin, 3 = Percents"
::= { channelEntry 3 } 

---
--- TABULKA PRO PARAMETRY HLIDANI 
---
 watchValTable OBJECT-TYPE
	SYNTAX  SEQUENCE OF WatchValEntry
	ACCESS  not-accessible
	STATUS  current
	DESCRIPTION	""
 ::= { table-watchValue 1 }

 watchValEntry OBJECT-TYPE
	SYNTAX  WatchValEntry
	ACCESS  not-accessible
	STATUS  current
	DESCRIPTION	""
	INDEX   { index }
 ::= { watchValTable 1 }

WatchValEntry ::=
    SEQUENCE {
        modeWatch
            INTEGER,
        limitHi
            INTEGER, 	
        limitLo
            INTEGER, 	
        limitHy
            INTEGER 	
    } 
--
-- OID 1.3.6.1.4.1.18248.20.1.3.1.1.1.1 - 3  
-- Hlidani mezi
--
modeWatch OBJECT-TYPE
	SYNTAX  	INTEGER(0..1)
	ACCESS		read-only
	STATUS		current
	DESCRIPTION	"1 = ON,0 = OFF"
::= { watchValEntry 1 } 
--
-- OID 1.3.6.1.4.1.18248.20.1.3.1.1.2.1 - 3  
-- Horni mez
--
limitHi OBJECT-TYPE
	SYNTAX  	INTEGER
	ACCESS		read-only
	STATUS		current
	DESCRIPTION	""
::= { watchValEntry 2 }
--
-- OID 1.3.6.1.4.1.18248.20.1.3.1.1.3.1 - 3  
-- Dolni mez
--
limitLo OBJECT-TYPE
	SYNTAX  	INTEGER
	ACCESS		read-only
	STATUS		current
	DESCRIPTION	""
::= { watchValEntry 3 }
--
-- OID 1.3.6.1.4.1.18248.20.1.3.1.1.4.1 - 3  
-- Velikost hystereze
--
limitHy OBJECT-TYPE
	SYNTAX  	INTEGER
	ACCESS		read-only
	STATUS		current
	DESCRIPTION	""
::= { watchValEntry 4 }
--
-- OID 1.3.6.1.4.1.18248.20.1.1.1.0  
-- Nazev zaoizeni
--
deviceName OBJECT-TYPE
	SYNTAX		DisplayString
	ACCESS		read-only
	STATUS		mandatory
	DESCRIPTION	"Device Name"
::= { device-var 1 } 
--
-- OID 1.3.6.1.4.1.18248.20.1.1.2.0  
-- Chybove hlaseni v trapu
--
psAlarmString OBJECT-TYPE
	SYNTAX		DisplayString
	ACCESS		read-only
	STATUS		mandatory
	DESCRIPTION	""
::= { device-var 2 } 


temp-msg TRAP-TYPE
        ENTERPRISE device-var
        VARIABLES {deviceName,psAlarmString}
		DESCRIPTION ""
            ::= 1


END
