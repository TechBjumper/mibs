-- file automatically created


TELDAT-TRAP-CNSL-MIB DEFINITIONS ::= BEGIN


IMPORTS
	MODULE-IDENTITY,OBJECT-TYPE,OBJECT-IDENTITY,NOTIFICATION-TYPE,Integer32,IpAddress
		FROM SNMPv2-SMI
	DisplayString
		FROM SNMPv2-TC
	telEventTraps
		FROM TELDAT-MIB;


cnslTrapsMIB MODULE-IDENTITY
    LAST-UPDATED "201401200930Z"
    ORGANIZATION "Teldat, S.A."
    CONTACT-INFO 
        "Teldat, S.A.
        Customer Service

        Postal: Parque Tecnologico de Madrid
                Tres Cantos 28760
                Madrid, SPAIN

        Tel.: +34 918 076 565

        http://www.teldat.com"
    DESCRIPTION
        "This Module Information Base file is defined for managing received
        SNMP notifications generated by the CNSL event subsystem."
    REVISION "201401200930Z"
    DESCRIPTION "Initial implementation"
        ::= { telEventTraps 183 }


cnslEventsGroup	OBJECT IDENTIFIER	::= { cnslTrapsMIB 1 }

cnslNotifications	OBJECT IDENTIFIER	::= { cnslTrapsMIB 2 }
cnslNotificationsPrefix	OBJECT IDENTIFIER	::= { cnslNotifications 0 }

cnslEventObjects1 OBJECT-IDENTITY
    STATUS current
    DESCRIPTION
        "Event CNSL.1
        Common command executed (from any process) by specified user."
    ::= { cnslEventsGroup 1 }

cnsl1-user-name OBJECT-TYPE
    SYNTAX DisplayString
    MAX-ACCESS accessible-for-notify
    STATUS current
    DESCRIPTION
        "Parameter 'user-name' in event CNSL.1"
    ::= { cnslEventObjects1 1 }

cnsl1-executed-command OBJECT-TYPE
    SYNTAX DisplayString
    MAX-ACCESS accessible-for-notify
    STATUS current
    DESCRIPTION
        "Parameter 'executed-command' in event CNSL.1"
    ::= { cnslEventObjects1 2 }

cnslEventObjects2 OBJECT-IDENTITY
    STATUS current
    DESCRIPTION
        "Event CNSL.2
        Command executed from config process by specified user."
    ::= { cnslEventsGroup 2 }

cnsl2-user-name OBJECT-TYPE
    SYNTAX DisplayString
    MAX-ACCESS accessible-for-notify
    STATUS current
    DESCRIPTION
        "Parameter 'user-name' in event CNSL.2"
    ::= { cnslEventObjects2 1 }

cnsl2-executed-command OBJECT-TYPE
    SYNTAX DisplayString
    MAX-ACCESS accessible-for-notify
    STATUS current
    DESCRIPTION
        "Parameter 'executed-command' in event CNSL.2"
    ::= { cnslEventObjects2 2 }

cnslEventObjects3 OBJECT-IDENTITY
    STATUS current
    DESCRIPTION
        "Event CNSL.3
        Command executed from running-config process by specified user."
    ::= { cnslEventsGroup 3 }

cnsl3-user-name OBJECT-TYPE
    SYNTAX DisplayString
    MAX-ACCESS accessible-for-notify
    STATUS current
    DESCRIPTION
        "Parameter 'user-name' in event CNSL.3"
    ::= { cnslEventObjects3 1 }

cnsl3-executed-command OBJECT-TYPE
    SYNTAX DisplayString
    MAX-ACCESS accessible-for-notify
    STATUS current
    DESCRIPTION
        "Parameter 'executed-command' in event CNSL.3"
    ::= { cnslEventObjects3 2 }

cnslEventObjects4 OBJECT-IDENTITY
    STATUS current
    DESCRIPTION
        "Event CNSL.4
        Error of specified type in command execution by specified user."
    ::= { cnslEventsGroup 4 }

cnsl4-user-name OBJECT-TYPE
    SYNTAX DisplayString
    MAX-ACCESS accessible-for-notify
    STATUS current
    DESCRIPTION
        "Parameter 'user-name' in event CNSL.4"
    ::= { cnslEventObjects4 1 }

cnsl4-error-type OBJECT-TYPE
    SYNTAX DisplayString
    MAX-ACCESS accessible-for-notify
    STATUS current
    DESCRIPTION
        "Parameter 'error-type' in event CNSL.4"
    ::= { cnslEventObjects4 2 }


cnslNotification1 NOTIFICATION-TYPE
    OBJECTS { 
              cnsl1-user-name, 
              cnsl1-executed-command 
            }
    STATUS current
    DESCRIPTION
        "Notification of Event CNSL.1

        Message: 'user $1 execute command $2'

        Parameters list:
              $1: cnsl1-user-name
              $2: cnsl1-executed-command

        Common command executed (from any process) by specified user."
    ::= { cnslNotificationsPrefix 1 }

cnslNotification2 NOTIFICATION-TYPE
    OBJECTS { 
              cnsl2-user-name, 
              cnsl2-executed-command 
            }
    STATUS current
    DESCRIPTION
        "Notification of Event CNSL.2

        Message: 'user $1 config command $2'

        Parameters list:
              $1: cnsl2-user-name
              $2: cnsl2-executed-command

        Command executed from config process by specified user."
    ::= { cnslNotificationsPrefix 2 }

cnslNotification3 NOTIFICATION-TYPE
    OBJECTS { 
              cnsl3-user-name, 
              cnsl3-executed-command 
            }
    STATUS current
    DESCRIPTION
        "Notification of Event CNSL.3

        Message: 'user $1 running-config command $2'

        Parameters list:
              $1: cnsl3-user-name
              $2: cnsl3-executed-command

        Command executed from running-config process by specified user."
    ::= { cnslNotificationsPrefix 3 }

cnslNotification4 NOTIFICATION-TYPE
    OBJECTS { 
              cnsl4-user-name, 
              cnsl4-error-type 
            }
    STATUS current
    DESCRIPTION
        "Notification of Event CNSL.4

        Message: 'user $1 error $2'

        Parameters list:
              $1: cnsl4-user-name
              $2: cnsl4-error-type

        Error of specified type in command execution by specified user."
    ::= { cnslNotificationsPrefix 4 }


END
