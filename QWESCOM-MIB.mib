--$Log: /QWESspan/PolicyPoint 6201/mibs-supported/qwescom.mib $
--
--8     9/07/00 10:35a Adesai
--change Telnet mib so it can store in configuration without any error.
--
--7     8/07/00 7:56p Rtanna
--Fixes from paul, steve, amit and raj for release 11x3t.
--
--6     7/29/00 3:06p Rtanna
--release for 11x3o
--
--5     7/27/00 7:05p Snguyen
--Integration 11x3n SNN 
--
--4     7/24/00 8:29p D-garrett
--Time Zone MIB Object.
--
--3     7/19/00 6:22p S-qu
--Files from Raj, Amit, Rohit, Steve, Paul and Tej.
--S. Qu  7/19/2000
--
--2     7/07/00 10:05p S-qu
--Port changes between 1.1x2F and 1.1x2H.  S. Qu  7/7/2000
--
--16    7/07/00 7:10p Rbhatia
--Multiple changes:
--1)Paul: Bug fixes for IGMP CP and SNMP
--2) David: CfUpdateObjDesc file had a bug updating data in the object
--decsp override file.
--3) Rohit: Bug fix for reset issue when loading diag code
--4) Amit: Changes to Ds1ObjHand.c file
--5)Tej:  Multicast changes to Web and CP
--6) Ernie/Raj: Fix for MIB walk problem.
--All the above changes check in by Rohit B.
--
--15    7/06/00 4:23a Elouie
--Added support for IGMP.
--
--14    6/23/00 6:25p Rbhatia
--Added additional field for Sub Event ID number in the Event Log Display
--MIB definations. 
--
--13    6/22/00 10:17p S-nguyen
--igmpSnmp.c - update to install igmp from cm
--icirc.c - added call to install igmp from cm.
--ip-snmpx.def - corrected defined range on igmp lp.
--qwescom.mib - added delete entry for igmp type.
-- SNN  IGMP install API integration. 
--
--12    6/12/00 4:50p Pinouye
--fix mib bug 
--
--11    6/12/00 3:18p Pinouye
--Added Eventlog mibs for configuration and display.
--- Added Evenlog mibs and logic for configuration and display.
--- Added Staging Ptr to Lis Table functions to do SNMP sets.
--
--10    6/08/00 6:23p G-fountain
--Rip Authentication merged.
--
--9     6/02/00 10:25p Tmehrok
--Updates for IGMP
--
--8     6/02/00 7:22p Elouie
--qwesLifLpIndex changed from DisplayString to Integer.
--
--7     5/23/00 11:44a Rbhatia
-- Release  1.1.x1h: Added EventLog code for initialization, Error
--Handling, Event Manager API and integrated Send Trap call into the
--Event Log system. 
--
--6     5/17/00 5:01p Elouie
--Integration1.1x1f:
--1) added cp display for forwardTrap and authentication for snmp
--2) added code to free cb->stagingPtr
--3) fix bug #2195 - contact, loaction and name OH was not getting null
--terminated string.
--4) clean-up unnecessary function, clean warnings
--5 added import for RowStatus
--6) trap Status & ilmiStatus is not initialized
--7) added ATM UNI sets.
--
--5     3/17/00 11:56a Elouie
--Integration1.1x1e :
--1) added cp display for forwardTrap and authentication for snmp
--2) added code to free cb->stagingPtr
--3) fix bug #2195 - contact, loaction and name OH was not getting null
--terminated string.
--4) clean-up unnecessary function, clean warnings
--5 added import for RowStatus
--6) trap Status & ilmiStatus is not initialized
--7) added ATM UNI sets.
--
--3     5/10/00 10:29a Adesai
--fixes for Release 1.1 (IP/Span SNMP changes)
--
--2     5/08/00 6:49p Rtanna
--Telnet authentication checked in for release 1.1
--
--1     5/03/00 7:38p Pinouye
--Initial Check in of the Integration for v1.1
--		QWESCOM Enterprise MIB
--
--		QWES.com, Inc.
--		14742 Newport Ave., Suite 203
--		Tustin, CA 92780
--		714 731 6900
--		sales@qwes.com
--
--		Copyright (c) 1998-1999 QWES.com, Inc.
--		All rights reserved.
--
--
-- 01 Jun 1999:	Initial release               E.L.
--


QWESCOM-MIB DEFINITIONS ::= BEGIN

    IMPORTS
	Counter, enterprises
	    FROM RFC1155-SMI
	IpAddress
	    FROM RFC1155-SMI
	TimeTicks
	    FROM RFC1155-SMI
	OBJECT-TYPE
	    FROM RFC-1212
	RowStatus
	    FROM SNMPv2-TC;
-- el10049    atmVplVpi,atmVclVci 
-- el100499	    FROM RFC2515-MIB;


	-- If any of the MIB compilers have problems with the DisplayString
	-- or PhysAddress, uncomment the next two lines.

       DisplayString		::=	OCTET STRING
       PhysAddress		::=	OCTET STRING
       TimeDateString		::=	INTEGER
       Boolean			::=	INTEGER
	--
	-- The QWESCOM enterprise OID.
	--

    qwescom			OBJECT IDENTIFIER ::= {	 enterprises 3662 }


	--
	-- Groups in the QWESCOM Enterprise mib
	--


    oemTree			OBJECT IDENTIFIER ::= { qwescom 3662 }

    oem				OBJECT IDENTIFIER ::= { oemTree 3662 }

    qproprietaryMib2		OBJECT IDENTIFIER ::= { oem 1 }

    qproducts			OBJECT IDENTIFIER ::= { oem 2 }

    qslots			OBJECT IDENTIFIER ::= { oem 3 }

    qFlowClass			OBJECT IDENTIFIER ::= { oem 4 }

    qatm                        OBJECT IDENTIFIER ::= { oem 5 }

    qcraftPort			OBJECT IDENTIFIER ::= { oem 6 }

    qeventGroup			OBJECT IDENTIFIER ::= { oem 8 }

    qextmib			OBJECT IDENTIFIER ::= { oem 9 }

    qmanufactRecord		OBJECT IDENTIFIER ::= { oem 10 }

    qethernet		        OBJECT IDENTIFIER ::= { oem 11 }

    qds1-e1		        OBJECT IDENTIFIER ::= { oem 12 }

    qconfigManager		OBJECT IDENTIFIER ::= { oem 13 }

    qportManagement		OBJECT IDENTIFIER ::= { oem 15 }

    qip                     OBJECT IDENTIFIER ::= { oem 16 }

    qmanagementGroup            OBJECT IDENTIFIER ::= { oem 17 }

    qOamGroup                   OBJECT IDENTIFIER ::= { oem 18 }

    qmiscGroup                  OBJECT IDENTIFIER ::= { oem 19 }

-- QWES.com qproprietaryMib2 { oem 1 }
--
-- This group contains the MIB variables that correspond to the
-- standard Internet Approved Managed Object MIBS (i.e. RFC-1213
-- RFC 1406, RFC-1695, RFC-2358, etc.).

--    qsystem	        OBJECT IDENTIFIER ::= {qproprietaryMib2  1}
--    qinterfaces	OBJECT IDENTIFIER ::= {qproprietaryMib2  2}
--    qat		OBJECT IDENTIFIER ::= {qproprietaryMib2  3}
--    qip		OBJECT IDENTIFIER ::= {qproprietaryMib2  4}
    qsnmp		OBJECT IDENTIFIER ::= {qproprietaryMib2 11}
    qigmp		OBJECT IDENTIFIER ::= {qip 7}

-- SNMP Community Table
   	qsnmpCommunityTable 		OBJECT-TYPE
		SYNTAX		   	SEQUENCE OF QsnmpCommunityEntry
		ACCESS			not-accessible
		STATUS			mandatory
		DESCRIPTION		"A list of SNMP Community entries.  The
					maximum number of SNMP Communities are
					five."
		::= { qsnmp 1 }

   	qsnmpCommunityEntry 		OBJECT-TYPE
		SYNTAX			QsnmpCommunityEntry
		ACCESS			not-accessible
		STATUS			mandatory
		DESCRIPTION		"One entry in the table."
	        INDEX   { qsnmpCommunityIndex }
   		::= { qsnmpCommunityTable 1 }

	QsnmpCommunityEntry ::=
		SEQUENCE {
		        qsnmpCommunityIndex
		            INTEGER,
		        qsnmpCommunityRights
		            INTEGER,
		        qsnmpCommunityName
		            DisplayString
			}

-- SNMP Community Entry fields
	qsnmpCommunityIndex 	OBJECT-TYPE
		SYNTAX			INTEGER (0..4)
		ACCESS			read-only
		STATUS			mandatory
		DESCRIPTION		"A unique value which identifies each
					SNMP Community."
		::= { qsnmpCommunityEntry 1 }

	qsnmpCommunityRights 	OBJECT-TYPE
		SYNTAX			INTEGER {
						readonly  (0),
						readwrite (1)
						}
		ACCESS			read-only
		STATUS			optional
                DESCRIPTION             "The first and third
					qsnmpCommunityIndex have read-write
                                        permission while the others have
					read-only privilege. Values 0 =
					ReadOnly, and 1 = ReadWrite"
                ::= { qsnmpCommunityEntry 2 }

	qsnmpCommunityName 	OBJECT-TYPE
		SYNTAX			DisplayString (SIZE (0..255))
		ACCESS			read-write
		STATUS			mandatory
		DESCRIPTION		"The SNMP Community Name used to access
					the unit with the associated permission
					from the qsnmpCommunityRights."
		::= { qsnmpCommunityEntry 3 }

-- SNMP NMS Table
   	qsnmpNMSTable 		OBJECT-TYPE
		SYNTAX		   	SEQUENCE OF QsnmpNMSEntry
		ACCESS			not-accessible
		STATUS			mandatory
		DESCRIPTION		"A list of SNMP Network Management
					System (NMS) entries."
		::= { qsnmp 2 }

   	qsnmpNMSEntry 		OBJECT-TYPE
		SYNTAX			QsnmpNMSEntry
		ACCESS			not-accessible
		STATUS			mandatory
		DESCRIPTION		"One entry in the table."
	        INDEX   { qsnmpNMSIndex }
   		::= { qsnmpNMSTable 1 }

	QsnmpNMSEntry ::=
		SEQUENCE {
		        qsnmpNMSIndex
		            INTEGER,
		        qsnmpNMSIpAddress
		            IpAddress
			}

-- SNMP NMS Address Entry fields
	qsnmpNMSIndex 		OBJECT-TYPE
		SYNTAX			INTEGER (0..4)
		ACCESS			read-only
		STATUS			mandatory
		DESCRIPTION		"A unique value which identifies each
					NMS."
		::= { qsnmpNMSEntry 1 }

	qsnmpNMSIpAddress 	OBJECT-TYPE
		SYNTAX			IpAddress
		ACCESS			read-write
		STATUS			mandatory
		DESCRIPTION		"The IP Address of a Network Management
					System, which is allowed to access MIB
					variables."
		::= { qsnmpNMSEntry 2 }

-- SNMP Trap IP Address Table
   	qsnmpTrapTable 		OBJECT-TYPE
		SYNTAX		   	SEQUENCE OF QsnmpTrapEntry
		ACCESS			not-accessible
		STATUS			mandatory
		DESCRIPTION		"A list of IP Address entries
					associated with traps."
		::= { qsnmp 3 }

   	qsnmpTrapEntry 		OBJECT-TYPE
		SYNTAX			QsnmpTrapEntry
		ACCESS			not-accessible
		STATUS			mandatory
		DESCRIPTION		"One entry in the table."
	        INDEX   { qsnmpTrapIndex }
   		::= { qsnmpTrapTable 1 }

	QsnmpTrapEntry ::=
		SEQUENCE {
		        qsnmpTrapIndex
		            INTEGER,
		        qsnmpTrapIpAddress
		            IpAddress
			}

-- SNMP Trap IP Address Entry fields
	qsnmpTrapIndex 		OBJECT-TYPE
		SYNTAX			INTEGER (0..4)
		ACCESS			read-only
		STATUS			mandatory
		DESCRIPTION		"A unique value which identifies each
					IP Address."
		::= { qsnmpTrapEntry 1 }

	qsnmpTrapIpAddress 	OBJECT-TYPE
		SYNTAX			IpAddress
		ACCESS			read-write
		STATUS			mandatory
		DESCRIPTION		"The IP Address of an IP entity, which
					is allowed to receive SNMP Trap
					events."
		::= { qsnmpTrapEntry 2 }

	qsnmpForwardTrap 	OBJECT-TYPE
		SYNTAX			INTEGER {
						enable (1),
						disable (2)
						}
		ACCESS			read-write
		STATUS			mandatory
		DESCRIPTION		"The flag which enables(1)/disables(2)
					SNMP Trap events to be transmitted."
		::= { qsnmp 4 }

-- QWES.com qproducts { oem 2 }
--
-- Each QWES.com product family is Assigned an Object Identifier.
-- This is the identifier stored in the MIB-II system group
-- item sysObjectID to identify the product to a network manager.
-- If product family specific items need to be defined they
-- should be defined in the appropriate product family subtree


-- QWES.com qslot { oem 3 }
--


-- QWES.com qFlowClass { oem 4 }
--
-- This group contains the definitions for all MIB objects used to
-- manage all traffic flow through Flow Classification, etc.  Chris
-- will expand.

-- ClassDefinition entry count

	qClassDefinitionMaxEntries 	OBJECT-TYPE
		SYNTAX			Counter
		ACCESS			read-only
		STATUS			mandatory
		DESCRIPTION		"The number of Class Definition
					entries."
		::= { qFlowClass 1 }

-- ClassDefinition table

   	qClassDefinitionTable	OBJECT-TYPE
		SYNTAX		   	SEQUENCE OF QClassDefinitionEntry
		ACCESS			not-accessible
		STATUS			mandatory
		DESCRIPTION		"A list of Class Definition entries.
					The number of entries is given by the
					value of qClassDefinitionMaxEntries."
		::= { qFlowClass 2 }

   	qClassDefinitionEntry 	OBJECT-TYPE
		SYNTAX			QClassDefinitionEntry
		ACCESS			not-accessible
		STATUS			mandatory
		DESCRIPTION		"One entry in the table."
	        INDEX   { qClassDefinitionIndex }
   		::= { qClassDefinitionTable 1 }

	QClassDefinitionEntry ::=
		SEQUENCE {
		        qClassDefinitionIndex
		            INTEGER,
		        qClassDefinitionAlias
		            DisplayString,
		        qClassDefinitionParentClassID
		            INTEGER,
		        qClassDefinitionFlowType
		            INTEGER,
		        qClassDefinitionSourceIPMask
		            OCTET STRING,
		        qClassDefinitionDestIPMask
		            IpAddress,
		        qClassDefinitionSourceIPLowerBound
		            IpAddress,
		        qClassDefinitionSourceIPUpperBound
		            IpAddress,
		        qClassDefinitionDestIPLowerBound
		            IpAddress,
		        qClassDefinitionDestIPUpperBound
		            IpAddress,
		        qClassDefinitionDSMask
		            INTEGER,
		        qClassDefinitionDSLowerBound
		            INTEGER,
		        qClassDefinitionDSUpperBound
		            INTEGER,
		        qClassDefinitionWellKnownApplication
		            INTEGER,
		        qClassDefinitionProtocol
		            INTEGER,
		        qClassDefinitionSourcePortLowerBound
		            INTEGER,
		        qClassDefinitionSourcePortUpperBound
		            INTEGER,
		        qClassDefinitionDestPortLowerBound
		            INTEGER,
		        qClassDefinitionDestPortUpperBound
		            INTEGER,
                        qClassDefinitionFlowAgingTime
		            INTEGER
		  }

-- Class Definition Entry fields
	qClassDefinitionIndex 	OBJECT-TYPE
		SYNTAX			INTEGER (2..1024)
		ACCESS			read-write
		STATUS			mandatory
		DESCRIPTION		"A unique value for each class
					definition. Values 0 and 1 are reserved
					for internal use."
		::= { qClassDefinitionEntry 1 }

	qClassDefinitionAlias 	OBJECT-TYPE
		SYNTAX			DisplayString (SIZE (0..255))
		ACCESS			read-write
		STATUS			optional
		DESCRIPTION		"A textual string containing user
					defined information about the Class
					Definition."
		::= { qClassDefinitionEntry 2 }

	qClassDefinitionParentClassID 	OBJECT-TYPE
		SYNTAX			INTEGER (0..1024)
		ACCESS			read-write
		STATUS			optional
		DESCRIPTION		"The qClassDefinitionIndex value of the
					parent for this Class Definition."
		::= { qClassDefinitionEntry 3 }

	qClassDefinitionFlowType 	OBJECT-TYPE
		SYNTAX			INTEGER {
						normal (1),
						dsingres (2),
						dsegress (3),
						dsnode (4),
						invalid (5)
						}
		ACCESS			read-write
		STATUS			mandatory
		DESCRIPTION		"The type of Class Definition being
					created.  INVALID causes the current
					Class Definition Entry to be removed."
		::= { qClassDefinitionEntry 4 }

	qClassDefinitionSourceIPMask 	OBJECT-TYPE
		SYNTAX			IpAddress
		ACCESS			read-write
		STATUS			optional
		DESCRIPTION		"The IP address mask for the source."
		::= { qClassDefinitionEntry 5 }

	qClassDefinitionSourceIPLowerBound 	OBJECT-TYPE
		SYNTAX			IpAddress
		ACCESS			read-write
		STATUS			optional
		DESCRIPTION		"The first source IP address which
					matches the class (after masking)."
		::= { qClassDefinitionEntry 6 }

	qClassDefinitionSourceIPUpperBound 	OBJECT-TYPE
		SYNTAX			IpAddress
		ACCESS			read-write
		STATUS			optional
		DESCRIPTION		"The last source IP address which
					matches the class (after masking)."
		::= { qClassDefinitionEntry 7 }

	qClassDefinitionDestIPMask 	OBJECT-TYPE
		SYNTAX			IpAddress
		ACCESS			read-write
		STATUS			optional
		DESCRIPTION		"The IP address mask for the
					destination."
		::= { qClassDefinitionEntry 8 }

	qClassDefinitionDestIPLowerBound 	OBJECT-TYPE
		SYNTAX			IpAddress
		ACCESS			read-write
		STATUS			optional
		DESCRIPTION		"The first destination IP address which
					matches the class (after masking)."
		::= { qClassDefinitionEntry 9 }

	qClassDefinitionDestIPUpperBound 	OBJECT-TYPE
		SYNTAX			IpAddress
		ACCESS			read-write
		STATUS			optional
		DESCRIPTION		"The last destination IP address which
					matches the class (after masking)."
		::= { qClassDefinitionEntry 10 }

	qClassDefinitionDSMask	OBJECT-TYPE
		SYNTAX			INTEGER (0..255)
		ACCESS			read-write
		STATUS			optional
		DESCRIPTION		"The DS/TOS byte mask value."
		::= { qClassDefinitionEntry 11 }

	qClassDefinitionDSLowerBound 	OBJECT-TYPE
		SYNTAX			INTEGER (0..255)
		ACCESS			read-write
		STATUS			optional
		DESCRIPTION		"The first DS/TOS byte value which
					matches the class (after masking)."
		::= { qClassDefinitionEntry 12 }

	qClassDefinitionDSUpperBound 	OBJECT-TYPE
		SYNTAX			INTEGER (0..255)
		ACCESS			read-write
		STATUS			optional
		DESCRIPTION		"The last DS/TOS byte value which
					matches the class (after masking)."
		::= { qClassDefinitionEntry 13 }

	qClassDefinitionWellKnownApplication OBJECT-TYPE
		SYNTAX			INTEGER {
						unspecified (0), -- none of the following:
								 -- following
						realaudio (1),
						netmeeting (2),
						echo (3),
						discard (4),
						rip (5),
						daytime (5),
						quoteofday (6),
						msp (7),
						ftp (8),
						telnet (9),
						smtp (10),
						msg (11),
						time (12),
						rap (13),
						rlp (14),
						whois (15),
						login (16),
						remotemail (17),
						xns (18),
						dns (19),
						sql (20),
						bootp (21),
						tftp (22),
						gopher (23),
						finger (24),
						http (25),
						kerberos (26),
						npp (27),
						hostname (28),
						isotsap (29),
						remotetelnet (30),
						sna (31),
						pop3 (32),
						rpc (33),
						authentication (34),
						audionews (35),
						sftp (36),
						uucp (37),
						networktime (38),
						pwdgen (39),
						ciscofna (40),
						ciscotna (41),
						ciscosys (42),
						netbios (43),
						news (44),
						management (45),
						send (46),
						appletalk (47),
						ipx (48),
						performancedata (49),
						ldap (50),
						novell (51),
						microsoft (52),
						doom (53),
						lotusnotes (54),
						audiomail (55),
						videomail (56),
						autodesk (57),
						ibm (58),
						vlsi (59),
						oracle (60),
						xwindows (61)
			               }
		ACCESS			read-write
		STATUS			mandatory
		DESCRIPTION		"The type of application to match."
		::= { qClassDefinitionEntry 14 }

	qClassDefinitionProtocol OBJECT-TYPE
		SYNTAX			INTEGER {
						all(0), -- any protocol matches
						udptcp(1), -- only udp and tcp
							   -- match
						udp(2),
						tcp(3),
						icmp(4),
						arp(5),
						rsvp(6),
						egp(7),
						ipinip(8),
						rdp(9),
						isotp4(10),
						idrp(11),
						pvp(12),
						isoip(13),
						vines(14),
						ttp(15),
						nsfnetigp(16),
						igrp(17),
						ospfigp(18)
			               }
		ACCESS			read-write
		STATUS			mandatory
		DESCRIPTION		"The IP protocol which matches the
					class."
		::= { qClassDefinitionEntry 15 }

	qClassDefinitionSourcePortLowerBound OBJECT-TYPE
		SYNTAX			INTEGER (0..65535)
		ACCESS			read-write
		STATUS			optional
		DESCRIPTION		"The first source UDP/TCP port which
					matches the class.  Only valid if
					qClassDefinitionWellKnownApplication =
					UNSPECIFIED, and
					qClassDefinitionProtocol = (ALL,
					UDPTCP, UDP, or TCP)."
		::= { qClassDefinitionEntry 16 }

	qClassDefinitionSourcePortUpperBound OBJECT-TYPE
		SYNTAX			INTEGER (0..65535)
		ACCESS			read-write
		STATUS			optional
		DESCRIPTION		"The last source UDP/TCP port which
					matches the class.  Only valid if
					qClassDefinitionWellKnownApplication =
					UNSPECIFIED, and
					qClassDefinitionProtocol = (ALL,
					UDPTCP, UDP, or TCP)."
		::= { qClassDefinitionEntry 17 }

	qClassDefinitionDestPortLowerBound OBJECT-TYPE
		SYNTAX			INTEGER (0..65535)
		ACCESS			read-write
		STATUS			optional
		DESCRIPTION		"The first dest UDP/TCP port which
					matches the class.  Only valid if
					qClassDefinitionWellKnownApplication =
					UNSPECIFIED, and
					qClassDefinitionProtocol = (ALL,
					UDPTCP, UDP, or TCP)."
		::= { qClassDefinitionEntry 18 }

	qClassDefinitionDestPortUpperBound OBJECT-TYPE
		SYNTAX			INTEGER (0..65535)
		ACCESS			read-write
		STATUS			optional
		DESCRIPTION		"The last dest UDP/TCP port which
					matches the class.  Only valid if
					qClassDefinitionWellKnownApplication =
					UNSPECIFIED, and
					qClassDefinitionProtocol = (ALL,
					UDPTCP, UDP, or TCP)."
		::= { qClassDefinitionEntry 19 }

        qClassDefinitionFlowAgingTime OBJECT-TYPE
		SYNTAX			INTEGER (0..65535)
		ACCESS			read-write
		STATUS			mandatory
		DESCRIPTION		"The number of seconds to use as the
					aging time for LIF related flow
					information."
		::= { qClassDefinitionEntry 20 }

-- qPolicyDefinitionMaxEntries entry count

	qPolicyDefinitionMaxEntries  OBJECT-TYPE
                SYNTAX			INTEGER (0..65535)
                ACCESS			read-write
		STATUS			mandatory
		DESCRIPTION		"The number of Policy Definition
					entries."

		::= { qFlowClass 3 }

-- qPolicyDefinition table

   	qPolicyDefinitionTable 		OBJECT-TYPE
		SYNTAX		   	SEQUENCE OF QPolicyDefinitionEntry
		ACCESS			not-accessible
		STATUS			mandatory
		DESCRIPTION		"A list of Policy Definition entries.
					The number of entries is given by the
					value of qPolicyDefinitionMaxEntries."
		::= { qFlowClass 4 }

   	qPolicyDefinitionEntry 		OBJECT-TYPE
		SYNTAX			QPolicyDefinitionEntry
		ACCESS			not-accessible
		STATUS			mandatory
DESCRIPTION ""
	        INDEX   { qPolicyDefinitionIndex }
   		::= { qPolicyDefinitionTable 1 }

	QPolicyDefinitionEntry ::=
		SEQUENCE {
		        qPolicyDefinitionIndex
		            INTEGER,
		        qPolicyDefinitionAlias
		            DisplayString,
		        qPolicyDefinitionType
		            INTEGER,
		        qPolicyDefinitionLP
		            INTEGER,
		        qPolicyDefinitionStartTime
		            TimeDateString,
		        qPolicyDefinitionEndTime
		            TimeDateString,
		        qPolicyDefinitionDayofWeek
		            INTEGER,
		        qPolicyDefinitionPipeID
		            INTEGER,
		        qPolicyDefinitionClassID
		            INTEGER,
		        qPolicyDefinitionChannelized
		            INTEGER,
		        qPolicyDefinitionOutboundDSValue
		            INTEGER,
		        qPolicyDefinitionPriority
		            INTEGER,
		        qPolicyDefinitionEvent
		            INTEGER
		  }

-- Policy Definition Entry fields
	qPolicyDefinitionIndex 	OBJECT-TYPE
		SYNTAX			INTEGER (2..1024)
		ACCESS			read-write
		STATUS			mandatory
		DESCRIPTION		"A unique value for each policy
					definition. Values 0 and 1 are
					reserved for internal use."
		::= { qPolicyDefinitionEntry 1 }

	qPolicyDefinitionAlias 	OBJECT-TYPE
		SYNTAX			DisplayString (SIZE (0..255))
		ACCESS			read-write
		STATUS			optional
		DESCRIPTION		"A textual string containing user
					defined information about the Policy
					Definition."
		::= { qPolicyDefinitionEntry 2 }

	qPolicyDefinitionType 	OBJECT-TYPE
		SYNTAX			INTEGER {
						normal (1), -- normal policy
						dsingress (2), -- diffserv
							       -- ingress node
						dsnode (3), -- diffserv node
						dsegress (4), -- diffserv egree
							      -- node
						discard (5), -- discard policy
							     -- ... all pdus go
							     -- into the bit
							     -- bucket
						delete (6) -- delete policy
							   -- descriptor
						}
		ACCESS			read-write
		STATUS			optional
		DESCRIPTION		"The type of Policy Definition. DELETE
					causes the current definition to be
					removed."
		::= { qPolicyDefinitionEntry 3 }

        qPolicyDefinitionLP     OBJECT-TYPE
		SYNTAX			INTEGER (0..1024)
		ACCESS			read-write
		STATUS			optional
		DESCRIPTION		"The logical interface this policy
					relates to."
		::= { qPolicyDefinitionEntry 4 }

	qPolicyDefinitionStartTime 	OBJECT-TYPE
		SYNTAX			TimeDateString
		ACCESS			read-write
		STATUS			optional
		DESCRIPTION		"The time of day this policy takes
					effect. NULL = always in effect."
		::= { qPolicyDefinitionEntry 5 }

	qPolicyDefinitionEndTime 	OBJECT-TYPE
		SYNTAX			TimeDateString
		ACCESS			read-write
		STATUS			optional
		DESCRIPTION		"The time of day this policy stops
					taking effect. NULL = always in
					effect."
		::= { qPolicyDefinitionEntry 6 }

	qPolicyDefinitionDayofWeek 	OBJECT-TYPE
		SYNTAX			INTEGER (0..255)
		ACCESS			read-write
		STATUS			optional
		DESCRIPTION		"Bit flags which indicate the day of
					week. Bit 0 = Monday, 1 = Tuesday,
					2 = Weds, 4 = Thurs, 8 = Fri, 16 = Sat,
					32 = Sun, 64 = Holidays."
		::= { qPolicyDefinitionEntry 7 }

	qPolicyDefinitionPipeID 	OBJECT-TYPE
		SYNTAX			INTEGER (0..1024)
		ACCESS			read-write
		STATUS			mandatory
		DESCRIPTION		"The pipe definition this policy
					references."
		::= { qPolicyDefinitionEntry 8 }

	qPolicyDefinitionClassID 	OBJECT-TYPE
		SYNTAX			INTEGER (0..1024)
		ACCESS			read-write
		STATUS			mandatory
		DESCRIPTION		"The class definition this policy
					references."
		::= { qPolicyDefinitionEntry 9 }

	qPolicyDefinitionChannelized 	OBJECT-TYPE
		SYNTAX			INTEGER (0..65535)
		ACCESS			read-write
		STATUS			optional
		DESCRIPTION		"Bit flags indicating which Classing range is used to create
					unique channels. 0 = off, 1 = Source IP, 2 = Dest IP
					4 = Source Port, 8 = Dest Port, 16 = Protocol, 32 = DS.
					The maximum number of channels (1-255) is set into the upper
					byte of this value. If a channel is selected, the default 
					maximum is 16."
		::= { qPolicyDefinitionEntry 10 }

	qPolicyDefinitionOutboundDSValue 	OBJECT-TYPE
		SYNTAX			INTEGER (0..256)
		ACCESS			read-write
		STATUS			optional
		DESCRIPTION		"The DS/TOS byte value to set in
					outbound PDUs. A value of 256 indicates
					no replacement."
		::= { qPolicyDefinitionEntry 11 }

	qPolicyDefinitionPriority 	OBJECT-TYPE
		SYNTAX			INTEGER (0..255)
		ACCESS			read-write
		STATUS			optional
		DESCRIPTION		"The relative priority of this policy."
		::= { qPolicyDefinitionEntry 12 }

	qPolicyDefinitionEvent OBJECT-TYPE
		SYNTAX			INTEGER {
						static (1), -- the policy is
							    -- always in effect.
						time (2), -- time of day.
						reducedbw (3), -- reduced
							       -- bandwidth on
							       -- lif/vcc.
						increasedbw (4) -- increased
								-- bandwidth on
								-- lif/vcc.
			               		}
		ACCESS			read-write
		STATUS			mandatory
		DESCRIPTION		"The type of event which causes this
					policy to come into effect."
		::= { qPolicyDefinitionEntry 13 }

-- qPipeDefinitionMaxEntries entry count

	qPipeDefinitionMaxEntries  OBJECT-TYPE
		SYNTAX			Counter
		ACCESS			read-only
		STATUS		   	mandatory
		DESCRIPTION		"The number of Pipe Definition
					entries."

		::= { qFlowClass 5 }

-- qPipeDefinition table

   	qPipeDefinitionTable 		OBJECT-TYPE
		SYNTAX		   	SEQUENCE OF QPipeDefinitionEntry
		ACCESS			not-accessible
		STATUS			mandatory
		DESCRIPTION		"A list of Pipe Definition entries. The
					number of entries is given by the value
					of qPipeDefinitionMaxEntries."
		::= { qFlowClass 6 }

   	qPipeDefinitionEntry 		OBJECT-TYPE
		SYNTAX				QPipeDefinitionEntry
		ACCESS				not-accessible
		STATUS				mandatory
DESCRIPTION ""
	        INDEX   { qPipeDefinitionIndex }
   		::= { qPipeDefinitionTable 1 }

	QPipeDefinitionEntry ::=
		SEQUENCE {
		        qPipeDefinitionIndex
		            INTEGER,
		        qPipeDefinitionAlias
		            DisplayString,
		        qPipeDefinitionType
		            INTEGER,
		        qPipeDefinitionCircuitID
		            INTEGER,
		        qPipeDefinitionBandwidth
		            INTEGER,
		        qPipeDefinitionPeak
		            INTEGER,
		        qPipeDefinitionMBS
		            INTEGER,
			qPipeDefinitionBufferAllocation
			    INTEGER,
		        qPipeDefinitionDelay
		            INTEGER,
			qPipeDefinitionPhyIdx
			    INTEGER,
			qPipeDefinitionPhyType
			    INTEGER
		  }

-- Pipe Definition Entry fields
	qPipeDefinitionIndex 	OBJECT-TYPE
		SYNTAX			INTEGER (2..1024)
		ACCESS			read-write
		STATUS			mandatory
		DESCRIPTION		"A unique value for each pipe
					definition. Values 0 and 1 are reserved
					for internal use."
		::= { qPipeDefinitionEntry 1 }

	qPipeDefinitionAlias 	OBJECT-TYPE
		SYNTAX			DisplayString (SIZE (0..255))
		ACCESS			read-write
		STATUS			optional
		DESCRIPTION		"A textual string containing user
					defined information about the Pipe
					Definition."
		::= { qPipeDefinitionEntry 2 }

	qPipeDefinitionType 	OBJECT-TYPE
		SYNTAX			INTEGER {
						valid (1), -- valid
						delete (2) -- delete pipe
							   -- definition
						}
		ACCESS			read-write
		STATUS			optional
		DESCRIPTION		"The type of Pipe Definition. DELETE
					causes the current definition to be
					removed."
		::= { qPipeDefinitionEntry 3 }

	qPipeDefinitionCircuitID OBJECT-TYPE
		SYNTAX			INTEGER (0..1024)
		ACCESS			read-write
		STATUS			optional
		DESCRIPTION		"The WAN circuit this pipe relates to."
		::= { qPipeDefinitionEntry 4 }

	qPipeDefinitionBandwidth OBJECT-TYPE
		SYNTAX			INTEGER
		ACCESS			read-write
		STATUS			optional
		DESCRIPTION		"The sustained bandwidth (bits/sec) of
					this pipe."
		::= { qPipeDefinitionEntry 5 }

	qPipeDefinitionPeak 	OBJECT-TYPE
		SYNTAX			INTEGER
		ACCESS			read-only
		STATUS			optional
		DESCRIPTION		"Peak bandwidth of this pipe
					(bits/sec).  Write-acces not supported
					in Release 1."
		::= { qPipeDefinitionEntry 6 }

	qPipeDefinitionMBS 	OBJECT-TYPE
		SYNTAX			INTEGER
		ACCESS			read-only
		STATUS			mandatory
		DESCRIPTION		"The maximum burst size (bytes).
					Write-acces not supported in Release
					1."
		::= { qPipeDefinitionEntry 7 }

        qPipeDefinitionBufferAllocation     OBJECT-TYPE
		SYNTAX			INTEGER
		ACCESS			read-write
		STATUS			mandatory
		DESCRIPTION		"The maximum queuing delay for this
					pipe."
		::= { qPipeDefinitionEntry 8 }

        qPipeDefinitionDelay     OBJECT-TYPE
		SYNTAX			INTEGER
		ACCESS			read-write
		STATUS			mandatory
		DESCRIPTION		"The maximum queuing delay for this
					pipe."
                ::= { qPipeDefinitionEntry 9 }

        qPipeDefinitionPhyIdx    OBJECT-TYPE
		SYNTAX			INTEGER
		ACCESS			read-only
		STATUS			mandatory
		DESCRIPTION		"The physical index for the port."
		::= { qPipeDefinitionEntry 10 }

	qPipeDefinitionPhyType 	OBJECT-TYPE
		SYNTAX			INTEGER
		ACCESS			read-only
		STATUS			mandatory
		DESCRIPTION		"The physical type for the port."
		::= { qPipeDefinitionEntry 11 }

-- Class Statistics table

   	qClassStatisticsTable 	OBJECT-TYPE
		SYNTAX		   	SEQUENCE OF QClassStatisticsEntry
		ACCESS			not-accessible
		STATUS			mandatory
		DESCRIPTION		"A list of Class Statistics entries.
					The number of entries is given by the
					value of qClassDefinitionMaxEntries."
		::= { qFlowClass 7 }

   	qClassStatisticsEntry 	OBJECT-TYPE
		SYNTAX			QClassStatisticsEntry
		ACCESS			not-accessible
		STATUS			mandatory
DESCRIPTION ""
	        INDEX   { qClassStatisticsIndex }
   		::= { qClassStatisticsTable 1 }

	QClassStatisticsEntry ::=
		SEQUENCE {
		        qClassStatisticsIndex
		            INTEGER,
		        qClassStatisticsAlias
		            DisplayString,
		        qClassStatisticsTransmittedCount
		            Counter,
		        qClassStatisticsDiscardCount
		            Counter,
		        qClassStatisticsFallbackCount
		            Counter
		  }

-- Class Statistics Entry fields
	qClassStatisticsIndex 	OBJECT-TYPE
		SYNTAX			INTEGER (0..1024)
		ACCESS			read-only
		STATUS			mandatory
		DESCRIPTION		"A unique value for each class stats
					entry. These match their corresponding
					Class Definition entry index."
		::= { qClassStatisticsEntry 1 }

	qClassStatisticsAlias 	OBJECT-TYPE
		SYNTAX			DisplayString
		ACCESS			read-only
		STATUS			mandatory
		DESCRIPTION		"A textual string containing user
					defined information about the Class
					Definition this stats entry relates
					to."
		::= { qClassStatisticsEntry 2 }

	qClassStatisticsTransmittedCount OBJECT-TYPE
		SYNTAX			Counter
		ACCESS			read-only
		STATUS			mandatory
		DESCRIPTION		"The number of bytes transmitted."
		::= { qClassStatisticsEntry 3 }

	qClassStatisticsDiscardCount OBJECT-TYPE
		SYNTAX			Counter
		ACCESS			read-only
		STATUS			mandatory
		DESCRIPTION		"The number of bytes discarded."
		::= { qClassStatisticsEntry 4 }

	qClassStatisticsFallbackCount	OBJECT-TYPE
		SYNTAX			Counter
		ACCESS			read-only
		STATUS			mandatory
		DESCRIPTION		"The number of bytes transmitted on the
					'all others' flow."
		::= { qClassStatisticsEntry 5 }


-- qatm group { oem 5 }
-- QWES.com atm circuit table { qatm 1 }
--
-- This group contains the definitions for all MIB objects used to
-- configure ATM circuits.

-- qatmCircuitTable table
   	qatmCircuitTable	OBJECT-TYPE
		SYNTAX			SEQUENCE OF QatmCircuitEntry
		ACCESS			not-accessible
		STATUS			mandatory
		DESCRIPTION		"A list of ATM circuit entries."
		::= { qatm 1 }

   	qatmCircuitEntry 	OBJECT-TYPE
		SYNTAX			QatmCircuitEntry
		ACCESS			not-accessible
		STATUS			mandatory
		DESCRIPTION		"One entry in the table."
	        INDEX   { qatmCircuitId }
   		::= { qatmCircuitTable 1 }

	QatmCircuitEntry ::=
		SEQUENCE {
		        qatmCircuitId
		            INTEGER,
		        qatmCircuitAlias
		            DisplayString,
		        qatmCircuitUNI
		            INTEGER,
		        qatmCircuitLogicalInterface
		            INTEGER,
		        qatmCircuitVpi
		            INTEGER,
		        qatmCircuitFirstVci
		            INTEGER,
				qatmCircuitMode
		            INTEGER,
				qatmCircuitStatus
		            INTEGER
		  }

-- ATM Circuit Entry fields
	qatmCircuitId 		OBJECT-TYPE
		SYNTAX			INTEGER (1..1024)
		ACCESS			read-write
		STATUS			mandatory
		DESCRIPTION		"A unique value for this circuit
					definition."
		::= { qatmCircuitEntry 1 }


	qatmCircuitAlias 		OBJECT-TYPE
		SYNTAX			DisplayString (SIZE (0..52))
		ACCESS			read-write
		STATUS			mandatory
		DESCRIPTION		"A unique alias for this circuit
					definition."
		::= { qatmCircuitEntry 2 }

	qatmCircuitUNI 	OBJECT-TYPE
		SYNTAX			INTEGER (1..1024)
		ACCESS			read-write
		STATUS			mandatory
		DESCRIPTION		"The UNI interface number for this
					circuit."
		::= { qatmCircuitEntry 3 }

	qatmCircuitLogicalInterface 	OBJECT-TYPE
		SYNTAX			INTEGER (2..1024)
		ACCESS			read-write
		STATUS			mandatory
		DESCRIPTION		"The LIF to assign this Circuit to. LIF
					1 is reserved as an Ethernet
					identifier."
		::= { qatmCircuitEntry 4 }

	qatmCircuitVpi 	OBJECT-TYPE
		SYNTAX			INTEGER (0..255)
		ACCESS			read-write
		STATUS			mandatory
		DESCRIPTION		"The Virtual Path Identifier for this
					circuit."
		::= { qatmCircuitEntry 5 }

	qatmCircuitFirstVci 	OBJECT-TYPE
		SYNTAX			INTEGER (0..255)
		ACCESS			read-write
		STATUS			mandatory
		DESCRIPTION		"The Virtual Path Identifier for this
					circuit."
		::= { qatmCircuitEntry 6 }

				
	qatmCircuitMode 	OBJECT-TYPE
		SYNTAX			INTEGER {
						cell (1),
						packet (2)
						}
		ACCESS			read-write
		STATUS			mandatory
		DESCRIPTION		"Determining the multiplexing mode for this connection."
		::= { qatmCircuitEntry 7 }

	qatmCircuitStatus 	OBJECT-TYPE
		SYNTAX			INTEGER {
						valid (1), -- the circuit is
							   -- valid
						deltete (2) -- delete the
							    -- circuit entry
						}
		ACCESS			read-write
		STATUS			mandatory
		DESCRIPTION		"Setting a value of 1 adds/modifies an
					entry. Setting a value of 2 deletes a
					current entry."
		::= { qatmCircuitEntry 8 }


-- ATM UNI table
   	qatmUniTable		OBJECT-TYPE
		SYNTAX			SEQUENCE OF QatmUniEntry
		ACCESS			not-accessible
		STATUS			mandatory
		DESCRIPTION		"This table contains the QWES.com
					proprietary configuration parameters
					for an ATM local Interface (UNI)."
		::= { qatm 2 }

   	qatmUniEntry 		OBJECT-TYPE
		SYNTAX			QatmUniEntry
		ACCESS			not-accessible
		STATUS			mandatory
		DESCRIPTION		"This list contains the QWES.com
					proprietary configuration
					parameters and state variables and is
					indexed by ifIndex values ATM
					interface."
		INDEX  {ifIndex}
   		::= { qatmUniTable 1 }

	QatmUniEntry ::=
		SEQUENCE {
		        qatmSpanPort
		            INTEGER,
		        qatmUniName
		            DisplayString,
		        qatmUniAlias
		            DisplayString,
		        qatmUniTrapStatus
		            INTEGER,
		        qatmUniMaxQueueDelay
		            INTEGER,
		        qatmUniMinAllocBuffer
		            INTEGER,
		        qatmUniSharedBuffer
		            INTEGER,
		        qatmUniLinkBandwidth
		            INTEGER,
		        qatmUniLinkDelay
		            INTEGER,
		        qatmUniBandwidthGranularity
		            INTEGER,
		        qatmUniIlmiStatus
		            INTEGER,
		        qatmUniRowStatus
		            INTEGER
		  }

-- ATM UNI Entry fields
	qatmSpanPort 	OBJECT-TYPE
		SYNTAX			INTEGER (0..25)
		ACCESS			read-write
		STATUS			mandatory
		DESCRIPTION		"The SPAN port  associates with
					this UNI."
		::= { qatmUniEntry 1 }

	qatmUniName 	OBJECT-TYPE
		SYNTAX			DisplayString (SIZE (0..255))
		ACCESS			read-write
		STATUS			mandatory
		DESCRIPTION		"Unique Name for this UNI."
		::= { qatmUniEntry 2 }

	qatmUniAlias 	OBJECT-TYPE
		SYNTAX			DisplayString (SIZE (0..255))
		ACCESS			read-write
		STATUS			mandatory
		DESCRIPTION		"A textual string containing user
					defined information about the UNI."
		::= { qatmUniEntry 3 }

	qatmUniTrapStatus	OBJECT-TYPE
		SYNTAX			INTEGER {
						enabled (1), 	
						disabled (2) 	
						}
		ACCESS			read-write
		STATUS			mandatory
		DESCRIPTION		"Indicates whether the Link Up/Link
					Down traps should be generated for this
					interface."
		::= { qatmUniEntry 4 }

	qatmUniMaxQueueDelay	OBJECT-TYPE
		SYNTAX			INTEGER
		ACCESS			read-write
		STATUS			mandatory
		DESCRIPTION		"xxxx"
		::= { qatmUniEntry 5 }

	qatmUniMinAllocBuffer	OBJECT-TYPE
		SYNTAX			INTEGER
		ACCESS			read-write
		STATUS			mandatory
		DESCRIPTION		"xxxx"
		::= { qatmUniEntry 6 }

	qatmUniSharedBuffer	OBJECT-TYPE
		SYNTAX			INTEGER
		ACCESS			read-write
		STATUS			mandatory
		DESCRIPTION		"xxxx"
		::= { qatmUniEntry 7 }

	qatmUniLinkBandwidth	OBJECT-TYPE
		SYNTAX			INTEGER
		ACCESS			read-write
		STATUS			mandatory
		DESCRIPTION		"xxxx"
		::= { qatmUniEntry 8 }

	qatmUniLinkDelay	OBJECT-TYPE
		SYNTAX			INTEGER
		ACCESS			read-write
		STATUS			mandatory
		DESCRIPTION		"xxxx"
		::= { qatmUniEntry 9 }

	qatmUniBandwidthGranularity	OBJECT-TYPE
		SYNTAX			INTEGER
		ACCESS			read-write
		STATUS			mandatory
		DESCRIPTION		"xxxx"
		::= { qatmUniEntry 10 }

	qatmUniIlmiStatus	OBJECT-TYPE
		SYNTAX INTEGER{
						enabled(1),
						disabled(2)
					  }
		ACCESS			read-write
		STATUS			mandatory
		DESCRIPTION		"Enable/Disable ILMI function for this UNI."
		::= { qatmUniEntry 11 }

	qatmUniRowStatus	OBJECT-TYPE
		SYNTAX 			RowStatus 
		ACCESS			read-write
		STATUS			mandatory
		DESCRIPTION		"This object is used to create, delete
            or modify a row in this table."
		::= { qatmUniEntry 12 }

-- qatmVplTable table
   	qatmVplTable		OBJECT-TYPE
		SYNTAX			SEQUENCE OF QatmVplEntry
		ACCESS			not-accessible
		STATUS			mandatory
		DESCRIPTION		"The Virtual Path Link (VPL) table."
		::= { qatm 3 }

   	qatmVplEntry 		OBJECT-TYPE
		SYNTAX			QatmVplEntry
		ACCESS			not-accessible
		STATUS			mandatory
		DESCRIPTION		"One entry in the table."
--		INDEX  {ifIndex, atmVplVpi }
		INDEX  {ifIndex, ifIndex }
   		::= { qatmVplTable 1 }

	QatmVplEntry ::=
		SEQUENCE {
		        qatmVplMaxVcc
		            INTEGER,
		        qatmVplLowestVci
		            INTEGER,
		        qatmVplMaxQueueDelay
		            INTEGER,
		        qatmVplReservedBuffer
		            INTEGER,
			qatmVplBwGranularity
		            INTEGER,
			qatmVplMtu
		            INTEGER,
		        qatmVplSharedBuffer
		            INTEGER
}

-- ATM VPL Entry fields
	qatmVplMaxVcc		OBJECT-TYPE
		SYNTAX			INTEGER (0..1024)
		ACCESS			read-write
		STATUS			mandatory
		DESCRIPTION		"The maximum number of VCCs initialized
					and active for this VPC.  If the value
					is 0, then this VPC is only for
					management purposes and is not assigned
					to a scheduler."
		::= { qatmVplEntry 1 }

	qatmVplLowestVci	OBJECT-TYPE
		SYNTAX			INTEGER	(0..65535)
		ACCESS			read-write
		STATUS			mandatory
		DESCRIPTION		"The start of a contiguous and
					increasing VCI range whose maximum is
					given by the maximum VCCs allowed."
		::= { qatmVplEntry 2 }

	qatmVplMaxQueueDelay	OBJECT-TYPE
		SYNTAX		 	INTEGER
		ACCESS		 	read-write
		STATUS		 	mandatory
		DESCRIPTION	 	"The maximum queueing delay in
					milliseconds (msec).  Combining this
					value with the sustained rate will
					determine the maximum buffering
					allowed."
		::= { qatmVplEntry 3 }

	qatmVplReservedBuffer	OBJECT-TYPE
		SYNTAX			INTEGER
		ACCESS			read-write
		STATUS			mandatory
		DESCRIPTION		"The minimum amount of buffering that
					this VCC will be allocated to use."
		::= { qatmVplEntry 4 }

	qatmVplBwGranularity	OBJECT-TYPE
		SYNTAX			INTEGER
		ACCESS			read-write
		STATUS			mandatory
		DESCRIPTION		"The bandwidth granularity can be apply
					to this VPC."
		::= { qatmVplEntry 5 }

	qatmVplMtu		OBJECT-TYPE
		SYNTAX			INTEGER
		ACCESS			read-write
		STATUS			mandatory
		DESCRIPTION		"The MTU size can be apply to this
					VPC."
		::= { qatmVplEntry 6 }

	qatmVplSharedBuffer	OBJECT-TYPE
		SYNTAX			INTEGER
		ACCESS			read-write
		STATUS			mandatory
		DESCRIPTION		"The amount of buffering to be assigned
					to a VPC for sharing on a First In
					First Out (FIFO) basis between flows on
					this VPC."
		::= { qatmVplEntry 7 }

-- qatmVclTable table
   	qatmVclTable		OBJECT-TYPE
		SYNTAX			SEQUENCE OF QatmVclEntry
		ACCESS			not-accessible
		STATUS			mandatory
		DESCRIPTION		"The Virtual Channel Link (VCL) table."
		::= { qatm 4 }

   	qatmVclEntry 		OBJECT-TYPE
		SYNTAX			QatmVclEntry
		ACCESS			not-accessible
		STATUS			mandatory
		DESCRIPTION		"One entry in the table."
--		INDEX  {ifIndex, atmVplVpi, atmVclVci }
		INDEX  {ifIndex, ifIndex, ifIndex }
   		::= { qatmVclTable 1 }

	QatmVclEntry ::=
		SEQUENCE {
		        qatmVclBwGranularity
		            INTEGER,
		        qatmVclMaxSubChannels
		            INTEGER,
		        qatmVclMaxQueueDelay
		            INTEGER,
		        qatmVclReservedBuffer
		            INTEGER,
		        qatmVclSharedBuffer
		            INTEGER
		  }

-- ATM VCL Entry fields
	qatmVclBwGranularity 	OBJECT-TYPE
		SYNTAX			INTEGER
		ACCESS			read-write
		STATUS			mandatory
		DESCRIPTION		"The bandwidth granularity can be apply
					to this VCC."
		::= { qatmVclEntry 1 }

	qatmVclMaxSubChannels 	OBJECT-TYPE
		SYNTAX			INTEGER	 (0..65535)
		ACCESS			read-write
		STATUS			mandatory
		DESCRIPTION		"The maximum number of sub-channels
					supported on this Virtual Circuit."
		::= { qatmVclEntry 2 }

	qatmVclMaxQueueDelay 	OBJECT-TYPE
		SYNTAX			INTEGER
		ACCESS			read-write
		STATUS			mandatory
		DESCRIPTION		"The maximum queueing delay in
					milliseconds (msec).  Combining this
					value with the sustained rate will
					determine the maximum buffering
					allowed."
		::= { qatmVclEntry 3 }

	qatmVclReservedBuffer 	OBJECT-TYPE
		SYNTAX			INTEGER
		ACCESS			read-write
		STATUS			mandatory
		DESCRIPTION		"The minimum reserved buffer in bytes
					that this VCC will be allocated to
					use."
		::= { qatmVclEntry 4 }

	qatmVclSharedBuffer	 OBJECT-TYPE
		SYNTAX			INTEGER
		ACCESS			read-write
		STATUS			mandatory
		DESCRIPTION		"The amount of buffering to be assigned
					to a VCC for sharing on a First In
					First Out (FIFO) basis between flows on
					this VCC."
		::= { qatmVclEntry 5 }

-- qatmAal5Table table
   	qatmAal5Table		OBJECT-TYPE
		SYNTAX			SEQUENCE OF QatmAal5Entry
		ACCESS			not-accessible
		STATUS			mandatory
		DESCRIPTION		"The ATM Adaptation Layer 5 (Aal5) table."
		::= { qatm 5 }

   	qatmAal5Entry 		OBJECT-TYPE
		SYNTAX			QatmAal5Entry
		ACCESS			not-accessible
		STATUS			mandatory
		DESCRIPTION		"One entry in the table."
		INDEX  {ifIndex}
   		::= { qatmAal5Table 1 }

	QatmAal5Entry ::=
		SEQUENCE {
		        qatmAal5Uni
		            INTEGER,
		        qatmAal5Aal5Name
		            DisplayString,
		        qatmAal5Aal5Alias
		            DisplayString,
		        qatmAal5AdminStatus
		            INTEGER,
		        qatmAal5TrapStatus
		            INTEGER,
		        qatmAal5MtuSize
		            INTEGER,
		        qatmAal5RowStatus
		            INTEGER
		  }

-- ATM Aal5 Entry fields
	qatmAal5Uni 	OBJECT-TYPE
  	    SYNTAX		INTEGER (1..25)	   
		ACCESS			read-write
		STATUS			mandatory
		DESCRIPTION		"The UNI port alias associates with
						this AAL5 interface."
		::= { qatmAal5Entry 1 }

	qatmAal5Aal5Name 	OBJECT-TYPE
		SYNTAX			DisplayString (SIZE (0..255))
		ACCESS			read-write
		STATUS			mandatory
		DESCRIPTION		"The AAL5 port name."
		::= { qatmAal5Entry 2 }

	qatmAal5Aal5Alias 	OBJECT-TYPE
		SYNTAX			DisplayString (SIZE (0..255))
		ACCESS			read-write
		STATUS			mandatory
		DESCRIPTION		"The alias for this AAL5 interface."
		::= { qatmAal5Entry 3 }

	qatmAal5AdminStatus 	OBJECT-TYPE
		SYNTAX INTEGER{
						up(1),	-- operation enabled
						down(2)	-- operation disabled
					  }
		ACCESS			read-write
		STATUS			mandatory
		DESCRIPTION		"The desired state for this interface."
		::= { qatmAal5Entry 4 }

	qatmAal5TrapStatus 	OBJECT-TYPE
		SYNTAX INTEGER{
						enabled(1),	-- operation enabled
						disabled(2)	-- operation disabled
					  }
		ACCESS			read-write
		STATUS			mandatory
		DESCRIPTION		"Indicates whether the Link Up/Link
						Down traps should be generated for this
						interface."
		::= { qatmAal5Entry 5 }

	qatmAal5MtuSize 	OBJECT-TYPE
  	    SYNTAX		INTEGER (1..65535)	   
		ACCESS			read-write
		STATUS			mandatory
		DESCRIPTION		"Set the largest PDU size for the AAL5 CPCS
						 layer that cen be processed by the AAL5 entity."
		::= { qatmAal5Entry 6 }

	qatmAal5RowStatus 	OBJECT-TYPE
  	    SYNTAX		INTEGER (1..6)	   
		ACCESS			read-write
		STATUS			mandatory
		DESCRIPTION		"Indicate the entry's status. 
						(1..5 = add) 6 = delete."
		::= { qatmAal5Entry 7 }


-- qatmTrafficDescriptorTable table
   	qatmTrafficDescriptorTable		OBJECT-TYPE
		SYNTAX			SEQUENCE OF QatmTrafficDescriptorEntry
		ACCESS			not-accessible
		STATUS			mandatory
		DESCRIPTION		"The TrafficDescriptor table."
		::= { qatm 6 }

   	qatmTrafficDescriptorEntry 		OBJECT-TYPE
		SYNTAX			QatmTrafficDescriptorEntry
		ACCESS			not-accessible
		STATUS			mandatory
		DESCRIPTION		"One entry in the table."
		INDEX  {ifIndex}
   		::= { qatmTrafficDescriptorTable 1 }

	QatmTrafficDescriptorEntry ::=
		SEQUENCE {
		        qatmTrafficDescriptorAlias
		            DisplayString
		  }

-- ATM TrafficDescriptor Entry fields
	qatmTrafficDescriptorAlias 	OBJECT-TYPE
		SYNTAX			DisplayString (SIZE (0..255))
		ACCESS			read-write
		STATUS			mandatory
		DESCRIPTION		"The alias for this traffic descriptor."
		::= { qatmTrafficDescriptorEntry 1 }

-- qatmTcTable table
   	qatmTcTable		OBJECT-TYPE
		SYNTAX			SEQUENCE OF QatmTcEntry
		ACCESS			not-accessible
		STATUS			mandatory
		DESCRIPTION		"The ATM TC table."
		::= { qatm 7 }

   	qatmTcEntry 		OBJECT-TYPE
		SYNTAX			QatmTcEntry
		ACCESS			not-accessible
		STATUS			mandatory
		DESCRIPTION		"One entry in the table."
		INDEX  {ifIndex}
   		::= { qatmTcTable 1 }

	QatmTcEntry ::=
		SEQUENCE {
		        qatmTcCellSync
		            INTEGER,
		        qatmTcPortErrors
		            INTEGER,
		        qatmTcDmaErrors
		            INTEGER,
		        qatmInvalidCells
		            INTEGER,
		        qatmCellsForInactiveVcc
		            INTEGER
		  }

-- ATM Tc Entry fields
	qatmTcCellSync 	OBJECT-TYPE
  	    SYNTAX		INTEGER	   
		ACCESS			read-only
		STATUS			mandatory
		DESCRIPTION		"The number of cell sync occurred on
						this Tc interface."
		::= { qatmTcEntry 1 }

	qatmTcPortErrors 	OBJECT-TYPE
  	    SYNTAX		INTEGER	   
		ACCESS			read-only
		STATUS			mandatory
		DESCRIPTION		"The number of errors received on
						this Tc interface."
		::= { qatmTcEntry 2 }
		        
	qatmTcDmaErrors 	OBJECT-TYPE
  	    SYNTAX		INTEGER	   
		ACCESS			read-only
		STATUS			mandatory
		DESCRIPTION		"The number of DMA errors received on
						this Tc interface."
		::= { qatmTcEntry 3 }
		        
	qatmInvalidCells 	OBJECT-TYPE
  	    SYNTAX		INTEGER	   
		ACCESS			read-only
		STATUS			mandatory
		DESCRIPTION		"The number of invalid cellls received on
						this Tc interface."
		::= { qatmTcEntry 4 }

	qatmCellsForInactiveVcc 	OBJECT-TYPE
  	    SYNTAX		INTEGER	   
		ACCESS			read-only
		STATUS			mandatory
		DESCRIPTION		"The number of  cellls received for an inactive Vcc."
		::= { qatmTcEntry 5 }


-- qatmAal5VccStatsTable table
   	qatmAal5VccStatsTable		OBJECT-TYPE
		SYNTAX			SEQUENCE OF QatmAal5VccStatsEntry
		ACCESS			not-accessible
		STATUS			mandatory
		DESCRIPTION		"The ATM AAL5 Vcc Statistics table."
		::= { qatm 8 }

   	qatmAal5VccStatsEntry 		OBJECT-TYPE
		SYNTAX			QatmAal5VccStatsEntry
		ACCESS			not-accessible
		STATUS			mandatory
		DESCRIPTION		"One entry in the table."
		INDEX  {ifIndex,ifIndex,ifIndex}
   		::= { qatmAal5VccStatsTable 1 }

	QatmAal5VccStatsEntry ::=
		SEQUENCE {
		        qatmAal5VccStatsInBytes
		            INTEGER,
		        qatmAal5VccStatsOutBytes
		            INTEGER,
		        qatmAal5VccStatsInSdus
		            INTEGER,
		        qatmAal5VccStatsOutSdus
		            INTEGER,
		        qatmAal5VccStatsErrsAndDiscards
		            INTEGER,
		        qatmAal5VccStatsLengthMismatchs
		            INTEGER,
		        qatmAal5VccStatsUserAborts
		            INTEGER,
		        qatmAal5VccStatsPoolDepleteds
		            INTEGER
		  }

-- ATM AAL5 VCC Entry fields
	qatmAal5VccStatsInBytes 	OBJECT-TYPE
  	    SYNTAX		INTEGER	   
		ACCESS			read-only
		STATUS			mandatory
		DESCRIPTION		"The number of bytes received by this AAL5 interface."
		::= { qatmAal5VccStatsEntry 1 }

	qatmAal5VccStatsOutBytes 	OBJECT-TYPE
  	    SYNTAX		INTEGER	   
		ACCESS			read-only
		STATUS			mandatory
		DESCRIPTION		"The number of bytes send by this AAL5 interface."
		::= { qatmAal5VccStatsEntry 2 }

	qatmAal5VccStatsInSdus 	OBJECT-TYPE
  	    SYNTAX			INTEGER	   
		ACCESS			read-only
		STATUS			mandatory
		DESCRIPTION		"The number of SDUs received by this AAL5 interface."
		::= { qatmAal5VccStatsEntry 3 }

	qatmAal5VccStatsOutSdus 	OBJECT-TYPE
  	    SYNTAX			INTEGER	   
		ACCESS			read-only
		STATUS			mandatory
		DESCRIPTION		"The number of SDUs send by this AAL5 interface."
		::= { qatmAal5VccStatsEntry 4 }

	qatmAal5VccStatsErrsAndDiscards 	OBJECT-TYPE
  	    SYNTAX			INTEGER	   
		ACCESS			read-only
		STATUS			mandatory
		DESCRIPTION		"The number of error and discard packets received by this AAL5 interface."
		::= { qatmAal5VccStatsEntry 5 }

	qatmAal5VccStatsLengthMismatchs 	OBJECT-TYPE
  	    SYNTAX			INTEGER	   
		ACCESS			read-only
		STATUS			mandatory
		DESCRIPTION		"The number of length mismatched packets received by this AAL5 interface."
		::= { qatmAal5VccStatsEntry 6 }

	qatmAal5VccStatsUserAborts 	OBJECT-TYPE
  	    SYNTAX			INTEGER	   
		ACCESS			read-only
		STATUS			mandatory
		DESCRIPTION		"The number of packets aborted by users."
		::= { qatmAal5VccStatsEntry 7 }

	qatmAal5VccStatsPoolDepleteds 	OBJECT-TYPE
  	    SYNTAX			INTEGER	   
		ACCESS			read-only
		STATUS			mandatory
		DESCRIPTION		"The number of packets aborted by users."
		::= { qatmAal5VccStatsEntry 8 }

-- qcraftPort group { oem 6 }
-- This group contains the MIB objects related to the craft port.

	qcpStatus OBJECT-TYPE
		SYNTAX		INTEGER
					{
					down(0),
					up(1)
				       }
		ACCESS		read-only
		STATUS		mandatory
		DESCRIPTION	""
                ::= { qcraftPort 1 }

	qcpBaudRate OBJECT-TYPE
		SYNTAX		INTEGER
					{
				       	br-1200(0),
				       	br-2400(1),
				       	br-4800(2),
				       	br-9600(3),
				       	br-14400(4),
				       	br-19200(5),
				       	br-28800(6),
				       	br-38400(7),
				       	br-57600(8),
				       	br-115200(9)
				       }
		ACCESS		read-write
		STATUS		mandatory
		DESCRIPTION	"The craft port command baud rate."
		::= { qcraftPort 2 }

	qcpStopBitLength OBJECT-TYPE
		SYNTAX		INTEGER
					{
				       	sb-1(0),
				       	sb-2(1)
				       }
		ACCESS		read-write
		STATUS		mandatory
		DESCRIPTION	""
                ::= { qcraftPort 3 }

	qcpParity OBJECT-TYPE
		SYNTAX		INTEGER
					{
				       	even(0),
				       	odd(1),
				       	none(2)
				       }
		ACCESS		read-write
		STATUS		mandatory
		DESCRIPTION	""
                ::= { qcraftPort 4 }

	qcpDataBits OBJECT-TYPE
		SYNTAX		INTEGER
					{
				       	db-7(0),
				       	db-8(1)
				       }
		ACCESS		read-write
		STATUS		mandatory
		DESCRIPTION	""
                ::= { qcraftPort 5 }

	qcpCharsSent OBJECT-TYPE
		SYNTAX		INTEGER
		ACCESS		read-write
		STATUS		mandatory
		DESCRIPTION	""
                ::= { qcraftPort 6 }

	qcpCharsReceived OBJECT-TYPE
		SYNTAX		INTEGER
		ACCESS		read-write
		STATUS		mandatory
		DESCRIPTION	""
                ::= { qcraftPort 7 }

--
--	qeventGroup { oem 8 }
--  This group contains the MIBs for the event logging.

	qEventConfigTable			OBJECT-TYPE
		SYNTAX			SEQUENCE OF QEventConfigEntry
		MAX-ACCESS		not-accessible
		STATUS			mandatory
		DESCRIPTION		"A list of Event System Configuration
 					Entries used for viewing / changing event
 					options"
		::= { qeventGroup 1 }				  

	qEventConfigEntry			OBJECT-TYPE
		SYNTAX			QEventConfigEntry
		MAX-ACCESS		not-accessible
		STATUS			mandatory
		DESCRIPTION		"One entry in the table"
		INDEX   { qEventConfigIndex }
		::= { qEventConfigTable 1 }

	QEventConfigEntry	 ::=	
		SEQUENCE	{
				qEventConfigIndex
					INTEGER,
				qEventSeverityType
					INTEGER,
				qLogFileType
					INTEGER,
				qLogOption
					INTEGER,
				qDisplayOption 
					INTEGER,
				qTrapOption
					INTEGER
			 	}

--  EVENT Configuration Entry fields
--
	qEventConfigIndex		OBJECT-TYPE
		SYNTAX			INTEGER (1..6)
		MAX-ACCESS		read-only
		STATUS			mandatory       
		DESCRIPTION		"A unique value for each event that has
 					  been logged into one of the Event Logs"
		::= { qEventConfigEntry 1 }

	qEventSeverityType 		OBJECT-TYPE
		SYNTAX			INTEGER {
						fatal(1),
						critical(2),
				       		mild(3),
						standard-snmp(4),
						informational(5),
						debug(6)
					}

		MAX-ACCESS		read-only
		STATUS			mandatory
		DESCRIPTION		"A unique value which identifies each
					Event Type (Severity)."
		DEFVAL { 4 }
		::= { qEventConfigEntry 2 }


	qLogFileType 			OBJECT-TYPE
		SYNTAX			INTEGER {
						alarm(1),
						system(2),
						none(3)
					}

		MAX-ACCESS		read-write
		STATUS			mandatory
		DESCRIPTION		"A unique value which allows the
					selection of the type of Log file
					to Log events into."
		DEFVAL { 2 }
		::= { qEventConfigEntry 3 }


	qLogOption 				OBJECT-TYPE
		SYNTAX			INTEGER {
						enable(1),
						disable(2)
					}

		MAX-ACCESS		read-write
		STATUS			mandatory
		DESCRIPTION		"A flag which enables(1)/disables(2) the 
					 logging feature of the Event Subsystem"
		DEFVAL { 2 }
		::= { qEventConfigEntry 4 }

	qDisplayOption 			OBJECT-TYPE
		SYNTAX			INTEGER {
						enable(1),
						disable(2)
					}
		MAX-ACCESS		read-write
		STATUS			mandatory
		DESCRIPTION		"A flag which enables(1)/disables(2) the 
					 display feature of the Event Subsystem"
		DEFVAL { 2 }
		::= { qEventConfigEntry 5 }



	qTrapOption 			OBJECT-TYPE
		SYNTAX			INTEGER {
						enable(1),
						disable(2)
					}
		MAX-ACCESS		read-write
		STATUS			mandatory
		DESCRIPTION			"A flag which enables(1)/disables(2) the 
					Send Trap feature of the Event Subsystem"
		DEFVAL { 2 }
		::= { qEventConfigEntry 6 }

--
-- Log Display MIBs:
--
	qEventSystemTable		OBJECT-TYPE
		SYNTAX			SEQUENCE OF QEventSystemEntry
		MAX-ACCESS		not-accessible
		STATUS			mandatory
		DESCRIPTION		"A list of Event Log Display
 					entries used for viewing the Logs."

		::= { qeventGroup 2 }				  

	qEventSystemEntry		OBJECT-TYPE
		SYNTAX			QEventSystemEntry     
		MAX-ACCESS		not-accessible
		STATUS			mandatory
		DESCRIPTION		"One entry in the table"
		INDEX   { qEventSystemIndex }
		::= { qEventSystemTable 1 }

			       
	QEventSystemEntry	 ::=	
		SEQUENCE	{
				qEventSystemIndex    
					INTEGER,
				qEventSystemDateTime
					DisplayString,
				qEventSystemType
					INTEGER,
				qEventSystemSubSystem
					INTEGER,
				qEventSystemID-Number
					INTEGER,
				qEventSystemDescription
					DisplayString
			 	}




	qEventSystemIndex		OBJECT-TYPE
		SYNTAX			INTEGER (0..255)
		MAX-ACCESS		read-only
		STATUS			mandatory
		DESCRIPTION		"A unique value for each event that has
					 been logged into one of the Event Logs"
		::= { qEventSystemEntry 1 }

	qEventSystemDateTime			OBJECT-TYPE
		SYNTAX			DisplayString
		MAX-ACCESS		read-only
		STATUS			mandatory
		DESCRIPTION		"The time of day an event occurs
					 SNMP Community."
		::= { qEventSystemEntry 2 }

	qEventSystemType		OBJECT-TYPE
		SYNTAX			INTEGER {
						fatal(1),
						critical(2),
						mild(3),
						standard-snmp(4),
						informational(5),
						debug(6)
					}
		MAX-ACCESS		read-only
		STATUS			mandatory
		DESCRIPTION		"This value will be used to identify the 
					  Event Type to be displayed"
		::= { qEventSystemEntry 3}

	qEventSystemSubSystem			OBJECT-TYPE
		SYNTAX			INTEGER {
						general-subsystem(1),
						ip-subsystem(2),
						atm-subsystem(3),
						ethernet-subsystem(4),
						tftp-subsystem(5),
						telnet-subsystem(6), 
						clip-subsystem(7), 
						flash-subsystem(8), 
						flow-subsystem(9), 
						serial-subsystem(10), 
						port-manager-subsystem(11),
						get-subsystem(12),   
						oam-subsystem(13),
						reset-subsystem(14), 
						time-subsystem(15),
						icmp-subsystem(16),
						igmp-subsystem(17),
						ping-subsystem(18),
						snmp-subsystem(19),
						tcp-subsystem(20),
						upd-subsystem(21),
						lp-subsystem(22),
						lif-subsystem(23),
						circuit-subsystem(24),
						arp-subsystem(25)
					}
		MAX-ACCESS		read-only
		STATUS			mandatory
		DESCRIPTION		"This value will be used to identify the 
					 Event Type to be displayed"
		::= { qEventSystemEntry 4}

	qEventSystemID-Number		OBJECT-TYPE
		SYNTAX			INTEGER 
		MAX-ACCESS		read-only
		STATUS			mandatory
		DESCRIPTION		"A unique value for each event that has
					 	been logged into one of the Event Logs"
		::= { qEventSystemEntry 5 }


	qEventSystemDescription			OBJECT-TYPE
		SYNTAX			DisplayString
		MAX-ACCESS		read-only
		STATUS			mandatory
		DESCRIPTION		"A textual string containing the
					 Description of the occurred Event."
		::= { qEventSystemEntry 6}
--
-- Log Alarm MIBs:
--
	qEventAlarmTable		OBJECT-TYPE
		SYNTAX			SEQUENCE OF QEventAlarmEntry
		MAX-ACCESS		not-accessible
		STATUS			mandatory
		DESCRIPTION		"A list of Event Log Display
 					entries used for viewing the Logs."

		::= { qeventGroup 3 }				  

	qEventAlarmEntry		OBJECT-TYPE
		SYNTAX			QEventAlarmEntry
		MAX-ACCESS		not-accessible
		STATUS			mandatory
		DESCRIPTION		"One entry in the table"
		INDEX   { qEventAlarmIndex }
		::= { qEventAlarmTable 1 }


	QEventAlarmEntry	 ::=	
		SEQUENCE	{
				qEventAlarmIndex
					INTEGER,
				qEventAlarmDateTime
					DisplayString,
				qEventAlarmType
					INTEGER,
				qEventAlarmSubSystem
					INTEGER,
				qEventAlarmID-Number
					INTEGER,
				qEventAlarmDescription
					DisplayString
			 	}




	qEventAlarmIndex		OBJECT-TYPE
		SYNTAX			INTEGER (0..255)
		MAX-ACCESS		read-only
		STATUS			mandatory
		DESCRIPTION		"A unique value for each event that has
					 been logged into one of the Event Logs"
		::= { qEventAlarmEntry 1 }

	qEventAlarmDateTime			OBJECT-TYPE
		SYNTAX			DisplayString
		MAX-ACCESS		read-only
		STATUS			mandatory
		DESCRIPTION		"The time of day an event occurs
					 SNMP Community."
		::= { qEventAlarmEntry 2 }

	qEventAlarmType				OBJECT-TYPE
		SYNTAX			INTEGER {
						fatal(1),
						critical(2),
						mild(3),
						standard-snmp(4),
						informational(5),
						debug(6)
					}

		MAX-ACCESS		read-only
		STATUS			mandatory
		DESCRIPTION		"This value will be used to identify the 
					  Event Type to be displayed"
		::= { qEventAlarmEntry 3}

	qEventAlarmSubSystem			OBJECT-TYPE
		 	SYNTAX		INTEGER {
						general-subsystem(1),
						ip-subsystem(2),
						atm-subsystem(3),
						ethernet-subsystem(4),
						tftp-subsystem(5),
						telnet-subsystem(6), 
						clip-subsystem(7), 
						flash-subsystem(8), 
						flow-subsystem(9), 
						serial-subsystem(10), 
						port-manager-subsystem(11),
						get-subsystem(12),   
						oam-subsystem(13),
						reset-subsystem(14), 
						time-subsystem(15),
						icmp-subsystem(16),
						igmp-subsystem(17),
						ping-subsystem(18),
						snmp-subsystem(19),
						tcp-subsystem(20),
						upd-subsystem(21),
						lp-subsystem(22),
						lif-subsystem(23),
						circuit-subsystem(24),
						arp-subsystem(25)
					}

		MAX-ACCESS		read-only
		STATUS			mandatory
		DESCRIPTION		"This value will be used to identify the 
					 Event Type to be displayed"
		::= { qEventAlarmEntry 4}
	qEventAlarmID-Number		OBJECT-TYPE
		SYNTAX			INTEGER 
		MAX-ACCESS		read-only
		STATUS			mandatory
		DESCRIPTION		"A unique value for each event that has
					 	been logged into one of the Event Logs"
		::= { qEventAlarmEntry 5 }


	qEventAlarmDescription			OBJECT-TYPE
		SYNTAX			DisplayString
		MAX-ACCESS		read-only
		STATUS			mandatory
		DESCRIPTION		"A textual string containing the
					 Description of the occurred Event."
		::= { qEventAlarmEntry 6}

-- QWES.com qextmib group { oem 9 }
-- This group contains the MIB objects provided by Phase2:
-- These groups are the extensions mib defined in qextmib
-- to be relative to an enterprise specific base.

    qipExt	OBJECT IDENTIFIER ::= {qextmib 1}
    qarpExt	OBJECT IDENTIFIER ::= {qextmib 2}
    qripExt	OBJECT IDENTIFIER ::= {qextmib 3}

-- the IP group

qipCircExtTable OBJECT-TYPE
	SYNTAX SEQUENCE OF QipCircExtEntry
	ACCESS not-accessible
	STATUS mandatory
        DESCRIPTION "Table of IP circuit parameters"
	::= {qipExt 1}

qipCircExtEntry OBJECT-TYPE
	SYNTAX QipCircExtEntry
	ACCESS not-accessible
	STATUS mandatory
	DESCRIPTION "A circuits IP parameters"
	INDEX {qipCircExtIndex}
	::= {qipCircExtTable 1}

QipCircExtEntry ::=
	SEQUENCE {
		qipCircExtIndex
			INTEGER,
		qipCircExtIfIndex
			INTEGER,
		qipCircExtAdminState
			INTEGER,
		qipCircExtOperState
			INTEGER
		}

qipCircExtIndex OBJECT-TYPE
	SYNTAX INTEGER
	ACCESS read-only
	STATUS mandatory
	DESCRIPTION "An index value which uniquely identifies
		this circuit within the router. This may or may
		not be related to the physical interface index."
	::= {qipCircExtEntry 1}

qipCircExtIfIndex OBJECT-TYPE
	SYNTAX INTEGER
	ACCESS read-only
	STATUS mandatory
	DESCRIPTION "An index value which uniquely identifies
		the local physical interface which this circuit
		uses. This value identifies the same interface
		identified by ifIndex in MIB-2."
	::= {qipCircExtEntry 2}

qipCircExtAdminState OBJECT-TYPE
	SYNTAX INTEGER{
			disabled(1),	-- operation disabled
			enabled(2)	-- operation enabled
		  }
	ACCESS read-write
	STATUS mandatory
	DESCRIPTION "Enable or disable the operation of IP
		on the specified interface."
	::= {qipCircExtEntry 3}

qipCircExtOperState OBJECT-TYPE
	SYNTAX INTEGER{
			off(1),	-- circuit not up
			on(2)	-- circuit up
		  }
	ACCESS read-only
	STATUS mandatory
	DESCRIPTION "The operational state of the circuit. May
		or may not be the same as administrative state."
	::= {qipCircExtEntry 4}

-- the ARP group

qarpExtTtl OBJECT-TYPE
	SYNTAX INTEGER
	ACCESS read-write
	STATUS mandatory
	DESCRIPTION "The lifetime of an ARP entry within the
		router."
	::= {qarpExt 1}

qarpCircExtTable OBJECT-TYPE
	SYNTAX SEQUENCE OF QarpCircExtEntry
	ACCESS not-accessible
	STATUS mandatory
	DESCRIPTION "Table of ARP circuit parameters"
	::= {qarpExt 2}

qarpCircExtEntry OBJECT-TYPE
	SYNTAX QarpCircExtEntry
	ACCESS not-accessible
	STATUS mandatory
	DESCRIPTION "A circuits ARP parameters"
	INDEX {qarpCircExtIndex}
	::= {qarpCircExtTable 1}

QarpCircExtEntry ::=
	SEQUENCE {
		qarpCircExtIndex
			INTEGER,
		qarpCircExtIfIndex
			INTEGER,
		qarpCircExtDoProxy
			INTEGER,
		qarpCircExtDoResp
			INTEGER
	}

qarpCircExtIndex OBJECT-TYPE
	SYNTAX INTEGER
	ACCESS read-only
	STATUS mandatory
	DESCRIPTION "An index value which uniquely identifies
		this circuit within the router. This may or may
		not be related to the physical interface index."
	::= {qarpCircExtEntry 1}

qarpCircExtIfIndex OBJECT-TYPE
	SYNTAX INTEGER
	ACCESS read-only
	STATUS mandatory
	DESCRIPTION "An index value which uniquely identifies
		the local physical interface which this circuit
		uses. This value identifies the same interface
		identified by ifIndex in MIB-2."
	::= {qarpCircExtEntry 2}

qarpCircExtDoProxy OBJECT-TYPE
	SYNTAX INTEGER{
			disabled(1),	-- operation disabled
			enabled(2)	-- operation enabled
		  }
	ACCESS read-write
	STATUS mandatory
	DESCRIPTION "Enable or disable ARP proxy responses
		on the specified interface."
	::= {qarpCircExtEntry 3}

qarpCircExtDoResp OBJECT-TYPE
	SYNTAX INTEGER{
			disabled(1),	-- operation disabled
			enabled(2)	-- operation enabled
		  }
	ACCESS read-only
	STATUS mandatory
	DESCRIPTION "Enable or disable the sending of ARP
		responses on specified circuit."
	::= {qarpCircExtEntry 4}

-- the RIP group

qripExtAdminState OBJECT-TYPE
	SYNTAX INTEGER{
			disabled(1),	-- operation disabled
			enabled(2)	-- operation enabled
		  }
	ACCESS read-write
	STATUS mandatory
	DESCRIPTION "Enable or disable the operation of RIP
		on all interfaces."
	::= {qripExt 1}

qripExtUpdateTime OBJECT-TYPE
	SYNTAX INTEGER
	ACCESS read-write
	STATUS mandatory
	DESCRIPTION "The time between transmission of RIP
		updates."
	::= {qripExt 2}

qripCircExtTable OBJECT-TYPE
	SYNTAX SEQUENCE OF QripCircExtEntry
	ACCESS not-accessible
	STATUS mandatory
	DESCRIPTION "Table of RIP circuit parameters"
	::= {qripExt 3}

qripCircExtEntry OBJECT-TYPE
	SYNTAX QripCircExtEntry
	ACCESS not-accessible
	STATUS mandatory
	DESCRIPTION "A circuits RIP parameters"
	INDEX {qripCircExtIndex}
	::= {qripCircExtTable 1}

QripCircExtEntry ::=
	SEQUENCE {
		qripCircExtIndex
			INTEGER,
		qripCircExtIfIndex
			INTEGER,
		qripCircExtTalk
			INTEGER,
		qripCircExtListen
			INTEGER,
		qripCircExtPoison
			INTEGER
	}

qripCircExtIndex OBJECT-TYPE
	SYNTAX INTEGER
	ACCESS read-only
	STATUS mandatory
	DESCRIPTION "An index value which uniquely identifies
		this circuit within the router. This may or may
		not be related to the physical interface index."
	::= {qripCircExtEntry 1}

qripCircExtIfIndex OBJECT-TYPE
	SYNTAX INTEGER
	ACCESS read-only
	STATUS mandatory
	DESCRIPTION "An index value which uniquely identifies
		the local physical interface which this circuit
		uses. This value identifies the same interface
		identified by ifIndex in MIB-2."
	::= {qripCircExtEntry 2}

qripCircExtTalk OBJECT-TYPE
	SYNTAX INTEGER{
			disabled(1),	-- operation disabled
			enabled(2)	-- operation enabled
		  }
	ACCESS read-write
	STATUS mandatory
	DESCRIPTION "Enable or disable RIP transmission
		on the specified interface."
	::= {qripCircExtEntry 3}

qripCircExtListen OBJECT-TYPE
	SYNTAX INTEGER{
			disabled(1),	-- operation disabled
			enabled(2)	-- operation enabled
		  }
	ACCESS read-write
	STATUS mandatory
	DESCRIPTION "Enable or disable RIP reception
		on the specified interface."
	::= {qripCircExtEntry 4}

qripCircExtPoison OBJECT-TYPE
	SYNTAX INTEGER{
			disabled(1),	-- operation disabled
			enabled(2)	-- operation enabled
		  }
	ACCESS read-write
	STATUS mandatory
	DESCRIPTION "Enable or disable operation of poison
		reverse on the specified interface. If poison
		is disabled, split-horzon operation is enabled."
	::= {qripCircExtEntry 5}


-- QWES.com Manufacturing Record  group
-- This group contains the MIB objects used to manage the Manufacturing
-- record.
-- Manufacturing Record group { oem 10 }
	qmrCheckSum OBJECT-TYPE
		SYNTAX		Counter
		ACCESS		read-only
		STATUS		mandatory
		DESCRIPTION	"The checksum of the manufacturing record."
		::= { qmanufactRecord 1 }

	qmrBurnDate OBJECT-TYPE
		SYNTAX		DisplayString
		ACCESS		read-only
		STATUS		mandatory
		DESCRIPTION	"The Date the manufacturing record was burned into flash."
		::= { qmanufactRecord 2 }

	qmrBurnTime OBJECT-TYPE
		SYNTAX		DisplayString
		ACCESS		read-only
		STATUS		mandatory
		DESCRIPTION	"The time the manufacturing record was burned into flash."
		::= { qmanufactRecord 3 }

	qmrOemName OBJECT-TYPE
		SYNTAX		DisplayString
		ACCESS		read-only
		STATUS		mandatory
		DESCRIPTION	"The OEM Name of the unit."
		::= { qmanufactRecord 4 }

	qmrOemID OBJECT-TYPE
		SYNTAX		Counter
		ACCESS		read-only
		STATUS		mandatory
		DESCRIPTION	"The OEM ID of the unit."
		::= { qmanufactRecord 5 }

	qmrSerialNumber OBJECT-TYPE
		SYNTAX		Counter
		ACCESS		read-only
		STATUS		mandatory
		DESCRIPTION	"The serial number of the unit."
		::= { qmanufactRecord 6 }

	qmrProductID OBJECT-TYPE
		SYNTAX		INTEGER
					{
				       	qwes-span(1)
				       }
		ACCESS		read-only
		STATUS		mandatory
		DESCRIPTION	"The product ID of the unit."
		::= { qmanufactRecord 7 }

	qmrModelID OBJECT-TYPE
		SYNTAX		INTEGER
					{
				       	prototype(1),
				       	rev3(2)
				       }
		ACCESS		read-only
		STATUS		mandatory
		DESCRIPTION	"The model ID of the unit."
		::= { qmanufactRecord 8 }

	qmrMacAddress OBJECT-TYPE
		SYNTAX		PhysAddress
		ACCESS		read-only
		STATUS		mandatory
		DESCRIPTION	"The MAC address of the unit."
		::= { qmanufactRecord 9 }

    qmrRepairTable OBJECT-TYPE
		SYNTAX		SEQUENCE OF QMrRepairEntry
		ACCESS		read-only
		STATUS		mandatory
		DESCRIPTION	"List of Repairs performed on the unit."
     	::= { qmanufactRecord 10 }

    qmrRepairEntry OBJECT-TYPE
		SYNTAX		QMrRepairEntry
		ACCESS		read-only
		STATUS		mandatory
		DESCRIPTION	"List of Repairs performed on the unit."
		INDEX		{
				 qmrRepType,
				 qmrRepCode
				 }
     	::= { qmrRepairTable 1 }

	QMrRepairEntry ::= SEQUENCE {
		qmrRepType		INTEGER,
		qmrRepCode		Counter,
		qmrRepDate		DisplayString,
		qmrRepTime		DisplayString
				    }

	qmrRepType OBJECT-TYPE
		SYNTAX		INTEGER
					{
				       	repair(1),
				       	eco(2)
				       }
		ACCESS		read-only
		STATUS		mandatory
		DESCRIPTION	"The Type of the repair."
		::= { qmrRepairEntry 1 }

	qmrRepCode OBJECT-TYPE
		SYNTAX	Counter
		ACCESS	read-only
		STATUS	mandatory
		DESCRIPTION
			"The code of the repair."
		::= {  qmrRepairEntry 2 }

	qmrRepDate OBJECT-TYPE
		SYNTAX		DisplayString
		ACCESS		read-only
		STATUS		mandatory
		DESCRIPTION	"The date of the repair."
		::= { qmrRepairEntry 3 }

	qmrRepTime OBJECT-TYPE
		SYNTAX		DisplayString
		ACCESS		read-only
		STATUS		mandatory
		DESCRIPTION	"The time of the repair."
		::= { qmrRepairEntry 4 }


-- QWES.com Ethernet group
-- This group contain the MIB objects used to configure the Ethernet Interface.
-- Ethernet group { oem 11 }

	qethernetCfgTable	OBJECT-TYPE
		SYNTAX		   	SEQUENCE OF QethernetCfgEntry
		ACCESS			not-accessible
		STATUS			mandatory
		DESCRIPTION		"A list of Ethernet Configuration
					entries.  The maximum number is based
					on the maximum interfaces."
		::= {qethernet 1}

   	qethernetCfgEntry 	OBJECT-TYPE
		SYNTAX			QethernetCfgEntry
		ACCESS			not-accessible
		STATUS			mandatory
		DESCRIPTION		"The Ethernet configuration information
					for each Ethernet interface."
		INDEX   { ifIndex }
   		::= { qethernetCfgTable 1 }

	QethernetCfgEntry ::=
		SEQUENCE {
		        qethernetMacAddress
		            PhysAddress,
		        qethernetSpeedMode
		            INTEGER,
		        qethernetEncapsulation
		            INTEGER,
			qethernetAutoSense
			    INTEGER,
			qethernetName
			    DisplayString
			}

	qethernetMacAddress	 OBJECT-TYPE
		SYNTAX			PhysAddress
		ACCESS			read-write
		STATUS			mandatory
		DESCRIPTION		"The ethernet's physical address.  An
					six byte hexidecimal identifier, which
					identifies the interface on the
					physical media."
		::= { qethernetCfgEntry 1 }

	qethernetSpeedMode 	OBJECT-TYPE
		SYNTAX			INTEGER {
						full-duplex-100-mbps (1),
						full-duplex-10-mbps (2),
						half-duplex-100-mbps (3),
						half-duplex-10-mbps (4)
						}
		ACCESS			read-write
		STATUS			mandatory
		DESCRIPTION		"The Ethernet chipset has five
					available modes: (1) 
					100-MBPS-FULL-DUPLEX - sets ethernet
					chipset to 100 mbps, full duplex mode;
					(2) 10-MBPS-FULL-DUPLEX - sets ethernet
					chipset to 10 mbps, full duplex mode;
					(3) 100-MBPS-HALF-DUPLEX - sets
					ethernet chipset to 100 mbps, half
					duplex mode; (4) 10-MBPS-HALF-DUPLEX -
					sets ethernet chipset to 10 mbps, half
					duplex mode."
		::= { qethernetCfgEntry 2 }

	qethernetEncapsulation 	OBJECT-TYPE
		SYNTAX			INTEGER {
						etherv2encap  (1),
						ieee8023encap (2)
						}
		ACCESS			read-write
		STATUS			mandatory
		DESCRIPTION		"The flag which sets the ethernets
					encapsulation type.  1 = Ethernet
					Version 2 encapsulation; 2 = IEEE 802.3
					encapsulation."
		::= { qethernetCfgEntry 3 }

	qethernetAutoSense	OBJECT-TYPE
        	SYNTAX 			INTEGER{ yes (1), no (2) }
        	ACCESS			read-write
		STATUS			mandatory
		DESCRIPTION		"This object is used to negotiate the
					speed/duplex.  The default is set to
					YES (1) - which negotiates from the
					configured speed/duplex
					(qethernetSpeedMode) or lower.  When
					set to NO (2) - this forces the
					configured speed/duplex mode and will
					not establish a link unless the other
					end complies."
		::= { qethernetCfgEntry 4 }

	qethernetName		OBJECT-TYPE
        	SYNTAX 			DisplayString (SIZE (0..255))
        	ACCESS			read-write
		STATUS			mandatory
		DESCRIPTION		"This object is used to???"
		::= { qethernetCfgEntry 5 }

	qethernetCurrentSpeedMode 	OBJECT-TYPE
		SYNTAX			INTEGER {
						full-duplex-100-mbps (1),
						full-duplex-10-mbps (2),
						half-duplex-100-mbps (3),
						half-duplex-10-mbps (4),
						no-link (5)
						}
		ACCESS			read-only
		STATUS			mandatory
		DESCRIPTION		"The Ethernet chipset has four
					available modes or operation: (1) 
					100-MBPS-FULL-DUPLEX - sets ethernet
					chipset to 100 mbps, full duplex mode;
					(2) 10-MBPS-FULL-DUPLEX - sets ethernet
					chipset to 10 mbps, full duplex mode;
					(3) 100-MBPS-HALF-DUPLEX - sets
					ethernet chipset to 100 mbps, half
					duplex mode; (4) 10-MBPS-HALF-DUPLEX -
					sets ethernet chipset to 10 mbps, half
					duplex mode.  This object will provide
					the current speed/duplex achieved or
					'No Link'."
		::= { qethernetCfgEntry 6 }


-- QWES.com DS1/E1 group
-- This group contains the MIB objects used to manage the DS1/E1 Interfaces.
-- DS1/E1 group { oem 12 }

	qds1AutoClockSourceSearching	OBJECT-TYPE
		SYNTAX			INTEGER	{ yes (1), no (2) }
		ACCESS			read-write
		STATUS			mandatory
		DESCRIPTION		"Selecting (1) YES will allow the
					Policy Point unit to automatically
					select the next available SPAN to
					provide clock if the Primary Clock
					Source fails.  Selecting (2) NO
					will instruct the unit to ignore all
					clock source ports except the primary
					source clock port."
		::= { qds1-e1 1 }

	qds1PrimaryClockSource	OBJECT-TYPE
		SYNTAX			INTEGER	{
					 	span-1 (2),
					 	span-2 (3),
					 	span-3 (4),
					 	span-4 (5),
					 	span-5 (6),
					 	span-6 (7)
						}
		ACCESS			read-write
		STATUS			mandatory
		DESCRIPTION		"Identifies the unit's primary clock
					source.  The first SPAN port - (2)
					SPAN-1; the second SPAN port - (3)
					SPAN-2; the third SPAN port  - (4)
					SPAN-3; the fourth SPAN port - (5)
					SPAN-4; the fifth SPAN port  - (6)
					SPAN-5; the sixth SPAN port  - (7)
					SPAN-6."
		::= { qds1-e1 2 }

	qds1PrimaryClockSourceAction	OBJECT-TYPE
		SYNTAX			INTEGER	{
					 	use-current-source (1),
					 	restore-to-primary-source (2)
						}
		ACCESS			read-write
		STATUS			mandatory
		DESCRIPTION		"Instructs the Span unit to (1)
					USE-CURRENT-SOURCE - stay with the
					current source clock, or (2)
					RETURN-TO-PRIMARY-SOURCE - restore the
					clock to the primary clock source."
		::= { qds1-e1 3 }

-- DS1/E1 Span Configuration Table
	qds1SpanCfgTable	OBJECT-TYPE
		SYNTAX		   	SEQUENCE OF Qds1SpanCfgEntry
		ACCESS			not-accessible
		STATUS			mandatory
		DESCRIPTION		"A list of Span Configuration entries.
					The maximum number is based on the
					maximum interfaces."
		::= {qds1-e1 4}

   	qds1SpanCfgEntry 	OBJECT-TYPE
		SYNTAX			Qds1SpanCfgEntry
		ACCESS			not-accessible
		STATUS			mandatory
		DESCRIPTION		"The DS1/E1 configuration information
					for each DS1/E1 interface."
		INDEX   { qds1LineCfgIndex }
   		::= { qds1SpanCfgTable 1 }

	Qds1SpanCfgEntry ::=
		SEQUENCE {
		        qds1LineCfgIndex
		            INTEGER,
		        qds1LineBuildOut
		            INTEGER,
		        qds1ClockSourceEligibility
		            INTEGER,
		        qds1ClockMode
		            INTEGER,
		        qds1PerformanceMonitor
		            INTEGER,
		        qds1Scrambler
		            INTEGER
			}

	qds1LineCfgIndex	OBJECT-TYPE
		SYNTAX			INTEGER
		ACCESS			read-only
		STATUS			mandatory
		DESCRIPTION		"A unique value which identifies a
					DS1/E1 interface.  This value 'should'
					be made equal to the ifIndex, however,
					this may not be the case, but will have
					an internal association with the
					ifEntry."
		::= { qds1SpanCfgEntry 1 }

	qds1LineBuildOut	OBJECT-TYPE
		SYNTAX			INTEGER{
					       	line-build-out-133-ft (1),
					       	line-build-out-266-ft (2),
					       	line-build-out-399-ft (3),
					       	line-build-out-533-ft (4),
					       	line-build-out-655-ft (5),
					       	line-build-out-n7-5db (6),
					       	line-build-out-n15db (7),
					       	line-build-out-n22-5db (8),
							not-applicable			(9)
					       }
		ACCESS			read-write
		STATUS			mandatory
		DESCRIPTION		"The Line Build Out specification for
					the DS1/E1 interface.  NOTE: (1)
					represents not only the
					LINE-BUILD-OUT-133-FT, but also 0 db
					CSU."
		::= { qds1SpanCfgEntry 2 }

	qds1ClockSourceEligibility	OBJECT-TYPE
		SYNTAX			INTEGER	{ 
						eligible (1),
						ineligible (2)
						}
		ACCESS			read-write
		STATUS			mandatory
		DESCRIPTION		"Identifies whether the DS1/E1
					interface is eligible to be the source
					clock or not."
		::= { qds1SpanCfgEntry 3 }

	qds1ClockMode			OBJECT-TYPE
		SYNTAX			INTEGER	{
						 slavetonetwork (1),
						 providemasterclock (2)
						 }
		ACCESS			read-write
		STATUS			mandatory
		DESCRIPTION		"Identifies the clock's mode of
					operation.  Setting the clock mode to
					(1) will allow the interface to act as
					the slave to the network clock, and
					setting the mode to (2) will allow the
					unit's interface to provide the master
					clock."
		::= { qds1SpanCfgEntry 4 }

	qds1PerformanceMonitor		OBJECT-TYPE
		SYNTAX			INTEGER	{ enable (1), disable (2) }
		ACCESS			read-write
		STATUS			optional
		DESCRIPTION		"Indicates whether or not performance
               				monitoring will be transmitted on this
					interface. ENABLE (1) will transmit the
					performance report according to the ANSI
					T1.403-1995 standard.  The performance
					report contains performance information
					for each of the four previous one-second
					intervals."
		::= { qds1SpanCfgEntry 5 }

	qds1Scrambler			OBJECT-TYPE
		SYNTAX			INTEGER	{ enable (1), disable (2) }
		ACCESS			read-write
		STATUS			optional
		DESCRIPTION		"Indicates whether or not scrambling
               				of data is being generated on this
					interface. ENABLE (1) will transmit the
					scrambled data according to the ITU-T
					0.191 Recommendation; DISABLE (2) will
					not scramble the data.  NOTE: A T1
					interface will NOT support scrambling,
					and therefore will be DISABLED."
		::= { qds1SpanCfgEntry 6 }

-- DS1/E1 Span Loopback Command/Configuration Table
	qds1SpanLoopBackCmdTable	OBJECT-TYPE
		SYNTAX		   	SEQUENCE OF Qds1SpanLoopBackCmdEntry
		ACCESS			not-accessible
		STATUS			mandatory
		DESCRIPTION		"A list of Span Loopback Configuration
					entries.  The maximum number is based
					on the maximum DS1/E1 interfaces."
		::= {qds1-e1 5}

   	qds1SpanLoopBackCmdEntry	OBJECT-TYPE
		SYNTAX			Qds1SpanLoopBackCmdEntry
		ACCESS			not-accessible
		STATUS			mandatory
		DESCRIPTION		"The DS1/E1 loopback configuration
					information for each DS1/E1 interface."
		INDEX   { qds1LineLoopbackIndex }
   		::= { qds1SpanLoopBackCmdTable 1 }

	Qds1SpanLoopBackCmdEntry ::=
		SEQUENCE {
		        qds1LineLoopbackIndex
		            INTEGER,
		        qds1LoopbackCommand
		            INTEGER,
		        qds1LoopbackDuration
		            INTEGER
			}

	qds1LineLoopbackIndex	OBJECT-TYPE
		SYNTAX			INTEGER
		ACCESS			read-only
		STATUS			mandatory
		DESCRIPTION		"A unique value which identifies DS1/E1
					interface.  This value should be made
					equal to the ifIndex."
		::= { qds1SpanLoopBackCmdEntry 1 }

	qds1LoopbackCommand	OBJECT-TYPE
		SYNTAX			INTEGER {
						activate (1),
						deactivate (2)
						}
		ACCESS			read-write
		STATUS			mandatory
		DESCRIPTION		"This object is used to (1) ACTIVATE
					the configured loopback on the selected
					interface (qds1LineIndex) of the
					specified entity.  If the dsx1OtherLoop
					(4) has been configured (see rfc2495 -
					dsx1LoopbackConfig), the supported
					loopback is the Local Port Loopback
					(LPL).  The Local Port Loopback is used
					to validate the ability to send and
					receive data to the local DS1/E1
					interface.  LPL will use OAM flow to
					verify data transfer.  Normal OAM flows
					are discontinued and an F4 OAM segment
					flow is automatically started on VPI=0,
					VCI=3 with a repeat timer of 1 second.
					When the loopback is set to (2)
					DEACTIVATE or comes to completion, the
					previous OAM configuration flows are
					restored."
						
		::= { qds1SpanLoopBackCmdEntry 2 }

	qds1LoopbackDuration	OBJECT-TYPE
		SYNTAX			INTEGER	(1..3600)
		ACCESS			read-write
		STATUS			mandatory
		DESCRIPTION		"The value indicates the duration (in
					SECONDS) that the Loopback will be in
					process."
		::= { qds1SpanLoopBackCmdEntry 3 }

-- DS1/E1 Span Loopback Statisics Table
	qds1SpanLoopBackStatsTable	OBJECT-TYPE
		SYNTAX		   	SEQUENCE OF Qds1SpanLoopBackStatsEntry
		ACCESS			not-accessible
		STATUS			mandatory
		DESCRIPTION		"A list of Span Loopback Statistics for
					each entries.  The maximum number is
					based on the maximum DS1/E1
					interfaces."
		::= {qds1-e1 6}

   	qds1SpanLoopBackStatsEntry	OBJECT-TYPE
		SYNTAX			Qds1SpanLoopBackStatsEntry
		ACCESS			not-accessible
		STATUS			mandatory
		DESCRIPTION		"The DS1/E1 loopback statistics
					information foreach DS1/E1 interface."
		INDEX   { qds1LineLoopbackStatIndex }
   		::= { qds1SpanLoopBackStatsTable 1 }

	Qds1SpanLoopBackStatsEntry ::=
		SEQUENCE {
		        qds1LineLoopbackStatIndex
		            INTEGER,
		        qds1OamSegmentSent
		            Counter,
		        qds1OamSegmentReceived
		            Counter,
		        qds1OamSegmentFailures
		            Counter,
				qds10amRunnigTime
					Counter
			}

	qds1LineLoopbackStatIndex	OBJECT-TYPE
		SYNTAX			INTEGER
		ACCESS			read-only
		STATUS			mandatory
		DESCRIPTION		"A unique value which identifies DS1/E1
					interface.  This value should be made
					equal to the ifIndex."
		::= { qds1SpanLoopBackStatsEntry 1 }

	qds1OamSegmentSent	OBJECT-TYPE
		SYNTAX			Counter
		ACCESS			read-only
		STATUS			mandatory
		DESCRIPTION		"The total number of segment OAM
					messages transmitted on the DS1/E1
					interface in question for the duration
					of the test." 
		::= { qds1SpanLoopBackStatsEntry 2 }

	qds1OamSegmentReceived	OBJECT-TYPE
		SYNTAX			Counter
		ACCESS			read-only
		STATUS			mandatory
		DESCRIPTION		"The total number of segment OAM
					messages received on the DS1/E1
					interface in question for the duration
					of the test." 
		::= { qds1SpanLoopBackStatsEntry 3 }

	qds1OamSegmentFailures	OBJECT-TYPE
		SYNTAX			Counter
		ACCESS			read-only
		STATUS			mandatory
		DESCRIPTION		"The total number of segment OAM
					messages timed out on the DS1/E1
					interface in question for the duration
					of the test." 
		::= { qds1SpanLoopBackStatsEntry 4 }

	qds10amRunnigTime	OBJECT-TYPE
		SYNTAX			Counter
		ACCESS			read-only
		STATUS			mandatory
		DESCRIPTION		"This is running time for the loop back." 
		::= { qds1SpanLoopBackStatsEntry 5 }

-- QWES.com Configuration Manager group
-- This group contains the MIB objects used to manage the Configuration
-- Manager.
-- Configuration Manager group { oem 13 }

	qcmSystemFile		OBJECT-TYPE
		SYNTAX			DisplayString (SIZE (0..20))
		ACCESS			read-write
		STATUS			mandatory
		DESCRIPTION				"The name of the configuration file to edit."
		::= { qconfigManager 1 }

	qcmConfigMaxEntries	OBJECT-TYPE
		SYNTAX			Counter
		ACCESS			read-only
		STATUS			mandatory
		DESCRIPTION		"The number of Configuration entries."
		::= { qconfigManager 2 }

-- Config Table
   	qcmConfigTable		 OBJECT-TYPE
		SYNTAX		 	SEQUENCE OF QcmConfigEntry
		ACCESS		 	not-accessible
		STATUS		 	mandatory
		DESCRIPTION				"A list of configuration file entries. The number of
							entries is given by the value of qcmConfigMaxEntries."
		::= { qconfigManager 3 }

   	qcmConfigEntry		 OBJECT-TYPE
		SYNTAX		 	QcmConfigEntry
		ACCESS		 	not-accessible
		STATUS		 	mandatory
DESCRIPTION ""
		INDEX		 	{qcmTableIndex}
   		::= { qcmConfigTable 1 }

	QcmConfigEntry ::=
		SEQUENCE {
		        qcmTableIndex
		            INTEGER,
		        qcmCurrentConfig
		            INTEGER,
		        qcmActionOnConfig
		            INTEGER,
		        qcmFileAlias
		            DisplayString,
		        qcmRelease
		            DisplayString,
		        qcmConfigFile
		            DisplayString,
		        qcmBootSequence
		            DisplayString,
		        qcmCreateDateTime
		            DisplayString,
		        qcmOperSchedDateTime
		            DisplayString
		  }

	qcmTableIndex 		 OBJECT-TYPE
		SYNTAX		 	INTEGER (1..65535)
		ACCESS		 	read-write
		STATUS		 	mandatory
		DESCRIPTION	 	"A unique value for each config file."
		::= { qcmConfigEntry 1 }

	qcmCurrentConfig	 OBJECT-TYPE
		SYNTAX					INTEGER {
					       	no(0),
					       	yes(1)
					       	}
		ACCESS			read-write
		STATUS			mandatory
		DESCRIPTION				"Flag that indicates if this record is the current operational configuration."
		::= { qcmConfigEntry 2 }

	qcmActionOnConfig 	OBJECT-TYPE
		SYNTAX					INTEGER {
					       	none(0),
					       	delete(1),
					       	activatenow(2),
					       	activatelater(3),
									save(4),
									saveas(5)
								}
		ACCESS					read-write
		STATUS					mandatory
		DESCRIPTION				"Operations that can be performed on the current table record."
		::= { qcmConfigEntry 3 }

	qcmFileAlias		OBJECT-TYPE
		SYNTAX			DisplayString (SIZE (0..20))
		ACCESS			read-write
		STATUS			mandatory
		DESCRIPTION				"The file alias name of the 'release' / 'configuration file' pair."
		::= { qcmConfigEntry 4 }

	qcmRelease		OBJECT-TYPE
		SYNTAX			DisplayString (SIZE (0..20))
		ACCESS			read-write
		STATUS			mandatory
		DESCRIPTION		"The name of the release file (executable)."
		::= { qcmConfigEntry 5 }

	qcmConfigFile		OBJECT-TYPE
		SYNTAX			DisplayString (SIZE (0..20))
		ACCESS			read-write
		STATUS			mandatory
		DESCRIPTION		"The name of the configuration file."
		::= { qcmConfigEntry 6 }

	qcmBootSequence		OBJECT-TYPE
		SYNTAX			DisplayString (SIZE (0..20))
		ACCESS			read-write
		STATUS			mandatory
		DESCRIPTION		"The boot sequence."
		::= { qcmConfigEntry 7 }

	qcmCreateDateTime	OBJECT-TYPE
		SYNTAX			DisplayString (SIZE (0..30))
		ACCESS			read-write
		STATUS			mandatory
		DESCRIPTION				"The creation date and time of the configuration file."
		::= { qcmConfigEntry 8 }

	qcmOperSchedDateTime	OBJECT-TYPE
		SYNTAX			DisplayString (SIZE (0..30))
		ACCESS			read-write
		STATUS			mandatory
		DESCRIPTION				"The date and time the configuration file became operational."
		::= { qcmConfigEntry 9 }
-- End of Config Table

-- Release Table
   	qcmReleaseTable		 OBJECT-TYPE
		SYNTAX		 	SEQUENCE OF QcmReleaseEntry
		ACCESS		 	not-accessible
		STATUS		 	mandatory
		DESCRIPTION	 	"A list of Release file entries."
		::= { qconfigManager 4 }

   	qcmReleaseEntry		 OBJECT-TYPE
		SYNTAX		 	QcmReleaseEntry
		ACCESS		 	not-accessible
		STATUS		 	mandatory
DESCRIPTION ""
		INDEX		 	{qcmReleaseIndex}
   		::= { qcmReleaseTable 1 }

	QcmReleaseEntry ::=
		SEQUENCE {
		        qcmReleaseIndex
		            INTEGER,
		        qcmReleaseName
		            DisplayString,
		        qcmReleaseVersion
		            INTEGER
		  }

	qcmReleaseIndex 	 OBJECT-TYPE
		SYNTAX		 	INTEGER (1..65535)
		ACCESS		 	read-only
		STATUS		 	mandatory
		DESCRIPTION	 	"A unique value for each Release file."
		::= { qcmReleaseEntry 1 }

	qcmReleaseName 		OBJECT-TYPE
		SYNTAX			DisplayString (SIZE (1..20))
		ACCESS			read-only
		STATUS			mandatory
		DESCRIPTION		"The name of a release file."
		::= { qcmReleaseEntry 2 }

	qcmReleaseVersion	OBJECT-TYPE
		SYNTAX			INTEGER (1..4294967295)
		ACCESS			read-only
		STATUS			mandatory
		DESCRIPTION		"The version of the release file."
		::= { qcmReleaseEntry 3 }
-- End of Release Table

-- Config Version Table
   	qcmConfigVerTable 	OBJECT-TYPE
		SYNTAX			SEQUENCE OF QcmConfigVerEntry
		ACCESS			not-accessible
		STATUS			mandatory
		DESCRIPTION		"A list of Config file entries."
		::= { qconfigManager 5 }

   	qcmConfigVerEntry   	 OBJECT-TYPE
		SYNTAX		 	QcmConfigVerEntry
		ACCESS		 	not-accessible
		STATUS		 	mandatory
DESCRIPTION ""
		INDEX		 	{qcmConfigVerIndex}
   		::= { qcmConfigVerTable 1 }

	QcmConfigVerEntry ::=
		SEQUENCE {
		        qcmConfigVerIndex
		            INTEGER,
		        qcmConfigName
		            DisplayString,
		        qcmConfigVersion
		            INTEGER,
		        qcmConfigWorkWithMin
		            INTEGER,
		        qcmConfigWorkWithMax
		            INTEGER
		  }

	qcmConfigVerIndex	 OBJECT-TYPE
		SYNTAX		 	INTEGER (1..65535)
		ACCESS		 	read-only
		STATUS		 	mandatory
		DESCRIPTION	 	"A unique value for each Config file."
		::= { qcmConfigVerEntry 1 }

	qcmConfigName 		 OBJECT-TYPE
		SYNTAX		 	DisplayString (SIZE (1..20))
		ACCESS		 	read-only
		STATUS		 	mandatory
		DESCRIPTION	 	"The name of a Config file."
		::= { qcmConfigVerEntry 2 }

	qcmConfigVersion	 OBJECT-TYPE
		SYNTAX		 	INTEGER (1..4294967295)
		ACCESS		 	read-only
		STATUS		 	mandatory
		DESCRIPTION	 	"The version of the Config file."
		::= { qcmConfigVerEntry 3 }

	qcmConfigWorkWithMin	 OBJECT-TYPE
		SYNTAX		 	INTEGER (1..4294967295)
		ACCESS		 	read-only
		STATUS		 	mandatory
		DESCRIPTION				"The minimum version of a Release file the Config file is compatable with."
		::= { qcmConfigVerEntry 4 }

	qcmConfigWorkWithMax	 OBJECT-TYPE
		SYNTAX		 	INTEGER (1..4294967295)
		ACCESS		 	read-only
		STATUS		 	mandatory
		DESCRIPTION				"The maximum version of a Release file the Config file is compatable with."
		::= { qcmConfigVerEntry 5 }
-- End of Config Version Table

	qcmWhichFile		OBJECT-TYPE
		SYNTAX					INTEGER
								{
					       	operational(0),
					       	base(1),
					       	new(2),
					       	default(3)
					       }
		ACCESS			read-write
		STATUS			mandatory
		DESCRIPTION				"Which file to do SNMP GETs and SETS on."
		::= { qconfigManager 6 }

	qcmUserBaseCfgFile	OBJECT-TYPE
		SYNTAX			DisplayString (SIZE (0..20))
		ACCESS			read-write
		STATUS			mandatory
		DESCRIPTION				"The name of the configuration file to edit."
		::= { qconfigManager 7 }

	qcmUserNewCfgFile 	OBJECT-TYPE
		SYNTAX			DisplayString (SIZE (0..20))
		ACCESS			read-write
		STATUS			mandatory
		DESCRIPTION				"The name of the new configuration file."
		::= { qconfigManager 8 }

	qcmUserFileAlias				OBJECT-TYPE
		SYNTAX					DisplayString (SIZE (0..20))
		ACCESS					read-write
		STATUS					mandatory
		DESCRIPTION				"The file alias of the system file."
		::= { qconfigManager 9 }

	qcmUserRelease 				OBJECT-TYPE
		SYNTAX					DisplayString (SIZE (0..20))
		ACCESS					read-write
		STATUS					mandatory
		DESCRIPTION				"The name of the release file."
		::= { qconfigManager 10 }

	qcmUserBootSequence			OBJECT-TYPE
		SYNTAX					DisplayString (SIZE (0..40))
		ACCESS					read-write
		STATUS					mandatory
		DESCRIPTION				"The boot sequence."
		::= { qconfigManager 11 }

	qcmUserDateTime				OBJECT-TYPE
		SYNTAX					DisplayString (SIZE (0..30))
		ACCESS					read-write
		STATUS					mandatory
		DESCRIPTION				"The date and time LDF is be scheduled."
		::= { qconfigManager 12 }

	qcmStartConfig 		OBJECT-TYPE
		SYNTAX			INTEGER {
									no(0),		-- do not start configuration
						yes(1) -- start configuration
						}
		ACCESS			read-write
		STATUS			mandatory
		DESCRIPTION		"Start the configuration process."
		::= { qconfigManager 13 }

	qcmStopConfig 		OBJECT-TYPE
		SYNTAX			INTEGER {
									no(0),		-- do not stop configuration
									yes(1)		-- stop and save configuration
								}
		ACCESS	   				read-write
		STATUS	   				mandatory
		DESCRIPTION				"Stop and Save the current configuration process."
		::= { qconfigManager 14 }

	qcmStartViewConfig 			OBJECT-TYPE
		SYNTAX					INTEGER {
									no(0),		-- do not start viewing a configuration file
									yes(1) 		-- start viewing a configuration file
								}
		ACCESS					read-write
		STATUS					mandatory
		DESCRIPTION				"Start viewing a configuration file."
		::= { qconfigManager 15 }

	qcmStopViewConfig 			OBJECT-TYPE
		SYNTAX					INTEGER {
									no(0),		-- do not stop viewing configuration file
									yes(1)		-- stop viewing configuration file
								}
		ACCESS					read-write
		STATUS					mandatory
		DESCRIPTION				"Stop viewing a configuration file."
		::= { qconfigManager 16 }

	qcmCancelConfig 	OBJECT-TYPE
		SYNTAX			INTEGER {
						 no(0),	-- do not start configuration
						 yes(1)	-- start configuration
						}
		ACCESS			read-write
		STATUS			mandatory
		DESCRIPTION				"Cancel the current configuration process."
		::= { qconfigManager 17 }


-- Port Group { oem 15 }
-- QWES.com LP table { qportManagement 1 }
--
-- This group contains the definitions for all MIB objects used to
-- configure an Logical Port (LP).

-- qwesLpTable table
   	qwesLpTable		OBJECT-TYPE
		SYNTAX			SEQUENCE OF QwesLpEntry
		ACCESS			not-accessible
		STATUS			mandatory
		DESCRIPTION		"A list of Logical Port entries."
		::= { qportManagement 1 }

   	qwesLpEntry 		OBJECT-TYPE
		SYNTAX			QwesLpEntry
		ACCESS			not-accessible
		STATUS			mandatory
		DESCRIPTION		"One entry in the table."
		INDEX   { ifIndex }
   		::= { qwesLpTable 1 }

	QwesLpEntry ::=
		SEQUENCE {
		        qwesLpName	 	DisplayString,
		        qwesLpAlias 		DisplayString,
		        qwesLpPhysicalInterface	INTEGER,
		        qwesLpDataLinkInterface	INTEGER,
		        qwesLpTrapStatus	INTEGER,
				qwesLpAdminStatus	INTEGER,
				qwesLpRowStatus	RowStatus
		  }

--
-- Logical Port Entry fields
--
   qwesLpName OBJECT-TYPE
       SYNTAX      DisplayString (SIZE (0..255))
       MAX-ACCESS  read-write
       STATUS      current
       DESCRIPTION
               "Display the name for the Logical Port."
       ::= { qwesLpEntry 1 }

   qwesLpAlias OBJECT-TYPE
       SYNTAX      DisplayString (SIZE (0..255))
       MAX-ACCESS  read-write
       STATUS      current
       DESCRIPTION
               "Enter an alias for the Logical Port Inteface name that has significant
               	to your organization."
       ::= { qwesLpEntry 2 }

	qwesLpPhysicalInterface OBJECT-TYPE
		SYNTAX			INTEGER (1..16)	-- See
						-- QWES-PHYSICAL-INTERFACE-MIN/MAX
		ACCESS			read-write
		STATUS			mandatory
		DESCRIPTION		"The physical port that this Logical
					Port associated."
		::= { qwesLpEntry 3 }

	qwesLpDataLinkInterface OBJECT-TYPE
		SYNTAX			INTEGER (25..88)-- See
						-- QWES-AAL5-INTERFACE-MIN/MAX
		ACCESS			read-write
		STATUS			mandatory
		DESCRIPTION		"The data link port that this Logical
					Port associated."
		::= { qwesLpEntry 4 }

	qwesLpTrapStatus 	OBJECT-TYPE
        SYNTAX  			INTEGER {
                   				yes(1), 
                   				no(2)
               					}
		ACCESS			read-write
		STATUS			mandatory
		DESCRIPTION		"Indicates whether the Link Up/Link
					Down traps should be generated for this
					interface."
		::= { qwesLpEntry 5 }

	qwesLpAdminStatus 	OBJECT-TYPE
        SYNTAX  			INTEGER {
                   				up(1), 
                   				down(2)
               					}
		ACCESS			read-write
		STATUS			mandatory
		DESCRIPTION		"The desired state of the interface set by management."
		::= { qwesLpEntry 6 }

	qwesLpRowStatus 	OBJECT-TYPE
        SYNTAX  			RowStatus
        ACCESS				read-write
		STATUS			mandatory
		DESCRIPTION		"This object is used to create a new
					row or modify or delete an existing row
					in this table."
		::= { qwesLpEntry 7 }


-- QWES.com LIF table { qportManagement 2 }
--
-- This group contains the definitions for all MIB objects used to
-- configure an Logical Interface (LIF).
-- qwesLifTable table
   	qwesLifTable		OBJECT-TYPE
		SYNTAX			SEQUENCE OF QwesLifEntry
		ACCESS			not-accessible
		STATUS			mandatory
		DESCRIPTION		"A list of Logical Interface entries."
		::= { qportManagement 2 }

   	qwesLifEntry 		OBJECT-TYPE
		SYNTAX			QwesLifEntry
		ACCESS			not-accessible
		STATUS			mandatory
		DESCRIPTION		"One entry in the table."
		INDEX   { ifIndex }
   		::= { qwesLifTable 1 }

	QwesLifEntry ::=
		SEQUENCE {
		        qwesLifName		DisplayString,
		        qwesLifAlias 		DisplayString,
		        qwesLifLpIndex		INTEGER,
		        qwesLifTrapStatus	INTEGER,
				qwesLifAdminStatus	INTEGER,
		        qwesLifRowStatus	RowStatus
		  }

--
-- Logical Inteface Entry fields
--
	qwesLifName		OBJECT-TYPE
		SYNTAX 			DisplayString (SIZE (0..255))
		MAX-ACCESS  		read-write
		STATUS      		current
		DESCRIPTION		"The name for the Logical Port."
		::= { qwesLifEntry 1 }

	qwesLifAlias		OBJECT-TYPE
		SYNTAX      		DisplayString (SIZE (0..255))
       		MAX-ACCESS  read-write
       		STATUS      current
       		DESCRIPTION		"The alias for the logical inteface
					name that has significant to your
					organization."
       		::= { qwesLifEntry 2 }

	qwesLifLpIndex		OBJECT-TYPE
       		SYNTAX      		INTEGER (257..512) -- See 
						-- QWES-LP-INTERFACE-MIN/MAX
		ACCESS			read-write
		STATUS			mandatory
		DESCRIPTION		"The logical port (LP) number that this
					logical interface has an association
					with."
		::= { qwesLifEntry 3 }

	qwesLifTrapStatus 	OBJECT-TYPE
        	SYNTAX  		INTEGER {
                   				yes(1), 
                   				no(2)
               					}
		ACCESS			read-write
		STATUS			mandatory
		DESCRIPTION		"Indicates whether the Link Up/Link
					Down traps should be generated for this
					interface."
		::= { qwesLifEntry 4 }

	qwesLifAdminStatus 	OBJECT-TYPE
        	SYNTAX  		INTEGER {
                   				up(1), 
                   				down(2)
               					}
		ACCESS			read-write
		STATUS			mandatory
		DESCRIPTION		"The desired state of the interface set by management."
		::= { qwesLifEntry 5 }

	qwesLifRowStatus 	OBJECT-TYPE
        	SYNTAX  		RowStatus
        	ACCESS			read-write
		STATUS			mandatory
		DESCRIPTION		"This object is used to create a new
					row or modify or delete an existing row
					in this table."
		::= { qwesLifEntry 6 }


-- QWES.com ATM ARP table { qportManagement 3 }
--
-- This group contains the definitions for all MIB objects used to
-- get an ATM ARP client entry.
-- qwesAtmArpTable table
   	qwesAtmArpTable		OBJECT-TYPE
		SYNTAX			SEQUENCE OF QWESLIFENTRY
		ACCESS			not-accessible
		STATUS			mandatory
		DESCRIPTION		"A list of ATM ARP entries."
		::= { qportManagement 3 }

   	qwesAtmArpEntry 		OBJECT-TYPE
		SYNTAX			QWESLIFENTRY
		ACCESS			not-accessible
		STATUS			mandatory
		DESCRIPTION		"One entry in the table."
		INDEX   { ifIndex }
   		::= { qwesAtmArpTable 1 }

	QWESLIFENTRY ::=
                SEQUENCE { qwesAtmArpLifIndex      INTEGER }

	qwesAtmArpLifIndex		OBJECT-TYPE
       	SYNTAX      	INTEGER
       	ACCESS			read-only
		STATUS			mandatory
		DESCRIPTION		"The logical interfacne (LIF) number that this
						 ATM ARP entry has an association with."
		::= { qwesAtmArpEntry 1 }


-- 
-- qmanagementGroup
--

	qSysTime			OBJECT-TYPE
		SYNTAX			DisplayString (SIZE (0..28))
		ACCESS			read-write
		STATUS			mandatory
		DESCRIPTION		"System Time in GMT."
		::= { qmanagementGroup 1 }

	qTftpType			OBJECT-TYPE
		SYNTAX			INTEGER 
		ACCESS			read-write
		STATUS			mandatory
		DESCRIPTION		"The file upload type. 1 = operational, 2 = config"
		::= { qmanagementGroup 2 }

	qTftpFileName		OBJECT-TYPE
		SYNTAX			DisplayString (SIZE (0..128))
		ACCESS			read-write
		STATUS			mandatory
		DESCRIPTION		"Local filename to download into. If it exists, it WILL be overwritten."
		::= { qmanagementGroup 3 }

	qTftpServerIpAddress	OBJECT-TYPE
		SYNTAX			IpAddress
		ACCESS			read-write
		STATUS			mandatory
		DESCRIPTION		"Server's IP address"
		::= { qmanagementGroup 4 }

 	qTftpServerFileName OBJECT-TYPE
		SYNTAX			DisplayString (SIZE (0..128))
		ACCESS			read-write
		STATUS			mandatory
		DESCRIPTION		"Server's filename to get"
		::= { qmanagementGroup 5 }

 	qTftpAdminStatus OBJECT-TYPE
		SYNTAX			INTEGER
		ACCESS			read-write
		STATUS			mandatory
		DESCRIPTION		"set to 1 to start TFTP download. 0 = ready for next download."
		::= { qmanagementGroup 6 }

 	qTftpOperStatus OBJECT-TYPE
		SYNTAX			INTEGER
		ACCESS			read-only
		STATUS			mandatory
		DESCRIPTION		"0=idle, 1=reading, 2=server IP error, 3=server filename error, 4 = done"
		::= { qmanagementGroup 7 }

 	qTftpRxCount OBJECT-TYPE
		SYNTAX			INTEGER
		ACCESS			read-only
		STATUS			mandatory
		DESCRIPTION		"Number of blocks received"
		::= { qmanagementGroup 8 }

	qTimeZone			OBJECT-TYPE
		SYNTAX     		INTEGER {
						   	eniwetok(1),
							samoa(2),
							hawaii(3),
							alaska(4),
							pacific(5),
							arizona(6),
							mountain(7),
							central(8),
							atlantic(9),
							newfoundland(10),
							buenos-aires(11),
							mid-atlantic(12),
							azores(13),
							gmt(14),
							paris(15),
							israel(16),
							moscow(17),
							tehran(18),
							abu-dhabi(19),
							islamabad(20),
							almaty(21),
							bangkok(22),
							beijing(23),
							tokyo(24),
							brisbane(25),
							new-caledonia(26),
							auckland(27)
						}
		ACCESS			read-write
		STATUS			mandatory
		DESCRIPTION		"Current time zone of the unit."
		::= { qmanagementGroup 9 }

-- QWES.com IP Port Group { qip 1 }
--
-- This group contains the definitions for all MIB objects used to
-- configure an IP Port.

-- qipPortTable table
   	qipPortTable		OBJECT-TYPE
		SYNTAX			SEQUENCE OF QWESIPENTRY
		ACCESS			not-accessible
		STATUS			mandatory
		DESCRIPTION		"A list of IP Port entries."
		::= { qip 1 }

   	qipPortEntry 		OBJECT-TYPE
		SYNTAX			QWESIPENTRY
		ACCESS			not-accessible
		STATUS			mandatory
		DESCRIPTION		"One entry in the table."
		INDEX   { qIpLp }
   		::= { qipPortTable 1 }

	QWESIPENTRY ::=
		SEQUENCE {
		        qIpLp	 	INTEGER,
		        qIpAddr     IpAddress,
		        qIpSubnet	IpAddress,
				qIpMulticast INTEGER,
				qIpRipStatus INTEGER,
				qIpArpTimeout INTEGER,
				qIpEncap     INTEGER
		  }
--
-- IP Port Entry fields
--
   qIpLp           OBJECT-TYPE
       SYNTAX      INTEGER
       MAX-ACCESS  read-write
       STATUS      current
       DESCRIPTION
               "The logical port number associated with this IP port."
       ::= { qipPortEntry 1 }

	qIpAddr 	        OBJECT-TYPE
		SYNTAX			IpAddress
		ACCESS			read-write
		STATUS			mandatory
		DESCRIPTION		"The IP address of this IP Port."
		::= { qipPortEntry 2 }

	qIpSubnet 	        OBJECT-TYPE
		SYNTAX			IpAddress
		ACCESS			read-write
		STATUS			mandatory
		DESCRIPTION		"The IP subnet ddress of this IP Port."
		::= { qipPortEntry 3 }

   qIpMulticast    OBJECT-TYPE
		SYNTAX     INTEGER {
					enable(1),
					disable(2)
					}
       MAX-ACCESS  read-write
       STATUS      current
       DESCRIPTION
               "Indicate whether or not multicast will be transmit on this interface."
       ::= { qipPortEntry 4 }

   qIpRipStatus    OBJECT-TYPE
		SYNTAX     INTEGER {
					enable(1),
					disable(2)
					}
       MAX-ACCESS  read-write
       STATUS      current
       DESCRIPTION
               "Indicate the RIP status."
       ::= { qipPortEntry 5 }

   qIpArpTimeout    OBJECT-TYPE
		SYNTAX      INTEGER
		MAX-ACCESS  read-write
       STATUS      current
       DESCRIPTION
               "The elapsed time of seconds before an ARP entry can be removed from the ARP table."
       ::= { qipPortEntry 6 }

   qIpEncap    OBJECT-TYPE
		SYNTAX     INTEGER {
					standard(1),
					hp(2)
					}
       MAX-ACCESS  read-write
       STATUS      current
       DESCRIPTION
               "Indicate the encapsulation type."
       ::= { qipPortEntry 7 }


-- Ip/Rip Port Group { oem 15 }
-- QWES.com RIP Port Group { qip 2 }
--
-- This group contains the definitions for all MIB objects used to
-- configure an RIP Port.

-- qRipPortTable table
   	qRipPortTable		OBJECT-TYPE
		SYNTAX			SEQUENCE OF QWESRIPENTRY
		ACCESS			not-accessible
		STATUS			mandatory
		DESCRIPTION		"A list of IP Port entries."
		::= { qip 2 }

   	qRipPortEntry 		OBJECT-TYPE
		SYNTAX			QWESRIPENTRY
		ACCESS			not-accessible
		STATUS			mandatory
		DESCRIPTION		"One entry in the table."
		INDEX   { qRipIpAddr }
   		::= { qRipPortTable 1 }

	QWESRIPENTRY ::=
		SEQUENCE {
                                qRipIpAddr                      IpAddress,        
                                qMode                           INTEGER,        
                                qAuthentication                 DisplayString,
				qSplitHorizon           	INTEGER,        
				qAdvertiseStaticRoutes		INTEGER,		
				qAdvertiseIntf			INTEGER,        
				qBroadcastType			INTEGER,        
				qHoldDownInterval		INTEGER,	    
				qUpdatesSend			INTEGER,        
				qUpdatesReceive			INTEGER,        
				qDefaultRouteMetric		INTEGER	    
                  }
--
-- RIP Port Entry fields
--
   qRipIpAddr              OBJECT-TYPE
        SYNTAX                  IpAddress
        ACCESS                  read-write
        STATUS                  mandatory
        DESCRIPTION             "The IP address associated with this RIP Port."
        ::= { qRipPortEntry 1 }

   qMode           OBJECT-TYPE
		SYNTAX     INTEGER {
                                        none (1),
                                        password (2),
                                        md5 (3)
					}
       MAX-ACCESS  read-write
       STATUS      current
       DESCRIPTION
               "Selects what type of rip authentication to be used on the selected port."
       DEFVAL { 1 }
       ::= { qRipPortEntry 2 }

   qAuthentication              OBJECT-TYPE
        SYNTAX                  DisplayString (SIZE (0..16))
        ACCESS                  read-write
        STATUS                  current
        DESCRIPTION             "This is the password to be used, when password type is selected for above authentication."
        ::= { qRipPortEntry 3 }

   qSplitHorizon   OBJECT-TYPE
		SYNTAX     INTEGER {
					poisoned-reverse(1),
					simple(2),
					disable (3)
					}
       MAX-ACCESS  read-write
       STATUS      current
       DESCRIPTION
               "."
       DEFVAL { 3 }
       ::= { qRipPortEntry 4 }

   qAdvertiseStaticRoutes   OBJECT-TYPE
		SYNTAX     INTEGER {
					yes(1),
					no(2)
					}
       MAX-ACCESS  read-write
       STATUS      current
       DESCRIPTION
               "."
       DEFVAL { 1 }
       ::= { qRipPortEntry 5 }

   qAdvertiseIntf   OBJECT-TYPE
		SYNTAX     INTEGER {
					yes(1),
					no(2)
					}
       MAX-ACCESS  read-write
       STATUS      current
       DESCRIPTION
               "."
       DEFVAL { 1 }
       ::= { qRipPortEntry 6 }

   qBroadcastType   OBJECT-TYPE
		SYNTAX     INTEGER {
					local(1),
					direct-with-ones(2),
					direct-with-zeros(3)
					}
       MAX-ACCESS  read-write
       STATUS      current
       DESCRIPTION
               "."
       DEFVAL { 1 }
       ::= { qRipPortEntry 7 }

   qHoldDownInterval   OBJECT-TYPE
	   SYNTAX     INTEGER(1..65535)
	   MAX-ACCESS  read-write
       STATUS      current
       DESCRIPTION
               "."
       DEFVAL { 60 }
       ::= { qRipPortEntry 8 }

   qUpdatesSend   OBJECT-TYPE
		SYNTAX     INTEGER {
					silent(1),
					version-1(2),
					rip-1-compatible(3),
					version-2(4),
					version-1-demand(5),
					version-2-demand(6)
					}
	   MAX-ACCESS  read-write
       STATUS      current
       DESCRIPTION
           "What the router sends on this interface.
           ripVersion1 implies sending RIP updates compliant
           with  RFC  1058.   rip1Compatible implies
           broadcasting RIP-2 updates using RFC 1058 route
           subsumption rules.  ripVersion2 implies
           multicasting RIP-2 updates.  ripV1Demand indicates
           the use of Demand RIP on a WAN interface under RIP
           Version 1 rules.  ripV2Demand indicates the use of
           Demand RIP on a WAN interface under Version 2 rules."
       DEFVAL { 2 }
       ::= { qRipPortEntry 9 }

   qUpdatesReceive   OBJECT-TYPE
		SYNTAX     INTEGER {
					rip1(1),
					rip2(2),
					rip1-or-rip2(3),
					none(3)
					}
	   MAX-ACCESS  read-write
       STATUS      current
       DESCRIPTION
           "This indicates which version of RIP updates
           are to be accepted.  Note that rip2 and
           rip1OrRip2 implies reception of multicast
           packets."
       DEFVAL { 3 }
       ::= { qRipPortEntry 10 }

   qDefaultRouteMetric   OBJECT-TYPE
		SYNTAX     INTEGER(1..15)
		MAX-ACCESS  read-write
       STATUS      current
       DESCRIPTION
           "This variable indicates the metric that is to
           be used for the default route entry in RIP updates
           originated on this interface.  A value of zero
           indicates that no default route should be
           originated; in this case, a default route via
           another router may be propagated."
       DEFVAL { 1 }
       ::= { qRipPortEntry 11 }


-- Ip Static Arp Group { oem 15 }
-- QWES.com Static ARP Group { qip 3 }
--
-- This group contains the definitions for all MIB objects used to
-- configure an static ARP entry.

-- qStaticArpTable table
   	qStaticArpTable		OBJECT-TYPE
		SYNTAX			SEQUENCE OF QWESSTATICARPENTRY
		ACCESS			not-accessible
		STATUS			mandatory
		DESCRIPTION		"A list of Static ARP entries."
		::= { qip 3 }

   	qStaticArpEntry 		OBJECT-TYPE
		SYNTAX			QWESSTATICARPENTRY
		ACCESS			not-accessible
		STATUS			mandatory
		DESCRIPTION		"One entry in the table."
		INDEX   { qStaticArpAddr }
   		::= { qStaticArpTable 1 }

	QWESSTATICARPENTRY ::=
		SEQUENCE {
		        qStaticArpAddr    IpAddress,        
				qLif			  INTEGER,        
				qPhysType		  INTEGER,        
				qMacAddr		  PhysAddress,
				qType			  INTEGER
		  }
--
-- Static Arp Entry fields
--
	qStaticArpAddr 	        OBJECT-TYPE
		SYNTAX			IpAddress
		ACCESS			read-write
		STATUS			mandatory
		DESCRIPTION		"The IP address associated with this ARP entry."
		::= { qStaticArpEntry 1 }

   qLif           OBJECT-TYPE
		SYNTAX     INTEGER(513..1536)
		MAX-ACCESS  read-write
       	STATUS      mandatory
       	DESCRIPTION
               "The Logical Interface which uniquely identifies the local 
                interface which this ARP entry can be reached."
       ::= { qStaticArpEntry 2 }

   qPhysType   OBJECT-TYPE
	   SYNTAX	INTEGER {
				ethernet(1),
				atm-and-others(2)
				}
		MAX-ACCESS  read-write
       	STATUS      mandatory
       	DESCRIPTION
               "The physical interface type associated with this ARP entry."
       ::= { qStaticArpEntry 3 }

   qMacAddr   OBJECT-TYPE
	   SYNTAX      PhysAddress
	   MAX-ACCESS  read-write
       STATUS      mandatory
       DESCRIPTION
               "The physical address associated with this ARP entry."
       ::= { qStaticArpEntry 4 }

   qType   OBJECT-TYPE
	   SYNTAX	INTEGER {
				add-activate(1),
				add-not-activate(2),
				delete(3)
				}
		MAX-ACCESS  read-write
       	STATUS      mandatory
       	DESCRIPTION
               "Defines the ARP entry current status. Setting this entry to invalid(2)
               has the effect of invalidating the correspding entry in the ARP table.
               Setting this entry to valid(1) has the effect of installing the entry
               in the ARP table and make it active."
       ::= { qStaticArpEntry 5 }

--
-- IP Node Parameters
--
      qipTtl OBJECT-TYPE
          SYNTAX  INTEGER
          ACCESS  read-write
          STATUS  mandatory
          DESCRIPTION
              "The time-to-live (in seconds) that a packet can live in  
              the network."
	      DEFVAL { 60 }
          ::= { qip 4 }

      qipRoutePriority OBJECT-TYPE
          SYNTAX  INTEGER {
					rip(1),
					static(2)
				}
          ACCESS  read-write
          STATUS  mandatory
          DESCRIPTION
              "The route priority indicates routing entry precedence in the system.
               If RIP is selected, then all routing entries learned by RIP will have
               higher priority then other entries.  Also, if STATIC is selected, then
               all routing entries which are static defined will have higher priority
               then other entries."
	      DEFVAL { 1 }
          ::= { qip 5 }

      qipRipStatus OBJECT-TYPE
          SYNTAX  INTEGER {
					enable(1),
					disable(2)
				}
          ACCESS  read-write
          STATUS  mandatory
          DESCRIPTION
              "The RIP system flag."
	      DEFVAL { 1 }
          ::= { qip 6 }

      qigmpInMsgs OBJECT-TYPE
          SYNTAX  INTEGER 
          ACCESS  read-only
          STATUS  mandatory
          DESCRIPTION
              "Messages received by the system."
          ::= { qigmp 1 }

      qigmpOutMsgs OBJECT-TYPE
          SYNTAX  INTEGER 
          ACCESS  read-only
          STATUS  mandatory
          DESCRIPTION
              "Messages transmitted  by the system."
          ::= { qigmp 2 }

      qigmpInErrors OBJECT-TYPE
          SYNTAX  INTEGER 
          ACCESS  read-only
          STATUS  mandatory
          DESCRIPTION
              "Error messages received  by the system."
          ::= { qigmp 3 }

      qigmpInReports OBJECT-TYPE
          SYNTAX  INTEGER 
          ACCESS  read-only
          STATUS  mandatory
          DESCRIPTION
              "Reported messages received  by the system."
          ::= { qigmp 4 }

      qigmpInQueries OBJECT-TYPE
          SYNTAX  INTEGER 
          ACCESS  read-only
          STATUS  mandatory
          DESCRIPTION
              "Querries received  by the system."
          ::= { qigmp 5 }

      qigmpInUnknownType OBJECT-TYPE
          SYNTAX  INTEGER 
          ACCESS  read-only
          STATUS  mandatory
          DESCRIPTION
              "Unkown messages received  by the system."
          ::= { qigmp 6 }

-- QWES.com Static IGMP Group
--
-- This group contains the definitions for all MIB objects used to
-- configure an static IGMP entry.

-- qIgmpStaticTable table
   	qIgmpStaticTable	OBJECT-TYPE
		SYNTAX			SEQUENCE OF QWESSTATICIGMPENTRY
		ACCESS			not-accessible
		STATUS			mandatory
		DESCRIPTION		"A list of Static IGMP entries."
		::= { qigmp 7 }

   	qIgmpStaticEntry	OBJECT-TYPE
		SYNTAX			QWESSTATICIGMPENTRY
		ACCESS			not-accessible
		STATUS			mandatory
		DESCRIPTION		"One entry in the table."
		INDEX   { qIgmpStaticAddr }
   		::= { qIgmpStaticTable 1 }

	QWESSTATICIGMPENTRY ::=
		SEQUENCE {
		        qIgmpStaticAddr    IpAddress,        
				qIgmpLp     	   INTEGER,        
				qIgmpType		   INTEGER
		  }
--
-- Static Igmp Entry fields
--
	qIgmpStaticAddr		OBJECT-TYPE
		SYNTAX			IpAddress
		ACCESS			read-write
		STATUS			mandatory
		DESCRIPTION		"The IP address associated with this IGMP entry."
		::= { qIgmpStaticEntry 1 }

   qIgmpLp			OBJECT-TYPE
       SYNTAX		INTEGER
       MAX-ACCESS	read-write
       STATUS		current
       DESCRIPTION
               "The logical port number associated with this IP port."
       ::= { qIgmpStaticEntry 2 }

   qIgmpType    OBJECT-TYPE
	   SYNTAX	INTEGER {
				add-activate(1),
				add-not-activate(2),
				delete(3)
				}
		MAX-ACCESS  read-write
       	STATUS      current
       	DESCRIPTION
               "Defines the IGMP entry current status. Setting this entry to invalid(2)
               has the effect of invalidating the correspding entry in the IGMP table.
               Setting this entry to valid(1) has the effect of installing the entry
               in the IGMP table and make it active."
       ::= { qIgmpStaticEntry 3 }

-- QWES.com IGMP Group
--
-- This group contains the definitions for all MIB objects used to
-- configure an IGMP group.

-- qIgmpGroupTable table
   	qIgmpGroupTable	OBJECT-TYPE
		SYNTAX			SEQUENCE OF QWESGroupIgmpEntry
		MAX-ACCESS		not-accessible
		STATUS			current
		DESCRIPTION		"A list of IGMP Group entries."
		::= { qigmp 8 }

   	qIgmpGroupEntry	    OBJECT-TYPE
		SYNTAX			QWESGroupIgmpEntry
		MAX-ACCESS		not-accessible
		STATUS			current
		DESCRIPTION		"One entry in the table."
		INDEX   { qIgmpGroupLp, qIgmpGroupAddr }
   		::= { qIgmpGroupTable 1 }

	QWESGroupIgmpEntry ::=
		SEQUENCE {
		        qIgmpGroupAddr    	  IpAddress,        
				qIgmpGroupLp     	  INTEGER,        
				qIgmpGroupMacAddr     PhysAddress,
				qIgmpGroupInstallType INTEGER 
		  }
--
-- Igmp Group Entry fields
--
	qIgmpGroupAddr		OBJECT-TYPE
		SYNTAX			IpAddress
		MAX-ACCESS		read-only
		STATUS			current
		DESCRIPTION		"The Multicast IP address associated with this IGMP entry."
		::= { qIgmpGroupEntry 1 }

   qIgmpGroupLp			OBJECT-TYPE
       SYNTAX			INTEGER
       MAX-ACCESS		read-only
       STATUS			current
       DESCRIPTION
               "The logical port number associated with this IP port."
       ::= { qIgmpGroupEntry 2 }

	qIgmpGroupMacAddr	OBJECT-TYPE
		SYNTAX			PhysAddress
		MAX-ACCESS		read-only
		STATUS			current
		DESCRIPTION	"The Multicast MAC address associated with the qIgmpGroupLp."
       ::= { qIgmpGroupEntry 3 }

   qIgmpGroupInstallType  OBJECT-TYPE
       SYNTAX			  INTEGER {
	                      static(1),
						  dynamic(2),
						  unknown(3)
						  }
       MAX-ACCESS		  read-only
       STATUS			  current
       DESCRIPTION
               "Defines how the multicast IP was installed.  Static(1) entries are
                specifically created by the user.  Dynamic(2) entries are learned.
                All others are unknown."
       ::= { qIgmpGroupEntry 4 }

-- Spare      { qip 8 }
-- Spare      { qip 9 }
-- Spare      { qip 10 }
-- Spare      { qip 11 }
-- Spare      { qip 12 }

      qarpInMsgs OBJECT-TYPE
          SYNTAX  INTEGER 
          ACCESS  read-only
          STATUS  mandatory
          DESCRIPTION
              "Arp messages received by the system."
          ::= { qip 13 }

      qarpOutMsgs OBJECT-TYPE
          SYNTAX  INTEGER 
          ACCESS  read-only
          STATUS  mandatory
          DESCRIPTION
              "Arp messages send by the system."
          ::= { qip 14 }

      qarpReqInMsg OBJECT-TYPE
          SYNTAX  INTEGER 
          ACCESS  read-only
          STATUS  mandatory
          DESCRIPTION
              "Request Arp messages received by the system."
          ::= { qip 15 }

      qarpReqOutMsgs OBJECT-TYPE
          SYNTAX  INTEGER 
          ACCESS  read-only
          STATUS  mandatory
          DESCRIPTION
              "Arp request messages send by the system."
          ::= { qip 16 }

      qarpRespInMsgs OBJECT-TYPE
          SYNTAX  INTEGER 
          ACCESS  read-only
          STATUS  mandatory
          DESCRIPTION
              "Arp reply messages received by the system."
          ::= { qip 17 }

      qarpRespOutMsgs OBJECT-TYPE
          SYNTAX  INTEGER 
          ACCESS  read-only
          STATUS  mandatory
          DESCRIPTION
              "Arp reply messages send by the system."
          ::= { qip 18 }

      qarpSendDiscards OBJECT-TYPE
          SYNTAX  INTEGER 
          ACCESS  read-only
          STATUS  mandatory
          DESCRIPTION
              "Arp discard messages send by the system."
          ::= { qip 19 }

      qarpSendTimeouts OBJECT-TYPE
          SYNTAX  INTEGER 
          ACCESS  read-only
          STATUS  mandatory
          DESCRIPTION
              "Arp timeout messages send by the system."
          ::= { qip 20 }

      qarpInResourceErrors OBJECT-TYPE
          SYNTAX  INTEGER 
          ACCESS  read-only
          STATUS  mandatory
          DESCRIPTION
              "Lack of resources Arp messages received by the system."
          ::= { qip 21 }

      qarpOutResourceErrors OBJECT-TYPE
          SYNTAX  INTEGER 
          ACCESS  read-only
          STATUS  mandatory
          DESCRIPTION
              "Lack of resources Arp messages send by the system."
          ::= { qip 22 }

-- Ip Rip Group { oem 15 }
-- QWES.com Static ARP Group { qip 23 }
--
-- This group contains the definitions for all MIB objects used to
-- display RIP related statistics

-- qRipStatsTable table
   	qRipStatsTable		OBJECT-TYPE
		SYNTAX			SEQUENCE OF QWESRIPSTATSENTRY
		ACCESS			not-accessible
		STATUS			mandatory
		DESCRIPTION		"A list of Static ARP entries."
		::= { qip 23 }

   	qRipStatsEntry 		OBJECT-TYPE
		SYNTAX			QWESRIPSTATSENTRY
		ACCESS			not-accessible
		STATUS			mandatory
		DESCRIPTION		"One entry in the table."
		INDEX   { qRipStatsAddr }
   		::= { qRipStatsTable 1 }

	QWESRIPSTATSENTRY ::=
		SEQUENCE {
				qRipStatsAddr 				IpAddress,			
				qrip2IfStatsUpdatesReceives	INTEGER
		  }
--
-- RIP related stats
--
      qRipStatsAddr OBJECT-TYPE
          SYNTAX  IpAddress
          ACCESS  not-accessible
          STATUS  mandatory
          DESCRIPTION
              "Rip updates received by this system."
          ::= { qRipStatsEntry 1 }
--

      qrip2IfStatsUpdatesReceives OBJECT-TYPE
          SYNTAX  Counter
          ACCESS  read-only
          STATUS  mandatory
          DESCRIPTION
              "Rip updates received by this system."
          ::= { qRipStatsEntry 2 }

-- 
--
--  qmanagementGroup   { oem 17 }
--
--  Management Group MIB definitions place holder.....  
-- 

--
-- OAM  Group { oem 18 }
-- QWES.com OAM Configuration Group { qOamGroup 1 }
--
-- This group contains the definitions for all MIB objects used to
-- configure the system OAM.

--
-- This group defines OAM group configuration such as "all circuit,
--		all uni1, all uni2, all uni3, all vpl, and all vcl."
-- 
-- qoamGroupConfigTable table
   	qoamGroupConfigTable		OBJECT-TYPE
		SYNTAX			SEQUENCE OF QOAMGROUPCONFIGENTRY
		ACCESS			not-accessible
		STATUS			mandatory
		DESCRIPTION		"A list of OAM group Configurable Parameters entries."
		::= { qOamGroup 1 }

   	qoamGroupConfigEntry 	OBJECT-TYPE
		SYNTAX			QOAMGROUPCONFIGENTRY
		ACCESS			not-accessible
		STATUS			mandatory
		DESCRIPTION		"One entry in the table."
		INDEX   { qoamGroupConfigIndex }
   		::= { qoamGroupConfigTable 1 }

	QOAMGROUPCONFIGENTRY ::=
		SEQUENCE {
		        qoamGroupConfigIndex	 	        INTEGER,
		        qoamGroupConfigAlias	 	        DisplayString,
		        qoamGroupConfigType  	 	        INTEGER,
		        qoamGroupConfigTransmitInterval	 	INTEGER,
		        qoamGroupConfigS2SAlarmThreshold	 	INTEGER,
		        qoamGroupConfigE2EAlarmThreshold	 	INTEGER,
				qoamGroupConfigStatus			 	INTEGER

		  }
--
-- OAM Configuration Entry fields
--
   qoamGroupConfigIndex	OBJECT-TYPE
	   SYNTAX		INTEGER
	   MAX-ACCESS 	read-only
       STATUS       current
       DESCRIPTION
               "The entry index of a particular group.  Currently, there
               	are 6 groups define: 
               			1) All circuit
               			2) All Uni1
               			3) All Uni2,
               			4) All Uni3,
               			5) All Vpl,
               			6) All Vcl."
       ::= { qoamGroupConfigEntry 1 }

   qoamGroupConfigAlias		OBJECT-TYPE
	   SYNTAX		        DisplayString (SIZE (0..255))
       MAX-ACCESS 	        read-only
       STATUS       current
       DESCRIPTION
               "Alias name of a specified circuit or for all configured UNIs,
               1=end-to-end, 2=segment-to-segment, 3=both."
       ::= { qoamGroupConfigEntry 2 }

   qoamGroupConfigType	OBJECT-TYPE
	   SYNTAX		INTEGER {
						segment-2-segment(1),
						end-2-end(2),
						both(3)
					}
       MAX-ACCESS 	read-write
       STATUS       current
       DESCRIPTION
               "The type of OAM to be generated."
       DEFVAL { 3 }
       ::= { qoamGroupConfigEntry 3 }

   qoamGroupConfigTransmitInterval	OBJECT-TYPE
	   SYNTAX		INTEGER (1..65535)	   
	   MAX-ACCESS 	read-write
       STATUS       current
       DESCRIPTION
               "The interval between OAM transmission in seconds."
       DEFVAL { 1 }
       ::= { qoamGroupConfigEntry 4 }

   qoamGroupConfigS2SAlarmThreshold	OBJECT-TYPE
	   SYNTAX		INTEGER (1..65535)	   
	   MAX-ACCESS 	read-write
       STATUS       current
       DESCRIPTION
               "The number of timed out segment-to-segment OAM replies 
               accumulated in sequence before an alarm is generated."
       DEFVAL { 5 }
       ::= { qoamGroupConfigEntry 5 }

   qoamGroupConfigE2EAlarmThreshold	OBJECT-TYPE
	   SYNTAX		INTEGER (1..65535)	   
	   MAX-ACCESS 	read-write
       STATUS       current
       DESCRIPTION
               "The number of timed out end-to-end OAM replies accumulated in 
               	sequence before an alarm is generated."
       DEFVAL { 5 }
       ::= { qoamGroupConfigEntry 6 }

   qoamGroupConfigStatus	OBJECT-TYPE
	   SYNTAX		INTEGER {
						enable(1),
						disable(2)
					}
       MAX-ACCESS 	read-write
       STATUS       current
       DESCRIPTION
               "Enable/disable OAM operation."
       DEFVAL { 1 }
       ::= { qoamGroupConfigEntry 7 }


--
-- This group defines one OAM configuration for a selected circuit.
-- 
-- qoamCircuitConfigTable table
   	qoamCircuitConfigTable		OBJECT-TYPE
		SYNTAX			SEQUENCE OF QOAMCIRCUITCONFIGENTRY
		ACCESS			not-accessible
		STATUS			mandatory
		DESCRIPTION		"A list of OAM Configurable Parameters entries."
		::= { qOamGroup 2 }

   	qoamCircuitConfigEntry 	OBJECT-TYPE
		SYNTAX			QOAMCIRCUITCONFIGENTRY
		ACCESS			not-accessible
		STATUS			mandatory
		DESCRIPTION		"One entry in the table."
		INDEX   { qoamCircuitConfigIndex }
   		::= { qoamCircuitConfigTable 1 }

	QOAMCIRCUITCONFIGENTRY ::=
		SEQUENCE {
		        qoamCircuitConfigIndex	 	        INTEGER,
		        qoamCircuitConfigType  	 	        INTEGER,
		        qoamCircuitConfigTransmitInterval	INTEGER,
		        qoamCircuitConfigS2SAlarmThreshold	INTEGER,
		        qoamCircuitConfigE2EAlarmThreshold	INTEGER,
				qoamCircuitConfigStatus			 	INTEGER

		  }
--
-- OAM Configuration Entry fields
--
   qoamCircuitConfigIndex	OBJECT-TYPE
	   SYNTAX		INTEGER(1..1024)
	   MAX-ACCESS 	read-write
       STATUS       current
       DESCRIPTION
               "The index for the selected circuit."
       ::= { qoamCircuitConfigEntry 1 }

   qoamCircuitConfigType	OBJECT-TYPE
	   SYNTAX		INTEGER {
						segment-2-segment(1),
						end-2-end(2),
						both(3)
					}
       MAX-ACCESS 	read-write
       STATUS       current
       DESCRIPTION
               "The type of OAM to be generated."
       DEFVAL { 3 }
       ::= { qoamCircuitConfigEntry 2 }

   qoamCircuitConfigTransmitInterval	OBJECT-TYPE
	   SYNTAX		INTEGER (1..65535)	   
	   MAX-ACCESS 	read-write
       STATUS       current
       DESCRIPTION
               "The interval between OAM transmission in seconds."
       DEFVAL { 1 }
       ::= { qoamCircuitConfigEntry 3 }

   qoamCircuitConfigS2SAlarmThreshold	OBJECT-TYPE
	   SYNTAX		INTEGER (1..65535)	   
	   MAX-ACCESS 	read-write
       STATUS       current
       DESCRIPTION
               "The number of timed out segment-to-segment OAM replies 
               accumulated in sequence before an alarm is generated."
       DEFVAL { 5 }
       ::= { qoamCircuitConfigEntry 4 }

   qoamCircuitConfigE2EAlarmThreshold	OBJECT-TYPE
	   SYNTAX		INTEGER (1..65535)	   
	   MAX-ACCESS 	read-write
       STATUS       current
       DESCRIPTION
               "The number of timed out end-to-end OAM replies accumulated in 
               	sequence before an alarm is generated."
       DEFVAL { 5 }
       ::= { qoamCircuitConfigEntry 5 }

   qoamCircuitConfigStatus	OBJECT-TYPE
	   SYNTAX	INTEGER {
				add-activate(1),
				add-not-activate(2),
				delete(3)
				}
       MAX-ACCESS 	read-write
       STATUS       current
       DESCRIPTION
               "Enable/disable OAM operation."
       DEFVAL { 1 }
       ::= { qoamCircuitConfigEntry 6 }


--
-- QWES.com OAM control Group { qOamGroup 3 }
--
-- This group contains the definitions for all MIB objects used to
-- control the system OAM.

-- qoamGroupControlTable table
   	qoamGroupControlTable		OBJECT-TYPE
		SYNTAX			SEQUENCE OF QOAMGROUPCONTROLENTRY
		ACCESS			not-accessible
		STATUS			mandatory
		DESCRIPTION		"A list of OAM Control Parameters entries."
		::= { qOamGroup 3 }

   	qoamGroupControlEntry 	OBJECT-TYPE
		SYNTAX			QOAMGROUPCONTROLENTRY
		ACCESS			not-accessible
		STATUS			mandatory
		DESCRIPTION		"One entry in the table."
		INDEX   { qoamGroupControlIndex }
   		::= { qoamGroupControlTable 1 }

	QOAMGROUPCONTROLENTRY ::=
		SEQUENCE {
		        qoamGroupControlIndex	 	        INTEGER,
		        qoamGroupControlType	 	        INTEGER,
				qoamGroupControlStatus				INTEGER
		  }
--
-- OAM Control Entry fields
--
   qoamGroupControlIndex	OBJECT-TYPE
	   SYNTAX		INTEGER(1..256)
       MAX-ACCESS 	read-write
       STATUS       current
       DESCRIPTION
               "The index for the selected circuit."
       ::= { qoamGroupControlEntry 1 }

   qoamGroupControlType	OBJECT-TYPE
	   SYNTAX		INTEGER {
						segment-2-segment(1),
						end-2-end(2),
						both(3)
					}
       MAX-ACCESS 	read-write
       STATUS       current
       DESCRIPTION
               "The type of OAM to be generated,
                1=end-to-end, 2=segment-to-segment, 3=both."
       DEFVAL { 3 }
       ::= { qoamGroupControlEntry 2 }

   qoamGroupControlStatus	OBJECT-TYPE
	   SYNTAX		INTEGER {
						start(1),
						stop(2),
						restore(3)
					}
       MAX-ACCESS 	read-write
       STATUS       current
       DESCRIPTION
               "Initiate or terminate OAM operation, 1=start and 2=stop"
       DEFVAL { 3 }
       ::= { qoamGroupControlEntry 3 }
--
-- QWES.com OAM control Group { qOamGroup 4 }
--
-- MIBs definition for OAM which is particular to a circuit
--
-- 

-- qoamCircuitControlTable table
   	qoamCircuitControlTable		OBJECT-TYPE
		SYNTAX			SEQUENCE OF QOAMCIRCUITCONTROLENTRY
		ACCESS			not-accessible
		STATUS			mandatory
		DESCRIPTION		"A list of OAM Control Parameters entry."
		::= { qOamGroup 4 }

   	qoamCircuitControlEntry 	OBJECT-TYPE
		SYNTAX			QOAMCIRCUITCONTROLENTRY
		ACCESS			not-accessible
		STATUS			mandatory
		DESCRIPTION		"One entry in the table."
		INDEX   { qoamCircuitControlIndex }
   		::= { qoamCircuitControlTable 1 }

	QOAMCIRCUITCONTROLENTRY ::=
		SEQUENCE {
		        qoamCircuitControlIndex	 	        INTEGER,
		        qoamCircuitControlType	 	        INTEGER,
				qoamCircuitControlStatus				INTEGER
		  }
--
-- OAM Control Entry fields
--
   qoamCircuitControlIndex	OBJECT-TYPE
	   SYNTAX		INTEGER(1..1024)
       MAX-ACCESS 	read-write
       STATUS       current
       DESCRIPTION
               "The index for the selected circuit."
       ::= { qoamCircuitControlEntry 1 }

   qoamCircuitControlType	OBJECT-TYPE
	   SYNTAX		INTEGER {
						segment-2-segment(1),
						end-2-end(2),
						both(3)
					}
       MAX-ACCESS 	read-write
       STATUS       current
       DESCRIPTION
               "The type of OAM to be generated,
                1=end-to-end, 2=segment-to-segment, 3=both."
       DEFVAL { 3 }
       ::= { qoamCircuitControlEntry 2 }

   qoamCircuitControlStatus	OBJECT-TYPE
	   SYNTAX		INTEGER {
						start(1),
						stop(2),
						restore(3)
					}
       MAX-ACCESS 	read-write
       STATUS       current
       DESCRIPTION
               "Initiate or terminate OAM operation, 1=start and 2=stop"
       DEFVAL { 3 }
       ::= { qoamCircuitControlEntry 3 }

--
-- QWES.com OAM Statistics Group { qOamGroup 3 }
--
-- This group contains the definitions for all MIB objects used 
-- for OAM statistics.

-- qoamStatsTable table
   	qoamStatsTable		OBJECT-TYPE
		SYNTAX			SEQUENCE OF QOAMSTATSENTRY
		ACCESS			not-accessible
		STATUS			mandatory
		DESCRIPTION		"A list of OAM statistics entries."
		::= { qOamGroup 5 }

   	qoamStatsEntry 	OBJECT-TYPE
		SYNTAX			QOAMSTATSENTRY
		ACCESS			not-accessible
		STATUS			mandatory
		DESCRIPTION		"One entry in the table."
		INDEX   { qatmCircuitId }
   		::= { qoamStatsTable 1 }

	QOAMSTATSENTRY ::=
		SEQUENCE {
		        qoamStatsCircuit	 	INTEGER,
		        qoamStatsVpi	 	    INTEGER,
		        qoamStatsVci	 	    INTEGER,
		        qoamStatsType	 	    INTEGER,
		        qoamStatsStatus	 	    INTEGER,
				qoamRequestTx	 	    INTEGER,
				qoamRequestRx	 	    INTEGER,
				qoamReplyRx	 	        INTEGER,
				qoamReplyTx	 	        INTEGER,
				qoamTimeouts	 	    INTEGER,
				qoamMinRt	 	        INTEGER,
				qoamMaxRt	 	        INTEGER,
				qoamAveRt	 	        INTEGER,
				qoamOtherInErrs	 	    INTEGER,
				qoamOtherOutErrs	 	INTEGER,
				qoamCrc10InErrs	 	    INTEGER,
				qoamCrc10OutErrs	 	INTEGER
		  }

   qoamStatsCircuit	OBJECT-TYPE
	   SYNTAX		INTEGER
	   MAX-ACCESS 	read-only
       STATUS       current
       DESCRIPTION
               "The circuit id identifies the entry."
       ::= { qoamStatsEntry 1 }

   qoamStatsVpi	OBJECT-TYPE
	   SYNTAX		INTEGER
	   MAX-ACCESS 	read-only
       STATUS       current
       DESCRIPTION
               "The first half of the VPI/VCI pairs associated with the circuit id."
       ::= { qoamStatsEntry 2 }

   qoamStatsVci	OBJECT-TYPE
	   SYNTAX		INTEGER
	   MAX-ACCESS 	read-only
       STATUS       current
       DESCRIPTION
               "The second half of the VPI/VCI pairs associated with the circuit id."
       ::= { qoamStatsEntry 3 }

   qoamStatsType	OBJECT-TYPE
	   SYNTAX		INTEGER {
						f4-segment(1),
						f4-end(2),
						f5-segment(3),
						f5-end(4)
					}
	   MAX-ACCESS 	read-only
       STATUS       current
       DESCRIPTION
               "The type of OAM."
       ::= { qoamStatsEntry 4 }

   qoamStatsStatus	OBJECT-TYPE
	   SYNTAX		INTEGER {
						on(1),
						off(2)
					}
	   MAX-ACCESS 	read-only
       STATUS       current
       DESCRIPTION
               "The current operational status of OAM on this circuit.
                ON=OAMs being transmitted, OFF=OAMs not being transmitted."
       ::= { qoamStatsEntry 5 }

   qoamRequestTx	OBJECT-TYPE
	   SYNTAX		INTEGER
	   MAX-ACCESS 	read-only
       STATUS       current
       DESCRIPTION
               "The total number of OAM requests transmitted."
       ::= { qoamStatsEntry 6 }

   qoamRequestRx	OBJECT-TYPE
	   SYNTAX		INTEGER
	   MAX-ACCESS 	read-only
       STATUS       current
       DESCRIPTION
               "The total number of OAM requests received."
       ::= { qoamStatsEntry 7 }

   qoamReplyTx	OBJECT-TYPE
	   SYNTAX		INTEGER
	   MAX-ACCESS 	read-only
       STATUS       current
       DESCRIPTION
               "The total number of OAM replies transmitted."
       ::= { qoamStatsEntry 8 }

   qoamReplyRx	OBJECT-TYPE
	   SYNTAX		INTEGER
	   MAX-ACCESS 	read-only
       STATUS       current
       DESCRIPTION
               "The total number of OAM replies received."
       ::= { qoamStatsEntry 9 }

   qoamTimeouts	OBJECT-TYPE
	   SYNTAX		INTEGER
	   MAX-ACCESS 	read-only
       STATUS       current
       DESCRIPTION
               "The total number of OAM replies that were not received
                before timeout."
       ::= { qoamStatsEntry 10 }

   qoamMinRt	OBJECT-TYPE
	   SYNTAX		INTEGER
	   MAX-ACCESS 	read-only
       STATUS       current
       DESCRIPTION
               "The minimum round trip time in seconds for receiving
                OAM replies since the counters were last reset."
       ::= { qoamStatsEntry 11 }

   qoamMaxRt	OBJECT-TYPE
	   SYNTAX		INTEGER
	   MAX-ACCESS 	read-only
       STATUS       current
       DESCRIPTION
               "The maximun round trip time in seconds for receiving
                OAM replies since the counters were last reset."
       ::= { qoamStatsEntry 12 }

   qoamAveRt	OBJECT-TYPE
	   SYNTAX		INTEGER
	   MAX-ACCESS 	read-only
       STATUS       current
       DESCRIPTION
               "The average round trip time in seconds for receiving
                OAM replies since the counters were last reset."
       ::= { qoamStatsEntry 13 }

   qoamOtherInErrs	OBJECT-TYPE
	   SYNTAX		INTEGER
	   MAX-ACCESS 	read-only
       STATUS       current
       DESCRIPTION
               "The number of OAM received but discarded due to errors."
       ::= { qoamStatsEntry 14 }

   qoamOtherOutErrs	OBJECT-TYPE
	   SYNTAX		INTEGER
	   MAX-ACCESS 	read-only
       STATUS       current
       DESCRIPTION
               "The number of OAM can't transmitted due to errors."
       ::= { qoamStatsEntry 15 }

   qoamCrc10InErrs	OBJECT-TYPE
	   SYNTAX		INTEGER
	   MAX-ACCESS 	read-only
       STATUS       current
       DESCRIPTION
               "The number of OAM received but discarded due to crc-10 
                checksum error."
       ::= { qoamStatsEntry 16 }

   qoamCrc10OutErrs	OBJECT-TYPE
	   SYNTAX		INTEGER
	   MAX-ACCESS 	read-only
       STATUS       current
       DESCRIPTION
               "The number of OAM can't transmitted due to crc-10
                checksum error."
       ::= { qoamStatsEntry 17 }

END
