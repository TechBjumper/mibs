DMTF-MOBILE-MIB DEFINITIONS ::= BEGIN

IMPORTS
	OBJECT-TYPE, NOTIFICATION-TYPE,
	MODULE-IDENTITY, enterprises, Counter32, Counter64, Gauge32, Integer32
		FROM SNMPv2-SMI
	Dmi-Date, DmiString,
	dmiEventDateTime,dmiCompId,dmiEventSeverity,
	dmiEventStateKey,dmiEventAssociatedGroup,
	dmiEventSystem,dmiEventSubSystem
		FROM DMTF-DMI-MIB;

DmiCounter		::= Counter32
DmiCounter64		::= Counter64
DmiGauge		::= Gauge32
DmiInteger		::= Integer32
DmiOctetstring		::= OCTET STRING
DmiCompId		::= INTEGER
DmiGroupId		::= INTEGER

dmtf                	OBJECT IDENTIFIER ::= { enterprises 412 }
dmtfStdMifs         	OBJECT IDENTIFIER ::= { dmtf 2 }
dmtfDynOids         	OBJECT IDENTIFIER ::= { dmtf 3 }

dmtfMobileComputerMIF	MODULE-IDENTITY
     LAST-UPDATED "9710221800Z"
     ORGANIZATION "Desktop Management Task Force"
     CONTACT-INFO
          "         DMTF Technical Advisory Committee

		    Mailstop JF2-53
                    2111 N.E. 25th Avenue
                    Hillsboro, OR 97124

		    Phone: +1 503 264-9300
                    Email: dmtf-info@dmtf.org
          "
     DESCRIPTION
          "This MIB is a translation of the DMTF Mobile Computer MIF,
          based on the translation rules defined by the
          DMTF DMI to SNMP Mapping Standard, Version 1.0.

	  DMI-based systems running a DMI-to-SNMP Mapping
          Agent provide the ability to access DMI component
          instrumentation via SNMP protocol operations.
          "
::= { dmtfStdMifs 8 }

SdmtfDeviceBay ::= SEQUENCE {
	dmtfDeviceBayState 	INTEGER,
	deviceBayIndex		DmiInteger,
	deviceBayType		DmiInteger,
	deviceBayLocation	DmiString,
	devicesSupported	DmiString,
	deviceCurrentlyAttached	DmiString
}

dmtfDeviceBayTable OBJECT-TYPE
	SYNTAX		SEQUENCE OF SdmtfDeviceBay
	MAX-ACCESS	not-accessible
	STATUS		current
	DESCRIPTION	"This group defines device bays characteristics "
	::= { dmtfMobileComputerMIF 9 }

dmtfDeviceBayEntry OBJECT-TYPE
	SYNTAX		SdmtfDeviceBay
	MAX-ACCESS	not-accessible
	STATUS		current
	DESCRIPTION	"This group defines device bays characteristics "
	--INDEX		{ DmiCompId,DmiGroupId, deviceBayIndex }
	::= { dmtfDeviceBayTable 1 }


dmtfDeviceBayState OBJECT-TYPE
	SYNTAX		INTEGER {
		active(1),
		notInService(2),
		notReady(3),
		createAndGo(4),
		createAndWait(5),
		destroy(6)
	}
	MAX-ACCESS	read-write
	STATUS		current
DESCRIPTION ""
	REFERENCE "'DMTF|Device Bay|001' 0"
	::= { dmtfDeviceBayEntry 0 }

deviceBayIndex OBJECT-TYPE
	SYNTAX		DmiInteger
	MAX-ACCESS	read-only
	STATUS		current
	DESCRIPTION	" Defines an index for the device bays in the system"
	REFERENCE "'DMTF|Device Bay|001' 1"
	::= { dmtfDeviceBayEntry 1 }

deviceBayType OBJECT-TYPE
	SYNTAX		INTEGER {
		other(1),
		unknown(2),
		proprietaryBay(3),
		standardDesktopDeviceBay(4),
		standardMobileDeviceBay(5),
		standardUltraMobileDeviceBay(6)
	}
	MAX-ACCESS	read-only
	STATUS		current
	DESCRIPTION	"Defines the type of Device Bay. Examples of Proprietary Bay
are: Swappable Bay, Multi-Function Bay and Media Bay Types "
	REFERENCE "'DMTF|Device Bay|001' 2"
	::= { dmtfDeviceBayEntry 2 }

deviceBayLocation OBJECT-TYPE
	SYNTAX		DmiString
	MAX-ACCESS	read-only
	STATUS		current
	DESCRIPTION	"Defines the physical location of the device bay"
	REFERENCE "'DMTF|Device Bay|001' 3"
	::= { dmtfDeviceBayEntry 3 }

devicesSupported OBJECT-TYPE
	SYNTAX		DmiString
	MAX-ACCESS	read-only
	STATUS		current
	DESCRIPTION	"Defines a string containing a list of devices supported in
this bay separated by commas."
	REFERENCE "'DMTF|Device Bay|001' 4"
	::= { dmtfDeviceBayEntry 4 }

deviceCurrentlyAttached OBJECT-TYPE
	SYNTAX		DmiString
	MAX-ACCESS	read-only
	STATUS		current
	DESCRIPTION	"Defines the name of the device currently attached to this
bay"
	REFERENCE "'DMTF|Device Bay|001' 5"
	::= { dmtfDeviceBayEntry 5 }

SdmtfDynamicStates ::= SEQUENCE {
	aCLineStatus	DmiInteger,
	dockingStatus	DmiInteger
}

dmtfDynamicStatesTable OBJECT-TYPE
	SYNTAX		SEQUENCE OF SdmtfDynamicStates
	MAX-ACCESS	not-accessible
	STATUS		current
	DESCRIPTION	"This group defines the dynamic states information in the
portable system"
	::= { dmtfMobileComputerMIF 2 }

dmtfDynamicStatesEntry OBJECT-TYPE
	SYNTAX		SdmtfDynamicStates
	MAX-ACCESS	not-accessible
	STATUS		current
	DESCRIPTION	"This group defines the dynamic states information in the
portable system"
	--INDEX		{ DmiCompId,DmiGroupId }
	::= { dmtfDynamicStatesTable 1 }


aCLineStatus OBJECT-TYPE
	SYNTAX		INTEGER {
		other(1),
		unknown(2),
		offLine(3),
		onLine(4),
		onBackupPower(5)
	}
	MAX-ACCESS	read-only
	STATUS		current
	DESCRIPTION	"This group defines status information about the AC line in
the notebook"
	REFERENCE "'DMTF|Dynamic States|001' 1"
	::= { dmtfDynamicStatesEntry 1 }

dockingStatus OBJECT-TYPE
	SYNTAX		INTEGER {
		other(1),
		unknown(2),
		docked(3),
		notDocked(4)
	}
	MAX-ACCESS	read-only
	STATUS		current
	DESCRIPTION	"Defines whether system is docked or not"
	REFERENCE "'DMTF|Dynamic States|001' 2"
	::= { dmtfDynamicStatesEntry 2 }

SdmtfInfraredPort ::= SEQUENCE {
	dmtfInfraredPortState INTEGER,
	iRIndex	DmiInteger,
	iRLocation	DmiString,
	iREnableState	DmiInteger,
	iRLimitSpeedEnable	DmiInteger,
	iRSpeedLimit	DmiInteger,
	iRPhysicalPortName	DmiString,
	iRVirtualCOMPortName	DmiString,
	iRVirtualLPTPortName	DmiString,
	iRProtocol	DmiInteger
}

dmtfInfraredPortTable OBJECT-TYPE
	SYNTAX		SEQUENCE OF SdmtfInfraredPort
	MAX-ACCESS	not-accessible
	STATUS		current
	DESCRIPTION	"This group defines attributes for Infrared Ports"
	::= { dmtfMobileComputerMIF 4 }

dmtfInfraredPortEntry OBJECT-TYPE
	SYNTAX		SdmtfInfraredPort
	MAX-ACCESS	not-accessible
	STATUS		current
	DESCRIPTION	"This group defines attributes for Infrared Ports"
	--INDEX		{ DmiCompId,DmiGroupId, iRIndex }
	::= { dmtfInfraredPortTable 1 }


dmtfInfraredPortState OBJECT-TYPE
	SYNTAX		INTEGER {
		active(1),
		notInService(2),
		notReady(3),
		createAndGo(4),
		createAndWait(5),
		destroy(6)
	}
	MAX-ACCESS	read-write
	STATUS		current
DESCRIPTION ""
	REFERENCE "'DMTF|Infrared Port|001' 0"
	::= { dmtfInfraredPortEntry 0 }

iRIndex OBJECT-TYPE
	SYNTAX		DmiInteger
	MAX-ACCESS	read-only
	STATUS		current
	DESCRIPTION	"Index to identify the IR port"
	REFERENCE "'DMTF|Infrared Port|001' 1"
	::= { dmtfInfraredPortEntry 1 }

iRLocation OBJECT-TYPE
	SYNTAX		DmiString
	MAX-ACCESS	read-only
	STATUS		current
	DESCRIPTION	"Location of the IR window on the device"
	REFERENCE "'DMTF|Infrared Port|001' 2"
	::= { dmtfInfraredPortEntry 2 }

iREnableState OBJECT-TYPE
	SYNTAX		INTEGER {
		other(1),
		unknown(2),
		enabled(3),
		disabled(4)
	}
	MAX-ACCESS	read-only
	STATUS		current
	DESCRIPTION	"Defines whether IR is enabled or disabled"
	REFERENCE "'DMTF|Infrared Port|001' 3"
	::= { dmtfInfraredPortEntry 3 }

iRLimitSpeedEnable OBJECT-TYPE
	SYNTAX		INTEGER {
		other(1),
		unknown(2),
		enabled(3),
		disabled(4)
	}
	MAX-ACCESS	read-only
	STATUS		current
	DESCRIPTION	"Defines whether IR speed is limited or not."
	REFERENCE "'DMTF|Infrared Port|001' 4"
	::= { dmtfInfraredPortEntry 4 }

iRSpeedLimit OBJECT-TYPE
	SYNTAX		DmiInteger
	MAX-ACCESS	read-only
	STATUS		current
	DESCRIPTION	"Defines connection speed limit of the IR port, in bits per
second."
	REFERENCE "'DMTF|Infrared Port|001' 5"
	::= { dmtfInfraredPortEntry 5 }

iRPhysicalPortName OBJECT-TYPE
	SYNTAX		DmiString
	MAX-ACCESS	read-only
	STATUS		current
	DESCRIPTION	"Defines the physical port that IR is connected to."
	REFERENCE "'DMTF|Infrared Port|001' 6"
	::= { dmtfInfraredPortEntry 6 }

iRVirtualCOMPortName OBJECT-TYPE
	SYNTAX		DmiString
	MAX-ACCESS	read-only
	STATUS		current
	DESCRIPTION	"Defines the virtual COM port the IR is connected to."
	REFERENCE "'DMTF|Infrared Port|001' 7"
	::= { dmtfInfraredPortEntry 7 }

iRVirtualLPTPortName OBJECT-TYPE
	SYNTAX		DmiString
	MAX-ACCESS	read-only
	STATUS		current
	DESCRIPTION	"Defines the virtual LPT port the IR is connected to."
	REFERENCE "'DMTF|Infrared Port|001' 8"
	::= { dmtfInfraredPortEntry 8 }

iRProtocol OBJECT-TYPE
	SYNTAX		INTEGER {
		other(1),
		unknown(2),
		sIR(3),
		fIR(4),
		mIR(5)
	}
	MAX-ACCESS	read-only
	STATUS		current
	DESCRIPTION	"Defines protocol used to establish the IR connection"
	REFERENCE "'DMTF|Infrared Port|001' 9"
	::= { dmtfInfraredPortEntry 9 }

SdmtfPointingDevice ::= SEQUENCE {
	pointingDeviceType	DmiInteger,
	pointingDeviceInterface	DmiInteger,
	pointingDeviceIRQ	DmiInteger,
	pointingDeviceButtons	DmiInteger,
	pointingDevicePortName	DmiString,
	pointingDeviceDriverName	DmiString,
	pointingDeviceDriverVersion	DmiString,
	fRUGroupIndex	DmiInteger,
	operationalGroupIndex	DmiInteger,
	securitySettings	DmiInteger
}

dmtfPointingDeviceTable OBJECT-TYPE
	SYNTAX		SEQUENCE OF SdmtfPointingDevice
	MAX-ACCESS	not-accessible
	STATUS		current
	DESCRIPTION	"This group defines the characteristics of a pointing device."
	::= { dmtfMobileComputerMIF 5 }

dmtfPointingDeviceEntry OBJECT-TYPE
	SYNTAX		SdmtfPointingDevice
	MAX-ACCESS	not-accessible
	STATUS		current
	DESCRIPTION	"This group defines the characteristics of a pointing device."
	--INDEX		{ DmiCompId,DmiGroupId }
	::= { dmtfPointingDeviceTable 1 }


pointingDeviceType OBJECT-TYPE
	SYNTAX		INTEGER {
		other(1),
		unknown(2),
		mouse(3),
		trackBall(4),
		trackPoint(5),
		glidePoint(6),
		touchPad(7)
	}
	MAX-ACCESS	read-only
	STATUS		current
	DESCRIPTION	"The type of this Pointing Device."
	REFERENCE "'DMTF|Pointing Device|001' 1"
	::= { dmtfPointingDeviceEntry 1 }

pointingDeviceInterface OBJECT-TYPE
	SYNTAX		INTEGER {
		other(1),
		unknown(2),
		serial(3),
		pS2(4),
		infrared(5),
		hPHIL(6),
		busMouse(7),
		aDB(8),
		busMouseDB9(160),
		busMouseMicroDIN(161),
		uSB(162)
	}
	MAX-ACCESS	read-only
	STATUS		current
	DESCRIPTION	"The interface type of this Pointing Device."
	REFERENCE "'DMTF|Pointing Device|001' 2"
	::= { dmtfPointingDeviceEntry 2 }

pointingDeviceIRQ OBJECT-TYPE
	SYNTAX		DmiInteger
	MAX-ACCESS	read-only
	STATUS		current
	DESCRIPTION	"The IRQ number used by this Pointing Device."
	REFERENCE "'DMTF|Pointing Device|001' 3"
	::= { dmtfPointingDeviceEntry 3 }

pointingDeviceButtons OBJECT-TYPE
	SYNTAX		DmiInteger
	MAX-ACCESS	read-only
	STATUS		current
	DESCRIPTION	"The number of Pointing Device buttons on this Pointing Device."
	REFERENCE "'DMTF|Pointing Device|001' 4"
	::= { dmtfPointingDeviceEntry 4 }

pointingDevicePortName OBJECT-TYPE
	SYNTAX		DmiString
	MAX-ACCESS	read-only
	STATUS		current
	DESCRIPTION	"The name of the port currently being used by this Pointing
Device."
	REFERENCE "'DMTF|Pointing Device|001' 5"
	::= { dmtfPointingDeviceEntry 5 }

pointingDeviceDriverName OBJECT-TYPE
	SYNTAX		DmiString
	MAX-ACCESS	read-only
	STATUS		current
	DESCRIPTION	"The name of the Pointing Device driver."
	REFERENCE "'DMTF|Pointing Device|001' 6"
	::= { dmtfPointingDeviceEntry 6 }

pointingDeviceDriverVersion OBJECT-TYPE
	SYNTAX		DmiString
	MAX-ACCESS	read-only
	STATUS		current
	DESCRIPTION	"The version number of the Pointing Device driver."
	REFERENCE "'DMTF|Pointing Device|001' 7"
	::= { dmtfPointingDeviceEntry 7 }

fRUGroupIndex OBJECT-TYPE
	SYNTAX		DmiInteger
	MAX-ACCESS	read-only
	STATUS		current
	DESCRIPTION	"If this is a Field Replaceable Unit or if it is part of another
FRU, this provides an index into the FRU table; 'value = -1' indicates that
the group is not a FRU."
	REFERENCE "'DMTF|Pointing Device|001' 8"
	::= { dmtfPointingDeviceEntry 8 }

operationalGroupIndex OBJECT-TYPE
	SYNTAX		DmiInteger
	MAX-ACCESS	read-only
	STATUS		current
	DESCRIPTION	"The index into the Operational State table for this device."
	REFERENCE "'DMTF|Pointing Device|001' 9"
	::= { dmtfPointingDeviceEntry 9 }

securitySettings OBJECT-TYPE
	SYNTAX		INTEGER {
		other(1),
		unknown(2),
		none(3),
		externalInterfaceLockedOut(4),
		externalInterfaceEnabled(5)
	}
	MAX-ACCESS	read-only
	STATUS		current
	DESCRIPTION	"Enum describing the current hardware security settings on
this device."
	REFERENCE "'DMTF|Pointing Device|001' 10"
	::= { dmtfPointingDeviceEntry 10 }

SdmtfPortableBattery ::= SEQUENCE {
	dmtfPortableBatteryState INTEGER,
	portableBatteryIndex	DmiInteger,
	portableBatteryLocation	DmiString,
	portableBatteryManufacturer	DmiString,
	portableBatteryManufactureDate	Dmi-Date,
	portableBatterySerialNumber	DmiString,
	portableBatteryDeviceName	DmiString,
	portableBatteryDeviceChemistry	DmiInteger,
	portableBatteryDesignCapacity	DmiInteger,
	portableBatteryDesignVoltage	DmiInteger,
	smartBatteryVersion	DmiString,
	fullChargeCapacity	DmiInteger,
	remainingCapacity	DmiInteger,
	maximumError	DmiInteger,
	portableBatteryChargingStatus	DmiInteger,
	remainingBatteryTime	DmiInteger,
	remainingTimeToFullBattery	DmiInteger,
	powerUnitIndex	DmiInteger
}

dmtfPortableBatteryTable OBJECT-TYPE
	SYNTAX		SEQUENCE OF SdmtfPortableBattery
	MAX-ACCESS	not-accessible
	STATUS		current
	DESCRIPTION	"This group defines general information about the portable
battery(s) in the system "
	::= { dmtfMobileComputerMIF 1 }

dmtfPortableBatteryEntry OBJECT-TYPE
	SYNTAX		SdmtfPortableBattery
	MAX-ACCESS	not-accessible
	STATUS		current
	DESCRIPTION	"This group defines general information about the portable
battery(s) in the system "
	--INDEX		{ DmiCompId,DmiGroupId, portableBatteryIndex }
	::= { dmtfPortableBatteryTable 1 }


dmtfPortableBatteryState OBJECT-TYPE
	SYNTAX		INTEGER {
		active(1),
		notInService(2),
		notReady(3),
		createAndGo(4),
		createAndWait(5),
		destroy(6)
	}
	MAX-ACCESS	read-write
	STATUS		current
DESCRIPTION ""
	REFERENCE "'DMTF|Portable Battery|001' 0"
	::= { dmtfPortableBatteryEntry 0 }

portableBatteryIndex OBJECT-TYPE
	SYNTAX		DmiInteger
	MAX-ACCESS	read-only
	STATUS		current
	DESCRIPTION	"The index into the portable battery table."
	REFERENCE "'DMTF|Portable Battery|001' 1"
	::= { dmtfPortableBatteryEntry 1 }

portableBatteryLocation OBJECT-TYPE
	SYNTAX		DmiString
	MAX-ACCESS	read-only
	STATUS		current
	DESCRIPTION	"The location of the battery"
	REFERENCE "'DMTF|Portable Battery|001' 2"
	::= { dmtfPortableBatteryEntry 2 }

portableBatteryManufacturer OBJECT-TYPE
	SYNTAX		DmiString
	MAX-ACCESS	read-only
	STATUS		current
	DESCRIPTION	"The name of the company that manufactured the battery."
	REFERENCE "'DMTF|Portable Battery|001' 3"
	::= { dmtfPortableBatteryEntry 3 }

portableBatteryManufactureDate OBJECT-TYPE
	SYNTAX		Dmi-Date
	MAX-ACCESS	read-only
	STATUS		current
	DESCRIPTION	"The battery manufacture date."
	REFERENCE "'DMTF|Portable Battery|001' 4"
	::= { dmtfPortableBatteryEntry 4 }

portableBatterySerialNumber OBJECT-TYPE
	SYNTAX		DmiString
	MAX-ACCESS	read-only
	STATUS		current
	DESCRIPTION	"The serial number for this battery."
	REFERENCE "'DMTF|Portable Battery|001' 5"
	::= { dmtfPortableBatteryEntry 5 }

portableBatteryDeviceName OBJECT-TYPE
	SYNTAX		DmiString
	MAX-ACCESS	read-only
	STATUS		current
	DESCRIPTION	"Device name for this battery.  For instance, Duracell DR-36."
	REFERENCE "'DMTF|Portable Battery|001' 6"
	::= { dmtfPortableBatteryEntry 6 }

portableBatteryDeviceChemistry OBJECT-TYPE
	SYNTAX		INTEGER {
		other(1),
		unknown(2),
		leadAcid(3),
		nickelCadmium(4),
		nickelMetalHydride(5),
		lithiumIon(6),
		zincAir(7),
		lithiumPolymer(8)
	}
	MAX-ACCESS	read-only
	STATUS		current
	DESCRIPTION	"The battery chemistry.  For instance, Lithium-ion or Nickel
metal hydride."
	REFERENCE "'DMTF|Portable Battery|001' 7"
	::= { dmtfPortableBatteryEntry 7 }

portableBatteryDesignCapacity OBJECT-TYPE
	SYNTAX		DmiInteger
	MAX-ACCESS	read-only
	STATUS		current
	DESCRIPTION	"The design capacity of the battery in mWatt-hours. If this
attribute is not supported, value = 0x80000000"
	REFERENCE "'DMTF|Portable Battery|001' 8"
	::= { dmtfPortableBatteryEntry 8 }

portableBatteryDesignVoltage OBJECT-TYPE
	SYNTAX		DmiInteger
	MAX-ACCESS	read-only
	STATUS		current
	DESCRIPTION	"The design voltage of the battery in mVolts. If this attribute
is not supported, value = 0x80000000"
	REFERENCE "'DMTF|Portable Battery|001' 9"
	::= { dmtfPortableBatteryEntry 9 }

smartBatteryVersion OBJECT-TYPE
	SYNTAX		DmiString
	MAX-ACCESS	read-only
	STATUS		current
	DESCRIPTION	"The Smart Battery Data Specification version number supported
by this battery. If the battery does not support this function, the value
should be left blank."
	REFERENCE "'DMTF|Portable Battery|001' 10"
	::= { dmtfPortableBatteryEntry 10 }

fullChargeCapacity OBJECT-TYPE
	SYNTAX		DmiInteger
	MAX-ACCESS	read-only
	STATUS		current
	DESCRIPTION	"The full charge capacity of the battery in mWatt-hours. Comparis
n of this value to the battery Design Capacity determines when the battery
requires replacement.  The battery industry has defined a battery's end of
life to be when the Full Charge Capacity falls below 80% of the Design Capacity.
 If this attribute is not supported, value = -1."
	REFERENCE "'DMTF|Portable Battery|001' 11"
	::= { dmtfPortableBatteryEntry 11 }

remainingCapacity OBJECT-TYPE
	SYNTAX		DmiInteger
	MAX-ACCESS	read-only
	STATUS		current
	DESCRIPTION	"The battery's remaining capacity in mWatt-hours. This value
is used with Design Capacity or Full Charge Capacity to calculate fuel gauge
information.  If this attribute is not supported, value = -1. "
	REFERENCE "'DMTF|Portable Battery|001' 12"
	::= { dmtfPortableBatteryEntry 12 }

maximumError OBJECT-TYPE
	SYNTAX		DmiInteger
	MAX-ACCESS	read-only
	STATUS		current
	DESCRIPTION	"The maximum error (as a percentage) in the Watt-hour data
reported by the battery. The maximum error indicates the upper bound on how
much additional energy the battery may have above the energy it reports having.
When this value exceeds some value, for instance, 10%, some action must be
taken (for instance, fully discharge then fully charge the battery) within
some specified time (for instance, within two recharge cycles of the battery).
If the action is not taken within the time frame, the error value"
	REFERENCE "'DMTF|Portable Battery|001' 13"
	::= { dmtfPortableBatteryEntry 13 }

portableBatteryChargingStatus OBJECT-TYPE
	SYNTAX		INTEGER {
		other(1),
		unknown(2),
		high(3),
		low(4),
		critical(5),
		charging(6),
		chargingAndHigh(7),
		chargingAndLow(8),
		chargingAndCritical(9),
		noSystemBattery(10)
	}
	MAX-ACCESS	read-only
	STATUS		current
	DESCRIPTION	" The charging battery status"
	REFERENCE "'DMTF|Portable Battery|001' 14"
	::= { dmtfPortableBatteryEntry 14 }

remainingBatteryTime OBJECT-TYPE
	SYNTAX		DmiInteger
	MAX-ACCESS	read-only
	STATUS		current
	DESCRIPTION	"The remaining battery time in minutes, at the current average
system power consumption level."
	REFERENCE "'DMTF|Portable Battery|001' 15"
	::= { dmtfPortableBatteryEntry 15 }

remainingTimeToFullBattery OBJECT-TYPE
	SYNTAX		DmiInteger
	MAX-ACCESS	read-only
	STATUS		current
	DESCRIPTION	"The remaining time to charge the battery fully in minutes,at
the current average system power consumption level and charging rate"
	REFERENCE "'DMTF|Portable Battery|001' 16"
	::= { dmtfPortableBatteryEntry 16 }

powerUnitIndex OBJECT-TYPE
	SYNTAX		DmiInteger
	MAX-ACCESS	read-only
	STATUS		current
	DESCRIPTION	"This is the ID of the Power Unit (logical portable battery)
to which this Portable Battery belongs. This value matches up with the Power
Unit Table Index attribute defined in the Power Unit Global Table."
	REFERENCE "'DMTF|Portable Battery|001' 17"
	::= { dmtfPortableBatteryEntry 17 }

SdmtfPowerManagementBinaryAssociationTable ::= SEQUENCE {
	dmtfPowerManagementBinaryAssociationTableState INTEGER,
	index-1	DmiInteger,
	type	DmiString,
	ref1	DmiString,
	ref2	DmiString
}

dmtfPowerManagementBinaryAssociationTable OBJECT-TYPE
	SYNTAX		SEQUENCE OF SdmtfPowerManagementBinaryAssociationTable
	MAX-ACCESS	not-accessible
	STATUS		current
	DESCRIPTION	""
	::= { dmtfMobileComputerMIF 8 }

dmtfPowerManagementBinaryAssociationEntry OBJECT-TYPE
	SYNTAX		SdmtfPowerManagementBinaryAssociationTable
	MAX-ACCESS	not-accessible
	STATUS		current
	DESCRIPTION	""
	--INDEX		{ DmiCompId,DmiGroupId, index }
	::= { dmtfPowerManagementBinaryAssociationTable 1 }


dmtfPowerManagementBinaryAssociationTableState OBJECT-TYPE
	SYNTAX		INTEGER {
		active(1),
		notInService(2),
		notReady(3),
		createAndGo(4),
		createAndWait(5),
		destroy(6)
	}
	MAX-ACCESS	read-write
	STATUS		current
DESCRIPTION ""
	REFERENCE "'DMTF|Power Management Binary Association Table|001' 0"
	::= { dmtfPowerManagementBinaryAssociationEntry 0 }

index OBJECT-TYPE
	SYNTAX		DmiInteger
	MAX-ACCESS	read-only
	STATUS		current
	DESCRIPTION	""
	REFERENCE "'DMTF|Power Management Binary Association Table|001' 1"
	::= { dmtfPowerManagementBinaryAssociationEntry 1 }

type OBJECT-TYPE
	SYNTAX		DmiString
	MAX-ACCESS	read-only
	STATUS		current
	DESCRIPTION	""
	REFERENCE "'DMTF|Power Management Binary Association Table|001' 2"
	::= { dmtfPowerManagementBinaryAssociationEntry 2 }

ref1 OBJECT-TYPE
	SYNTAX		DmiString
	MAX-ACCESS	read-only
	STATUS		current
	DESCRIPTION	""
	REFERENCE "'DMTF|Power Management Binary Association Table|001' 3"
	::= { dmtfPowerManagementBinaryAssociationEntry 3 }

ref2 OBJECT-TYPE
	SYNTAX		DmiString
	MAX-ACCESS	read-only
	STATUS		current
	DESCRIPTION	""
	REFERENCE "'DMTF|Power Management Binary Association Table|001' 4"
	::= { dmtfPowerManagementBinaryAssociationEntry 4 }

SdmtfPowerManagementTable ::= SEQUENCE {
	dmtfPowerManagementTableState INTEGER,
	powerManagementEnabledDisabled	DmiInteger,
	currentPowerManagementState	DmiInteger,
	d1TimerValue	DmiInteger,
	d2TimerValue	DmiInteger,
	d3TimerValue	DmiInteger
}

dmtfPowerManagementTable OBJECT-TYPE
	SYNTAX		SEQUENCE OF SdmtfPowerManagementTable
	MAX-ACCESS	not-accessible
	STATUS		current
	DESCRIPTION	"This group defines the power management state of components
and groups within the system"
	::= { dmtfMobileComputerMIF 7 }

dmtfPowerManagementEntry OBJECT-TYPE
	SYNTAX		SdmtfPowerManagementTable
	MAX-ACCESS	not-accessible
	STATUS		current
	DESCRIPTION	"This group defines the power management state of components
and groups within the system"
	--INDEX		{ DmiCompId,DmiGroupId, PowerManagementEnabledDisabled }
	::= { dmtfPowerManagementTable 1 }


dmtfPowerManagementTableState OBJECT-TYPE
	SYNTAX		INTEGER {
		active(1),
		notInService(2),
		notReady(3),
		createAndGo(4),
		createAndWait(5),
		destroy(6)
	}
	MAX-ACCESS	read-write
	STATUS		current
DESCRIPTION ""
	REFERENCE "'DMTF|Power Management Table|001' 0"
	::= { dmtfPowerManagementEntry 0 }

powerManagementEnabledDisabled OBJECT-TYPE
	SYNTAX		INTEGER {
		other(1),
		unknown(2),
		enabled(3),
		disabled(4)
	}
	MAX-ACCESS	read-only
	STATUS		current
	DESCRIPTION	"Enabled/Disabled state of power management on this device."
	REFERENCE "'DMTF|Power Management Table|001' 1"
	::= { dmtfPowerManagementEntry 1 }

currentPowerManagementState OBJECT-TYPE
	SYNTAX		INTEGER {
		other(1),
		unknown(2),
		d0WorkingFullyON(3),
		d1Sleeping(4),
		d2NonVolatileSleepSoftOff(5),
		d3OFF(6)
	}
	MAX-ACCESS	read-only
	STATUS		current
	DESCRIPTION	"The current PM state (D0,D1,D2,D3)."
	REFERENCE "'DMTF|Power Management Table|001' 2"
	::= { dmtfPowerManagementEntry 2 }

d1TimerValue OBJECT-TYPE
	SYNTAX		DmiInteger
	MAX-ACCESS	read-only
	STATUS		current
	DESCRIPTION	"The time-out value in milliseconds to go from D0 (full ON)
to D1 state.  If D1 state is not supported the value is -1. If the transition
is not controlled by a timer then the value is 0."
	REFERENCE "'DMTF|Power Management Table|001' 3"
	::= { dmtfPowerManagementEntry 3 }

d2TimerValue OBJECT-TYPE
	SYNTAX		DmiInteger
	MAX-ACCESS	read-only
	STATUS		current
	DESCRIPTION	"The time-out value in milliseconds to go from the next higher
 supported state (either D0 or D1) to the D2 state.  If D2 state is not supporte
 the value is -1.  If the transition is not controlled by a timer then the
value is 0."
	REFERENCE "'DMTF|Power Management Table|001' 4"
	::= { dmtfPowerManagementEntry 4 }

d3TimerValue OBJECT-TYPE
	SYNTAX		DmiInteger
	MAX-ACCESS	read-only
	STATUS		current
	DESCRIPTION	"The time-out value in milliseconds to go from the next higher
supported state (either D0, D1, or D2) to the D3 state. If D3 state is not
supported the value is -1 meaning the device can never be turned off. If
the transition is not controlled by a timer then the value is 0."
	REFERENCE "'DMTF|Power Management Table|001' 5"
	::= { dmtfPowerManagementEntry 5 }

SdmtfSystemPowerManagement ::= SEQUENCE {
	powerManagementCapabilities	DmiInteger,
	reducedCPUClockSpeed	DmiInteger,
	overrideAC	DmiInteger,
	ringEventResume	DmiInteger,
	alarmResume	DmiInteger
}

dmtfSystemPowerManagementTable OBJECT-TYPE
	SYNTAX		SEQUENCE OF SdmtfSystemPowerManagement
	MAX-ACCESS	not-accessible
	STATUS		current
	DESCRIPTION	"This group defines system power management attributes"
	::= { dmtfMobileComputerMIF 6 }

dmtfSystemPowerManagementEntry OBJECT-TYPE
	SYNTAX		SdmtfSystemPowerManagement
	MAX-ACCESS	not-accessible
	STATUS		current
	DESCRIPTION	"This group defines system power management attributes"
	--INDEX		{ DmiCompId,DmiGroupId }
	::= { dmtfSystemPowerManagementTable 1 }


powerManagementCapabilities OBJECT-TYPE
	SYNTAX		INTEGER {
		other(1),
		unknown(2),
		aPM11(3),
		aPM12(4),
		aCPI10(5)
	}
	MAX-ACCESS	read-only
	STATUS		current
	DESCRIPTION	"Defines what type of Power Management this system supports
(i.e APM 1.2, ACPI 1.0)"
	REFERENCE "'DMTF|System Power Management|001' 1"
	::= { dmtfSystemPowerManagementEntry 1 }

reducedCPUClockSpeed OBJECT-TYPE
	SYNTAX		INTEGER {
		other(1),
		unknown(2),
		enabled(3),
		disabled(4)
	}
	MAX-ACCESS	read-only
	STATUS		current
	DESCRIPTION	" Defines whether to enable CPU to slow down when possible"
	REFERENCE "'DMTF|System Power Management|001' 2"
	::= { dmtfSystemPowerManagementEntry 2 }

overrideAC OBJECT-TYPE
	SYNTAX		INTEGER {
		other(1),
		unknown(2),
		enabled(3),
		disabled(4)
	}
	MAX-ACCESS	read-only
	STATUS		current
	DESCRIPTION	"Enables/Disables power savings when AC is connected"
	REFERENCE "'DMTF|System Power Management|001' 3"
	::= { dmtfSystemPowerManagementEntry 3 }

ringEventResume OBJECT-TYPE
	SYNTAX		INTEGER {
		other(1),
		unknown(2),
		enabled(3),
		disabled(4)
	}
	MAX-ACCESS	read-only
	STATUS		current
	DESCRIPTION	"Enables system to resume operation when a modem ring occurs
on a serial port or a wakeup occurs on a PC Card"
	REFERENCE "'DMTF|System Power Management|001' 4"
	::= { dmtfSystemPowerManagementEntry 4 }

alarmResume OBJECT-TYPE
	SYNTAX		INTEGER {
		other(1),
		unknown(2),
		enabled(3),
		disabled(4)
	}
	MAX-ACCESS	read-only
	STATUS		current
	DESCRIPTION	"Enables system to resume operation from suspend/standby mode
at a time determined by an application program."
	REFERENCE "'DMTF|System Power Management|001' 5"
	::= { dmtfSystemPowerManagementEntry 5 }

SdmtfVideoOutputDevice ::= SEQUENCE {
	dmtfVideoOutputDeviceState INTEGER,
	index	DmiInteger,
	builtIn	DmiInteger,
	type-1	DmiInteger,
	colorSupport	DmiInteger,
	brightness	DmiInteger,
	contrast	DmiInteger,
	videoGroupReference	DmiString
}

dmtfVideoOutputDeviceTable OBJECT-TYPE
	SYNTAX		SEQUENCE OF SdmtfVideoOutputDevice
	MAX-ACCESS	not-accessible
	STATUS		current
	DESCRIPTION	"This group defines the attributes for video output devices"
	::= { dmtfMobileComputerMIF 3 }

dmtfVideoOutputDeviceEntry OBJECT-TYPE
	SYNTAX		SdmtfVideoOutputDevice
	MAX-ACCESS	not-accessible
	STATUS		current
	DESCRIPTION	"This group defines the attributes for video output devices"
	--INDEX		{ DmiCompId,DmiGroupId, index }
	::= { dmtfVideoOutputDeviceTable 1 }


dmtfVideoOutputDeviceState OBJECT-TYPE
	SYNTAX		INTEGER {
		active(1),
		notInService(2),
		notReady(3),
		createAndGo(4),
		createAndWait(5),
		destroy(6)
	}
	MAX-ACCESS	read-write
	STATUS		current
DESCRIPTION ""
	REFERENCE "'DMTF|Video Output Device|001' 0"
	::= { dmtfVideoOutputDeviceEntry 0 }

index2 OBJECT-TYPE
	SYNTAX		DmiInteger
	MAX-ACCESS	read-only
	STATUS		current
	DESCRIPTION	"Defines the index into the video output group"
	REFERENCE "'DMTF|Video Output Device|001' 1"
	::= { dmtfVideoOutputDeviceEntry 1 }

builtIn OBJECT-TYPE
	SYNTAX		INTEGER {
		other(1),
		unknown(2),
		yes(3),
		no(4)
	}
	MAX-ACCESS	read-only
	STATUS		current
	DESCRIPTION	"Defines whether the video output device is built in"
	REFERENCE "'DMTF|Video Output Device|001' 2"
	::= { dmtfVideoOutputDeviceEntry 2 }

type2 OBJECT-TYPE
	SYNTAX		INTEGER {
		other(1),
		unknown(2),
		cRT(3),
		tFT(4),
		sTN(5),
		dSTN(6)
	}
	MAX-ACCESS	read-only
	STATUS		current
	DESCRIPTION	"Defines the type of the video output device "
	REFERENCE "'DMTF|Video Output Device|001' 3"
	::= { dmtfVideoOutputDeviceEntry 3 }

colorSupport OBJECT-TYPE
	SYNTAX		INTEGER {
		other(1),
		unknown(2),
		yes(3),
		no(4)
	}
	MAX-ACCESS	read-only
	STATUS		current
	DESCRIPTION	"Defines whether the video output device supports color"
	REFERENCE "'DMTF|Video Output Device|001' 4"
	::= { dmtfVideoOutputDeviceEntry 4 }

brightness OBJECT-TYPE
	SYNTAX		DmiInteger
	MAX-ACCESS	read-only
	STATUS		current
	DESCRIPTION	"The percentage (0-100) of total brightness of the video output
device. If feature not available, value = 0x80000000"
	REFERENCE "'DMTF|Video Output Device|001' 5"
	::= { dmtfVideoOutputDeviceEntry 5 }

contrast OBJECT-TYPE
	SYNTAX		DmiInteger
	MAX-ACCESS	read-only
	STATUS		current
	DESCRIPTION	"The percentage (0-100) of total contrast of the videooutput
device. If feature not available, value = 0x80000000"
	REFERENCE "'DMTF|Video Output Device|001' 6"
	::= { dmtfVideoOutputDeviceEntry 6 }

videoGroupReference OBJECT-TYPE
	SYNTAX		DmiString
	MAX-ACCESS	read-only
	STATUS		current
	DESCRIPTION	"Defines the reference into the video group"
	REFERENCE "'DMTF|Video Output Device|001' 7"
	::= { dmtfVideoOutputDeviceEntry 7 }

dmtfPortableBatteryTraps OBJECT IDENTIFIER ::= {dmtfPortableBatteryTable 0 }

dmtfPortableBatteryEvSys OBJECT-TYPE
	SYNTAX		INTEGER {
		other(1),
		unknown(2),
		system1(3),
		system2(4)
	}
	MAX-ACCESS	not-accessible
	STATUS		current
	DESCRIPTION	"The major functional aspect of the product causing the fault."
	::= {dmtfPortableBatteryTable 6 }

dmtfPortableBatteryEvSub OBJECT-TYPE
	SYNTAX		INTEGER {
		other(1),
		unknown(2),
		subsystem1(3),
		subsystem2(4)
	}
	MAX-ACCESS	not-accessible
	STATUS		current
	DESCRIPTION	"The minor functional aspect of the product causing the fault."
	::= {dmtfPortableBatteryTable 7 }

dmtfPortableBatteryLowCombinedBatterysCharge NOTIFICATION-TYPE
	OBJECTS {
		dmiEventDateTime,
		dmiCompId,
		dmiEventSeverity,
		dmiEventStateKey,
		dmiEventAssociatedGroup
,		dmtfPortableBatteryEvSys
,		dmtfPortableBatteryEvSub
		}
	STATUS current
	DESCRIPTION "The combined charge of all batteries in the
		    portable computer is running low."
	REFERENCE "'DMTF|Portable Battery|001' 1"
	::= { dmtfPortableBatteryTraps 1 }

dmtfPortableBatteryCriticalCombinedBatterysCharge NOTIFICATION-TYPE
	OBJECTS {
		dmiEventDateTime,
		dmiCompId,
		dmiEventSeverity,
		dmiEventStateKey,
		dmiEventAssociatedGroup
,		dmtfPortableBatteryEvSys
,		dmtfPortableBatteryEvSub
		}
	STATUS current
	DESCRIPTION "The combined charge of all batteries in the
		    portable computer is critcally low."
	REFERENCE "'DMTF|Portable Battery|001' 2"
	::= { dmtfPortableBatteryTraps 2 }

dmtfPortableBatteryMaintenanceRequired NOTIFICATION-TYPE
	OBJECTS {
		dmiEventDateTime,
		dmiCompId,
		dmiEventSeverity,
		dmiEventStateKey,
		dmiEventAssociatedGroup
,		dmtfPortableBatteryEvSys
,		dmtfPortableBatteryEvSub
		}
	STATUS current
	DESCRIPTION "A battery in the portable computer is 
		    defective and requires maintenance."
	REFERENCE "'DMTF|Portable Battery|001' 3"
	::= { dmtfPortableBatteryTraps 3 }

END
