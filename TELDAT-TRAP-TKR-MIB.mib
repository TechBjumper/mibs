-- file automatically created


TELDAT-TRAP-TKR-MIB DEFINITIONS ::= BEGIN


IMPORTS
	MODULE-IDENTITY,OBJECT-TYPE,OBJECT-IDENTITY,NOTIFICATION-TYPE,Integer32,IpAddress
		FROM SNMPv2-SMI
	DisplayString
		FROM SNMPv2-TC
	telEventTraps
		FROM TELDAT-MIB;


tkrTrapsMIB MODULE-IDENTITY
    LAST-UPDATED "201401200930Z"
    ORGANIZATION "Teldat, S.A."
    CONTACT-INFO 
        "Teldat, S.A.
        Customer Service

        Postal: Parque Tecnologico de Madrid
                Tres Cantos 28760
                Madrid, SPAIN

        Tel.: +34 918 076 565

        http://www.teldat.com"
    DESCRIPTION
        "This Module Information Base file is defined for managing received
        SNMP notifications generated by the TKR event subsystem."
    REVISION "201401200930Z"
    DESCRIPTION "Initial implementation"
        ::= { telEventTraps 84 }


tkrEventsGroup	OBJECT IDENTIFIER	::= { tkrTrapsMIB 1 }

tkrNotifications	OBJECT IDENTIFIER	::= { tkrTrapsMIB 2 }
tkrNotificationsPrefix	OBJECT IDENTIFIER	::= { tkrNotifications 0 }

tkrEventObjects3 OBJECT-IDENTITY
    STATUS current
    DESCRIPTION
        "Event TKR.3
        This message is generated when a frame with an unknown organization
        code (not 000000) in the SNAP header is received. The frame was
        addressed to the router."
    ::= { tkrEventsGroup 3 }

tkr3-number OBJECT-TYPE
    SYNTAX Integer32
    MAX-ACCESS accessible-for-notify
    STATUS current
    DESCRIPTION
        "Parameter 'number' in event TKR.3"
    ::= { tkrEventObjects3 1 }

tkr3-source-MAC OBJECT-TYPE
    SYNTAX DisplayString
    MAX-ACCESS accessible-for-notify
    STATUS current
    DESCRIPTION
        "Parameter 'source-MAC' in event TKR.3"
    ::= { tkrEventObjects3 2 }

tkr3-interface OBJECT-TYPE
    SYNTAX DisplayString
    MAX-ACCESS accessible-for-notify
    STATUS current
    DESCRIPTION
        "Parameter 'interface' in event TKR.3"
    ::= { tkrEventObjects3 3 }

tkrEventObjects5 OBJECT-IDENTITY
    STATUS current
    DESCRIPTION
        "Event TKR.5
        This message is generated when a frame with an unknown SNAP type
        (within organization code 000000) is received. The frame was
        addressed to the router."
    ::= { tkrEventsGroup 5 }

tkr5-type-code OBJECT-TYPE
    SYNTAX Integer32
    MAX-ACCESS accessible-for-notify
    STATUS current
    DESCRIPTION
        "Parameter 'type-code' in event TKR.5"
    ::= { tkrEventObjects5 1 }

tkr5-source-MAC OBJECT-TYPE
    SYNTAX DisplayString
    MAX-ACCESS accessible-for-notify
    STATUS current
    DESCRIPTION
        "Parameter 'source-MAC' in event TKR.5"
    ::= { tkrEventObjects5 2 }

tkr5-interface OBJECT-TYPE
    SYNTAX DisplayString
    MAX-ACCESS accessible-for-notify
    STATUS current
    DESCRIPTION
        "Parameter 'interface' in event TKR.5"
    ::= { tkrEventObjects5 3 }

tkrEventObjects6 OBJECT-IDENTITY
    STATUS current
    DESCRIPTION
        "Event TKR.6
        This message is generated when a frame with an unknown SNAP type
        (within organization code 000000) is received. The frame was a
        broadcast."
    ::= { tkrEventsGroup 6 }

tkr6-type-code OBJECT-TYPE
    SYNTAX Integer32
    MAX-ACCESS accessible-for-notify
    STATUS current
    DESCRIPTION
        "Parameter 'type-code' in event TKR.6"
    ::= { tkrEventObjects6 1 }

tkr6-source-MAC OBJECT-TYPE
    SYNTAX DisplayString
    MAX-ACCESS accessible-for-notify
    STATUS current
    DESCRIPTION
        "Parameter 'source-MAC' in event TKR.6"
    ::= { tkrEventObjects6 2 }

tkr6-interface OBJECT-TYPE
    SYNTAX DisplayString
    MAX-ACCESS accessible-for-notify
    STATUS current
    DESCRIPTION
        "Parameter 'interface' in event TKR.6"
    ::= { tkrEventObjects6 3 }

tkrEventObjects14 OBJECT-IDENTITY
    STATUS current
    DESCRIPTION
        "Event TKR.14
        The self-test for the 802.5 Token-Ring card has reported an error
        during self-test. The phases are: 'Initial test', 'Board reset',
        'Configuration', 'Open', 'Open: Lobe media test', 'Open: Physical
        Insertion', 'Open: Address verification', 'Open: Roll call poll',
        'Open: Request parameters', 'Packet output' and 'Packet receive'.
        See message TKR-45 for IBM Token-Ring self-test failures."
    ::= { tkrEventsGroup 14 }

tkr14-selftest-phase OBJECT-TYPE
    SYNTAX DisplayString
    MAX-ACCESS accessible-for-notify
    STATUS current
    DESCRIPTION
        "Parameter 'selftest-phase' in event TKR.14"
    ::= { tkrEventObjects14 1 }

tkr14-error-condition OBJECT-TYPE
    SYNTAX DisplayString
    MAX-ACCESS accessible-for-notify
    STATUS current
    DESCRIPTION
        "Parameter 'error-condition' in event TKR.14"
    ::= { tkrEventObjects14 2 }

tkr14-interface OBJECT-TYPE
    SYNTAX DisplayString
    MAX-ACCESS accessible-for-notify
    STATUS current
    DESCRIPTION
        "Parameter 'interface' in event TKR.14"
    ::= { tkrEventObjects14 3 }

tkrEventObjects15 OBJECT-IDENTITY
    STATUS current
    DESCRIPTION
        "Event TKR.15
        In protocol P-SRT, we have found a not supported case (i.e. is not an
        ARE / STE frame)."
    ::= { tkrEventsGroup 15 }

tkr15-srt-type OBJECT-TYPE
    SYNTAX Integer32
    MAX-ACCESS accessible-for-notify
    STATUS current
    DESCRIPTION
        "Parameter 'srt-type' in event TKR.15"
    ::= { tkrEventObjects15 1 }

tkr15-interface OBJECT-TYPE
    SYNTAX DisplayString
    MAX-ACCESS accessible-for-notify
    STATUS current
    DESCRIPTION
        "Parameter 'interface' in event TKR.15"
    ::= { tkrEventObjects15 2 }

tkrEventObjects16 OBJECT-IDENTITY
    STATUS current
    DESCRIPTION
        "Event TKR.16
        The interface has been brought down because of an adaptor status check.
        The interface will not be self-tested, and will not come back
        automatically. The adapter-check-code indicates which error ocurred."
    ::= { tkrEventsGroup 16 }

tkr16-adapter-check-code OBJECT-TYPE
    SYNTAX Integer32
    MAX-ACCESS accessible-for-notify
    STATUS current
    DESCRIPTION
        "Parameter 'adapter-check-code' in event TKR.16"
    ::= { tkrEventObjects16 1 }

tkr16-interface OBJECT-TYPE
    SYNTAX DisplayString
    MAX-ACCESS accessible-for-notify
    STATUS current
    DESCRIPTION
        "Parameter 'interface' in event TKR.16"
    ::= { tkrEventObjects16 2 }

tkrEventObjects17 OBJECT-IDENTITY
    STATUS current
    DESCRIPTION
        "Event TKR.17
        The user has set the packet size for the 802.5 interface larger
        than is allowed for a 4 Megabit/second interface. The 8144, 11407
        and 17800 byte sizes are only legal on a 16 Megabit/second interface."
    ::= { tkrEventsGroup 17 }

tkr17-configured-size OBJECT-TYPE
    SYNTAX Integer32
    MAX-ACCESS accessible-for-notify
    STATUS current
    DESCRIPTION
        "Parameter 'configured-size' in event TKR.17"
    ::= { tkrEventObjects17 1 }

tkr17-maximum-size OBJECT-TYPE
    SYNTAX Integer32
    MAX-ACCESS accessible-for-notify
    STATUS current
    DESCRIPTION
        "Parameter 'maximum-size' in event TKR.17"
    ::= { tkrEventObjects17 2 }

tkr17-interface OBJECT-TYPE
    SYNTAX DisplayString
    MAX-ACCESS accessible-for-notify
    STATUS current
    DESCRIPTION
        "Parameter 'interface' in event TKR.17"
    ::= { tkrEventObjects17 3 }

tkrEventObjects18 OBJECT-IDENTITY
    STATUS current
    DESCRIPTION
        "Event TKR.18
        An error was detected on initialization of SRT or CAMS,
        or SRT or CAMS not found."
    ::= { tkrEventsGroup 18 }

tkr18-interface OBJECT-TYPE
    SYNTAX DisplayString
    MAX-ACCESS accessible-for-notify
    STATUS current
    DESCRIPTION
        "Parameter 'interface' in event TKR.18"
    ::= { tkrEventObjects18 1 }

tkrEventObjects19 OBJECT-IDENTITY
    STATUS current
    DESCRIPTION
        "Event TKR.19
        A packet has been received which is too short to contain MAC and LLC
        headers."
    ::= { tkrEventsGroup 19 }

tkr19-length OBJECT-TYPE
    SYNTAX Integer32
    MAX-ACCESS accessible-for-notify
    STATUS current
    DESCRIPTION
        "Parameter 'length' in event TKR.19"
    ::= { tkrEventObjects19 1 }

tkr19-source-address OBJECT-TYPE
    SYNTAX DisplayString
    MAX-ACCESS accessible-for-notify
    STATUS current
    DESCRIPTION
        "Parameter 'source-address' in event TKR.19"
    ::= { tkrEventObjects19 2 }

tkr19-interface OBJECT-TYPE
    SYNTAX DisplayString
    MAX-ACCESS accessible-for-notify
    STATUS current
    DESCRIPTION
        "Parameter 'interface' in event TKR.19"
    ::= { tkrEventObjects19 3 }

tkrEventObjects21 OBJECT-IDENTITY
    STATUS current
    DESCRIPTION
        "Event TKR.21
        An Ethernet Loopback Protocol (Configuration Testing Protocol) packet
        was received."
    ::= { tkrEventsGroup 21 }

tkr21-source-MAC-address OBJECT-TYPE
    SYNTAX DisplayString
    MAX-ACCESS accessible-for-notify
    STATUS current
    DESCRIPTION
        "Parameter 'source-MAC-address' in event TKR.21"
    ::= { tkrEventObjects21 1 }

tkr21-destination-MAC-address OBJECT-TYPE
    SYNTAX DisplayString
    MAX-ACCESS accessible-for-notify
    STATUS current
    DESCRIPTION
        "Parameter 'destination-MAC-address' in event TKR.21"
    ::= { tkrEventObjects21 2 }

tkr21-interface OBJECT-TYPE
    SYNTAX DisplayString
    MAX-ACCESS accessible-for-notify
    STATUS current
    DESCRIPTION
        "Parameter 'interface' in event TKR.21"
    ::= { tkrEventObjects21 3 }

tkrEventObjects22 OBJECT-IDENTITY
    STATUS current
    DESCRIPTION
        "Event TKR.22
        An Ethernet Loopback Protocol (Configuration Testing Protocol) packet
        had an odd skip-Count in the packet. It will be discarded."
    ::= { tkrEventsGroup 22 }

tkr22-count OBJECT-TYPE
    SYNTAX Integer32
    MAX-ACCESS accessible-for-notify
    STATUS current
    DESCRIPTION
        "Parameter 'count' in event TKR.22"
    ::= { tkrEventObjects22 1 }

tkr22-source-MAC-address OBJECT-TYPE
    SYNTAX DisplayString
    MAX-ACCESS accessible-for-notify
    STATUS current
    DESCRIPTION
        "Parameter 'source-MAC-address' in event TKR.22"
    ::= { tkrEventObjects22 2 }

tkr22-destination-MAC-address OBJECT-TYPE
    SYNTAX DisplayString
    MAX-ACCESS accessible-for-notify
    STATUS current
    DESCRIPTION
        "Parameter 'destination-MAC-address' in event TKR.22"
    ::= { tkrEventObjects22 3 }

tkr22-interface OBJECT-TYPE
    SYNTAX DisplayString
    MAX-ACCESS accessible-for-notify
    STATUS current
    DESCRIPTION
        "Parameter 'interface' in event TKR.22"
    ::= { tkrEventObjects22 4 }

tkrEventObjects23 OBJECT-IDENTITY
    STATUS current
    DESCRIPTION
        "Event TKR.23
        An Ethernet Loopback Protocol (Configuration Testing Protocol) packet
        had a skipCount in the packet that points to beyond the end of the
        packet. It will be discarded."
    ::= { tkrEventsGroup 23 }

tkr23-count OBJECT-TYPE
    SYNTAX Integer32
    MAX-ACCESS accessible-for-notify
    STATUS current
    DESCRIPTION
        "Parameter 'count' in event TKR.23"
    ::= { tkrEventObjects23 1 }

tkr23-source-MAC-address OBJECT-TYPE
    SYNTAX DisplayString
    MAX-ACCESS accessible-for-notify
    STATUS current
    DESCRIPTION
        "Parameter 'source-MAC-address' in event TKR.23"
    ::= { tkrEventObjects23 2 }

tkr23-destination-MAC-address OBJECT-TYPE
    SYNTAX DisplayString
    MAX-ACCESS accessible-for-notify
    STATUS current
    DESCRIPTION
        "Parameter 'destination-MAC-address' in event TKR.23"
    ::= { tkrEventObjects23 3 }

tkr23-interface OBJECT-TYPE
    SYNTAX DisplayString
    MAX-ACCESS accessible-for-notify
    STATUS current
    DESCRIPTION
        "Parameter 'interface' in event TKR.23"
    ::= { tkrEventObjects23 4 }

tkrEventObjects24 OBJECT-IDENTITY
    STATUS current
    DESCRIPTION
        "Event TKR.24
        An Ethernet Loopback Protocol (Configuration Testing Protocol) packet
        did not have a function code of forward (2). It will be discarded."
    ::= { tkrEventsGroup 24 }

tkr24-function OBJECT-TYPE
    SYNTAX Integer32
    MAX-ACCESS accessible-for-notify
    STATUS current
    DESCRIPTION
        "Parameter 'function' in event TKR.24"
    ::= { tkrEventObjects24 1 }

tkr24-source-MAC-address OBJECT-TYPE
    SYNTAX DisplayString
    MAX-ACCESS accessible-for-notify
    STATUS current
    DESCRIPTION
        "Parameter 'source-MAC-address' in event TKR.24"
    ::= { tkrEventObjects24 2 }

tkr24-destination-MAC-address OBJECT-TYPE
    SYNTAX DisplayString
    MAX-ACCESS accessible-for-notify
    STATUS current
    DESCRIPTION
        "Parameter 'destination-MAC-address' in event TKR.24"
    ::= { tkrEventObjects24 3 }

tkr24-interface OBJECT-TYPE
    SYNTAX DisplayString
    MAX-ACCESS accessible-for-notify
    STATUS current
    DESCRIPTION
        "Parameter 'interface' in event TKR.24"
    ::= { tkrEventObjects24 4 }

tkrEventObjects25 OBJECT-IDENTITY
    STATUS current
    DESCRIPTION
        "Event TKR.25
        An Ethernet Loopback Protocol (Configuration Testing Protocol) packet
        has a forward address that is a multicast. It will be discarded."
    ::= { tkrEventsGroup 25 }

tkr25-forward-MAC-address OBJECT-TYPE
    SYNTAX DisplayString
    MAX-ACCESS accessible-for-notify
    STATUS current
    DESCRIPTION
        "Parameter 'forward-MAC-address' in event TKR.25"
    ::= { tkrEventObjects25 1 }

tkr25-source-MAC-address OBJECT-TYPE
    SYNTAX DisplayString
    MAX-ACCESS accessible-for-notify
    STATUS current
    DESCRIPTION
        "Parameter 'source-MAC-address' in event TKR.25"
    ::= { tkrEventObjects25 2 }

tkr25-destination-MAC-address OBJECT-TYPE
    SYNTAX DisplayString
    MAX-ACCESS accessible-for-notify
    STATUS current
    DESCRIPTION
        "Parameter 'destination-MAC-address' in event TKR.25"
    ::= { tkrEventObjects25 3 }

tkr25-interface OBJECT-TYPE
    SYNTAX DisplayString
    MAX-ACCESS accessible-for-notify
    STATUS current
    DESCRIPTION
        "Parameter 'interface' in event TKR.25"
    ::= { tkrEventObjects25 4 }

tkrEventObjects26 OBJECT-IDENTITY
    STATUS current
    DESCRIPTION
        "Event TKR.26
        An Ethernet Loopback Protocol (Configuration Testing Protocol) packet
        is being forwarded to the specified next hop."
    ::= { tkrEventsGroup 26 }

tkr26-source-MAC-address OBJECT-TYPE
    SYNTAX DisplayString
    MAX-ACCESS accessible-for-notify
    STATUS current
    DESCRIPTION
        "Parameter 'source-MAC-address' in event TKR.26"
    ::= { tkrEventObjects26 1 }

tkr26-destination-MAC-address OBJECT-TYPE
    SYNTAX DisplayString
    MAX-ACCESS accessible-for-notify
    STATUS current
    DESCRIPTION
        "Parameter 'destination-MAC-address' in event TKR.26"
    ::= { tkrEventObjects26 2 }

tkr26-interface OBJECT-TYPE
    SYNTAX DisplayString
    MAX-ACCESS accessible-for-notify
    STATUS current
    DESCRIPTION
        "Parameter 'interface' in event TKR.26"
    ::= { tkrEventObjects26 3 }

tkrEventObjects27 OBJECT-IDENTITY
    STATUS current
    DESCRIPTION
        "Event TKR.27
        An Ethernet Loopback Protocol (Configuration Testing Protocol) packet
        could not be forwarded to the specified address, for the reason
        specified by the code parameter."
    ::= { tkrEventsGroup 27 }

tkr27-forward-MAC-address OBJECT-TYPE
    SYNTAX DisplayString
    MAX-ACCESS accessible-for-notify
    STATUS current
    DESCRIPTION
        "Parameter 'forward-MAC-address' in event TKR.27"
    ::= { tkrEventObjects27 1 }

tkr27-code OBJECT-TYPE
    SYNTAX Integer32
    MAX-ACCESS accessible-for-notify
    STATUS current
    DESCRIPTION
        "Parameter 'code' in event TKR.27"
    ::= { tkrEventObjects27 2 }

tkr27-interface OBJECT-TYPE
    SYNTAX DisplayString
    MAX-ACCESS accessible-for-notify
    STATUS current
    DESCRIPTION
        "Parameter 'interface' in event TKR.27"
    ::= { tkrEventObjects27 3 }

tkrEventObjects30 OBJECT-IDENTITY
    STATUS current
    DESCRIPTION
        "Event TKR.30
        A handler received a frame with an unexpected type."
    ::= { tkrEventsGroup 30 }

tkr30-MAC-frame-type OBJECT-TYPE
    SYNTAX Integer32
    MAX-ACCESS accessible-for-notify
    STATUS current
    DESCRIPTION
        "Parameter 'MAC-frame-type' in event TKR.30"
    ::= { tkrEventObjects30 1 }

tkr30-hardware-address OBJECT-TYPE
    SYNTAX DisplayString
    MAX-ACCESS accessible-for-notify
    STATUS current
    DESCRIPTION
        "Parameter 'hardware-address' in event TKR.30"
    ::= { tkrEventObjects30 2 }

tkr30-interface OBJECT-TYPE
    SYNTAX DisplayString
    MAX-ACCESS accessible-for-notify
    STATUS current
    DESCRIPTION
        "Parameter 'interface' in event TKR.30"
    ::= { tkrEventObjects30 3 }

tkrEventObjects44 OBJECT-IDENTITY
    STATUS current
    DESCRIPTION
        "Event TKR.44
        An incorrect command field has been sent to the driver. The interface
        will be re-initialized."
    ::= { tkrEventsGroup 44 }

tkr44-command OBJECT-TYPE
    SYNTAX Integer32
    MAX-ACCESS accessible-for-notify
    STATUS current
    DESCRIPTION
        "Parameter 'command' in event TKR.44"
    ::= { tkrEventObjects44 1 }

tkr44-interface OBJECT-TYPE
    SYNTAX DisplayString
    MAX-ACCESS accessible-for-notify
    STATUS current
    DESCRIPTION
        "Parameter 'interface' in event TKR.44"
    ::= { tkrEventObjects44 2 }

tkrEventObjects46 OBJECT-IDENTITY
    STATUS current
    DESCRIPTION
        "Event TKR.46
        A Token Ring frame has been received and code doesn't support Token Ring
        interface. The frame is discarded."
    ::= { tkrEventsGroup 46 }

tkr46-source-MAC-address OBJECT-TYPE
    SYNTAX DisplayString
    MAX-ACCESS accessible-for-notify
    STATUS current
    DESCRIPTION
        "Parameter 'source-MAC-address' in event TKR.46"
    ::= { tkrEventObjects46 1 }

tkr46-destination-MAC-address OBJECT-TYPE
    SYNTAX DisplayString
    MAX-ACCESS accessible-for-notify
    STATUS current
    DESCRIPTION
        "Parameter 'destination-MAC-address' in event TKR.46"
    ::= { tkrEventObjects46 2 }

tkr46-interface OBJECT-TYPE
    SYNTAX DisplayString
    MAX-ACCESS accessible-for-notify
    STATUS current
    DESCRIPTION
        "Parameter 'interface' in event TKR.46"
    ::= { tkrEventObjects46 3 }


tkrNotification1 NOTIFICATION-TYPE
    STATUS current
    DESCRIPTION
        "Notification of Event TKR.1

        Message: '----'

        Reserved for possible future use."
    ::= { tkrNotificationsPrefix 1 }

tkrNotification2 NOTIFICATION-TYPE
    STATUS current
    DESCRIPTION
        "Notification of Event TKR.2

        Message: '----'

        Reserved for possible future use."
    ::= { tkrNotificationsPrefix 2 }

tkrNotification3 NOTIFICATION-TYPE
    OBJECTS { 
              tkr3-number, 
              tkr3-source-MAC,
              tkr3-interface 
            }
    STATUS current
    DESCRIPTION
        "Notification of Event TKR.3

        Message: 'Unknown SNAP manufacturer code $1 from $2 interface $3'

        Parameters list:
              $1: tkr3-number
              $2: tkr3-source-MAC
              $3: tkr3-interface

        This message is generated when a frame with an unknown organization
        code (not 000000) in the SNAP header is received. The frame was
        addressed to the router."
    ::= { tkrNotificationsPrefix 3 }

tkrNotification4 NOTIFICATION-TYPE
    STATUS current
    DESCRIPTION
        "Notification of Event TKR.4

        Message: '----'

        Reserved for possible future use."
    ::= { tkrNotificationsPrefix 4 }

tkrNotification5 NOTIFICATION-TYPE
    OBJECTS { 
              tkr5-type-code, 
              tkr5-source-MAC,
              tkr5-interface 
            }
    STATUS current
    DESCRIPTION
        "Notification of Event TKR.5

        Message: 'Unknown SNAP type $1 from $2 interface $3'

        Parameters list:
              $1: tkr5-type-code
              $2: tkr5-source-MAC
              $3: tkr5-interface

        This message is generated when a frame with an unknown SNAP type
        (within organization code 000000) is received. The frame was
        addressed to the router."
    ::= { tkrNotificationsPrefix 5 }

tkrNotification6 NOTIFICATION-TYPE
    OBJECTS { 
              tkr6-type-code, 
              tkr6-source-MAC,
              tkr6-interface 
            }
    STATUS current
    DESCRIPTION
        "Notification of Event TKR.6

        Message: 'Unknown SNAP type $1 from $2 interface $3'

        Parameters list:
              $1: tkr6-type-code
              $2: tkr6-source-MAC
              $3: tkr6-interface

        This message is generated when a frame with an unknown SNAP type
        (within organization code 000000) is received. The frame was a
        broadcast."
    ::= { tkrNotificationsPrefix 6 }

tkrNotification7 NOTIFICATION-TYPE
    STATUS current
    DESCRIPTION
        "Notification of Event TKR.7

        Message: '----'

        Reserved for possible future use."
    ::= { tkrNotificationsPrefix 7 }

tkrNotification8 NOTIFICATION-TYPE
    STATUS current
    DESCRIPTION
        "Notification of Event TKR.8

        Message: '----'

        Reserved for possible future use."
    ::= { tkrNotificationsPrefix 8 }

tkrNotification9 NOTIFICATION-TYPE
    STATUS current
    DESCRIPTION
        "Notification of Event TKR.9

        Message: '----'

        Reserved for possible future use."
    ::= { tkrNotificationsPrefix 9 }

tkrNotification10 NOTIFICATION-TYPE
    STATUS current
    DESCRIPTION
        "Notification of Event TKR.10

        Message: '----'

        Reserved for possible future use."
    ::= { tkrNotificationsPrefix 10 }

tkrNotification11 NOTIFICATION-TYPE
    STATUS current
    DESCRIPTION
        "Notification of Event TKR.11

        Message: '----'

        Reserved for possible future use."
    ::= { tkrNotificationsPrefix 11 }

tkrNotification12 NOTIFICATION-TYPE
    STATUS current
    DESCRIPTION
        "Notification of Event TKR.12

        Message: '----'

        Reserved for possible future use."
    ::= { tkrNotificationsPrefix 12 }

tkrNotification13 NOTIFICATION-TYPE
    STATUS current
    DESCRIPTION
        "Notification of Event TKR.13

        Message: '----'

        Reserved for possible future use."
    ::= { tkrNotificationsPrefix 13 }

tkrNotification14 NOTIFICATION-TYPE
    OBJECTS { 
              tkr14-selftest-phase, 
              tkr14-error-condition,
              tkr14-interface 
            }
    STATUS current
    DESCRIPTION
        "Notification of Event TKR.14

        Message: '$1 failed: $2, interface $3'

        Parameters list:
              $1: tkr14-selftest-phase
              $2: tkr14-error-condition
              $3: tkr14-interface

        The self-test for the 802.5 Token-Ring card has reported an error
        during self-test. The phases are: 'Initial test', 'Board reset',
        'Configuration', 'Open', 'Open: Lobe media test', 'Open: Physical
        Insertion', 'Open: Address verification', 'Open: Roll call poll',
        'Open: Request parameters', 'Packet output' and 'Packet receive'.
        See message TKR-45 for IBM Token-Ring self-test failures."
    ::= { tkrNotificationsPrefix 14 }

tkrNotification15 NOTIFICATION-TYPE
    OBJECTS { 
              tkr15-srt-type, 
              tkr15-interface 
            }
    STATUS current
    DESCRIPTION
        "Notification of Event TKR.15

        Message: 'Not supported P-SRT $1, interface $2'

        Parameters list:
              $1: tkr15-srt-type
              $2: tkr15-interface

        In protocol P-SRT, we have found a not supported case (i.e. is not an
        ARE / STE frame)."
    ::= { tkrNotificationsPrefix 15 }

tkrNotification16 NOTIFICATION-TYPE
    OBJECTS { 
              tkr16-adapter-check-code, 
              tkr16-interface 
            }
    STATUS current
    DESCRIPTION
        "Notification of Event TKR.16

        Message: 'Down, adapter check $1, interface $2'

        Parameters list:
              $1: tkr16-adapter-check-code
              $2: tkr16-interface

        The interface has been brought down because of an adaptor status check.
        The interface will not be self-tested, and will not come back
        automatically. The adapter-check-code indicates which error ocurred."
    ::= { tkrNotificationsPrefix 16 }

tkrNotification17 NOTIFICATION-TYPE
    OBJECTS { 
              tkr17-configured-size, 
              tkr17-maximum-size,
              tkr17-interface 
            }
    STATUS current
    DESCRIPTION
        "Notification of Event TKR.17

        Message: 'pkt sz $1 too big for 4 Mbps, limiting to $2, interface $3'

        Parameters list:
              $1: tkr17-configured-size
              $2: tkr17-maximum-size
              $3: tkr17-interface

        The user has set the packet size for the 802.5 interface larger
        than is allowed for a 4 Megabit/second interface. The 8144, 11407
        and 17800 byte sizes are only legal on a 16 Megabit/second interface."
    ::= { tkrNotificationsPrefix 17 }

tkrNotification18 NOTIFICATION-TYPE
    OBJECTS { 
              tkr18-interface 
            }
    STATUS current
    DESCRIPTION
        "Notification of Event TKR.18

        Message: 'Error on initialize SRT or CAMS or not found in interface $1'

        Parameters list:
              $1: tkr18-interface

        An error was detected on initialization of SRT or CAMS,
        or SRT or CAMS not found."
    ::= { tkrNotificationsPrefix 18 }

tkrNotification19 NOTIFICATION-TYPE
    OBJECTS { 
              tkr19-length, 
              tkr19-source-address,
              tkr19-interface 
            }
    STATUS current
    DESCRIPTION
        "Notification of Event TKR.19

        Message: 'runt packet ($1 bytes) from node $2, interface $3'

        Parameters list:
              $1: tkr19-length
              $2: tkr19-source-address
              $3: tkr19-interface

        A packet has been received which is too short to contain MAC and LLC
        headers."
    ::= { tkrNotificationsPrefix 19 }

tkrNotification20 NOTIFICATION-TYPE
    STATUS current
    DESCRIPTION
        "Notification of Event TKR.20

        Message: '----'

        Reserved for possible future use."
    ::= { tkrNotificationsPrefix 20 }

tkrNotification21 NOTIFICATION-TYPE
    OBJECTS { 
              tkr21-source-MAC-address, 
              tkr21-destination-MAC-address,
              tkr21-interface 
            }
    STATUS current
    DESCRIPTION
        "Notification of Event TKR.21

        Message: 'Loopback Protocol frame received from $1 to $2, interface $3'

        Parameters list:
              $1: tkr21-source-MAC-address
              $2: tkr21-destination-MAC-address
              $3: tkr21-interface

        An Ethernet Loopback Protocol (Configuration Testing Protocol) packet
        was received."
    ::= { tkrNotificationsPrefix 21 }

tkrNotification22 NOTIFICATION-TYPE
    OBJECTS { 
              tkr22-count, 
              tkr22-source-MAC-address,
              tkr22-destination-MAC-address,
              tkr22-interface 
            }
    STATUS current
    DESCRIPTION
        "Notification of Event TKR.22

        Message: 'Loopback Protocol, odd skipCount $1 from $2 to $3, interface $4'

        Parameters list:
              $1: tkr22-count
              $2: tkr22-source-MAC-address
              $3: tkr22-destination-MAC-address
              $4: tkr22-interface

        An Ethernet Loopback Protocol (Configuration Testing Protocol) packet
        had an odd skip-Count in the packet. It will be discarded."
    ::= { tkrNotificationsPrefix 22 }

tkrNotification23 NOTIFICATION-TYPE
    OBJECTS { 
              tkr23-count, 
              tkr23-source-MAC-address,
              tkr23-destination-MAC-address,
              tkr23-interface 
            }
    STATUS current
    DESCRIPTION
        "Notification of Event TKR.23

        Message: 'Loopback Protocol, bad skipCount $1 from $2 to $3, interface $4'

        Parameters list:
              $1: tkr23-count
              $2: tkr23-source-MAC-address
              $3: tkr23-destination-MAC-address
              $4: tkr23-interface

        An Ethernet Loopback Protocol (Configuration Testing Protocol) packet
        had a skipCount in the packet that points to beyond the end of the
        packet. It will be discarded."
    ::= { tkrNotificationsPrefix 23 }

tkrNotification24 NOTIFICATION-TYPE
    OBJECTS { 
              tkr24-function, 
              tkr24-source-MAC-address,
              tkr24-destination-MAC-address,
              tkr24-interface 
            }
    STATUS current
    DESCRIPTION
        "Notification of Event TKR.24

        Message: 'Loopback Protocol, function $1 not Forward Data from $2 to $3, interface $4'

        Parameters list:
              $1: tkr24-function
              $2: tkr24-source-MAC-address
              $3: tkr24-destination-MAC-address
              $4: tkr24-interface

        An Ethernet Loopback Protocol (Configuration Testing Protocol) packet
        did not have a function code of forward (2). It will be discarded."
    ::= { tkrNotificationsPrefix 24 }

tkrNotification25 NOTIFICATION-TYPE
    OBJECTS { 
              tkr25-forward-MAC-address, 
              tkr25-source-MAC-address,
              tkr25-destination-MAC-address,
              tkr25-interface 
            }
    STATUS current
    DESCRIPTION
        "Notification of Event TKR.25

        Message: 'Loopback Protocol, multicast forward address $1 from $2 to $3, interface $4'

        Parameters list:
              $1: tkr25-forward-MAC-address
              $2: tkr25-source-MAC-address
              $3: tkr25-destination-MAC-address
              $4: tkr25-interface

        An Ethernet Loopback Protocol (Configuration Testing Protocol) packet
        has a forward address that is a multicast. It will be discarded."
    ::= { tkrNotificationsPrefix 25 }

tkrNotification26 NOTIFICATION-TYPE
    OBJECTS { 
              tkr26-source-MAC-address, 
              tkr26-destination-MAC-address,
              tkr26-interface 
            }
    STATUS current
    DESCRIPTION
        "Notification of Event TKR.26

        Message: 'Loopback Protocol, forwarding from $1 to $2, interface $3'

        Parameters list:
              $1: tkr26-source-MAC-address
              $2: tkr26-destination-MAC-address
              $3: tkr26-interface

        An Ethernet Loopback Protocol (Configuration Testing Protocol) packet
        is being forwarded to the specified next hop."
    ::= { tkrNotificationsPrefix 26 }

tkrNotification27 NOTIFICATION-TYPE
    OBJECTS { 
              tkr27-forward-MAC-address, 
              tkr27-code,
              tkr27-interface 
            }
    STATUS current
    DESCRIPTION
        "Notification of Event TKR.27

        Message: 'Loopback Protocol, forward to $1 discarded, for reason $2, interface $3'

        Parameters list:
              $1: tkr27-forward-MAC-address
              $2: tkr27-code
              $3: tkr27-interface

        An Ethernet Loopback Protocol (Configuration Testing Protocol) packet
        could not be forwarded to the specified address, for the reason
        specified by the code parameter."
    ::= { tkrNotificationsPrefix 27 }

tkrNotification28 NOTIFICATION-TYPE
    STATUS current
    DESCRIPTION
        "Notification of Event TKR.28

        Message: '----'

        Reserved for possible future use."
    ::= { tkrNotificationsPrefix 28 }

tkrNotification29 NOTIFICATION-TYPE
    STATUS current
    DESCRIPTION
        "Notification of Event TKR.29

        Message: '----'

        Reserved for possible future use."
    ::= { tkrNotificationsPrefix 29 }

tkrNotification30 NOTIFICATION-TYPE
    OBJECTS { 
              tkr30-MAC-frame-type, 
              tkr30-hardware-address,
              tkr30-interface 
            }
    STATUS current
    DESCRIPTION
        "Notification of Event TKR.30

        Message: 'Unexpected frame type MAC $1 of $2 interface $3'

        Parameters list:
              $1: tkr30-MAC-frame-type
              $2: tkr30-hardware-address
              $3: tkr30-interface

        A handler received a frame with an unexpected type."
    ::= { tkrNotificationsPrefix 30 }

tkrNotification31 NOTIFICATION-TYPE
    STATUS current
    DESCRIPTION
        "Notification of Event TKR.31

        Message: '----'

        Reserved for possible future use."
    ::= { tkrNotificationsPrefix 31 }

tkrNotification32 NOTIFICATION-TYPE
    STATUS current
    DESCRIPTION
        "Notification of Event TKR.32

        Message: '----'

        Reserved for possible future use."
    ::= { tkrNotificationsPrefix 32 }

tkrNotification33 NOTIFICATION-TYPE
    STATUS current
    DESCRIPTION
        "Notification of Event TKR.33

        Message: '----'

        Reserved for possible future use."
    ::= { tkrNotificationsPrefix 33 }

tkrNotification34 NOTIFICATION-TYPE
    STATUS current
    DESCRIPTION
        "Notification of Event TKR.34

        Message: 'unable to allocate buffer in handler'

        The handler was unable to allocate a buffer."
    ::= { tkrNotificationsPrefix 34 }

tkrNotification35 NOTIFICATION-TYPE
    STATUS current
    DESCRIPTION
        "Notification of Event TKR.35

        Message: '----'

        Reserved for possible future use."
    ::= { tkrNotificationsPrefix 35 }

tkrNotification36 NOTIFICATION-TYPE
    STATUS current
    DESCRIPTION
        "Notification of Event TKR.36

        Message: '----'

        Reserved for possible future use."
    ::= { tkrNotificationsPrefix 36 }

tkrNotification37 NOTIFICATION-TYPE
    STATUS current
    DESCRIPTION
        "Notification of Event TKR.37

        Message: '----'

        Reserved for possible future use."
    ::= { tkrNotificationsPrefix 37 }

tkrNotification38 NOTIFICATION-TYPE
    STATUS current
    DESCRIPTION
        "Notification of Event TKR.38

        Message: '----'

        Reserved for possible future use."
    ::= { tkrNotificationsPrefix 38 }

tkrNotification39 NOTIFICATION-TYPE
    STATUS current
    DESCRIPTION
        "Notification of Event TKR.39

        Message: '----'

        Reserved for possible future use."
    ::= { tkrNotificationsPrefix 39 }

tkrNotification40 NOTIFICATION-TYPE
    STATUS current
    DESCRIPTION
        "Notification of Event TKR.40

        Message: '----'

        Reserved for possible future use."
    ::= { tkrNotificationsPrefix 40 }

tkrNotification41 NOTIFICATION-TYPE
    STATUS current
    DESCRIPTION
        "Notification of Event TKR.41

        Message: '----'

        Reserved for possible future use."
    ::= { tkrNotificationsPrefix 41 }

tkrNotification42 NOTIFICATION-TYPE
    STATUS current
    DESCRIPTION
        "Notification of Event TKR.42

        Message: '----'

        Reserved for possible future use."
    ::= { tkrNotificationsPrefix 42 }

tkrNotification43 NOTIFICATION-TYPE
    STATUS current
    DESCRIPTION
        "Notification of Event TKR.43

        Message: '----'

        Reserved for possible future use."
    ::= { tkrNotificationsPrefix 43 }

tkrNotification44 NOTIFICATION-TYPE
    OBJECTS { 
              tkr44-command, 
              tkr44-interface 
            }
    STATUS current
    DESCRIPTION
        "Notification of Event TKR.44

        Message: 'I5IOCTL Bad Command $1. Interface $2 being restarted.'

        Parameters list:
              $1: tkr44-command
              $2: tkr44-interface

        An incorrect command field has been sent to the driver. The interface
        will be re-initialized."
    ::= { tkrNotificationsPrefix 44 }

tkrNotification45 NOTIFICATION-TYPE
    STATUS current
    DESCRIPTION
        "Notification of Event TKR.45

        Message: '----'

        Reserved for possible future use."
    ::= { tkrNotificationsPrefix 45 }

tkrNotification46 NOTIFICATION-TYPE
    OBJECTS { 
              tkr46-source-MAC-address, 
              tkr46-destination-MAC-address,
              tkr46-interface 
            }
    STATUS current
    DESCRIPTION
        "Notification of Event TKR.46

        Message: 'Received frame from $1 to $2, Token Ring unsupported, frame discarded, interface $3'

        Parameters list:
              $1: tkr46-source-MAC-address
              $2: tkr46-destination-MAC-address
              $3: tkr46-interface

        A Token Ring frame has been received and code doesn't support Token Ring
        interface. The frame is discarded."
    ::= { tkrNotificationsPrefix 46 }


END
