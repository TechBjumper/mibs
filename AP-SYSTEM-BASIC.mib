-- ********************************************************************
-- * Wireless LAN Enterprise Access Point Management Base
-- ********************************************************************

	AP-SYSTEM-BASIC DEFINITIONS ::= BEGIN
 
		IMPORTS
			OBJECT-GROUP			
	 			FROM SNMPv2-CONF			
			enterprises, IpAddress,Unsigned32, OBJECT-TYPE, MODULE-IDENTITY, TimeTicks			
				FROM SNMPv2-SMI			
			DisplayString, RowStatus, TruthValue, MacAddress			
				FROM SNMPv2-TC;

--
-- Node definitions
--

-- The Enterprises Number
		-- .1.3.6.1.4.1.27662	
		pepwave OBJECT IDENTIFIER ::= { enterprises 27662 }
        
		-- .1.3.6.1.4.1.27662.200
		productID  OBJECT IDENTIFIER ::= { pepwave 200 }

		-- .1.3.6.1.4.1.27662.200.1
		apMib OBJECT IDENTIFIER ::= { productID 1 }

		-- .1.3.6.1.4.1.27662.200.1.1
		apGeneralMib OBJECT IDENTIFIER ::= { apMib 1 }

-- ********************************************************************
-- *  MODULE IDENTITY
-- ********************************************************************

		ap-system-basic-mib MODULE-IDENTITY 
			LAST-UPDATED "2011081900Z"		-- 08 19, 2011 at 12:00 GMT
			ORGANIZATION 
				"PEPWAVE"
			CONTACT-INFO 
				""
			DESCRIPTION 
				"The MIB module for PEPWAVE Enterprise WiFi AP.
				iso(1).org(3).dod(6).internet(1).private(4).
				enterprises(1).pepwave(27662).productID(200).apMib(1).apGeneralMib(1).ap-system-basic-mib(1)"
			::= { apGeneralMib 1 }

--   Wireless LAN Access Point Identifier
-- 
-- **********************************************************************
-- *  MIB attribute OBJECT-TYPE definitions follow
-- **********************************************************************
	apSystemInfo OBJECT IDENTIFIER ::= { ap-system-basic-mib 1 }		

-- **********************************************************************
-- *  AP System Basic Information
-- **********************************************************************

	apSystemBasicInfo OBJECT IDENTIFIER ::= { apSystemInfo 1 }

		apSerialNumber OBJECT-TYPE
			SYNTAX OCTET STRING (SIZE (14))
			MAX-ACCESS read-only
			STATUS current
			DESCRIPTION
				"This attribute indicates the serial number of the AP."
			::= { apSystemBasicInfo 1 }

		apMacAddress OBJECT-TYPE
			SYNTAX OCTET STRING (SIZE (14))
			MAX-ACCESS read-only
			STATUS current
			DESCRIPTION
				"This attribute indicates the MAC Address of the AP."
			::= { apSystemBasicInfo 2 }

		apSoftwareVerstion OBJECT-TYPE
			SYNTAX OCTET STRING (SIZE (1..32))
			MAX-ACCESS read-only
			STATUS current
			DESCRIPTION
				"This attribute indicates the software version of the AP."
			::= { apSystemBasicInfo 3 }	

		apTime OBJECT-TYPE
			SYNTAX OCTET STRING (SIZE (1..64))
			MAX-ACCESS read-only
			STATUS current
			DESCRIPTION
				"This field indicates the current system time in a format:
				YYYY/MM/DD hh:mm:ss."
			::= { apSystemBasicInfo 4 }	

		apUpTime OBJECT-TYPE
--			SYNTAX OCTET STRING (SIZE (1..64))
        		SYNTAX TimeTicks
			MAX-ACCESS read-only
			STATUS current
			DESCRIPTION
				"This attribute indicates the up time of the AP."
			::= { apSystemBasicInfo 5 }	


		apStatus OBJECT-TYPE
			SYNTAX INTEGER {
				unknown(0),
				running(1), 
				bootup(2), 
				activating(3), 
				firmwareUpgrading(4)				
			}
			MAX-ACCESS read-only
			STATUS current
			DESCRIPTION
				"This attribute indicates the status of AP."
			::= { apSystemBasicInfo 6 }
		
		apControllerStatus OBJECT-TYPE
			SYNTAX OCTET STRING (SIZE (0..64))
			MAX-ACCESS read-only
			STATUS current
			DESCRIPTION
				"This attribute indicates the controller status of the AP."
			::= { apSystemBasicInfo 7 }	

		 apCurrentControllerIp OBJECT-TYPE
			SYNTAX IpAddress
			MAX-ACCESS read-only
			STATUS current
			DESCRIPTION
				"This attribute indicates the currrent controller IP of the AP."
			::= { apSystemBasicInfo 8 }	

-- **********************************************************************
-- *  AP System Configuration
-- **********************************************************************

	apSystemConfig OBJECT IDENTIFIER ::= { ap-system-basic-mib 2 }

-- **********************************************************************
-- *  AP System Basic Configuration
-- **********************************************************************
	apSystemBasicConfig OBJECT IDENTIFIER ::= { apSystemConfig 1 }

		apName OBJECT-TYPE
			SYNTAX OCTET STRING (SIZE (1..32))
			MAX-ACCESS read-write
			STATUS current
			DESCRIPTION
				"This attribute indicates the name of AP."
			::= { apSystemBasicConfig 1 }		
		
		apLocation OBJECT-TYPE
			SYNTAX OCTET STRING (SIZE (0..32))
			MAX-ACCESS read-write
			STATUS current
			DESCRIPTION
				"This attribute indicates the location of AP."
			::= { apSystemBasicConfig 2 }

		apTimeZone OBJECT-TYPE
			SYNTAX INTEGER { 
				africa-cairo(0),
				africa-kampala(1),
				africa-lagos(2),
				asia-china(3),
				asia-hong-kong(4),
				asia-jakarta(5),
				asia-seoul(6),
				asia-taiwan(7),
				asia-tokyo(8),
				europe-athens(9),
				europe-berlin(10),
				europe-dublin(11),
				europe-moscow(12),
				us-alaska(13),
				us-aleutian(14),
				us-arizona(15),
				us-central(16),
				us-eastern(17),
				us-east-indiana(18),
				us-hawaii(19),
				us-indiana-starke(20),
				us-michigan(21),
				us-mountain(22),
				us-pacific(23),
				us-samoa(24),
				gmt(25),
				utc(26),
				wet(27),
				gmt-14(28),
				gmt-13(29),
				gmt-12(30),
				gmt-11(31),
				gmt-10(32),
				gmt-9(33),
				gmt-8(34),
				gmt-7(35),
				gmt-6(36),
				gmt-5(37),
				gmt-4(38),
				gmt-3(39),
				gmt-2(40),
				gmt-1(41),
				gmt-plus-1(42),
				gmt-plus-2(43),
				gmt-plus-3(44),
				gmt-plus-4(45),
				gmt-plus-5(46),
				gmt-plus-6(47),
				gmt-plus-7(48),
				gmt-plus-8(49),
				gmt-plus-9(50),
				gmt-plus-10(51),
				gmt-plus-11(52),
				gmt-plus-12(53)							
			}
			MAX-ACCESS read-write
			STATUS current
			DESCRIPTION
				"This attribute indicates the time zone of AP."
			::= { apSystemBasicConfig 3 }	

		apControllerIp OBJECT-TYPE
			SYNTAX OCTET STRING (SIZE (0..64))
			MAX-ACCESS read-write
			STATUS current
			DESCRIPTION
				"This attribute indicates the controller IP address or domain name."
			::= { apSystemBasicConfig 4 }	
		
		apSystemDomain OBJECT-TYPE
			SYNTAX OCTET STRING (SIZE (0..64))
			MAX-ACCESS read-write
			STATUS current
			DESCRIPTION
				"This attribute indicates the system domain name."
			::= { apSystemBasicConfig 5 }

		apNtpServer  OBJECT-TYPE
			SYNTAX OCTET STRING (SIZE (0..64))
			MAX-ACCESS read-write
			STATUS current
			DESCRIPTION
				"This attribute indicates the address or domain name of the NTP server."
			::= { apSystemBasicConfig 6 }

		apMode OBJECT-TYPE
			SYNTAX INTEGER { 
				bridge(0),
				router(1)
			}
			MAX-ACCESS read-write
			STATUS current
			DESCRIPTION
				"This attribute indicates the mode of AP."
			::= { apSystemBasicConfig 7 }

		apEthSpeedDuplex OBJECT-TYPE
			SYNTAX INTEGER {
				auto(0),  
				eth-10baseTx-HD(1),
				eth-10baseTx-FD(2),
				eth-100baseTx-HD(3),
				eth-100baseTx-FD(4),
				eth-1000baseTx-FD(5)
			}
			MAX-ACCESS read-write
			STATUS current
			DESCRIPTION
				"This attribute indicates the ethernet speed and config type settings."
			::= { apSystemBasicConfig 8 }

		apVlan OBJECT-TYPE
			SYNTAX INTEGER(0..4095)
			MAX-ACCESS read-write
			STATUS current
			DESCRIPTION
				"This attribute indicates the management vlan id."
			::= { apSystemBasicConfig 9 }

		apEthAdvertise OBJECT-TYPE
			SYNTAX INTEGER { 
				off(0),
				on(1)
			}
			MAX-ACCESS read-write
			STATUS current
			DESCRIPTION
				"This attribute indicates the advertise of AP."
			::= { apSystemBasicConfig 10 }

-- **********************************************************************
-- *  AP System Schedule Reboot Configuration
-- **********************************************************************

		apSystemScheduleRebootConfigTable OBJECT-TYPE
			SYNTAX SEQUENCE OF ApSystemScheduleRebootConfigEntry
			MAX-ACCESS not-accessible
			STATUS current
			DESCRIPTION
				"wireless interface settings table."
			::= { apSystemConfig 2 }

		apSystemScheduleRebootConfigEntry OBJECT-TYPE
			SYNTAX ApSystemScheduleRebootConfigEntry
			MAX-ACCESS not-accessible
			STATUS current
			DESCRIPTION
				"An entry in the apSystemScheduleRebootConfigTable" 
			INDEX { apScheduleRebootIndex }
			::= { apSystemScheduleRebootConfigTable 1 }

		ApSystemScheduleRebootConfigEntry ::=
			SEQUENCE {
				apScheduleRebootIndex
					INTEGER,
				apScheduleReboot
					INTEGER,
				apScheduleRebootType								
					INTEGER,
				apScheduleRebootDom
					INTEGER, 
				apScheduleRebootDow
					INTEGER,
				apScheduleRebootHr				
					INTEGER,
				apScheduleRebootMin
					INTEGER
			}
        
		apScheduleRebootIndex OBJECT-TYPE
			SYNTAX INTEGER
			MAX-ACCESS read-only
			STATUS current
			DESCRIPTION
				"This attribute indicates the schedule reboot index of AP."
			::= { apSystemScheduleRebootConfigEntry 1 }

		apScheduleReboot OBJECT-TYPE
			SYNTAX INTEGER{
				disable(0), 
				enable(1)
			}
			MAX-ACCESS read-write
			STATUS current
			DESCRIPTION
				"This attribute indicates the schedule reboot status of AP."
			::= { apSystemScheduleRebootConfigEntry 2 }
			
		apScheduleRebootType OBJECT-TYPE
			SYNTAX INTEGER{
				monthly(0), 
				weekly(1), 
				daily(2)
			}
			MAX-ACCESS read-write
			STATUS current
			DESCRIPTION
				"This attribute indicates the schedule reboot type of AP."
			::= { apSystemScheduleRebootConfigEntry 3 }

		apScheduleRebootDom OBJECT-TYPE
			SYNTAX INTEGER{		
				na(0),		
				day-1(1),
				day-2(2),
				day-3(3),
				day-4(4),
				day-5(5),
				day-6(6),
				day-7(7),
				day-8(8),
				day-9(9),
				day-10(10),
				day-11(11),
				day-12(12),
				day-13(13),
				day-14(14),
				day-15(15),
				day-16(16),
				day-17(17),
				day-18(18),
				day-19(19),
				day-20(20),
				day-21(21),
				day-22(22),
				day-23(23),
				day-24(24),
				day-25(25),
				day-26(26),
				day-27(27),
				day-28(28),
				day-29(29),
				day-30(30),
				day-31(31)
			}
			MAX-ACCESS read-write
			STATUS current
			DESCRIPTION
				"This attribute schedule reboot day of month."
			::= { apSystemScheduleRebootConfigEntry 4 }	

		apScheduleRebootDow OBJECT-TYPE
			SYNTAX INTEGER{
				sunday(0), 
				monday(1), 
				tuesday(2), 
				wednesday(3), 
				thursday(4), 
				friday(5), 
				saturday(6),
				na(7)
			}
			MAX-ACCESS read-write
			STATUS current
			DESCRIPTION
				"This attribute schedule reboot day of week."
			::= { apSystemScheduleRebootConfigEntry 5 }

		apScheduleRebootHr OBJECT-TYPE
			SYNTAX INTEGER (0..23)
			MAX-ACCESS read-write
			STATUS current
			DESCRIPTION
				"This attribute schedule reboot hour."
			::= { apSystemScheduleRebootConfigEntry 6 }

		apScheduleRebootMin OBJECT-TYPE
			SYNTAX INTEGER{
				mins-0(0), 
				mins-15(15), 
				mins-30(30), 
				mins-45(45)
			}
			MAX-ACCESS read-write
			STATUS current
			DESCRIPTION
				"This attribute schedule reboot minutes (00/15/30/45)."
			::= { apSystemScheduleRebootConfigEntry 7 }	
END
