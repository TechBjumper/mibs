-- file automatically created


TELDAT-TRAP-LLDP-MIB DEFINITIONS ::= BEGIN


IMPORTS
	MODULE-IDENTITY,OBJECT-TYPE,OBJECT-IDENTITY,NOTIFICATION-TYPE,Integer32,IpAddress
		FROM SNMPv2-SMI
	DisplayString
		FROM SNMPv2-TC
	telEventTraps
		FROM TELDAT-MIB;


lldpTrapsMIB MODULE-IDENTITY
    LAST-UPDATED "201401200930Z"
    ORGANIZATION "Teldat, S.A."
    CONTACT-INFO 
        "Teldat, S.A.
        Customer Service

        Postal: Parque Tecnologico de Madrid
                Tres Cantos 28760
                Madrid, SPAIN

        Tel.: +34 918 076 565

        http://www.teldat.com"
    DESCRIPTION
        "This Module Information Base file is defined for managing received
        SNMP notifications generated by the LLDP event subsystem."
    REVISION "201401200930Z"
    DESCRIPTION "Initial implementation"
        ::= { telEventTraps 235 }


lldpEventsGroup	OBJECT IDENTIFIER	::= { lldpTrapsMIB 1 }

lldpNotifications	OBJECT IDENTIFIER	::= { lldpTrapsMIB 2 }
lldpNotificationsPrefix	OBJECT IDENTIFIER	::= { lldpNotifications 0 }

lldpEventObjects1 OBJECT-IDENTITY
    STATUS current
    DESCRIPTION
        "Event LLDP.1
        A LLDP packet has been sent on the specified interface."
    ::= { lldpEventsGroup 1 }

lldp1-interface OBJECT-TYPE
    SYNTAX DisplayString
    MAX-ACCESS accessible-for-notify
    STATUS current
    DESCRIPTION
        "Parameter 'interface' in event LLDP.1"
    ::= { lldpEventObjects1 1 }

lldpEventObjects2 OBJECT-IDENTITY
    STATUS current
    DESCRIPTION
        "Event LLDP.2
        A packet was not send because of errors in the outgoing interface."
    ::= { lldpEventsGroup 2 }

lldp2-interface OBJECT-TYPE
    SYNTAX DisplayString
    MAX-ACCESS accessible-for-notify
    STATUS current
    DESCRIPTION
        "Parameter 'interface' in event LLDP.2"
    ::= { lldpEventObjects2 1 }

lldpEventObjects3 OBJECT-IDENTITY
    STATUS current
    DESCRIPTION
        "Event LLDP.3
        A LLDP packet can not be sent because of lack of buffers."
    ::= { lldpEventsGroup 3 }

lldp3-interface OBJECT-TYPE
    SYNTAX DisplayString
    MAX-ACCESS accessible-for-notify
    STATUS current
    DESCRIPTION
        "Parameter 'interface' in event LLDP.3"
    ::= { lldpEventObjects3 1 }


lldpNotification1 NOTIFICATION-TYPE
    OBJECTS { 
              lldp1-interface 
            }
    STATUS current
    DESCRIPTION
        "Notification of Event LLDP.1

        Message: 'Sending LLDP packet on ifc $1'

        Parameters list:
              $1: lldp1-interface

        A LLDP packet has been sent on the specified interface."
    ::= { lldpNotificationsPrefix 1 }

lldpNotification2 NOTIFICATION-TYPE
    OBJECTS { 
              lldp2-interface 
            }
    STATUS current
    DESCRIPTION
        "Notification of Event LLDP.2

        Message: 'error sending packet on interface $1'

        Parameters list:
              $1: lldp2-interface

        A packet was not send because of errors in the outgoing interface."
    ::= { lldpNotificationsPrefix 2 }

lldpNotification3 NOTIFICATION-TYPE
    OBJECTS { 
              lldp3-interface 
            }
    STATUS current
    DESCRIPTION
        "Notification of Event LLDP.3

        Message: 'No buffer to send LLDP packet on ifc $1'

        Parameters list:
              $1: lldp3-interface

        A LLDP packet can not be sent because of lack of buffers."
    ::= { lldpNotificationsPrefix 3 }


END
