-- **********************************************************************
-- TOS-SV.mib
--
-- Topsec Enterprise Specific MIB: Structure of Management Information
--
-- Copyright (c) 1998-2008, Beijing Topsec Network Security Technology Co.,Ltd. 
-- All Rights Reserved
--
-- The contents of this document are subject to change without notice.
-- **********************************************************************
--
--  Change History:
--
--	Mar 18,2008 - Edit by tos lk 
--
--  Mar 17,2008 - splited from old mib TOSVI-new.mib
--
-- **********************************************************************
TOS-SV DEFINITIONS ::= BEGIN

	IMPORTS
	    MODULE-IDENTITY,NOTIFICATION-TYPE,OBJECT-TYPE,                                       
	    Integer32, Opaque,Gauge,IpAddress   
	    FROM SNMPv2-SMI
	    
	    TEXTUAL-CONVENTION,DisplayString,DateAndTime
			FROM SNMPv2-TC
			
			tosMib
			FROM TOS-SMI;
			
	--start list TOS SSLVPN table information
    tosSvTable MODULE-IDENTITY
		  LAST-UPDATED "08-03-18"  
	    ORGANIZATION "TOPSEC"
	    CONTACT-INFO
	            " Topsec Beijing
	              China
	              E-mail: support@topsec.com.cn "
	    
	    DESCRIPTION
	            "the product information table"
	    
	    REVISION    "20071109"
	    DESCRIPTION
	            "initial version"
	            	            
	    REVISION    "20080317"
	    DESCRIPTION
	            "split the whole mib file into several part"

	    REVISION    "20080318"
	    DESCRIPTION
	            "edit the file tos-sv.mib"  
	            
       ::= { tosMib 13  }

    tosSvEntry OBJECT-TYPE
       SYNTAX     TosSvEntry
       MAX-ACCESS not-accessible
       STATUS     current
       DESCRIPTION
               "An entry (conceptual row) containing the information on SV."
       --INDEX      {  SVIndex }
       ::= {  tosSvTable 1 }
    
    TosSvEntry ::= SEQUENCE {
       svMaxUser    INTEGER,
       svOnlineUser INTEGER,
       svPf DisplayString,
       svNetAcc DisplayString,
       svWf        DisplayString,
       svFs        DisplayString
            }
    
    svMaxUser OBJECT-TYPE
       SYNTAX      INTEGER 
       MAX-ACCESS  read-only
       STATUS      current
       DESCRIPTION
               "The max user SSL VPN ."
       ::= { tosSvEntry 1 }
       
    svOnlineUser OBJECT-TYPE
       SYNTAX      INTEGER
       MAX-ACCESS  read-only
       STATUS      current
       DESCRIPTION
               "The num of the SSL VPN oonline user ."
       ::= { tosSvEntry 2 }
    
    svPf  OBJECT-TYPE
       SYNTAX      DisplayString   
       MAX-ACCESS  read-only
       STATUS      current
       DESCRIPTION
               "The status of port forword module."
       ::= { tosSvEntry 3 }
    
    svNetAcc  OBJECT-TYPE
       SYNTAX      DisplayString   
       MAX-ACCESS  read-only
       STATUS      current
       DESCRIPTION
               "The status of net access module."
       ::= { tosSvEntry 4 }
    
    svWf  OBJECT-TYPE
       SYNTAX      DisplayString   
       MAX-ACCESS  read-only
       STATUS      current
       DESCRIPTION
               "The status of web forword module."
       ::= { tosSvEntry 5 }
    
    svFs  OBJECT-TYPE
       SYNTAX      DisplayString   
       MAX-ACCESS  read-only
       STATUS      current
       DESCRIPTION
               "The status of file share module."
       ::= { tosSvEntry 6 }


--end list TOS SSLVPN table information

END
