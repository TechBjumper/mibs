-- MODULE-IDENTITY
--  OrgName
--    Netasq
--  ContactInfo
--     Customer Support
--     
--     3,  rue Aricheme
--     59650 Villeneuve d'Ascq
--     FRANCE
--    
--     Tel: +33 03 20 61 96 30
--     E-mail: support@netasq.com
--     Http://www.netasq.com

--
--  Last modified date: 07/30/2002
--    

NETASQ-VPNSA-MIB DEFINITIONS ::= BEGIN
IMPORTS
    MODULE-IDENTITY,  OBJECT-TYPE ,  Integer32,  Counter64	FROM SNMPv2-SMI
    DisplayString								FROM RFC1213-MIB 
    ntqVPN										FROM NETASQ-SMI-MIB;
       
        ntqVPNSATable OBJECT-TYPE
                SYNTAX SEQUENCE OF NtqVPNSAEntry
                MAX-ACCESS  not-accessible
                STATUS  current
                DESCRIPTION 
                        "List of Security Association"
                ::= { ntqVPN 1 }
                
        ntqVPNSAEntry OBJECT-TYPE
        SYNTAX  NtqVPNSAEntry
        MAX-ACCESS  not-accessible
        STATUS  current
        DESCRIPTION
               "Each entry in the ntqVPNSATable holds a set of parameters."
        INDEX   { ntqVPNSAIndex }
        ::= { ntqVPNSATable 1 }
        
        NtqVPNSAEntry ::=
                SEQUENCE {
                        ntqVPNSAIndex
                                INTEGER, 
                        ntqVPNIPSrc
                                DisplayString, 
                        ntqVPNIPDst
                                DisplayString, 
                        ntqVPNType
                                INTEGER, 
                        ntqVPNMode
                                INTEGER, 
                        ntqVPNSpi
                                Integer32, 
                        ntqVPNPeerSpi
                                Integer32, 
                        ntqVPNReqID
                                Integer32, 
                        ntqVPNEnc
                                DisplayString, 
                        ntqVPNAuth
                                INTEGER, 
                        ntqVPNState
                                INTEGER, 
                        ntqVPNLifetime
                                Counter64, 
                        ntqVPNBytes
                                Counter64, 
                        ntqVPNMaxLifetime
                                Counter64, 
                        ntqVPNMaxBytes
                                Counter64
                }
                
        ntqVPNSAIndex OBJECT-TYPE
        SYNTAX  INTEGER
        MAX-ACCESS  read-only
        STATUS  current
        DESCRIPTION
             "A unique value for phase one table.  Its value
              ranges between 1 and 65535 and may not be contigous. 
              the index has no other meaning but a pure index" 
        ::= { ntqVPNSAEntry 1 }
        
        ntqVPNIPSrc OBJECT-TYPE
                SYNTAX DisplayString
                MAX-ACCESS read-only
                STATUS current
                DESCRIPTION
                        "IP source"
                ::= { ntqVPNSAEntry 2 }
                
        ntqVPNIPDst OBJECT-TYPE
                SYNTAX DisplayString
                MAX-ACCESS read-only
                STATUS current
                DESCRIPTION
                        "IP destination"
                ::= { ntqVPNSAEntry 3 }
                
        ntqVPNType OBJECT-TYPE
                SYNTAX INTEGER {
                        unspec(0), 
                        unknown(1), 
                        ah(2), 
                        esp(3), 
                        rsvp(4), 
                        ospfv2(5), 
                        ripv2(6), 
                        mip(7), 
                        ipcomp(8)
                }
                MAX-ACCESS read-only
                STATUS current
                DESCRIPTION
                        "Type"
                ::= { ntqVPNSAEntry 4 }
                
        ntqVPNMode OBJECT-TYPE
                SYNTAX INTEGER {
                        any(0), 
                        transport(1), 
                        tunnel(2)
                }
                MAX-ACCESS read-only
                STATUS current
                DESCRIPTION
                        "Mode"
                ::= { ntqVPNSAEntry 5 }
                
        ntqVPNSpi OBJECT-TYPE
                SYNTAX Integer32
                MAX-ACCESS read-only
                STATUS current
                DESCRIPTION
                        "Secure property index"
                ::= { ntqVPNSAEntry 6 }
                
        ntqVPNPeerSpi OBJECT-TYPE
                SYNTAX Integer32
                MAX-ACCESS read-only
                STATUS current
                DESCRIPTION
                        "Secure property index"
                ::= { ntqVPNSAEntry 7 }
                
        ntqVPNReqID OBJECT-TYPE
                SYNTAX Integer32
                MAX-ACCESS read-only
                STATUS current
                DESCRIPTION
                        "ReqID"
                ::= { ntqVPNSAEntry 8 }
                
        ntqVPNEnc OBJECT-TYPE
                SYNTAX DisplayString
                MAX-ACCESS read-only
                STATUS current
                DESCRIPTION
                        "Enc"
                ::= { ntqVPNSAEntry 9 }
                
        ntqVPNAuth OBJECT-TYPE
                SYNTAX INTEGER {
                        none(0), 
                        hmac-md5(1), 
                        hmac-sha1(2), 
                        md5(3), 
                        sha(4), 
                        null(5)
                }
                MAX-ACCESS read-only
                STATUS current
                DESCRIPTION
                        "Auth"
                ::= { ntqVPNSAEntry 10 }
                
        ntqVPNState OBJECT-TYPE
                SYNTAX INTEGER {
                        larval(0), 
                        mature(1), 
                        dying(2), 
                        dead(3)
                }
                MAX-ACCESS read-only
                STATUS current
                DESCRIPTION
                        "VPN State"
                ::= { ntqVPNSAEntry 11 }
                
        ntqVPNLifetime OBJECT-TYPE
                SYNTAX Counter64
                MAX-ACCESS read-only
                STATUS current
                DESCRIPTION
                        "Lifetime"
                ::= { ntqVPNSAEntry 12 }
                
        ntqVPNBytes OBJECT-TYPE
                SYNTAX Counter64
                MAX-ACCESS read-only
                STATUS current
                DESCRIPTION
                        "Bytes"
                ::= { ntqVPNSAEntry 13 }
                
        ntqVPNMaxLifetime OBJECT-TYPE
                SYNTAX Counter64
                MAX-ACCESS read-only
                STATUS current
                DESCRIPTION
                        "MaxLifetime"
                ::= { ntqVPNSAEntry 14 }
                
        ntqVPNMaxBytes OBJECT-TYPE
                SYNTAX Counter64
                MAX-ACCESS read-only
                STATUS current
                DESCRIPTION
                        "MaxBytes"
                ::= { ntqVPNSAEntry 15 }
END
