--          *****************************
--          *                           *
--          *         ONEOS MIB         *
--          *                           *
--          *****************************
--
--          ONEOS_MIB_STD_V05.1.R005_E001
--
--          Creation date : 21/03/2005
--
--          Compatibility with ONEOS_V31
--
--          Compatibility with ONEOS_V32
--


     ONEACCESS-VRRP-MIB DEFINITIONS ::= BEGIN

     IMPORTS
		MODULE-IDENTITY, OBJECT-TYPE, NOTIFICATION-TYPE, Counter32,Unsigned32
			FROM SNMPv2-SMI
--		DisplayString
--			FROM RFC1213-MIB
		MODULE-COMPLIANCE, OBJECT-GROUP
			FROM SNMPv2-CONF
 	    	oacExpIMIpVrrp,oacExpIMVrrpNotifications,oacMIBModules
			FROM ONEACCESS-GLOBAL-REG
			oacEventText
			FROM ONEACCESS-EVENTS-MIB;

     oacVrrpMIBModule MODULE-IDENTITY
        LAST-UPDATED "201110270000Z"
        ORGANIZATION " OneAccess "
         CONTACT-INFO
           "Pascal KESTELOOT
            Postal: ONE ACCESS
                    381 Avenue du General de Gaulle
                    92140 Clamart, France
		    FRANCE

            Tel: (+33) 01 41 87 70 00
            Fax: (+33) 01 41 87 74 00

            E-mail: pascal.kesteloot@oneaccess-net.com"

         DESCRIPTION
                    	"Contact updated"
    	REVISION        "201110270000Z"

        DESCRIPTION
              "This MIB module describes IP VRRP Management objects."

	::= { oacMIBModules 670 }


vrrpTrapNewBackup NOTIFICATION-TYPE
     OBJECTS      { oacEventText
                  }
     STATUS       current
     DESCRIPTION
         "The newBackup trap indicates that the sending agent
         has transitioned to 'Backup' state."
     ::= { oacExpIMVrrpNotifications 1 }


END
--
