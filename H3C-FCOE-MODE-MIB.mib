-- =====================================================================
-- Copyright (c) 2004-2013 Hangzhou H3C Tech. Co., Ltd. All rights reserved.
--
-- Description:
--      This MIB module is for configuring and monitoring the working mode of
--    FCoE (Fibre Channel over Ethernet) features.
-- Reference:
-- Version: V1.0
-- History:
--   V1.0 Initial version
--        created by linlongjun 2013-03-08
-- =====================================================================
H3C-FCOE-MODE-MIB DEFINITIONS ::= BEGIN

IMPORTS
    Integer32, OBJECT-TYPE, MODULE-IDENTITY
        FROM SNMPv2-SMI
    h3cCommon
        FROM HUAWEI-3COM-OID-MIB;

h3cFcoeMode MODULE-IDENTITY
    LAST-UPDATED   "201303081100Z"
    ORGANIZATION
        "Hangzhou H3C Tech. Co., Ltd."
    CONTACT-INFO
        "Platform Team Hangzhou H3C Tech. Co., Ltd.
         Hai-Dian District Beijing P.R. China
         http://www.h3c.com
         Zip:100085
        "
    DESCRIPTION
        "This MIB module is for configuring and monitoring the working mode of
         FCoE (Fibre Channel over Ethernet) features."
    REVISION       "201303081100Z"
    DESCRIPTION
        "Initial version of this MIB module."
    ::= { h3cCommon 135 }

--
-- Node definitions
--
h3cFcoeModeMibObjects OBJECT IDENTIFIER ::= { h3cFcoeMode 1 }

h3cFcoeModeCfgMode OBJECT-TYPE
    SYNTAX         Integer32
    MAX-ACCESS     read-write
    STATUS         current
    DESCRIPTION
        "This object specifies the FCoE modes the switch supports.

         The object has four available values:
         1: non-FCoE mode.
         2: FCF mode.
         3: NPV mode.
         4: Transit mode.

         The switch mode can only be converted from non-FCoE mode to one of FCoE
         modes, or vice versa, but cannot be converted directly among the other
         three FCoE modes.

         To convert among the other three FCoE modes, the switch should first
         be converted to non-FCoE mode.  After converting the switch to non-FCoE
         mode, FCoE-related configurations in the original FCoE mode will be
         cleared."
    ::= { h3cFcoeModeMibObjects 1 }

h3cFcoeModeCfgLastResult OBJECT-TYPE
    SYNTAX INTEGER {
                      success(1),
                      noLicence(2),
                      needReset(3),
                      unknownFault(4)
                   }
    MAX-ACCESS     read-only
    STATUS         current
    DESCRIPTION
        "This object specifies the result of the latest FCoE mode configuration.

        The object has four values:
        success      - Configured successfully.
        noLicence    - Configured unsuccessfully for lack of licence.
        needReset    - Configured unsuccessfully, because the desired mode is
                       not non-FCoE mode, and the mode should be first set to
                       non-FCoE mode.
        unknownFault - Configured unsuccessfully for unknown fault."
    ::= { h3cFcoeModeMibObjects 2 }

END
