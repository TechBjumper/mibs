NBASE-EXP-MIB DEFINITIONS ::= BEGIN

        IMPORTS
                enterprises 			FROM RFC1155-SMI

                OBJECT-TYPE                   FROM RFC-1212
                DisplayString                 FROM RFC1213-MIB;


nbase           OBJECT IDENTIFIER ::= { enterprises 629 }
nbSwitchG1      OBJECT IDENTIFIER ::= { nbase 1 }
nbsMegaMibs     OBJECT IDENTIFIER ::= { nbSwitchG1 16 }
nbsExpansionPortMIB	 OBJECT IDENTIFIER ::= { nbsMegaMibs 1 }
nbsAtmLanePortMIB OBJECT IDENTIFIER ::= { nbsMegaMibs 2 }
nbsFddiPortMIB OBJECT IDENTIFIER ::= { nbsMegaMibs 3 }


--- *********************************
--- Extension MIB for expansion ports
--- *********************************


nbsExpPortMaxNum OBJECT-TYPE
        SYNTAX  INTEGER
        ACCESS  read-only
        STATUS  mandatory
DESCRIPTION ""
        ::= { nbsExpansionPortMIB 1 }


nbsExpPortTable OBJECT-TYPE
        SYNTAX  SEQUENCE OF NbsExpPortEntry
        ACCESS  not-accessible
        STATUS  mandatory
        DESCRIPTION
                "A table of Expansion Ports in the devices."
        ::= { nbsExpansionPortMIB 2 }

nbsExpPortEntry      OBJECT-TYPE
        SYNTAX  NbsExpPortEntry
        ACCESS  not-accessible
        STATUS  mandatory
        DESCRIPTION
                "Contains the features general to NBase Expansion port modules."
        INDEX { nbsExpPortTblPortNumber }

        ::= { nbsExpPortTable 1 }

NbsExpPortEntry ::= SEQUENCE {

        nbsExpPortTblPortNumber	INTEGER,
        nbsExpPortTblHwType	INTEGER,
        nbsExpPortTblSwType	INTEGER,
        nbsExpPortTblSquall	DisplayString,
        nbsExpPortTblHwVersion	DisplayString,
        nbsExpPortTblMCodeVrsn	DisplayString,
        nbsExpPortTblSwVersion	DisplayString,
	nbsExpPortTblStatus	INTEGER,
	nbsExpPortTftpSwFileName DisplayString,
	nbsExpPortInitDownload	INTEGER
        }

nbsExpPortTblPortNumber	OBJECT-TYPE
        SYNTAX  INTEGER
        ACCESS  read-only
        STATUS  mandatory
	DESCRIPTION
		"The Port Number of the Expansion Port.  This port number is the same
		as the port number used for all other purposes."
        ::= { nbsExpPortEntry 1 }

nbsExpPortTblHwType	OBJECT-TYPE
        SYNTAX  INTEGER {
		other (1),	-- unknown hardware
		cpu-card (2)	-- I960 CPU card
	}
        ACCESS  read-only
        STATUS  mandatory
	DESCRIPTION
		"The Hardware Type of the Expansion port."
        ::= { nbsExpPortEntry 2 }

nbsExpPortTblSwType	OBJECT-TYPE
        SYNTAX  INTEGER {
		other (1),	-- unknown software
		atm-lec (2),	-- LAN Emulation over ATM
		atm-mpoa (3),	-- Multi-Protocol over ATM
		fddi (4),	-- FDDI
		wan-router (5)	-- T1 Wide Area Network Router
	}
        ACCESS  read-only
        STATUS  mandatory
	DESCRIPTION
		"The Software Type of the Expansion port."
        ::= { nbsExpPortEntry 3 }

nbsExpPortTblSquall	OBJECT-TYPE
        SYNTAX  DisplayString
        ACCESS  read-only
        STATUS  mandatory
	DESCRIPTION
		"The Squall Module, if any, attached to this Expansion Port."
        ::= { nbsExpPortEntry 4 }

nbsExpPortTblHwVersion	OBJECT-TYPE
        SYNTAX  DisplayString
        ACCESS  read-only
        STATUS  mandatory
	DESCRIPTION
		"A description of the Hardware Version of the Expansion Port."
        ::= { nbsExpPortEntry 5 }

nbsExpPortTblMCodeVrsn	OBJECT-TYPE
        SYNTAX  DisplayString
        ACCESS  read-only
        STATUS  mandatory
	DESCRIPTION
		"A description of the Hardware Version of the Expansion Port."
        ::= { nbsExpPortEntry 6 }

nbsExpPortTblSwVersion	OBJECT-TYPE
        SYNTAX  DisplayString
        ACCESS  read-only
        STATUS  mandatory
	DESCRIPTION
		"A description of the Software Version of the Expansion Port."
        ::= { nbsExpPortEntry 7 }

nbsExpPortTblStatus	OBJECT-TYPE
        SYNTAX  INTEGER {
	    other (1),		-- not running, but no errors (e.g., downloading)
	    ok (2),
	    error (3)
	}
        ACCESS  read-only
        STATUS  mandatory
	DESCRIPTION
		"The status of the Expansion Port."
        ::= { nbsExpPortEntry 8 }

nbsExpPortTftpSwFileName         OBJECT-TYPE
        SYNTAX  DisplayString
        ACCESS  read-write
        STATUS  mandatory
        DESCRIPTION
                "The Software File Name for the Expansion Port. This is the remote
                 file name string provided to the TFTP client application
                 when starting a Firmware Update process.
                 This value is stored in the system NVRAM as well as in 
                 the SNMP Agent current configuration."

        ::= { nbsExpPortEntry 9 }

nbsExpPortInitDownload	OBJECT-TYPE
        SYNTAX  INTEGER{
                active    (1),-- a  download sesssion is activated(WRITE) or active(READ)
                inactive  (2) -- no download sesssion is active(READ)
	}
        ACCESS  read-write
        STATUS  mandatory
        DESCRIPTION
		"This is used to initiate a download session from the TFTP server.
		 The filename which will be requested my be modified via the
		 nbsExpPortTftpSwFileName object.
		 Note that the only writeable value is active(1), if no session is 
		 active at this moment."

        ::= { nbsExpPortEntry 10 }

nbsAtmLanePortMaxNum OBJECT-TYPE
        SYNTAX  INTEGER
        ACCESS  read-only
        STATUS  mandatory
DESCRIPTION ""
        ::= {  nbsAtmLanePortMIB 1 }


nbsAtmLanePortTable OBJECT-TYPE
        SYNTAX  SEQUENCE OF NbsAtmLanePortEntry
        ACCESS  not-accessible
        STATUS  mandatory
        DESCRIPTION
                "A table of Lan Emulation Clients, indexed by the physical port number."
        ::= { nbsAtmLanePortMIB 2 }

nbsAtmLanePortEntry      OBJECT-TYPE
        SYNTAX  NbsAtmLanePortEntry
        ACCESS  not-accessible
        STATUS  mandatory
        DESCRIPTION
                "Contains the features specific to the ATM Lan Emulation Client."
        INDEX { nbsAtmLanePortNumber }

        ::= { nbsAtmLanePortTable 1 }

NbsAtmLanePortEntry ::= SEQUENCE {

		nbsAtmLanePortNumber	INTEGER,
		laneLecsAddress		OCTET STRING(SIZE(20)),
		sonetCircuitId		DisplayString,
		signalingStatus		INTEGER
        }

nbsAtmLanePortNumber	OBJECT-TYPE
        SYNTAX  INTEGER
        ACCESS  read-only
        STATUS  mandatory
	DESCRIPTION
		"The Port Number of the Lan Emulation Client."
        ::= { nbsAtmLanePortEntry 1 }

laneLecsAddress	OBJECT-TYPE
        SYNTAX  OCTET STRING(SIZE(20))
        ACCESS  read-write
        STATUS  mandatory
	DESCRIPTION
		"The ATM Address (20 Octet string) of the desired Lan Emulation
		 Configuration Server."
        ::= { nbsAtmLanePortEntry 2 }

sonetCircuitId	OBJECT-TYPE
        SYNTAX  DisplayString
        ACCESS  read-write
        STATUS  mandatory
	DESCRIPTION
		"The Circuit Identifier, if any for the SONET interface.  This
		 information is typically provided by the owner of the SONET
		 physical line."
        ::= { nbsAtmLanePortEntry 3 }

signalingStatus	OBJECT-TYPE
	SYNTAX  INTEGER	{
	    up(1),
	    down(2)
	}
        ACCESS  read-only
        STATUS  mandatory
	DESCRIPTION
		"The Status of the ATM UNI signaling between the uplink and 
		 the ATM switch"
        ::= { nbsAtmLanePortEntry 4 }

nbsFddiPortMaxNum OBJECT-TYPE
        SYNTAX  INTEGER
        ACCESS  read-only
        STATUS  mandatory
DESCRIPTION ""
        ::= {  nbsFddiPortMIB 1 }


nbsFddiPortTable OBJECT-TYPE
        SYNTAX  SEQUENCE OF NbsFddiPortEntry
        ACCESS  not-accessible
        STATUS  mandatory
        DESCRIPTION
                "A table of FDDI ports, indexed by the physical port number."
        ::= { nbsFddiPortMIB 2 }

nbsFddiPortEntry      OBJECT-TYPE
        SYNTAX  NbsFddiPortEntry
        ACCESS  not-accessible
        STATUS  mandatory
        DESCRIPTION
                "Contains the features specific to the FDDI Port."
        INDEX { nbsFddiPortNumber }

        ::= { nbsFddiPortTable 1 }

NbsFddiPortEntry ::= SEQUENCE {

        nbsFddiPortNumber	INTEGER,
	nbsFddiSmtIndex		INTEGER
        }

nbsFddiPortNumber	OBJECT-TYPE
        SYNTAX  INTEGER
        ACCESS  read-only
        STATUS  mandatory
	DESCRIPTION
		"The Port Number of the Lan Emulation Client."
        ::= { nbsFddiPortEntry 1 }

nbsFddiSmtIndex	OBJECT-TYPE
        SYNTAX  INTEGER
        ACCESS  read-only
        STATUS  mandatory
	DESCRIPTION
		"The FDDI MIB SMT index number of this port"
        ::= { nbsFddiPortEntry 2 }

END
