XYLANTRAP-13-MIB DEFINITIONS ::= BEGIN

	--  RCSID information

	--  $RCSfile: xylan-traps.mib,v $
	--  $Revision: 1.23 $            $State: Exp $
	--  $Date: 1998/09/25 22:45:33 $
	--  $Author: phillier $


	--  xylan-omnicore-trap.mib 
	--  Revision: 1.00
	--  Date: October 21, 1995

	--  Alcatel Internetworking, Inc.
	--  26801 W. Agoura Road
	--  Calabasas, CA 91301
	--  (818) 880-3500
	--  support@ind.alcatel.com

	--  This module provides authoritative definitions for Alcatel Internetworking, Inc.
	--  enterprise specific traps.

	--  This module will be extended, as needed.

	--  Alcatel Internetworking, Inc. reserves the right to make changes in
	--  specification and oher information contained in this document
	--  without prior notice.  The reader should consult Alcatel Internetworking,
	--  Inc. to determine whether any such changes have been made.
	--  Current MIBs are availible from the following URLs:
	--		ftp://ftp.ind.alcatel.com/pub/products/mibs
	--		http://www.ind.alcatel.com

	--  In no event shall Alcatel Internetworking, Inc. be liable for any incidental,
	--  indirect, special, or consequential damages whatsoever (including
	--  but not limited to lost profits) arising out of or related to this
	--  document or the information contained in it, even if Alcatel Internetworking,
	--  Inc. has been advised of, known, or should have known, the
	--  possibility of such damages.
 
	--  Alcatel Internetworking, Inc. grants vendors, end-users, and other interested
	--  parties a non-exclusive license to use this Specification in connection
	--  with the management of Alcatel Internetworking, Inc. products.
 
	--  Copyright (C) 1995, Alcatel Internetworking, Inc. All Rights Reserved.
 

	IMPORTS
	    xylanPnni, xylanSwitchDevice,
	    omniswitch5, omniswitch9, pizzaSwitch, microSwitch, omniAccess512,
	    omnicore13
		FROM XYLAN-BASE-MIB

	    chasControlSlot, chasControlState, chasModuleSlot,
	    chasModuleSubUnit, chasModuleType, chasPowerSupply1State,
	    chasPowerSupply2State, chasModuleOperStatus, chasFanTray1State,
	    chasFanTray2State
		FROM CHASSIS-MIB

	    vBrdgTpFdbAddress, vLanNumber, vLanAdmStatus, 
	    atVLANGroupId, atVLANId, atVLANAdminStatus,
            vDupMacMac, vDupMacSlot, vDupMacIntf, vDupMacTime
		FROM XYLAN-VLAN-MIB

	    phyPortSlot, phyPortIF, phyPortPCause,
	    vportSlot, vportIF, vportFuncType, vportFuncTypeInstance,
	    vportAdmStatus
		FROM PORT-MIB

	    atmxServiceSlotIndex, atmxServicePortIndex, atmxServiceNumber,
	    atmxServiceAdmStatus, atmxPortSlotIndex, atmxPortPortIndex,
	    atmxVccSlotIndex, atmxVccPortIndex, atmxVccVpi,
	    atmxVccVci, atmxVccAdmStatus, atmxPortEnableILMI, atmxPortSSCOPstatus,
	    xylanLecSlotNumber, xylanLecPortNumber, xylanLecServiceNumber,
	    xylanLecReasonOfChange
		FROM XYLAN-ATM-MIB

		fddimibSMTIndex, fddimibSMTCFState, fddimibPORTIndex, 
		fddimibPORTLerFlag, fddimibPORTLCTFailCts
		FROM FDDI-SMT73-MIB

            frxVcControlSlotIndex, frxVcControlPortIndex, frxVcControlDlci
                FROM XYLAN-FRAME-RELAY-MIB
            
	    systemEventTrapNumber
		FROM XYLAN-MGMTSTN-MIB

            xylanIpAssocAddr, xylanIpAssocMac,
            xylanIpAssocSlot, xylanIpAssocIntf,
            xylanIpAssocDupMac,  xylanIpAssocDupSlot, xylanIpAssocDupIntf 
                FROM XYLAN-IP-MIB

	    healthThreshDevTrapData,
            healthThreshModTrapCount, 
            healthThreshModTrapData,
            healthThreshPortTrapSlot, 
            healthThreshPortTrapCount, 
            healthThreshPortTrapData
                FROM XYLAN-HEALTH-MIB

            xPnniFiltIndex,
	    xPnniTrapPnPortId,
	    xPnniTrapRouteAddrAddress,
	    xPnniTrapRouteAddrPrefixLength,
            xPnniTrapNeighborId,
	    xPnniTrapNodeId,
            xPnniTrapNodeDownReason,
	    xPnniTrapNodeDownRemoteIPAddr
                FROM XYLANPNNI-MIB

	    xylnatmClockingxCtrlBusLine,
            xylnatmClockingxSrcOperState
                FROM XYLAN-CSM-MIB

            xylanXIPXMAPLastTrapPort,
            xylanXIPXMAPLastTrapReason,
            xylanXIPXMAPstate,
            xylanXIPGMAPLastTrapReason,
            xylanXIPGMAPLastTrapPort,
            xylanXIPGMAPLastTrapMac,
            xylanXIPGMAPLastTrapProtocol,
            xylanXIPGMAPLastTrapGroup
                FROM XYLAN-XIP-MIB

            xylanAVLlastuser, xylanAVLlastauthevent,
            xylanAVLlastauthmac, xylanAVLlastport,
            xylanAVLlastslot
                FROM XYLAN-AVL-MIB

            atBindRuleGroupId, atBindRuleVlanId,
            atBindRuleIPAddress, atBindRuleMacAddress,
            atBindRuleProtocol, atBindRulePortId,
            atProtoRule, atBindRuleIndex
                FROM XYLAN-VLAN-MIB

            lecControlDirectVci
                FROM LAN-EMULATION-CLIENT-MIB

            mpcRowStatus,
            mpcFlowDetectProtocol,
            mpcStatRxMpoaResolveReplyInsufECResources,
            mpcIngressCacheDestAddr,
            mpcIngressCacheDestAtmAddr,
            mpcIndex,
            mpcMpsIndex,
            mpcRetryTimeMaximum 
                FROM MPOA-MIB

            xylanOamF4VPSlotIndex, xylanOamF4VPPortIndex, xylanOamF4VPVpiIndex,
            xylanOamF5VCSlotIndex, xylanOamF5VCPortIndex, xylanOamF5VCVpiIndex,
            xylanOamF5VCVciIndex
                FROM XYLAN-OAM-MIB

	    mplsLdpEntityID, 
            mplsLdpPeerIndex, 
            mplsLdpPeerID, 
            mplsLdpSessionIndex
                FROM MPLS-LDP-MIB
            
	    chasAccountName,
	    chasAccountFileCount,
	    chasAccountFillingLevel,
	    chasAccountThreshold1,
	    chasAccountThreshold2,
	    chasAccountThreshold3,
	    chasAccountDeviceInUse,
	    chasAccountDevicePrimary,
	    chasAccountDeviceSecondary
		FROM CHASSIS-MIB
		
	    lecID,
	    lecActualLanName,
	    lecAtmAddress,
	    lecInterfaceState
		FROM LAN-EMULATION-CLIENT-MIB

            policyEventIndex
                FROM POLICY-MIB

	    TRAP-TYPE
                FROM RFC-1215;

        --  These definitions use the TRAP-TYPE macro as
        --  defined in RFC 1215 [10]
 
	-- traps for the chassis mgr

	tempAlarm13 TRAP-TYPE
	    ENTERPRISE  omnicore13
	    DESCRIPTION
		"A tempAlarm indicates a temperature sensor has changed
		its state from underThreshold(4) to overThreshold(3)."
	    ::= 1
	
	moduleChange13 TRAP-TYPE
	    ENTERPRISE  omnicore13
	    VARIABLES   { chasModuleSlot, chasModuleSubUnit, chasModuleType }
	    DESCRIPTION
		"A moduleChange trap occurs when a module is inserted or
		removed from the chassis."
	    ::= 2

	powerEvent13 TRAP-TYPE
	    ENTERPRISE  omnicore13
	    VARIABLES   { chasPowerSupply1State, chasPowerSupply2State }
	    DESCRIPTION
		"A powerEvent trap occurs when a power supply is inserted or
		removed from the chassis, or a problem condition is
		recognized on a power supply."
	    ::= 3

	controllerEvent13 TRAP-TYPE
	    ENTERPRISE  omnicore13
	    VARIABLES   { chasControlSlot, chasControlState }
	    DESCRIPTION
		"A controlEvent trap occurs when a chassis controller (MPM)
		loses or gains the state of master(3).  If this is due to
		chassis controller being inserted or removed from the slot,
		a moduleChange trap will also be sent."
	    ::= 4

	loginViolation13 TRAP-TYPE
	    ENTERPRISE  omnicore13
	    DESCRIPTION
		"A loginViolation trap occurs when a login attempt fails
		due to an incorrect login-id or password."
	    ::= 5

	macVlanViolation13 TRAP-TYPE
	    ENTERPRISE  omnicore13
	    VARIABLES   { vBrdgTpFdbAddress }
	    DESCRIPTION
		"A macVlanViolation trap occurs when a frame is received from
		a port with a VLAN ID different from the VLAN where the
		frame previously has received."
	    ::= 6

	macDuplicatePort13 TRAP-TYPE
	    ENTERPRISE  omnicore13
	    VARIABLES   { vBrdgTpFdbAddress }
	    DESCRIPTION
		"A macDuplicatePort trap occurs when a frame is received from
		a source port different from the port where the frame previously
		has received although they both ports belong to the same VLAN."
	    ::= 7

	portLinkUpEvent13 TRAP-TYPE
	    ENTERPRISE  omnicore13
	    VARIABLES  { vportSlot, vportIF, vportFuncType,
			 vportFuncTypeInstance }
	    DESCRIPTION
		"A portLinkTrap occurs whenever a phy, log, or virt port
		is enabled."
	    ::= 8

	portLinkDownEvent13 TRAP-TYPE
	    ENTERPRISE  omnicore13
	    VARIABLES  { vportSlot, vportIF, vportFuncType,
			 vportFuncTypeInstance }
	    DESCRIPTION
		"A portLinkTrap occurs whenever a phy, log, or virt port
		is disabled."
	    ::= 9

	portPartitioned13 TRAP-TYPE
	    ENTERPRISE  omnicore13
	    VARIABLES  { vportSlot, vportIF, vportFuncType,
			 vportFuncTypeInstance }
	    DESCRIPTION
		"A portPartioned trap occurs when the physical port
		 has transitioned thru enable/disable states faster
		 than 10 times in the past second...indicative of a
		 flakey cable."
	    ::= 10

	portRecordMismatch13 TRAP-TYPE
	    ENTERPRISE  omnicore13
	    VARIABLES { vportSlot, vportIF, vportFuncType,
			vportFuncTypeInstance }
	    DESCRIPTION
		"A portRecordMismatch trap occurs when the specified
		 port data is found to be diferent than the privious
		 configuration. Typically this will be generated when
		 a NIC of one type is swapped out for a DIFFERENT type.
		 IE ethernet for fddi, atm for token-ring, etc..."
	    ::= 11


	-- group/vlan state changes

	groupChange13 TRAP-TYPE
	    ENTERPRISE  omnicore13
	    VARIABLES { vLanNumber, vLanAdmStatus }
	    DESCRIPTION
		"A groupChange trap occurs whenever a group is
		 created or deleted from the system via the UI
		 or SNMP. The group and status code are sent as
		 part of the variable binding.

		 The status codes are:
			1 - disable
			2 - enable
			3 - delete
			4 - create
			5 - modify	(see xylan-vport MIB)"
	    ::= 14

	vlanChange13 TRAP-TYPE
	    ENTERPRISE  omnicore13
	    VARIABLES { atVLANGroupId, atVLANId, atVLANAdminStatus }
	    DESCRIPTION
		"A vlanChange trap occurs whenever a VLAN is
		 created or deleted from the system via the UI
		 or SNMP. The group, vlan and status code are sent as
		 part of the variable binding. See groupChange for
		 the status codes."
	    ::= 15

	portMove13 TRAP-TYPE
	    ENTERPRISE  omnicore13
	    VARIABLES { vportSlot, vportIF, vportFuncType,
			vportFuncTypeInstance, vportAdmStatus }
	    DESCRIPTION
		"A portMove trap occurs when the specified
		 port is moved from a group/vlan or has had
		 its configuration changed."
	    ::= 16

	moduleResetReload13 TRAP-TYPE
	    ENTERPRISE  omnicore13
	    VARIABLES { chasModuleSlot, chasModuleSubUnit, chasModuleType,
			chasModuleOperStatus }
	    DESCRIPTION
		"A moduleResetReload trap occurs when the specified
		 module has been reset or reloaded by the chassis mgr."
	    ::= 17

	systemEvent13 TRAP-TYPE
	    ENTERPRISE  omnicore13
	    VARIABLES { systemEventTrapNumber }
	    DESCRIPTION
		"A systemEvent trap occurs when a potentially
		 fatal system error occurrs. Such as: out of FLASH/
		 memory space. The event type is in the var bind.
		 A Descriptive string MAY be present. The following
		 trap numbers are defined (see xylan-trapc.mib):

			10	Unspecified log event
			11	Log file full
			12	Log file erased

			20	Unspecified memory event
			21	Memory shortage

			30	Unsepcified CPU event
			31	Long term CPU overload
			32	Short term CPU overload

			40	Unspecified ffs event
			41	Attempt to write to full ffs
			42	System/user directed purge
			43	Removed imgs/cfgs
			44	Exec file removed
			45	Config file removed
			46	Exec file updated
			47	Config file updated

			50	Unspecified chassis event
			51	Module failed to init
			52	Module failed to load
			53	Module startup failed
			54	Module failed
			55	Driver failed "
	    ::= 18

	vlanRouteTableFull13 TRAP-TYPE
	    ENTERPRISE  omnicore13
	    DESCRIPTION
		"A vlanRouteTableFull trap occurs when either the
		 IP or IPX route table is full. (discovered on
		 insertion attempt)"
	    ::= 19

	sapTableFull13 TRAP-TYPE
	    ENTERPRISE  omnicore13
	    DESCRIPTION
		"A sapTableFull trap occurs when the IPX SAP
		 table is found to be full on insertion."
	    ::= 20

	atmSSCOPstate13 TRAP-TYPE
	    ENTERPRISE  omnicore13
	    VARIABLES { atmxPortSlotIndex, atmxPortPortIndex,
	    atmxPortSSCOPstatus }
	    DESCRIPTION
		"A atmSSCOPstate trap occurs when the signalling
		 state for the specified physical port changes."
	    ::= 21

	ilmiState13 TRAP-TYPE
	    ENTERPRISE  omnicore13
	    VARIABLES { atmxPortSlotIndex, atmxPortPortIndex,
			atmxPortEnableILMI }
	    DESCRIPTION
		"A ilmiState trap occurs when the ILMI state for
		 the specified physical port changes."
	    ::= 22

	atmConnection13 TRAP-TYPE
	    ENTERPRISE  omnicore13
	    VARIABLES { atmxVccSlotIndex, atmxVccPortIndex, atmxVccVpi,
			atmxVccVci, atmxVccAdmStatus }
	    DESCRIPTION
		"A atmConnection trap occurs when the specified
		 ATM Vcc is created or deleted."
	    ::= 23

	atmService13 TRAP-TYPE
	    ENTERPRISE  omnicore13
	    VARIABLES { atmxServiceSlotIndex, atmxServicePortIndex,
			atmxServiceNumber, atmxServiceAdmStatus }
	    DESCRIPTION
		"A atmService trap occurs when the specified
		 ATM service is created or deleted>"
	    ::= 24

	dlciNew13 TRAP-TYPE
	    ENTERPRISE  omnicore13
	    VARIABLES { frxVcControlSlotIndex, frxVcControlPortIndex, frxVcControlDlci}
	    DESCRIPTION
		"Frame-Relay Dlci Just Created"
	    ::= 27

	dlciDel13 TRAP-TYPE
	    ENTERPRISE  omnicore13
	    VARIABLES { frxVcControlSlotIndex, frxVcControlPortIndex, frxVcControlDlci}
	    DESCRIPTION
		"Frame-Relay Dlci Just Deleted"
	    ::= 28

	dlciUp13 TRAP-TYPE
	    ENTERPRISE  omnicore13
	    VARIABLES { frxVcControlSlotIndex, frxVcControlPortIndex, frxVcControlDlci}
	    DESCRIPTION
		"Frame-Relay Dlci Just Changed to Active"
	    ::= 29

	dlciDn13 TRAP-TYPE
	    ENTERPRISE  omnicore13
	    VARIABLES { frxVcControlSlotIndex, frxVcControlPortIndex, frxVcControlDlci}
	    DESCRIPTION
		"Frame-Relay Dlci Just Changed to InActive"
	    ::= 30

	portManualForwardingMode13 TRAP-TYPE
	    ENTERPRISE  omnicore13
            VARIABLES { vportSlot, vportIF, vportFuncType,
                        vportFuncTypeInstance }
            DESCRIPTION
                "A portManualForwardingMode trap occurs when the specified
                 port is placed into manual mode forwarding as its default
                 setting whenever the port is assigned to a Group that is
                 participating in the IBM spanning tree algorithm."
            ::= 31

	fddiCFStateChange13 TRAP-TYPE
	    ENTERPRISE  omnicore13
            VARIABLES { fddimibSMTIndex, fddimibSMTCFState }
            DESCRIPTION
                "A fddiCFStateChange trap occurs when the specified
                 fddi physical port changes from wrap configuration state."
            ::= 32

	duplicateIPaddress13 TRAP-TYPE
	    ENTERPRISE  omnicore13
            VARIABLES { xylanIpAssocAddr, xylanIpAssocMac,
                        xylanIpAssocSlot, xylanIpAssocIntf,
                        xylanIpAssocDupMac,  xylanIpAssocDupSlot, 
                        xylanIpAssocDupIntf }
            DESCRIPTION
                "A duplicateIPaddress trap occurs whenever the switch 
                 detects a duplicate IP address."
            ::= 35

	duplicateMACaddress13 TRAP-TYPE
	    ENTERPRISE  omnicore13
            VARIABLES { vDupMacMac, vDupMacSlot,
                        vDupMacIntf, vDupMacTime }
            DESCRIPTION
                "A duplicateMACaddress trap occurs whenever the switch
                 detects a duplicate MAC address of one of its own
                 router ports."
            ::= 36

	healthThresholdRising13 TRAP-TYPE
	    ENTERPRISE  omnicore13
	    DESCRIPTION
		"A healthThresholdRising trap occurs when at least
		 one of the user-specified thresholds is exceeded
		 for the first time."
	    ::= 37

	healthThresholdFalling13 TRAP-TYPE
	    ENTERPRISE  omnicore13
	    DESCRIPTION
		"A healthThresholdFalling trap occurs when at least
		 one of the user-specified thresholds was exceeded
		 during the previous cycle and none of them are exceeded 
		 this cycle."
	    ::= 38

	healthThresholdDevice13 TRAP-TYPE
	    ENTERPRISE  omnicore13
            VARIABLES { healthThreshDevTrapData } 
	    DESCRIPTION
		"A healthThresholdDevice trap occurs when at least
		 one device-level threshold crossing is detected."
	    ::= 39

	healthThresholdModule13 TRAP-TYPE
	    ENTERPRISE  omnicore13
            VARIABLES { healthThreshModTrapCount, 
                        healthThreshModTrapData } 
	    DESCRIPTION
		"A healthThresholdModule trap occurs when at least
		 one module-level threshold crossing is detected."
	    ::= 40

	healthThresholdPort13 TRAP-TYPE
	    ENTERPRISE  omnicore13
            VARIABLES { healthThreshPortTrapSlot, 
                        healthThreshPortTrapCount, 
                        healthThreshPortTrapData } 
	    DESCRIPTION
		"A healthThresholdPort trap occurs when at least
		 one port-level threshold crossing is detected."
	    ::= 63

	xylanXIPXMAPPortStatusChange13 TRAP-TYPE
	    ENTERPRISE  omnicore13
            VARIABLES { xylanXIPXMAPLastTrapPort,
                        xylanXIPXMAPLastTrapReason }
	    DESCRIPTION
		"A xylanXIPXMAPPortStatusChange trap occurs when a 
                 change in status occurs in an XMAP-tracked virtual
                 port."
	    ::= 41

	xylanXIPXMAPStateChange13 TRAP-TYPE
	    ENTERPRISE  omnicore13
            VARIABLES { xylanXIPXMAPstate }
	    DESCRIPTION
		"A xylanXIPXMAPStateChange trap occurs when XMAP
                 is turned on or off."
	    ::= 42

	avlAuthAttempt13 TRAP-TYPE
	    ENTERPRISE  omnicore13
            VARIABLES { xylanAVLlastuser, xylanAVLlastauthevent,
                        xylanAVLlastauthmac, xylanAVLlastport,
                        xylanAVLlastslot }
            DESCRIPTION
                "The last Authenticated VLAN authentication attempt."
            ::= 43

	xylanXIPGMAPFailedUpdate13 TRAP-TYPE
	    ENTERPRISE  omnicore13
            VARIABLES { xylanXIPGMAPLastTrapReason, xylanXIPGMAPLastTrapPort,
            		xylanXIPGMAPLastTrapMac, xylanXIPGMAPLastTrapProtocol,
            		xylanXIPGMAPLastTrapGroup }
	    DESCRIPTION
		"A xylanXIPGMAPFailedUpdate trap occurs when GMAP is unable
		 to update the forwarding database to reflect information 
		 in its internal database."
	    ::= 44

	clkBusLineStateChange13 TRAP-TYPE
	    ENTERPRISE  omnicore13
            VARIABLES { xylnatmClockingxCtrlBusLine,
                        xylnatmClockingxSrcOperState }
	    DESCRIPTION
		"A clkBusLineStateChange trap occurs when 1 of the
	         following occurs at the 8k or the 19m bus line:
                 1) bus line's status changes (active or inactive)
                 2) clock switching has occured

                 The following are sent as part of the variable 
                 binding:

	            Status code: 
                       inactive - 1
	               active   - 2

	            Bus line:
	               eightKhz    - 1
	               nineteenMhz - 2"
	    ::= 45

	bind-violation13 TRAP-TYPE
	    ENTERPRISE  omnicore13
            VARIABLES { atBindRuleGroupId, atBindRuleVlanId,
			atBindRuleIPAddress, atBindRuleMacAddress,
                        atBindRuleProtocol, atBindRulePortId,
                        atProtoRule, atBindRuleIndex }
 	    DESCRIPTION 
                "A bind-violation trap occurs whenever
                 a binding rule which has been configured gets violated."
            ::= 46     
	
	phyPortPartition13 TRAP-TYPE
	    ENTERPRISE  omnicore13
            VARIABLES { phyPortSlot, 
	                phyPortIF, phyPortPCause}
	    DESCRIPTION
                "A phyPortPartition trap occurs when the device detects link
                 state is active for a physical port, but line errors, 
		 or system behaviour, indicate that the cable/media is 
		 unuseable.  The device will then force the disabling of 
		 the port in question and generate this trap.
		 The device will retry using the port in question should a
                 cable drop occur, which may indicate a user has attempted 
		 to fix the bad media."
	    ::= 47

	policyEvent13 TRAP-TYPE
	    ENTERPRISE  omnicore13
            VARIABLES { policyEventIndex  }
            DESCRIPTION
                "This trap signifies that the switch subagent has
                 detected that the event represented by eventIndex has
                 occurred in the switch."
            ::= 48

-- Traps 50-59 are reserved for PNNI...

	pnniRouteConflictPort13 TRAP-TYPE
	    ENTERPRISE  omnicore13
            VARIABLES { xPnniTrapPnPortId, xPnniTrapRouteAddrAddress, 
		           xPnniTrapRouteAddrPrefixLength }
            DESCRIPTION
                "This trap occurs when PNNI detects that a static 
                 route on the pnnixIfPortId port has been created 
                 and this port has been configured as a PNNI port.

                 This may cause mis-routing in a PNNI network if the 
                 port turns out to be an Inside port."
            ::= 50


	pnniRouteConflictSamePG13 TRAP-TYPE
	    ENTERPRISE  omnicore13
            VARIABLES { xPnniTrapPnPortId, xPnniTrapRouteAddrAddress, 
		           xPnniTrapRouteAddrPrefixLength }
            DESCRIPTION
                "This trap occurs when PNNI detects that a static 
                 route on the pnnixIfPortId port has been created 
                 and this route matches (a prefix of) the Peer 
                 Group ID. This may cause mis-routing in a PNNI 
                 network."
            ::= 51

	xPnniFilterAlarm13 TRAP-TYPE
	    ENTERPRISE  omnicore13
            VARIABLES { xPnniFiltIndex }
            DESCRIPTION
                "An alarm indicating that a PNNI filter has denied access
                to a call attempt.  The filter denying the access is
                identified in the variable."
            ::= 52

	xPnniPmPThresholdReached13 TRAP-TYPE
	    ENTERPRISE  omnicore13
            DESCRIPTION
                "An alarm indicating that no more Point-to-Multipoint calls
                 may be established until ongoing PMP calls are released due
                 to capacity restrictions of the local fabric."
            ::= 53

	xPnniDtlTableExhaustion13 TRAP-TYPE
	    ENTERPRISE  omnicore13
            DESCRIPTION
                "An alarm indicating that no more calls may be established
                due to capacity restrictions of the DTL Table."
            ::= 54

	xPnniNeighborFailure13 TRAP-TYPE
	    ENTERPRISE  omnicore13
            VARIABLES { xPnniTrapNeighborId, xPnniTrapPnPortId } 
            DESCRIPTION
                "An alarm indicating that a neighbor on a particular port 
                has ceased communication with this switching system."
            ::= 55

	xPnniNodeDown13 TRAP-TYPE
	    ENTERPRISE  omnicore13
            VARIABLES { xPnniTrapNodeId, xPnniTrapNodeDownReason,
                        xPnniTrapNodeDownRemoteIPAddr } 
            DESCRIPTION
                "An alarm indicating that a PNNI node (instance) within
                 this switching system has been disabled and the reason.
                 If the reason is due to remote action, the IP address
                 causing the action is specified in the trap."
            ::= 56

	xPnniLinkFailure13 TRAP-TYPE
	    ENTERPRISE  omnicore13
            VARIABLES { xPnniTrapPnPortId } 
            DESCRIPTION
                "An alarm indicating that a particular port has transitioned
                from operational state within this switching system."
            ::= 57

	fddiLerFlagChange13 TRAP-TYPE
	    ENTERPRISE  omnicore13
            VARIABLES { fddimibSMTIndex, fddimibPORTIndex, fddimibPORTLerFlag }
            DESCRIPTION
                "A fddiLerFlagChange trap occurs when the LER flag on a port
                 changes from CLEAR to SET."
            ::= 65 

	fddiLCTFailCntIncr13 TRAP-TYPE
	    ENTERPRISE  omnicore13
            VARIABLES { fddimibSMTIndex, fddimibPORTIndex, fddimibPORTLCTFailCts}
            DESCRIPTION
                "A fddiLCTFailCntIncr trap occurs when the LCT flag on a port
                 is incremented."
            ::= 66
	    
-- Traps 67, 68, 69 are reserved for MPOA MPC

	mpcStatisticsOverflow13 TRAP-TYPE
	    ENTERPRISE  omnicore13
            VARIABLES { mpcIndex, mpcStatRxMpoaResolveReplyInsufECResources } 
            DESCRIPTION
                "A statistic overflow trap occurs when a paticular entry of mpcStatisticsTable 
		reach the threshold value, the paticular statistics is identified by 
		statisticsNum of trap data which is the entry index of the mpcStatisticsTable.
		The current threshold valye is hard coded to 2024.
		The Trap PDU data format:
		struct {
                unsigned int mpcIndex;             Index of MPC 
		unsigned int statisticsNum;        Entry Index of mpcStatisticsTable
		unsigned long statisticsThreshold; Trap Threshold Value of Entry
		unsigned long statisticsValue;     Current Statistics Value of Entry
		}
                where statisticsNum, statisticsThreshold and statisticsValue entry 
                attached with objecid mpcStatRxMpoaResolveReplyInsufECResources" 
            ::= 67
	    
	mpcShortCut13 TRAP-TYPE
	    ENTERPRISE  omnicore13
            VARIABLES { mpcRowStatus, lecControlDirectVci, mpcFlowDetectProtocol,
                        mpcIngressCacheDestAddr, mpcIngressCacheDestAtmAddr, mpcIndex, mpcMpsIndex } 
            DESCRIPTION
                "A shortcut trap occurs when the shortcut path established, closed or
		failed to complete path.
                event type: 01	shortcut established
			    02	shortcut closed
			    03	failed to complete path

		The Trap PDU data format:
		struct {
		unsigned int event_type;
		unsigned int vcNumber;           VCI number of destination
		unsigned int prototype;          1: IP, 11: IPX
		unsigned char destNet_addr[10];	 IP or IPX address of destination
		unsigned char destAtm_addr[20];	 ATM address of destination
		unsigned int mpcIndex;           Index of MPC
		unsigned int mpsIndex;           Index of MPS
		}"
            ::= 68
	    
	mpcIngressRetryTimeOut13 TRAP-TYPE
	    ENTERPRISE  omnicore13
            VARIABLES { mpcIndex, mpcRetryTimeMaximum, mpcIngressCacheDestAddr,
                        mpcIngressCacheDestAtmAddr, mpcFlowDetectProtocol, mpcMpsIndex   } 
            DESCRIPTION
                "A ingress retry timeout trap occurs when the retry time exceed the 
		MPC-p5 time.
		The Trap PDU data format:
		struct {
		unsigned int mpcIndex;           Index of MPC
		unsigned int max_timeout_sec;    Timeout value in second
		unsigned char destNet_addr[10];  IP or IPX address of destination
		unsigned char destAtm_addr[20];  ATM address of destination
		unsigned int prototype;          1: IP, 11: IPX
		unsigned int mpsIndex;           Index of MPS
		}"
            ::= 69 

-- Traps 70-79 are reserved for OAM...
--   The section describes the traps defined for F4/F5 OAM

	oamVCAIS13 TRAP-TYPE
	    ENTERPRISE  omnicore13
          VARIABLES     {
                             xylanOamF5VCSlotIndex,
                             xylanOamF5VCPortIndex,
                             xylanOamF5VCVpiIndex,
                             xylanOamF5VCVciIndex
                        }
          DESCRIPTION   
              "This trap signifies that the specified connection is in VC-AIS 
               state."
          ::= 71

	oamVCRDI13 TRAP-TYPE
	    ENTERPRISE  omnicore13
          VARIABLES     {
                             xylanOamF5VCSlotIndex,
                             xylanOamF5VCPortIndex,
                             xylanOamF5VCVpiIndex,
                             xylanOamF5VCVciIndex
                        }
          DESCRIPTION   
              "This trap signifies that the specified connection is in VC-RDI 
               state."
          ::= 72

	oamVCLOC13 TRAP-TYPE
	    ENTERPRISE  omnicore13
          VARIABLES     {
                             xylanOamF5VCSlotIndex,
                             xylanOamF5VCPortIndex,
                             xylanOamF5VCVpiIndex,
                             xylanOamF5VCVciIndex
                        }
          DESCRIPTION   
              "This trap signifies that the specified connection is in VC-LOC 
               state."
          ::= 73

	oamVCUnsuccessLoop13 TRAP-TYPE
	    ENTERPRISE  omnicore13
          VARIABLES     {
                             xylanOamF5VCSlotIndex,
                             xylanOamF5VCPortIndex,
                             xylanOamF5VCVpiIndex,
                             xylanOamF5VCVciIndex
                        }
          DESCRIPTION 
              "This trap signifies that the specified connection is unsuccessful 
               Loopback state."
          ::= 74

	oamVPAIS13 TRAP-TYPE
	    ENTERPRISE  omnicore13
          VARIABLES     {
                             xylanOamF4VPSlotIndex,
                             xylanOamF4VPPortIndex,
                             xylanOamF4VPVpiIndex
                        }
          DESCRIPTION 
              "This trap signifies that the specified VP connection is in VP-AIS 
               state."
          ::= 75

	oamVPRDI13 TRAP-TYPE
	    ENTERPRISE  omnicore13
          VARIABLES     {
                             xylanOamF4VPSlotIndex,
                             xylanOamF4VPPortIndex,
                             xylanOamF4VPVpiIndex
                        }
          DESCRIPTION 
              "This trap signifies that the specified VP connection is in VP-RDI 
               state."
          ::= 76

	oamVPLOC13 TRAP-TYPE
	    ENTERPRISE  omnicore13
          VARIABLES     {
                             xylanOamF4VPSlotIndex,
                             xylanOamF4VPPortIndex,
                             xylanOamF4VPVpiIndex
                        }
          DESCRIPTION
              "This trap signifies that the specified VP connection is in VP-LOC 
               state."
          ::= 77

	oamVPUnsuccessLoop13 TRAP-TYPE
	    ENTERPRISE  omnicore13
          VARIABLES     {
                             xylanOamF4VPSlotIndex,
                             xylanOamF4VPPortIndex,
                             xylanOamF4VPVpiIndex
                        }
          DESCRIPTION 
              "This trap signifies that the specified VP connection is in  
               Unsuccessful loopback state."
          ::= 78

-- Traps 80-85 are reserved for MPLS

	ldpPeerCreate13 TRAP-TYPE
	    ENTERPRISE  omnicore13
	    VARIABLES   { mplsLdpEntityID, mplsLdpPeerIndex, mplsLdpPeerID}
	    DESCRIPTION
		"A LDP peer is identified by LDP Hello mechanism and
		peer entry is created."
	    ::= 80
										 
	ldpPeerDelete13 TRAP-TYPE
	    ENTERPRISE  omnicore13
	    VARIABLES   { mplsLdpEntityID, mplsLdpPeerIndex, mplsLdpPeerID}
	    DESCRIPTION
		"A LDP peer is lost and peer entry is deleted."
	    ::= 81
																			  
	ldpSessionCreate13 TRAP-TYPE
	    ENTERPRISE  omnicore13
	    VARIABLES   { mplsLdpEntityID, mplsLdpPeerIndex, mplsLdpPeerID, mplsLdpSessionIndex}
	    DESCRIPTION
		"A LDP session with the peer is established and a session entry
		is created."
	    ::= 82
		
	ldpSessionDelete13 TRAP-TYPE
	    ENTERPRISE  omnicore13
	    VARIABLES   { mplsLdpEntityID, mplsLdpPeerIndex, mplsLdpPeerID, mplsLdpSessionIndex}
	    DESCRIPTION
		"A LDP session with the peer is lost and session entry is deleted."
	    ::= 83

-- Accounting related traps 86-95

	accountEvent13 TRAP-TYPE
	    ENTERPRISE  omnicore13
		VARIABLES { chasAccountName , chasAccountFileCount }
		DESCRIPTION
			"An account event is generated to signal that a
		 	new accounting file is available on the switch."
		::= 86


	accountOver1Event13 TRAP-TYPE
	    ENTERPRISE  omnicore13
		VARIABLES { chasAccountFillingLevel,chasAccountThreshold1 } 
		DESCRIPTION
			"This event is generated when the filling level
		 	exceeds the first threshold.
		 	This event is for information only, and signals
		 	that accounting data are accumulating on the switch."
		::= 87


	accountUnder1Event13 TRAP-TYPE
	    ENTERPRISE  omnicore13
		VARIABLES { chasAccountFillingLevel,chasAccountThreshold1 }
		DESCRIPTION
			"This event is generated when the filling level
		 	goes below the first threshold.
		 	This event is for information only."
		::= 88


	accountOver2Alarm13 TRAP-TYPE
	    ENTERPRISE  omnicore13
		VARIABLES { chasAccountFillingLevel,chasAccountThreshold2,
 				chasAccountDeviceInUse}
		DESCRIPTION
			"This alarm is generated when the filling level
		 	exceeds the second threshold.
		 	It signals that the switch changes over to the 
			 alternate collection device."
		::= 89

	accountUnder2Event13 TRAP-TYPE
	    ENTERPRISE  omnicore13
		VARIABLES { chasAccountFillingLevel,chasAccountThreshold2}
		DESCRIPTION
			"This event is generated when the filling level
		 	is lowering below the second threshold."
		::= 90


	accountOver3Alarm13 TRAP-TYPE
	    ENTERPRISE  omnicore13
		VARIABLES { chasAccountFillingLevel,chasAccountThreshold3 }
		DESCRIPTION
		 	"This event is generated when the filling level
			 exceeds the third threshold.
		 	It signals that the switch is now in congestion."
		::= 91


	accountUnder3Event13 TRAP-TYPE
	    ENTERPRISE  omnicore13
		VARIABLES { chasAccountFillingLevel,chasAccountThreshold3}
		DESCRIPTION
			"This event is generated when the filling level
		 	is lowering below the third threshold."
		::= 92


	accountNoDeviceAlarm13 TRAP-TYPE
	    ENTERPRISE  omnicore13
		VARIABLES { chasAccountDevicePrimary, 
 			chasAccountDeviceSecondary}
		DESCRIPTION
			"This alarm is generated when the TCP connection
		 	establishment fails with both the primary and the
		 	secondary collection devices."
		::= 93


	accountFileAlarm13 TRAP-TYPE
	    ENTERPRISE  omnicore13
		VARIABLES { chasAccountFileCount }
		DESCRIPTION
			"This alarm is generated when too many files are
 			awaiting collection."
		::= 94

	lecStateChangeEvent13 TRAP-TYPE
	    ENTERPRISE  omnicore13
            VARIABLES { lecID, lecActualLanName, lecAtmAddress, xylanLecSlotNumber,
                        xylanLecPortNumber, xylanLecServiceNumber, lecInterfaceState, lecInterfaceState, xylanLecReasonOfChange }
            DESCRIPTION
                "When a Lec status changes, a trap message will be send out to a network
                 manager, the trap packet has the data format:

                        struct {
                 unsigned int lec_id;
                 unsigned char elan_name[33];
                 unsigned char atm_addr[20];
                 unsigned int slot_number;
                 unsigned int port_number;
                 unsigned int service_number;
                 unsigned int new_state;
                 unsigned int pre_state;
                 unsigned int reason_of_change;
                 }"
            ::= 96

	fantrayEvent13 TRAP-TYPE
	    ENTERPRISE  omnicore13
            VARIABLES   { chasFanTray1State, chasFanTray2State } 
            DESCRIPTION 
                "A fantrayEvent trap occurs when a problem condition
		 is recognized on a chassis fan tray."
            ::= 97

	sonetAisTypeTrap13 TRAP-TYPE
	    ENTERPRISE  omnicore13
	    VARIABLES {atmxServiceSlotIndex, atmxServicePortIndex, 
                   xylanLecServiceNumber, xylanLecServiceNumber }
		DESCRIPTION
			"This trap is generated when there is any of the following
            AIS types of errors on Sonet PMC 
            SONET_LINK_RX_AIS,
            SEC_LINE_AIS,
            SEC_PATH_AIS."
		::= 98

	sonetRdiTypeTrap13 TRAP-TYPE
	    ENTERPRISE  omnicore13
	    VARIABLES {atmxServiceSlotIndex, atmxServicePortIndex, 
                   xylanLecServiceNumber, xylanLecServiceNumber }
		DESCRIPTION
			"This trap is generated when there is any of the following
            RDI types of errors on Sonet
            SONET_LINK_RX_RDI,
            SEC_LINE_RDI,
            SEC_PATH_RDI."
		::= 99
	END
