-- Teldat, S.A.

    -- Parque Tecnolgico de Madrid

    -- 28760, Tres Cantos (Madrid)

    -- Tlf: +34-918076565

    -- Fax: +34-918076521

    -- e-mail: id@teldat.es


    -- MIB privada de Teldat

    -- Monitorizacin del equipo VisorALARM


    -- Historial:

    -- 1.0  14/02/07  J. Rodrigo        Codificacin inicial.
--------------------------------------------------------------------------------

TELDAT-MON-VisorALARM-MIB DEFINITIONS ::= BEGIN

    IMPORTS
            OBJECT-TYPE
        FROM RFC-1212
            telproducts
        FROM TELDAT-MIB;


    -- Grupos en la MIB de TELDAT

    -- teladmin                         OBJECT IDENTIFIER ::= {teldat 1}
    -- telxface                         OBJECT IDENTIFIER ::= {teldat 2}
    -- telproto                         OBJECT IDENTIFIER ::= {teldat 3}
    -- telProducts                      OBJECT IDENTIFIER ::= {teldat 4}
    -- telDot3ChipSets                  OBJECT IDENTIFIER ::= {teldat 5}

    -- Grupo telproducts

    telProductsVisorAlarm               OBJECT IDENTIFIER ::= {telproducts 153}

    -- Grupo telProductsVisorAlarm

    telProductsVAlarmMonitor            OBJECT IDENTIFIER ::= {telProductsVisorAlarm 2}

    -- Grupo telProductsVAlarmMonitor

    -- Grupo de parmetros globales de monitorizacin

    telProductsVAlarmMonGlobal          OBJECT IDENTIFIER ::= {telProductsVAlarmMonitor 1}

    telProductsVAlarmMonFrontal OBJECT-TYPE
        SYNTAX INTEGER{
            yes(1),
            no(2)
            }
        ACCESS read-only
        STATUS mandatory
        DESCRIPTION
        ""
        ::= {telProductsVAlarmMonGlobal 1}

    -- Tabla de LEDs

    telProductsVAlarmMonLedTable OBJECT-TYPE
        SYNTAX SEQUENCE OF TelProductsVAlarmMonLedEntry
        ACCESS not-accessible
        STATUS mandatory
        DESCRIPTION
        ""
        ::= {telProductsVAlarmMonitor 2}

    telProductsVAlarmMonLedEntry OBJECT-TYPE
        SYNTAX TelProductsVAlarmMonLedEntry
        ACCESS not-accessible
        STATUS mandatory
        DESCRIPTION
        ""
        INDEX {telProductsVAlarmMonLedIndex}
        ::= {telProductsVAlarmMonLedTable 1}

    TelProductsVAlarmMonLedEntry ::=
        SEQUENCE {
            telProductsVAlarmMonLedIndex
                INTEGER,
            telProductsVAlarmMonLedStatus
                INTEGER
            }

    telProductsVAlarmMonLedIndex OBJECT-TYPE
        SYNTAX INTEGER
        ACCESS read-only
        STATUS mandatory
        DESCRIPTION
        ""
        ::= {telProductsVAlarmMonLedEntry 1}

    telProductsVAlarmMonLedStatus OBJECT-TYPE
        SYNTAX INTEGER{
            off(0),
            red(1),
            green(2),
            orange(3),
            blink(4)
            }
        ACCESS read-only
        STATUS mandatory
        DESCRIPTION
        ""
        ::= {telProductsVAlarmMonLedEntry 2}

END
