PSA-LinGrmpdTrap-MIB DEFINITIONS ::= BEGIN

--PRIMEQUEST system management MIB for Partition
--
--
--$Copyright$
--Copyright Fujitsu Limited 2004 - 2008
--All rights reserved
--
--
--MIB Revision: 01180001
--

IMPORTS
	OBJECT-TYPE								FROM RFC-1212
	TRAP-TYPE								FROM RFC-1215
	mib-2, DisplayString					FROM RFC1213-MIB
	TimeTicks, Counter, Gauge, IpAddress	FROM RFC1155-SMI
	mgmt, enterprises						FROM RFC1155-SMI;

--enterprises	OBJECT IDENTIFIER ::={ iso org(3) dod(6) internet(1) private(4) 1 }
--
--PRIMEQUEST system management MIB nodes
--fujitsu:                    1.3.6.1.4.1.211
-- products:                  1.3.6.1.4.1.211.1
--  iaServer:                 1.3.6.1.4.1.211.1.31
--   primequest:              1.3.6.1.4.1.211.1.31.1
--    partition:	           1.3.6.1.4.1.211.1.31.1.2
--
--Trap enterprise is "psaLinGrmpdTrap"

--FUJITSU PRIMEQUEST system management MIB nodes for Partition
  fujitsu        OBJECT IDENTIFIER  ::={ enterprises 211 }
  products       OBJECT IDENTIFIER  ::={ fujitsu 1 }
  iaServer       OBJECT IDENTIFIER  ::={ products 31 }
  primequest     OBJECT IDENTIFIER  ::={ iaServer 1 }
   partition     OBJECT IDENTIFIER  ::={ primequest 2 }
    parititonVariables	OBJECT IDENTIFIER	::={ partition	200 }
    partitionEnterprise		OBJECT IDENTIFIER  ::={ partition 201 }
     psaComTrap				OBJECT IDENTIFIER  ::={ partitionEnterprise 1 }
     psaLinLanComTrap			OBJECT IDENTIFIER  ::={ partitionEnterprise 2 }
     psaLinIntelE100Trap		OBJECT IDENTIFIER  ::={ partitionEnterprise 3 }
     psaLinIntelE1000Trap		OBJECT IDENTIFIER  ::={ partitionEnterprise 4 }
     psaLinBcm5700Trap			OBJECT IDENTIFIER  ::={ partitionEnterprise 5 }
     psaLinEmulexTrap			OBJECT IDENTIFIER  ::={ partitionEnterprise 6 }
     psaLinLsiLogicTrap		OBJECT IDENTIFIER  ::={ partitionEnterprise 7 }
     psaLinScsiComTrap			OBJECT IDENTIFIER  ::={ partitionEnterprise 8 }
     psaLinGrmpdTrap			OBJECT IDENTIFIER  ::={ partitionEnterprise 9 }
     psaLinGdsTrap				OBJECT IDENTIFIER  ::={ partitionEnterprise 10 }
     psaLinGlsTrap				OBJECT IDENTIFIER  ::={ partitionEnterprise 11 }
     psaLinTg3Trap				OBJECT IDENTIFIER  ::={ partitionEnterprise 12 }
     psaLinIbTrap				OBJECT IDENTIFIER  ::={ partitionEnterprise 13 }
     psaLinXframe2Trap			OBJECT IDENTIFIER  ::={ partitionEnterprise 14 }
     psaGschTrap				OBJECT IDENTIFIER  ::={ partitionEnterprise 15 }
     psaLinIntelE1000ETrap		OBJECT IDENTIFIER  ::={ partitionEnterprise 16 }
     psaExternalFileUnitTrap	OBJECT IDENTIFIER  ::={ partitionEnterprise 101 }

--***************************************************************************************
--
--FUJITSU PRIMEQUEST system management trap parameter variables for Partition
--	They aren't directly accessibles(can't use snmp get/set command), but sent with trap
--
--***************************************************************************************

     trapVarComInfo	OBJECT IDENTIFIER	::={ parititonVariables 1 }

trapPartitionName OBJECT-TYPE
   SYNTAX   DisplayString
   ACCESS   not-accessible
   STATUS   mandatory
   DESCRIPTION "Partition name which trap is generated."
   ::= { trapVarComInfo 1 }

trapPartitionId OBJECT-TYPE
   SYNTAX   INTEGER
   ACCESS   not-accessible
   STATUS   mandatory
   DESCRIPTION "Paritition identifier which trap is generated."
   ::= { trapVarComInfo 2 }

trapEventLevel OBJECT-TYPE
   SYNTAX   DisplayString
   ACCESS   not-accessible
   STATUS   mandatory
   DESCRIPTION "Event level"
   ::= { trapVarComInfo 3 }

trapEventId OBJECT-TYPE
   SYNTAX   INTEGER
   ACCESS   not-accessible
   STATUS   mandatory
   DESCRIPTION "Event Identifier"
   ::= { trapVarComInfo 4 }

trapUnitName OBJECT-TYPE
   SYNTAX   DisplayString
   ACCESS   not-accessible
   STATUS   mandatory
   DESCRIPTION "Unit name which trap is generated."
   ::= { trapVarComInfo 5 }

trapMmbVip OBJECT-TYPE
   SYNTAX   DisplayString
   ACCESS   not-accessible
   STATUS   mandatory
   DESCRIPTION "Management board vertual IP address."
   ::= { trapVarComInfo 6 }

     trapVarDivInfo	OBJECT IDENTIFIER	::={ parititonVariables 2 }

trapPartNo OBJECT-TYPE
   SYNTAX   DisplayString
   ACCESS   not-accessible
   STATUS   mandatory
   DESCRIPTION "Parts number of trap source."
   ::= { trapVarDivInfo 1 }

trapStepping OBJECT-TYPE
   SYNTAX   DisplayString
   ACCESS   not-accessible
   STATUS   mandatory
   DESCRIPTION " "
   ::= { trapVarDivInfo 2 }

trapSerialNo OBJECT-TYPE
   SYNTAX   DisplayString
   ACCESS   not-accessible
   STATUS   mandatory
   DESCRIPTION "Serial number of trap source. "
   ::= { trapVarDivInfo 3 }

trapModelNo OBJECT-TYPE
   SYNTAX   DisplayString
   ACCESS   not-accessible
   STATUS   mandatory
   DESCRIPTION "Model number of trap source."
   ::= { trapVarDivInfo 4 }

trapSuspect OBJECT-TYPE
   SYNTAX   DisplayString
   ACCESS   not-accessible
   STATUS   mandatory
   DESCRIPTION "Logical name or pci bus number of trap source."
   ::= { trapVarDivInfo 5 }

trapVendorId OBJECT-TYPE
   SYNTAX   DisplayString
   ACCESS   not-accessible
   STATUS   mandatory
   DESCRIPTION "Vendor identifier of trap source."
   ::= { trapVarDivInfo 6 }

trapDeviceId OBJECT-TYPE
   SYNTAX   DisplayString
   ACCESS   not-accessible
   STATUS   mandatory
   DESCRIPTION "Device identifier of trap source."
   ::= { trapVarDivInfo 7 }

trapRevision OBJECT-TYPE
   SYNTAX   DisplayString
   ACCESS   not-accessible
   STATUS   mandatory
   DESCRIPTION "Revision of trap source."
   ::= { trapVarDivInfo 8 }

trapCardName OBJECT-TYPE
   SYNTAX   DisplayString
   ACCESS   not-accessible
   STATUS   mandatory
   DESCRIPTION "Device name of trap source."
   ::= { trapVarDivInfo 9 }

trapErrDetail OBJECT-TYPE
   SYNTAX   DisplayString
   ACCESS   not-accessible
   STATUS   mandatory
   DESCRIPTION " "
   ::= { trapVarDivInfo 10 }

trapErrCode OBJECT-TYPE
   SYNTAX   DisplayString
   ACCESS   not-accessible
   STATUS   mandatory
   DESCRIPTION " "
   ::= { trapVarDivInfo 11 }

trapIrpCode OBJECT-TYPE
   SYNTAX   DisplayString
   ACCESS   not-accessible
   STATUS   mandatory
   DESCRIPTION " "
   ::= { trapVarDivInfo 12 }

trapHbaNo OBJECT-TYPE
   SYNTAX   INTEGER
   ACCESS   not-accessible
   STATUS   mandatory
   DESCRIPTION " "
   ::= { trapVarDivInfo 13 }

trapErrCause OBJECT-TYPE
   SYNTAX   DisplayString
   ACCESS   not-accessible
   STATUS   mandatory
   DESCRIPTION " "
   ::= { trapVarDivInfo 14 }

trapPathNo OBJECT-TYPE
   SYNTAX   INTEGER
   ACCESS   not-accessible
   STATUS   mandatory
   DESCRIPTION " "
   ::= { trapVarDivInfo 15 }

trapDiskId OBJECT-TYPE
   SYNTAX   DisplayString
   ACCESS   not-accessible
   STATUS   mandatory
   DESCRIPTION " "
   ::= { trapVarDivInfo 16 }

trapFmrDiskId OBJECT-TYPE
   SYNTAX   DisplayString
   ACCESS   not-accessible
   STATUS   mandatory
   DESCRIPTION " "
   ::= { trapVarDivInfo 17 }

trapCurDiskId OBJECT-TYPE
   SYNTAX   DisplayString
   ACCESS   not-accessible
   STATUS   mandatory
   DESCRIPTION " "
   ::= { trapVarDivInfo 18 }

trapPathId OBJECT-TYPE
   SYNTAX   DisplayString
   ACCESS   not-accessible
   STATUS   mandatory
   DESCRIPTION " "
   ::= { trapVarDivInfo 19 }

trapPhysIf OBJECT-TYPE
   SYNTAX   DisplayString
   ACCESS   not-accessible
   STATUS   mandatory
   DESCRIPTION " "
   ::= { trapVarDivInfo 20 }

trapVirtualIf OBJECT-TYPE
   SYNTAX   DisplayString
   ACCESS   not-accessible
   STATUS   mandatory
   DESCRIPTION " "
   ::= { trapVarDivInfo 21 }

trapLogicalIp OBJECT-TYPE
   SYNTAX   DisplayString
   ACCESS   not-accessible
   STATUS   mandatory
   DESCRIPTION " "
   ::= { trapVarDivInfo 22 }

trapWatchIp OBJECT-TYPE
   SYNTAX   DisplayString
   ACCESS   not-accessible
   STATUS   mandatory
   DESCRIPTION " "
   ::= { trapVarDivInfo 23 }

trapInterface OBJECT-TYPE
   SYNTAX   DisplayString
   ACCESS   not-accessible
   STATUS   mandatory
   DESCRIPTION " "
   ::= { trapVarDivInfo 24 }

trapSourceIp OBJECT-TYPE
   SYNTAX   DisplayString
   ACCESS   not-accessible
   STATUS   mandatory
   DESCRIPTION " "
   ::= { trapVarDivInfo 25 }

trapDestIp OBJECT-TYPE
   SYNTAX   DisplayString
   ACCESS   not-accessible
   STATUS   mandatory
   DESCRIPTION " "
   ::= { trapVarDivInfo 26 }

trapModelName OBJECT-TYPE
   SYNTAX   DisplayString
   ACCESS   not-accessible
   STATUS   mandatory
   DESCRIPTION "Model name of trap source."
   ::= { trapVarDivInfo 27 }

trapFlagcode OBJECT-TYPE
   SYNTAX   DisplayString
   ACCESS   not-accessible
   STATUS   mandatory
   DESCRIPTION " "
   ::= { trapVarDivInfo 28 }

--***************************************************************************************
--
--FUJITSU PRIMEQUEST system management TRAP definition for Partition
--	Trap enterprise:	psaLinGrmpdTrap (.1.3.6.1.4.1.211.1.31.1.2.201.9)
--
--***************************************************************************************

grmpdEvent0 TRAP-TYPE
   ENTERPRISE   psaLinGrmpdTrap
   VARIABLES {
      trapPartitionName,
      trapPartitionId,
      trapEventLevel,
      trapEventId,
      trapUnitName,
      trapMmbVip
   }
   DESCRIPTION "GRMPD: Software error (No Host Template)"
   --#TYPE			"Grmpd Event 0"
   --#SUMMARY		"%s(PID=%d) %s %d %s GRMPD: Software error (No Host Template)"
   --#ARGUMENTS		{ 0, 1, 2, 3, 4 }
   --#SEVERITY		MAJOR
   ::= 15000

grmpdEvent1 TRAP-TYPE
   ENTERPRISE   psaLinGrmpdTrap
   VARIABLES {
      trapPartitionName,
      trapPartitionId,
      trapEventLevel,
      trapEventId,
      trapUnitName,
      trapErrDetail,
      trapMmbVip
   }
   DESCRIPTION "GRMPD: Software error (No Entry )"
   --#TYPE			"Grmpd Event 1"
   --#SUMMARY		"%s(PID=%d) %s %d %s GRMPD: Software error (No Entry %s)"
   --#ARGUMENTS		{ 0, 1, 2, 3, 4, 5 }
   --#SEVERITY		MAJOR
   ::= 15001

grmpdEvent2 TRAP-TYPE
   ENTERPRISE   psaLinGrmpdTrap
   VARIABLES {
      trapPartitionName,
      trapPartitionId,
      trapEventLevel,
      trapEventId,
      trapUnitName,
      trapMmbVip
   }
   DESCRIPTION "GRMPD: Software error (memory allocate failed)"
   --#TYPE			"Grmpd Event 2"
   --#SUMMARY		"%s(PID=%d) %s %d %s GRMPD: Software error (memory allocate failed)"
   --#ARGUMENTS		{ 0, 1, 2, 3, 4 }
   --#SEVERITY		MAJOR
   ::= 15002

grmpdEvent3 TRAP-TYPE
   ENTERPRISE   psaLinGrmpdTrap
   VARIABLES {
      trapPartitionName,
      trapPartitionId,
      trapEventLevel,
      trapEventId,
      trapUnitName,
      trapMmbVip
   }
   DESCRIPTION "GRMPD: Software error (vhba instance overflow)"
   --#TYPE			"Grmpd Event 3"
   --#SUMMARY		"%s(PID=%d) %s %d %s GRMPD: Software error (vhba instance overflow)"
   --#ARGUMENTS		{ 0, 1, 2, 3, 4 }
   --#SEVERITY		MAJOR
   ::= 15003

grmpdEvent4 TRAP-TYPE
   ENTERPRISE   psaLinGrmpdTrap
   VARIABLES {
      trapPartitionName,
      trapPartitionId,
      trapEventLevel,
      trapEventId,
      trapUnitName,
      trapMmbVip
   }
   DESCRIPTION "GRMPD: Software error (Scsi_Done free space not found)"
   --#TYPE			"Grmpd Event 4"
   --#SUMMARY		"%s(PID=%d) %s %d %s GRMPD: Software error (Scsi_Done free space not found)"
   --#ARGUMENTS		{ 0, 1, 2, 3, 4 }
   --#SEVERITY		MAJOR
   ::= 15004

grmpdEvent5 TRAP-TYPE
   ENTERPRISE   psaLinGrmpdTrap
   VARIABLES {
      trapPartitionName,
      trapPartitionId,
      trapEventLevel,
      trapEventId,
      trapUnitName,
      trapMmbVip
   }
   DESCRIPTION "GRMPD: Software error (internal error)"
   --#TYPE			"Grmpd Event 5"
   --#SUMMARY		"%s(PID=%d) %s %d %s GRMPD: Software error (internal error)"
   --#ARGUMENTS		{ 0, 1, 2, 3, 4 }
   --#SEVERITY		MAJOR
   ::= 15005

grmpdEvent6 TRAP-TYPE
   ENTERPRISE   psaLinGrmpdTrap
   VARIABLES {
      trapPartitionName,
      trapPartitionId,
      trapEventLevel,
      trapEventId,
      trapUnitName,
      trapMmbVip
   }
   DESCRIPTION "GRMPD: Software error (memory allocate failed)"
   --#TYPE			"Grmpd Event 6"
   --#SUMMARY		"%s(PID=%d) %s %d %s GRMPD: Software error (memory allocate failed)"
   --#ARGUMENTS		{ 0, 1, 2, 3, 4 }
   --#SEVERITY		MAJOR
   ::= 15006

grmpdEvent7 TRAP-TYPE
   ENTERPRISE   psaLinGrmpdTrap
   VARIABLES {
      trapPartitionName,
      trapPartitionId,
      trapEventLevel,
      trapEventId,
      trapUnitName,
      trapErrCode,
      trapMmbVip
   }
   DESCRIPTION "GRMPD: Software error (register_chrdrv failed)"
   --#TYPE			"Grmpd Event 7"
   --#SUMMARY		"%s(PID=%d) %s %d %s GRMPD: Software error (register_chrdrv failed:retcode=%s)"
   --#ARGUMENTS		{ 0, 1, 2, 3, 4, 5 }
   --#SEVERITY		MAJOR
   ::= 15007

grmpdEvent8 TRAP-TYPE
   ENTERPRISE   psaLinGrmpdTrap
   VARIABLES {
      trapPartitionName,
      trapPartitionId,
      trapEventLevel,
      trapEventId,
      trapUnitName,
      trapIrpCode,
      trapMmbVip
   }
   DESCRIPTION "GRMPD: Software error (create_irp failed)"
   --#TYPE			"Grmpd Event 8"
   --#SUMMARY		"%s(PID=%d) %s %d %s GRMPD: Software error (%s:create_irp failed)"
   --#ARGUMENTS		{ 0, 1, 2, 3, 4, 5 }
   --#SEVERITY		MAJOR
   ::= 15008

grmpdEvent9 TRAP-TYPE
   ENTERPRISE   psaLinGrmpdTrap
   VARIABLES {
      trapPartitionName,
      trapPartitionId,
      trapEventLevel,
      trapEventId,
      trapUnitName,
      trapIrpCode,
      trapMmbVip
   }
   DESCRIPTION "GRMPD: Software error (add_irp failed)"
   --#TYPE			"Grmpd Event 9"
   --#SUMMARY		"%s(PID=%d) %s %d %s GRMPD: Software error (%s:add_irp failed)"
   --#ARGUMENTS		{ 0, 1, 2, 3, 4, 5 }
   --#SEVERITY		MAJOR
   ::= 15009

grmpdEvent10 TRAP-TYPE
   ENTERPRISE   psaLinGrmpdTrap
   VARIABLES {
      trapPartitionName,
      trapPartitionId,
      trapEventLevel,
      trapEventId,
      trapUnitName,
      trapErrDetail,
      trapMmbVip
   }
   DESCRIPTION "GRMPD: Software error (cannot find real HBA)"
   --#TYPE			"Grmpd Event 10"
   --#SUMMARY		"%s(PID=%d) %s %d %s GRMPD: Software error (%s:cannot find real HBA)"
   --#ARGUMENTS		{ 0, 1, 2, 3, 4, 5 }
   --#SEVERITY		MAJOR
   ::= 15010

grmpdEvent11 TRAP-TYPE
   ENTERPRISE   psaLinGrmpdTrap
   VARIABLES {
      trapPartitionName,
      trapPartitionId,
      trapEventLevel,
      trapEventId,
      trapUnitName,
      trapMmbVip
   }
   DESCRIPTION "GRMPD: Software error (cannot get hostdata)"
   --#TYPE			"Grmpd Event 11"
   --#SUMMARY		"%s(PID=%d) %s %d %s GRMPD: Software error (cannot get hostdata)"
   --#ARGUMENTS		{ 0, 1, 2, 3, 4 }
   --#SEVERITY		MAJOR
   ::= 15011

grmpdEvent12 TRAP-TYPE
   ENTERPRISE   psaLinGrmpdTrap
   VARIABLES {
      trapPartitionName,
      trapPartitionId,
      trapEventLevel,
      trapEventId,
      trapUnitName,
      trapMmbVip
   }
   DESCRIPTION "GRMPD: Software error (internal error)"
   --#TYPE			"Grmpd Event 12"
   --#SUMMARY		"%s(PID=%d) %s %d %s GRMPD: Software error (internal error)"
   --#ARGUMENTS		{ 0, 1, 2, 3, 4 }
   --#SEVERITY		MAJOR
   ::= 15012

grmpdEvent13 TRAP-TYPE
   ENTERPRISE   psaLinGrmpdTrap
   VARIABLES {
      trapPartitionName,
      trapPartitionId,
      trapEventLevel,
      trapEventId,
      trapUnitName,
      trapHbaNo,
      trapMmbVip
   }
   DESCRIPTION "GRMPD: Software error (no response from real hba driver)"
   --#TYPE			"Grmpd Event 13"
   --#SUMMARY		"%s(PID=%d) %s %d %s GRMPD: Software error (no response from real hba(%d) driver)"
   --#ARGUMENTS		{ 0, 1, 2, 3, 4, 5 }
   --#SEVERITY		MAJOR
   ::= 15013

grmpdEvent14 TRAP-TYPE
   ENTERPRISE   psaLinGrmpdTrap
   VARIABLES {
      trapPartitionName,
      trapPartitionId,
      trapEventLevel,
      trapEventId,
      trapUnitName,
      trapMmbVip
   }
   DESCRIPTION "GRMPD: Software error (cannot register scsi cmnd private)"
   --#TYPE			"Grmpd Event 14"
   --#SUMMARY		"%s(PID=%d) %s %d %s GRMPD: Software error (cannot register scsi cmnd private)"
   --#ARGUMENTS		{ 0, 1, 2, 3, 4 }
   --#SEVERITY		MAJOR
   ::= 15014

grmpdEvent15 TRAP-TYPE
   ENTERPRISE   psaLinGrmpdTrap
   VARIABLES {
      trapPartitionName,
      trapPartitionId,
      trapEventLevel,
      trapEventId,
      trapUnitName,
      trapMmbVip
   }
   DESCRIPTION "GRMPD: Software error (internal error)"
   --#TYPE			"Grmpd Event 15"
   --#SUMMARY		"%s(PID=%d) %s %d %s GRMPD: Software error (internal error)"
   --#ARGUMENTS		{ 0, 1, 2, 3, 4 }
   --#SEVERITY		MAJOR
   ::= 15015

grmpdEvent16 TRAP-TYPE
   ENTERPRISE   psaLinGrmpdTrap
   VARIABLES {
      trapPartitionName,
      trapPartitionId,
      trapEventLevel,
      trapEventId,
      trapUnitName,
      trapMmbVip
   }
   DESCRIPTION "GRMPD: Software error (internal error)"
   --#TYPE			"Grmpd Event 16"
   --#SUMMARY		"%s(PID=%d) %s %d %s GRMPD: Software error (internal error)"
   --#ARGUMENTS		{ 0, 1, 2, 3, 4 }
   --#SEVERITY		MAJOR
   ::= 15016

grmpdEvent17 TRAP-TYPE
   ENTERPRISE   psaLinGrmpdTrap
   VARIABLES {
      trapPartitionName,
      trapPartitionId,
      trapEventLevel,
      trapEventId,
      trapUnitName,
      trapMmbVip
   }
   DESCRIPTION "GRMPD: Software error (register failed)"
   --#TYPE			"Grmpd Event 17"
   --#SUMMARY		"%s(PID=%d) %s %d %s GRMPD: Software error (register failed)"
   --#ARGUMENTS		{ 0, 1, 2, 3, 4 }
   --#SEVERITY		MAJOR
   ::= 15017

grmpdEvent18 TRAP-TYPE
   ENTERPRISE   psaLinGrmpdTrap
   VARIABLES {
      trapPartitionName,
      trapPartitionId,
      trapEventLevel,
      trapEventId,
      trapUnitName,
      trapMmbVip
   }
   DESCRIPTION "GRMPD: Software error (unknown error)"
   --#TYPE			"Grmpd Event 18"
   --#SUMMARY		"%s(PID=%d) %s %d %s GRMPD: Software error (unknown error)"
   --#ARGUMENTS		{ 0, 1, 2, 3, 4 }
   --#SEVERITY		MAJOR
   ::= 15018

grmpdEvent19 TRAP-TYPE
   ENTERPRISE   psaLinGrmpdTrap
   VARIABLES {
      trapPartitionName,
      trapPartitionId,
      trapEventLevel,
      trapEventId,
      trapUnitName,
      trapMmbVip
   }
   DESCRIPTION "GRMPD: Software error (memory allocate failed)"
   --#TYPE			"Grmpd Event 19"
   --#SUMMARY		"%s(PID=%d) %s %d %s GRMPD: Software error (memory allocate failed)"
   --#ARGUMENTS		{ 0, 1, 2, 3, 4 }
   --#SEVERITY		MAJOR
   ::= 15019

grmpdEvent20 TRAP-TYPE
   ENTERPRISE   psaLinGrmpdTrap
   VARIABLES {
      trapPartitionName,
      trapPartitionId,
      trapEventLevel,
      trapEventId,
      trapUnitName,
      trapMmbVip
   }
   DESCRIPTION "GRMPD: Software error (Too many HBA. Skipping)"
   --#TYPE			"Grmpd Event 20"
   --#SUMMARY		"%s(PID=%d) %s %d %s GRMPD: Software error (Too many HBA. Skipping)"
   --#ARGUMENTS		{ 0, 1, 2, 3, 4 }
   --#SEVERITY		MINOR
   ::= 15020

grmpdEvent21 TRAP-TYPE
   ENTERPRISE   psaLinGrmpdTrap
   VARIABLES {
      trapPartitionName,
      trapPartitionId,
      trapEventLevel,
      trapEventId,
      trapUnitName,
      trapMmbVip
   }
   DESCRIPTION "GRMPD: Software error (device append failed)"
   --#TYPE			"Grmpd Event 21"
   --#SUMMARY		"%s(PID=%d) %s %d %s GRMPD: Software error (device append failed)"
   --#ARGUMENTS		{ 0, 1, 2, 3, 4 }
   --#SEVERITY		MAJOR
   ::= 15021

grmpdEvent22 TRAP-TYPE
   ENTERPRISE   psaLinGrmpdTrap
   VARIABLES {
      trapPartitionName,
      trapPartitionId,
      trapEventLevel,
      trapEventId,
      trapUnitName,
      trapMmbVip
   }
   DESCRIPTION "GRMPD: Software error (AttachDevList=NULL in attach_prep)"
   --#TYPE			"Grmpd Event 22"
   --#SUMMARY		"%s(PID=%d) %s %d %s GRMPD: Software error (AttachDevList=NULL in attach_prep)"
   --#ARGUMENTS		{ 0, 1, 2, 3, 4 }
   --#SEVERITY		MAJOR
   ::= 15022

grmpdEvent23 TRAP-TYPE
   ENTERPRISE   psaLinGrmpdTrap
   VARIABLES {
      trapPartitionName,
      trapPartitionId,
      trapEventLevel,
      trapEventId,
      trapUnitName,
      trapMmbVip
   }
   DESCRIPTION "GRMPD: Software error (rhba overflow)"
   --#TYPE			"Grmpd Event 23"
   --#SUMMARY		"%s(PID=%d) %s %d %s GRMPD: Software error (rhba overflow)"
   --#ARGUMENTS		{ 0, 1, 2, 3, 4 }
   --#SEVERITY		MAJOR
   ::= 15023

grmpdEvent24 TRAP-TYPE
   ENTERPRISE   psaLinGrmpdTrap
   VARIABLES {
      trapPartitionName,
      trapPartitionId,
      trapEventLevel,
      trapEventId,
      trapUnitName,
      trapMmbVip
   }
   DESCRIPTION "GRMPD: Software error (internal error)"
   --#TYPE			"Grmpd Event 24"
   --#SUMMARY		"%s(PID=%d) %s %d %s GRMPD: Software error (internal error)"
   --#ARGUMENTS		{ 0, 1, 2, 3, 4 }
   --#SEVERITY		MAJOR
   ::= 15024

grmpdEvent25 TRAP-TYPE
   ENTERPRISE   psaLinGrmpdTrap
   VARIABLES {
      trapPartitionName,
      trapPartitionId,
      trapEventLevel,
      trapEventId,
      trapUnitName,
      trapMmbVip
   }
   DESCRIPTION "GRMPD: Software error (memory allocate failed)"
   --#TYPE			"Grmpd Event 25"
   --#SUMMARY		"%s(PID=%d) %s %d %s GRMPD: Software error (memory allocate failed)"
   --#ARGUMENTS		{ 0, 1, 2, 3, 4 }
   --#SEVERITY		MAJOR
   ::= 15025

grmpdEvent26 TRAP-TYPE
   ENTERPRISE   psaLinGrmpdTrap
   VARIABLES {
      trapPartitionName,
      trapPartitionId,
      trapEventLevel,
      trapEventId,
      trapUnitName,
      trapMmbVip
   }
   DESCRIPTION "GRMPD: Software error (sense information detected)"
   --#TYPE			"Grmpd Event 26"
   --#SUMMARY		"%s(PID=%d) %s %d %s GRMPD: Software error (sense information detected)"
   --#ARGUMENTS		{ 0, 1, 2, 3, 4 }
   --#SEVERITY		MINOR
   ::= 15026

grmpdEvent27 TRAP-TYPE
   ENTERPRISE   psaLinGrmpdTrap
   VARIABLES {
      trapPartitionName,
      trapPartitionId,
      trapEventLevel,
      trapEventId,
      trapUnitName,
      trapErrCause,
      trapMmbVip
   }
   DESCRIPTION "GRMPD: Software error (I/O error)"
   --#TYPE			"Grmpd Event 27"
   --#SUMMARY		"%s(PID=%d) %s %d %s GRMPD: Software error (I/O error.-%s)"
   --#ARGUMENTS		{ 0, 1, 2, 3, 4, 5 }
   --#SEVERITY		MINOR
   ::= 15027

grmpdEvent28 TRAP-TYPE
   ENTERPRISE   psaLinGrmpdTrap
   VARIABLES {
      trapPartitionName,
      trapPartitionId,
      trapEventLevel,
      trapEventId,
      trapUnitName,
      trapMmbVip
   }
   DESCRIPTION "GRMPD: Software error (internal error)"
   --#TYPE			"Grmpd Event 28"
   --#SUMMARY		"%s(PID=%d) %s %d %s GRMPD: Software error (internal error)"
   --#ARGUMENTS		{ 0, 1, 2, 3, 4 }
   --#SEVERITY		MINOR
   ::= 15028

grmpdEvent29 TRAP-TYPE
   ENTERPRISE   psaLinGrmpdTrap
   VARIABLES {
      trapPartitionName,
      trapPartitionId,
      trapEventLevel,
      trapEventId,
      trapUnitName,
      trapMmbVip
   }
   DESCRIPTION "GRMPD: Software error (retry out by flow control)"
   --#TYPE			"Grmpd Event 29"
   --#SUMMARY		"%s(PID=%d) %s %d %s GRMPD: Software error (retry out by flow control)"
   --#ARGUMENTS		{ 0, 1, 2, 3, 4 }
   --#SEVERITY		MINOR
   ::= 15029

grmpdEvent30 TRAP-TYPE
   ENTERPRISE   psaLinGrmpdTrap
   VARIABLES {
      trapPartitionName,
      trapPartitionId,
      trapEventLevel,
      trapEventId,
      trapUnitName,
      trapPathNo,
      trapMmbVip
   }
   DESCRIPTION "GRMPD: Software error (Auto Path Test changed path status to fail)"
   --#TYPE			"Grmpd Event 30"
   --#SUMMARY		"%s(PID=%d) %s %d %s GRMPD: Software error (Auto Path Test changed path status to fail:path %d)"
   --#ARGUMENTS		{ 0, 1, 2, 3, 4, 5 }
   --#SEVERITY		MINOR
   ::= 15030

grmpdEvent31 TRAP-TYPE
   ENTERPRISE   psaLinGrmpdTrap
   VARIABLES {
      trapPartitionName,
      trapPartitionId,
      trapEventLevel,
      trapEventId,
      trapUnitName,
      trapPathNo,
      trapMmbVip
   }
   DESCRIPTION "GRMPD: Software error (Auto Path Diagnosis detected path error)"
   --#TYPE			"Grmpd Event 31"
   --#SUMMARY		"%s(PID=%d) %s %d %s GRMPD: Software error (Auto Path Diagnosis detected path error:path %d)"
   --#ARGUMENTS		{ 0, 1, 2, 3, 4, 5 }
   --#SEVERITY		MINOR
   ::= 15031

grmpdEvent32 TRAP-TYPE
   ENTERPRISE   psaLinGrmpdTrap
   VARIABLES {
      trapPartitionName,
      trapPartitionId,
      trapEventLevel,
      trapEventId,
      trapUnitName,
      trapMmbVip
   }
   DESCRIPTION "GRMPD: Software error (internal error)"
   --#TYPE			"Grmpd Event 32"
   --#SUMMARY		"%s(PID=%d) %s %d %s GRMPD: Software error (internal error)"
   --#ARGUMENTS		{ 0, 1, 2, 3, 4 }
   --#SEVERITY		MAJOR
   ::= 15032

grmpdEvent37 TRAP-TYPE
   ENTERPRISE   psaLinGrmpdTrap
   VARIABLES {
      trapPartitionName,
      trapPartitionId,
      trapEventLevel,
      trapEventId,
      trapUnitName,
      trapMmbVip
   }
   DESCRIPTION "GRMPD: Software error (mplb_path_io_watch timeout)"
   --#TYPE			"Grmpd Event 37"
   --#SUMMARY		"%s(PID=%d) %s %d %s GRMPD: Software error (mplb_path_io_watch timeout)"
   --#ARGUMENTS		{ 0, 1, 2, 3, 4 }
   --#SEVERITY		MAJOR
   ::= 15037

grmpdEvent38 TRAP-TYPE
   ENTERPRISE   psaLinGrmpdTrap
   VARIABLES {
      trapPartitionName,
      trapPartitionId,
      trapEventLevel,
      trapEventId,
      trapUnitName,
      trapMmbVip
   }
   DESCRIPTION "GRMPD: Software error (mplb_io_watch timeout)"
   --#TYPE			"Grmpd Event 38"
   --#SUMMARY		"%s(PID=%d) %s %d %s GRMPD: Software error (mplb_io_watch timeout)"
   --#ARGUMENTS		{ 0, 1, 2, 3, 4 }
   --#SEVERITY		MAJOR
   ::= 15038

grmpdEvent39 TRAP-TYPE
   ENTERPRISE   psaLinGrmpdTrap
   VARIABLES {
      trapPartitionName,
      trapPartitionId,
      trapEventLevel,
      trapEventId,
      trapUnitName,
      trapMmbVip
   }
   DESCRIPTION "MPD: Adapter or Device or FC-Network error (MPD detected event)"
   --#TYPE			"Grmpd Event 39"
   --#SUMMARY		"%s(PID=%d) %s %d %s MPD: Adapter or Device or FC-Network error (MPD detected event)"
   --#ARGUMENTS		{ 0, 1, 2, 3, 4 }
   --#SEVERITY		MINOR
   ::= 15039

END
