-- ODS FDDI Enterprise Specific MIB (April 09, 1992)

ODS-FDDIMIB DEFINITIONS ::= BEGIN

IMPORTS
        enterprises, NetworkAddress, IpAddress, Counter, Gauge,
                TimeTicks, OBJECT-TYPE FROM RFC1155-SMI
					 DisplayString FROM SNMPv2-TC
        snmp FROM RFC1158-MIB;


ods                     OBJECT IDENTIFIER ::= { enterprises 50 }

enc                     OBJECT IDENTIFIER ::= { ods 1 }
enBridge                OBJECT IDENTIFIER ::= { ods 2 }
tokenRing               OBJECT IDENTIFIER ::= { ods 3 }
trBridge                OBJECT IDENTIFIER ::= { ods 4 }
fddi	                OBJECT IDENTIFIER ::= { ods 5 }


-- --------------------------------------------------------

-- The fddi group contains objects pertaining to the
-- concentrator as a whole.

fddiChassisId OBJECT-TYPE
        SYNTAX  INTEGER 
        ACCESS  read-only
        STATUS  mandatory
        DESCRIPTION
                        "The type of chassis used for the concentrator.
                        For modular concentrators, the hardware is
                        further qualifed by the value of fddiCardId for
                        each card installed in the concentrator."
        ::= { fddi 1 }


fddiChassisDescr OBJECT-TYPE
        SYNTAX  DisplayString (SIZE (0..255))
        ACCESS  read-only
        STATUS  mandatory
        DESCRIPTION
                        "A textual description of the concentrator chassis
                         being used."
        ::= { fddi 2 }


fddiPowerSupplyMap OBJECT-TYPE
        SYNTAX  INTEGER {
                        left(1),
                        right(2),
			both(3)
                }
        ACCESS  read-only
        STATUS  mandatory
        DESCRIPTION
                        "Specifies the location of the power supply(s)
                         in the chassis. Bit 0 represents the left
                         power supply and bit 1 represents the right.
                         If the bit is set then the corresponding power
                         supply is present."
        ::= { fddi 3 }

fddiPowerSupplyStatus OBJECT-TYPE
        SYNTAX  INTEGER {
                        leftgood(1),
                        rightgood(2),
			bothgood(3)
                }
        ACCESS  read-only
        STATUS  mandatory
        DESCRIPTION
                        "Specifies the status of the power supply(s)
                         in the chassis. Bit 0 represent the left 
                         power supply status an bit 1 represents 
                         the right. If the bit is set then the 
                         corresponding supply is good."
        ::= { fddi 4 }


fddiCardCapacity OBJECT-TYPE
        SYNTAX  INTEGER
        ACCESS  read-only
        STATUS  mandatory
        DESCRIPTION
                        "The number of card slots that is contained in
                         the concentrator chassis."
        ::= { fddi 5 }


fddiCardNumber OBJECT-TYPE
        SYNTAX  INTEGER
        ACCESS  read-only
        STATUS  mandatory
        DESCRIPTION
                        "The number of cards that are currently installed
                         in the concentrator chassis."
        ::= { fddi 6 }


-- --------------------------------------------------------


-- The card table contains information pertaining to each
-- card installed in the concentrator.  The size of the
-- table may change dynamically as old cards are removed
-- or new ones are installed.

fddiCardTable OBJECT-TYPE
        SYNTAX  SEQUENCE OF CardEntry
        ACCESS  not-accessible
        STATUS  mandatory
        DESCRIPTION
                        "A list of card entries for each card installed in
                        the concentrator.  The number of entries is given
                        by the value of fddiCardNumber."
        ::= { fddi 7 }

fddiCardEntry OBJECT-TYPE
        SYNTAX  CardEntry
        ACCESS  not-accessible
        STATUS  mandatory
        DESCRIPTION
                        "A card entry containing objects pertaining to a
                        card installed in the concentrator."
        INDEX   { fddiCardIndex }
        ::= { fddiCardTable 1 }

CardEntry ::= SEQUENCE {
        fddiCardIndex               INTEGER,
        fddiCardID                  INTEGER,
        fddiCardDescrip             DisplayString,
        fddiCardStatus              INTEGER,
        fddiCardPortNumber          INTEGER,
        fddiCardPortIndex           INTEGER,
        fddiCardBypassStatus        INTEGER
}


fddiCardIndex OBJECT-TYPE
        SYNTAX  INTEGER
        ACCESS  read-only
        STATUS  mandatory
        DESCRIPTION
                        "The slot in which the card is installed.  This
                        value uniquely identifies the card.  Its value
                        ranges between 1 and the value of fddiCardCapacity."
        ::= { fddiCardEntry 1 }


fddiCardId OBJECT-TYPE
        SYNTAX  INTEGER 
        ACCESS  read-only
        STATUS  mandatory
        DESCRIPTION
                        "The type of card installed in the concentrator."
        ::= { fddiCardEntry 2 }

fddiCardDescr OBJECT-TYPE
        SYNTAX  DisplayString (SIZE (0..255))
        ACCESS  read-only
        STATUS  mandatory
        DESCRIPTION
                        "A textual description of the card including
                        the ODS model number, media type and number of
                        ports."
        ::= { fddiCardEntry 3 }

fddiCardStatus OBJECT-TYPE
        SYNTAX  INTEGER  { onLine(1),
                           offLine(2)
                }
        ACCESS  read-only
        STATUS  mandatory
        DESCRIPTION
                        "This value indicated whether the card is
                         on-line or off-line."
        ::= { fddiCardEntry 4 }

fddiCardPortNumber OBJECT-TYPE
        SYNTAX  INTEGER
        ACCESS  read-only
        STATUS  mandatory
        DESCRIPTION
                        "This value specifies the number of ports contained
                         on the card."
        ::= { fddiCardEntry 5 }

fddiCardPortIndex OBJECT-TYPE
        SYNTAX  INTEGER  
        ACCESS  read-only
        STATUS  mandatory
        DESCRIPTION
                        "This value is the SMT index of the first port on
                         this card."
        ::= { fddiCardEntry 6 }

fddiCardBypassStatus OBJECT-TYPE
        SYNTAX  INTEGER  { enabled(1),
                           disabled(2),
                           unsupported(3)
                }
        ACCESS  read-only
        STATUS  mandatory
        DESCRIPTION
                        "This value specifies the status of the optical
                         bypass for this card."
        ::= { fddiCardEntry 7 }


END
