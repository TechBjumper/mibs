PSA-WinBcm5700Trap-MIB DEFINITIONS ::= BEGIN

--PRIMEQUEST system management MIB for Partition
--
--
--$Copyright$
--Copyright Fujitsu Limited 2004
--All rights reserved
--
--
--MIB Revision: 01010001
--

IMPORTS
	OBJECT-TYPE								FROM RFC-1212
	TRAP-TYPE								FROM RFC-1215
	mib-2, DisplayString					FROM RFC1213-MIB
	TimeTicks, Counter, Gauge, IpAddress	FROM RFC1155-SMI
	mgmt, enterprises						FROM RFC1155-SMI;

--enterprises	OBJECT IDENTIFIER ::={ iso org(3) dod(6) internet(1) private(4) 1 }
--
--PRIMEQUEST system management MIB nodes
--fujitsu:                    1.3.6.1.4.1.211
-- products:                  1.3.6.1.4.1.211.1
--  iaServer:                 1.3.6.1.4.1.211.1.31
--   primequest:              1.3.6.1.4.1.211.1.31.1
--    partition:	           1.3.6.1.4.1.211.1.31.1.2
--
--Trap enterprise is "psaWinBcm5700Trap"

--FUJITSU PRIMEQUEST system management MIB nodes for Partition
  fujitsu        OBJECT IDENTIFIER  ::={ enterprises 211 }
  products       OBJECT IDENTIFIER  ::={ fujitsu 1 }
  iaServer       OBJECT IDENTIFIER  ::={ products 31 }
  primequest     OBJECT IDENTIFIER  ::={ iaServer 1 }
   partition     OBJECT IDENTIFIER  ::={ primequest 2 }
    parititonVariables	OBJECT IDENTIFIER	::={ partition	200 }
    partitionEnterprise	OBJECT IDENTIFIER  ::={ partition 201 }
     psaComTrap			OBJECT IDENTIFIER  ::={ partitionEnterprise 1 }
     psaWinIntelE100Trap	OBJECT IDENTIFIER  ::={ partitionEnterprise 51 }
     psaWinIntelE1000Trap	OBJECT IDENTIFIER  ::={ partitionEnterprise 52 }
     psaWinBcm5700Trap		OBJECT IDENTIFIER  ::={ partitionEnterprise 53 }
     psaWinEmulexTrap		OBJECT IDENTIFIER  ::={ partitionEnterprise 54 }
     psaWinLsiLogicTrap	OBJECT IDENTIFIER  ::={ partitionEnterprise 55 }
     psaWinGrmpdTrap		OBJECT IDENTIFIER  ::={ partitionEnterprise 57 }

--***************************************************************************************
--
--FUJITSU PRIMEQUEST system management trap parameter variables for Partition
--	They aren't directly accessibles(can't use snmp get/set command), but sent with trap
--
--***************************************************************************************

     trapVarComInfo	OBJECT IDENTIFIER	::={ parititonVariables 1 }

trapPartitionName OBJECT-TYPE
   SYNTAX   DisplayString
   ACCESS   not-accessible
   STATUS   mandatory
   DESCRIPTION "Partition name which trap is generated."
   ::= { trapVarComInfo 1 }

trapPartitionId OBJECT-TYPE
   SYNTAX   INTEGER
   ACCESS   not-accessible
   STATUS   mandatory
   DESCRIPTION "Paritition identifier which trap is generated."
   ::= { trapVarComInfo 2 }

trapEventLevel OBJECT-TYPE
   SYNTAX   DisplayString
   ACCESS   not-accessible
   STATUS   mandatory
   DESCRIPTION "Event level"
   ::= { trapVarComInfo 3 }

trapEventId OBJECT-TYPE
   SYNTAX   INTEGER
   ACCESS   not-accessible
   STATUS   mandatory
   DESCRIPTION "Event Identifier"
   ::= { trapVarComInfo 4 }

trapUnitName OBJECT-TYPE
   SYNTAX   DisplayString
   ACCESS   not-accessible
   STATUS   mandatory
   DESCRIPTION "Unit name which trap is generated."
   ::= { trapVarComInfo 5 }

trapMmbVip OBJECT-TYPE
   SYNTAX   DisplayString
   ACCESS   not-accessible
   STATUS   mandatory
   DESCRIPTION "Management board vertual IP address."
   ::= { trapVarComInfo 6 }

     trapVarDivInfo	OBJECT IDENTIFIER	::={ parititonVariables 2 }

trapPartNo OBJECT-TYPE
   SYNTAX   DisplayString
   ACCESS   not-accessible
   STATUS   mandatory
   DESCRIPTION "Part number of trap source."
   ::= { trapVarDivInfo 1 }

trapStepping OBJECT-TYPE
   SYNTAX   DisplayString
   ACCESS   not-accessible
   STATUS   mandatory
   DESCRIPTION " "
   ::= { trapVarDivInfo 2 }

trapSerialNo OBJECT-TYPE
   SYNTAX   DisplayString
   ACCESS   not-accessible
   STATUS   mandatory
   DESCRIPTION "Serial number of trap source. "
   ::= { trapVarDivInfo 3 }

trapModelNo OBJECT-TYPE
   SYNTAX   DisplayString
   ACCESS   not-accessible
   STATUS   mandatory
   DESCRIPTION "Model number of trap source."
   ::= { trapVarDivInfo 4 }

trapSuspect OBJECT-TYPE
   SYNTAX   DisplayString
   ACCESS   not-accessible
   STATUS   mandatory
   DESCRIPTION "Logical name or pci bus number of trap source."
   ::= { trapVarDivInfo 5 }

trapVendorId OBJECT-TYPE
   SYNTAX   DisplayString
   ACCESS   not-accessible
   STATUS   mandatory
   DESCRIPTION "Vendor identifier of trap source."
   ::= { trapVarDivInfo 6 }

trapDeviceId OBJECT-TYPE
   SYNTAX   DisplayString
   ACCESS   not-accessible
   STATUS   mandatory
   DESCRIPTION "Device identifier of trap source."
   ::= { trapVarDivInfo 7 }

trapRevision OBJECT-TYPE
   SYNTAX   DisplayString
   ACCESS   not-accessible
   STATUS   mandatory
   DESCRIPTION "Revision of trap source."
   ::= { trapVarDivInfo 8 }

trapCardName OBJECT-TYPE
   SYNTAX   DisplayString
   ACCESS   not-accessible
   STATUS   mandatory
   DESCRIPTION "Device name of trap source."
   ::= { trapVarDivInfo 9 }

trapErrDetail OBJECT-TYPE
   SYNTAX   DisplayString
   ACCESS   not-accessible
   STATUS   mandatory
   DESCRIPTION " "
   ::= { trapVarDivInfo 10 }

trapErrCode OBJECT-TYPE
   SYNTAX   DisplayString
   ACCESS   not-accessible
   STATUS   mandatory
   DESCRIPTION " "
   ::= { trapVarDivInfo 11 }

trapIrpCode OBJECT-TYPE
   SYNTAX   DisplayString
   ACCESS   not-accessible
   STATUS   mandatory
   DESCRIPTION " "
   ::= { trapVarDivInfo 12 }

trapHbaNo OBJECT-TYPE
   SYNTAX   INTEGER
   ACCESS   not-accessible
   STATUS   mandatory
   DESCRIPTION " "
   ::= { trapVarDivInfo 13 }

trapErrCause OBJECT-TYPE
   SYNTAX   DisplayString
   ACCESS   not-accessible
   STATUS   mandatory
   DESCRIPTION " "
   ::= { trapVarDivInfo 14 }

trapPathNo OBJECT-TYPE
   SYNTAX   INTEGER
   ACCESS   not-accessible
   STATUS   mandatory
   DESCRIPTION " "
   ::= { trapVarDivInfo 15 }

trapDiskId OBJECT-TYPE
   SYNTAX   DisplayString
   ACCESS   not-accessible
   STATUS   mandatory
   DESCRIPTION " "
   ::= { trapVarDivInfo 16 }

trapFmrDiskId OBJECT-TYPE
   SYNTAX   DisplayString
   ACCESS   not-accessible
   STATUS   mandatory
   DESCRIPTION " "
   ::= { trapVarDivInfo 17 }

trapCurDiskId OBJECT-TYPE
   SYNTAX   DisplayString
   ACCESS   not-accessible
   STATUS   mandatory
   DESCRIPTION " "
   ::= { trapVarDivInfo 18 }

trapPathId OBJECT-TYPE
   SYNTAX   DisplayString
   ACCESS   not-accessible
   STATUS   mandatory
   DESCRIPTION " "
   ::= { trapVarDivInfo 19 }

trapPhysIf OBJECT-TYPE
   SYNTAX   DisplayString
   ACCESS   not-accessible
   STATUS   mandatory
   DESCRIPTION " "
   ::= { trapVarDivInfo 20 }

trapVirtualIf OBJECT-TYPE
   SYNTAX   DisplayString
   ACCESS   not-accessible
   STATUS   mandatory
   DESCRIPTION " "
   ::= { trapVarDivInfo 21 }

trapLogicalIp OBJECT-TYPE
   SYNTAX   DisplayString
   ACCESS   not-accessible
   STATUS   mandatory
   DESCRIPTION " "
   ::= { trapVarDivInfo 22 }

trapWatchIp OBJECT-TYPE
   SYNTAX   DisplayString
   ACCESS   not-accessible
   STATUS   mandatory
   DESCRIPTION " "
   ::= { trapVarDivInfo 23 }

trapInterface OBJECT-TYPE
   SYNTAX   DisplayString
   ACCESS   not-accessible
   STATUS   mandatory
   DESCRIPTION " "
   ::= { trapVarDivInfo 24 }

trapSourceIp OBJECT-TYPE
   SYNTAX   DisplayString
   ACCESS   not-accessible
   STATUS   mandatory
   DESCRIPTION " "
   ::= { trapVarDivInfo 25 }

trapDestIp OBJECT-TYPE
   SYNTAX   DisplayString
   ACCESS   not-accessible
   STATUS   mandatory
   DESCRIPTION " "
   ::= { trapVarDivInfo 26 }

--***************************************************************************************
--
--FUJITSU PRIMEQUEST system management TRAP definition for Partition
--	Trap enterprise:	psaWinBcm5700Trap (.1.3.6.1.4.1.211.1.31.1.2.201.53)
--
--***************************************************************************************

bcm5700WinEvent0 TRAP-TYPE
   ENTERPRISE   psaWinBcm5700Trap
   VARIABLES {
      trapPartitionName,
      trapPartitionId,
      trapEventLevel,
      trapEventId,
      trapUnitName,
      trapSuspect,
      trapMmbVip
   }
   DESCRIPTION "b57nd: Software error (Failed to allocate memory)"
   --#TYPE			"Bcm5700 Win Event 0"
   --#SUMMARY		"%s(PID=%d) %s %d %s b57nd:%s Software error (Failed to allocate memory)"
   --#ARGUMENTS		{ 0, 1, 2, 3, 4, 5 }
   --#SEVERITY		MAJOR
   ::= 21300

bcm5700WinEvent1 TRAP-TYPE
   ENTERPRISE   psaWinBcm5700Trap
   VARIABLES {
      trapPartitionName,
      trapPartitionId,
      trapEventLevel,
      trapEventId,
      trapUnitName,
      trapSuspect,
      trapMmbVip
   }
   DESCRIPTION "b57nd: Software error (Failed to allocate map registers)"
   --#TYPE			"Bcm5700 Win Event 1"
   --#SUMMARY		"%s(PID=%d) %s %d %s b57nd:%s Software error (Failed to allocate map registers) "
   --#ARGUMENTS		{ 0, 1, 2, 3, 4, 5 }
   --#SEVERITY		MINOR
   ::= 21301

bcm5700WinEvent2 TRAP-TYPE
   ENTERPRISE   psaWinBcm5700Trap
   VARIABLES {
      trapPartitionName,
      trapPartitionId,
      trapEventLevel,
      trapEventId,
      trapUnitName,
      trapSuspect,
      trapVendorId,
      trapDeviceId,
      trapRevision,
      trapMmbVip
   }
   DESCRIPTION "b57nd: Adapter error (Failed to access configuration information)"
   --#TYPE			"Bcm5700 Win Event 2"
   --#SUMMARY		"%s(PID=%d) %s %d %s b57nd:%s Adapter error (Failed to access configuration information) vendor-id=%s device-id=%s revision=%s"
   --#ARGUMENTS		{ 0, 1, 2, 3, 4, 5, 6, 7, 8 }
   --#SEVERITY		MAJOR
   ::= 21302

bcm5700WinEvent3 TRAP-TYPE
   ENTERPRISE   psaWinBcm5700Trap
   VARIABLES {
      trapPartitionName,
      trapPartitionId,
      trapEventLevel,
      trapEventId,
      trapUnitName,
      trapSuspect,
      trapVendorId,
      trapDeviceId,
      trapRevision,
      trapMmbVip
   }
   DESCRIPTION "b57nd: Adapter error (Medium not supported)"
   --#TYPE			"Bcm5700 Win Event 3"
   --#SUMMARY		"%s(PID=%d) %s %d %s b57nd:%s Adapter error (Medium not supported) vendor-id=%s device-id=%s revision=%s"
   --#ARGUMENTS		{ 0, 1, 2, 3, 4, 5, 6, 7, 8 }
   --#SEVERITY		MAJOR
   ::= 21303

bcm5700WinEvent4 TRAP-TYPE
   ENTERPRISE   psaWinBcm5700Trap
   VARIABLES {
      trapPartitionName,
      trapPartitionId,
      trapEventLevel,
      trapEventId,
      trapUnitName,
      trapSuspect,
      trapMmbVip
   }
   DESCRIPTION "b57nd: Software error (Unable to register)"
   --#TYPE			"Bcm5700 Win Event 4"
   --#SUMMARY		"%s(PID=%d) %s %d %s b57nd:%s Software error (Unable to register)"
   --#ARGUMENTS		{ 0, 1, 2, 3, 4, 5 }
   --#SEVERITY		MINOR
   ::= 21304

bcm5700WinEvent5 TRAP-TYPE
   ENTERPRISE   psaWinBcm5700Trap
   VARIABLES {
      trapPartitionName,
      trapPartitionId,
      trapEventLevel,
      trapEventId,
      trapUnitName,
      trapSuspect,
      trapMmbVip
   }
   DESCRIPTION "b57nd: Software error (Unable to map IO space)"
   --#TYPE			"Bcm5700 Win Event 5"
   --#SUMMARY		"%s(PID=%d) %s %d %s b57nd:%s Software error (Unable to map IO space)"
   --#ARGUMENTS		{ 0, 1, 2, 3, 4, 5 }
   --#SEVERITY		MINOR
   ::= 21305

bcm5700WinEvent6 TRAP-TYPE
   ENTERPRISE   psaWinBcm5700Trap
   VARIABLES {
      trapPartitionName,
      trapPartitionId,
      trapEventLevel,
      trapEventId,
      trapUnitName,
      trapSuspect,
      trapMmbVip
   }
   DESCRIPTION "b57nd: Software error (Cannot enter low-power mode)"
   --#TYPE			"Bcm5700 Win Event 6"
   --#SUMMARY		"%s(PID=%d) %s %d %s b57nd:%s Software error (Cannot enter low-power mode)"
   --#ARGUMENTS		{ 0, 1, 2, 3, 4, 5 }
   --#SEVERITY		MAJOR
   ::= 21306

bcm5700WinEvent7 TRAP-TYPE
   ENTERPRISE   psaWinBcm5700Trap
   VARIABLES {
      trapPartitionName,
      trapPartitionId,
      trapEventLevel,
      trapEventId,
      trapUnitName,
      trapSuspect,
      trapVendorId,
      trapDeviceId,
      trapRevision,
      trapMmbVip
   }
   DESCRIPTION "b57nd: Adapter error (Unknown PHY detected)"
   --#TYPE			"Bcm5700 Win Event 7"
   --#SUMMARY		"%s(PID=%d) %s %d %s b57nd:%s Adapter error (Unknown PHY detected) vendor-id=%s device-id=%s revision=%s"
   --#ARGUMENTS		{ 0, 1, 2, 3, 4, 5, 6, 7, 8 }
   --#SEVERITY		MAJOR
   ::= 21307

bcm5700WinEvent8 TRAP-TYPE
   ENTERPRISE   psaWinBcm5700Trap
   VARIABLES {
      trapPartitionName,
      trapPartitionId,
      trapEventLevel,
      trapEventId,
      trapUnitName,
      trapSuspect,
      trapVendorId,
      trapDeviceId,
      trapRevision,
      trapMmbVip
   }
   DESCRIPTION "b57nd: Adapter error (This driver does not support this device)"
   --#TYPE			"Bcm5700 Win Event 8"
   --#SUMMARY		"%s(PID=%d) %s %d %s b57nd:%s Adapter error (This driver does not support this device) vendor-id=%s device-id=%s revision=%s"
   --#ARGUMENTS		{ 0, 1, 2, 3, 4, 5, 6, 7, 8 }
   --#SEVERITY		MAJOR
   ::= 21308

bcm5700WinEvent9 TRAP-TYPE
   ENTERPRISE   psaWinBcm5700Trap
   VARIABLES {
      trapPartitionName,
      trapPartitionId,
      trapEventLevel,
      trapEventId,
      trapUnitName,
      trapSuspect,
      trapMmbVip
   }
   DESCRIPTION "b57nd: Software error (Driver initialization failed)"
   --#TYPE			"Bcm5700 Win Event 9"
   --#SUMMARY		"%s(PID=%d) %s %d %s b57nd:%s Software error (Driver initialization failed)"
   --#ARGUMENTS		{ 0, 1, 2, 3, 4, 5 }
   --#SEVERITY		MAJOR
   ::= 21309

END
