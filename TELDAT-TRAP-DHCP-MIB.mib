-- file automatically created


TELDAT-TRAP-DHCP-MIB DEFINITIONS ::= BEGIN


IMPORTS
	MODULE-IDENTITY,OBJECT-TYPE,OBJECT-IDENTITY,NOTIFICATION-TYPE,Integer32,IpAddress
		FROM SNMPv2-SMI
	DisplayString
		FROM SNMPv2-TC
	telEventTraps
		FROM TELDAT-MIB;


dhcpTrapsMIB MODULE-IDENTITY
    LAST-UPDATED "201401200930Z"
    ORGANIZATION "Teldat, S.A."
    CONTACT-INFO 
        "Teldat, S.A.
        Customer Service

        Postal: Parque Tecnologico de Madrid
                Tres Cantos 28760
                Madrid, SPAIN

        Tel.: +34 918 076 565

        http://www.teldat.com"
    DESCRIPTION
        "This Module Information Base file is defined for managing received
        SNMP notifications generated by the DHCP event subsystem."
    REVISION "201401200930Z"
    DESCRIPTION "Initial implementation"
        ::= { telEventTraps 133 }


dhcpEventsGroup	OBJECT IDENTIFIER	::= { dhcpTrapsMIB 1 }

dhcpNotifications	OBJECT IDENTIFIER	::= { dhcpTrapsMIB 2 }
dhcpNotificationsPrefix	OBJECT IDENTIFIER	::= { dhcpNotifications 0 }

dhcpEventObjects3 OBJECT-IDENTITY
    STATUS current
    DESCRIPTION
        "Event DHCP.3
        Message generated when the router relays packets received from
        DHCP clients and addressed to DHCP servers."
    ::= { dhcpEventsGroup 3 }

dhcp3-source-ip-address OBJECT-TYPE
    SYNTAX IpAddress
    MAX-ACCESS accessible-for-notify
    STATUS current
    DESCRIPTION
        "Parameter 'source-ip-address' in event DHCP.3"
    ::= { dhcpEventObjects3 1 }

dhcp3-destination-ip-address OBJECT-TYPE
    SYNTAX IpAddress
    MAX-ACCESS accessible-for-notify
    STATUS current
    DESCRIPTION
        "Parameter 'destination-ip-address' in event DHCP.3"
    ::= { dhcpEventObjects3 2 }

dhcpEventObjects4 OBJECT-IDENTITY
    STATUS current
    DESCRIPTION
        "Event DHCP.4
        Message generated when the router relays packets received from
        DHCP servers and addressed to DHCP clients."
    ::= { dhcpEventsGroup 4 }

dhcp4-source-ip-address OBJECT-TYPE
    SYNTAX IpAddress
    MAX-ACCESS accessible-for-notify
    STATUS current
    DESCRIPTION
        "Parameter 'source-ip-address' in event DHCP.4"
    ::= { dhcpEventObjects4 1 }

dhcp4-destination-ip-address OBJECT-TYPE
    SYNTAX IpAddress
    MAX-ACCESS accessible-for-notify
    STATUS current
    DESCRIPTION
        "Parameter 'destination-ip-address' in event DHCP.4"
    ::= { dhcpEventObjects4 2 }

dhcpEventObjects5 OBJECT-IDENTITY
    STATUS current
    DESCRIPTION
        "Event DHCP.5
        DHCP message received in server from relay on an IP address."
    ::= { dhcpEventsGroup 5 }

dhcp5-message-type OBJECT-TYPE
    SYNTAX DisplayString
    MAX-ACCESS accessible-for-notify
    STATUS current
    DESCRIPTION
        "Parameter 'message-type' in event DHCP.5"
    ::= { dhcpEventObjects5 1 }

dhcp5-source-ip-address OBJECT-TYPE
    SYNTAX IpAddress
    MAX-ACCESS accessible-for-notify
    STATUS current
    DESCRIPTION
        "Parameter 'source-ip-address' in event DHCP.5"
    ::= { dhcpEventObjects5 2 }

dhcpEventObjects6 OBJECT-IDENTITY
    STATUS current
    DESCRIPTION
        "Event DHCP.6
        DHCP message received in server from host on an known IP address."
    ::= { dhcpEventsGroup 6 }

dhcp6-message-type OBJECT-TYPE
    SYNTAX DisplayString
    MAX-ACCESS accessible-for-notify
    STATUS current
    DESCRIPTION
        "Parameter 'message-type' in event DHCP.6"
    ::= { dhcpEventObjects6 1 }

dhcp6-source-ip-address OBJECT-TYPE
    SYNTAX IpAddress
    MAX-ACCESS accessible-for-notify
    STATUS current
    DESCRIPTION
        "Parameter 'source-ip-address' in event DHCP.6"
    ::= { dhcpEventObjects6 2 }

dhcpEventObjects7 OBJECT-IDENTITY
    STATUS current
    DESCRIPTION
        "Event DHCP.7
        DHCP message received in server any host on local subnet."
    ::= { dhcpEventsGroup 7 }

dhcp7-message-type OBJECT-TYPE
    SYNTAX DisplayString
    MAX-ACCESS accessible-for-notify
    STATUS current
    DESCRIPTION
        "Parameter 'message-type' in event DHCP.7"
    ::= { dhcpEventObjects7 1 }

dhcpEventObjects8 OBJECT-IDENTITY
    STATUS current
    DESCRIPTION
        "Event DHCP.8
        Message generated when server offer or send an acknowledge
        allocating an IP address."
    ::= { dhcpEventsGroup 8 }

dhcp8-message-type OBJECT-TYPE
    SYNTAX DisplayString
    MAX-ACCESS accessible-for-notify
    STATUS current
    DESCRIPTION
        "Parameter 'message-type' in event DHCP.8"
    ::= { dhcpEventObjects8 1 }

dhcp8-param OBJECT-TYPE
    SYNTAX DisplayString
    MAX-ACCESS accessible-for-notify
    STATUS current
    DESCRIPTION
        "Parameter 'param' in event DHCP.8"
    ::= { dhcpEventObjects8 2 }

dhcp8-destination-ip-address OBJECT-TYPE
    SYNTAX IpAddress
    MAX-ACCESS accessible-for-notify
    STATUS current
    DESCRIPTION
        "Parameter 'destination-ip-address' in event DHCP.8"
    ::= { dhcpEventObjects8 3 }

dhcpEventObjects11 OBJECT-IDENTITY
    STATUS current
    DESCRIPTION
        "Event DHCP.11
        Found HOST definition with unknown hardware type (neither ethernet nor
        token ring)."
    ::= { dhcpEventsGroup 11 }

dhcp11-HW-type OBJECT-TYPE
    SYNTAX Integer32
    MAX-ACCESS accessible-for-notify
    STATUS current
    DESCRIPTION
        "Parameter 'HW-type' in event DHCP.11"
    ::= { dhcpEventObjects11 1 }

dhcpEventObjects12 OBJECT-IDENTITY
    STATUS current
    DESCRIPTION
        "Event DHCP.12
        Error in the DHCP module."
    ::= { dhcpEventsGroup 12 }

dhcp12-message OBJECT-TYPE
    SYNTAX DisplayString
    MAX-ACCESS accessible-for-notify
    STATUS current
    DESCRIPTION
        "Parameter 'message' in event DHCP.12"
    ::= { dhcpEventObjects12 1 }

dhcpEventObjects13 OBJECT-IDENTITY
    STATUS current
    DESCRIPTION
        "Event DHCP.13
        Warnings in the DHCP module."
    ::= { dhcpEventsGroup 13 }

dhcp13-message OBJECT-TYPE
    SYNTAX DisplayString
    MAX-ACCESS accessible-for-notify
    STATUS current
    DESCRIPTION
        "Parameter 'message' in event DHCP.13"
    ::= { dhcpEventObjects13 1 }

dhcpEventObjects14 OBJECT-IDENTITY
    STATUS current
    DESCRIPTION
        "Event DHCP.14
        Common information on the standard operation of the DHCP server."
    ::= { dhcpEventsGroup 14 }

dhcp14-message OBJECT-TYPE
    SYNTAX DisplayString
    MAX-ACCESS accessible-for-notify
    STATUS current
    DESCRIPTION
        "Parameter 'message' in event DHCP.14"
    ::= { dhcpEventObjects14 1 }

dhcpEventObjects15 OBJECT-IDENTITY
    STATUS current
    DESCRIPTION
        "Event DHCP.15
        State change of a shared network which is controlled by a NSLA advisor."
    ::= { dhcpEventsGroup 15 }

dhcp15-shared-id OBJECT-TYPE
    SYNTAX Integer32
    MAX-ACCESS accessible-for-notify
    STATUS current
    DESCRIPTION
        "Parameter 'shared-id' in event DHCP.15"
    ::= { dhcpEventObjects15 1 }

dhcp15-nsla-advisor-id OBJECT-TYPE
    SYNTAX Integer32
    MAX-ACCESS accessible-for-notify
    STATUS current
    DESCRIPTION
        "Parameter 'nsla-advisor-id' in event DHCP.15"
    ::= { dhcpEventObjects15 2 }

dhcp15-state OBJECT-TYPE
    SYNTAX DisplayString
    MAX-ACCESS accessible-for-notify
    STATUS current
    DESCRIPTION
        "Parameter 'state' in event DHCP.15"
    ::= { dhcpEventObjects15 3 }

dhcpEventObjects16 OBJECT-IDENTITY
    STATUS current
    DESCRIPTION
        "Event DHCP.16
        State change of a DHCP relay agent because all its servers are
        not accesibles."
    ::= { dhcpEventsGroup 16 }

dhcp16-state OBJECT-TYPE
    SYNTAX DisplayString
    MAX-ACCESS accessible-for-notify
    STATUS current
    DESCRIPTION
        "Parameter 'state' in event DHCP.16"
    ::= { dhcpEventObjects16 1 }

dhcp16-indicator OBJECT-TYPE
    SYNTAX Integer32
    MAX-ACCESS accessible-for-notify
    STATUS current
    DESCRIPTION
        "Parameter 'indicator' in event DHCP.16"
    ::= { dhcpEventObjects16 2 }


dhcpNotification1 NOTIFICATION-TYPE
    STATUS current
    DESCRIPTION
        "Notification of Event DHCP.1

        Message: 'BOOTREQUEST packet received'

        The router has received a packet from a DHCP client requesting a
        response to a DHCP server."
    ::= { dhcpNotificationsPrefix 1 }

dhcpNotification2 NOTIFICATION-TYPE
    STATUS current
    DESCRIPTION
        "Notification of Event DHCP.2

        Message: 'BOOTREPLY packet received'

        The router has received a packet from a DHCP server in response to a
        BOOTREQUEST."
    ::= { dhcpNotificationsPrefix 2 }

dhcpNotification3 NOTIFICATION-TYPE
    OBJECTS { 
              dhcp3-source-ip-address, 
              dhcp3-destination-ip-address 
            }
    STATUS current
    DESCRIPTION
        "Notification of Event DHCP.3

        Message: 'Relay BOOTREQUEST from $1 to DHCP server $2'

        Parameters list:
              $1: dhcp3-source-ip-address
              $2: dhcp3-destination-ip-address

        Message generated when the router relays packets received from
        DHCP clients and addressed to DHCP servers."
    ::= { dhcpNotificationsPrefix 3 }

dhcpNotification4 NOTIFICATION-TYPE
    OBJECTS { 
              dhcp4-source-ip-address, 
              dhcp4-destination-ip-address 
            }
    STATUS current
    DESCRIPTION
        "Notification of Event DHCP.4

        Message: 'Relay BOOTREPLAY from DHCP server $1 to DHCP client $2'

        Parameters list:
              $1: dhcp4-source-ip-address
              $2: dhcp4-destination-ip-address

        Message generated when the router relays packets received from
        DHCP servers and addressed to DHCP clients."
    ::= { dhcpNotificationsPrefix 4 }

dhcpNotification5 NOTIFICATION-TYPE
    OBJECTS { 
              dhcp5-message-type, 
              dhcp5-source-ip-address 
            }
    STATUS current
    DESCRIPTION
        "Notification of Event DHCP.5

        Message: 'DHCP $1 packet received from relay on $2'

        Parameters list:
              $1: dhcp5-message-type
              $2: dhcp5-source-ip-address

        DHCP message received in server from relay on an IP address."
    ::= { dhcpNotificationsPrefix 5 }

dhcpNotification6 NOTIFICATION-TYPE
    OBJECTS { 
              dhcp6-message-type, 
              dhcp6-source-ip-address 
            }
    STATUS current
    DESCRIPTION
        "Notification of Event DHCP.6

        Message: 'DHCP $1 packet received from host on $2'

        Parameters list:
              $1: dhcp6-message-type
              $2: dhcp6-source-ip-address

        DHCP message received in server from host on an known IP address."
    ::= { dhcpNotificationsPrefix 6 }

dhcpNotification7 NOTIFICATION-TYPE
    OBJECTS { 
              dhcp7-message-type 
            }
    STATUS current
    DESCRIPTION
        "Notification of Event DHCP.7

        Message: 'DHCP $1 packet received from any host on local subnet'

        Parameters list:
              $1: dhcp7-message-type

        DHCP message received in server any host on local subnet."
    ::= { dhcpNotificationsPrefix 7 }

dhcpNotification8 NOTIFICATION-TYPE
    OBJECTS { 
              dhcp8-message-type, 
              dhcp8-param,
              dhcp8-destination-ip-address 
            }
    STATUS current
    DESCRIPTION
        "Notification of Event DHCP.8

        Message: 'DHCP $1 packet sent to a $2 host on $3'

        Parameters list:
              $1: dhcp8-message-type
              $2: dhcp8-param
              $3: dhcp8-destination-ip-address

        Message generated when server offer or send an acknowledge
        allocating an IP address."
    ::= { dhcpNotificationsPrefix 8 }

dhcpNotification9 NOTIFICATION-TYPE
    STATUS current
    DESCRIPTION
        "Notification of Event DHCP.9

        Message: 'Packet BOOTREQUEST'

        Message generated when server receives a BOOTREQUEST."
    ::= { dhcpNotificationsPrefix 9 }

dhcpNotification10 NOTIFICATION-TYPE
    STATUS current
    DESCRIPTION
        "Notification of Event DHCP.10

        Message: 'Sent Packet BOOTREPLY'

        Message generated when server sends a BOOTREPLY."
    ::= { dhcpNotificationsPrefix 10 }

dhcpNotification11 NOTIFICATION-TYPE
    OBJECTS { 
              dhcp11-HW-type 
            }
    STATUS current
    DESCRIPTION
        "Notification of Event DHCP.11

        Message: 'Unknown Hardware type: $1'

        Parameters list:
              $1: dhcp11-HW-type

        Found HOST definition with unknown hardware type (neither ethernet nor
        token ring)."
    ::= { dhcpNotificationsPrefix 11 }

dhcpNotification12 NOTIFICATION-TYPE
    OBJECTS { 
              dhcp12-message 
            }
    STATUS current
    DESCRIPTION
        "Notification of Event DHCP.12

        Message: 'error: $1'

        Parameters list:
              $1: dhcp12-message

        Error in the DHCP module."
    ::= { dhcpNotificationsPrefix 12 }

dhcpNotification13 NOTIFICATION-TYPE
    OBJECTS { 
              dhcp13-message 
            }
    STATUS current
    DESCRIPTION
        "Notification of Event DHCP.13

        Message: '$1'

        Parameters list:
              $1: dhcp13-message

        Warnings in the DHCP module."
    ::= { dhcpNotificationsPrefix 13 }

dhcpNotification14 NOTIFICATION-TYPE
    OBJECTS { 
              dhcp14-message 
            }
    STATUS current
    DESCRIPTION
        "Notification of Event DHCP.14

        Message: '$1'

        Parameters list:
              $1: dhcp14-message

        Common information on the standard operation of the DHCP server."
    ::= { dhcpNotificationsPrefix 14 }

dhcpNotification15 NOTIFICATION-TYPE
    OBJECTS { 
              dhcp15-shared-id, 
              dhcp15-nsla-advisor-id,
              dhcp15-state 
            }
    STATUS current
    DESCRIPTION
        "Notification of Event DHCP.15

        Message: 'Shared network $1 controlled by NLSA advisor $2 changes to $3'

        Parameters list:
              $1: dhcp15-shared-id
              $2: dhcp15-nsla-advisor-id
              $3: dhcp15-state

        State change of a shared network which is controlled by a NSLA advisor."
    ::= { dhcpNotificationsPrefix 15 }

dhcpNotification16 NOTIFICATION-TYPE
    OBJECTS { 
              dhcp16-state, 
              dhcp16-indicator 
            }
    STATUS current
    DESCRIPTION
        "Notification of Event DHCP.16

        Message: 'DHCP relay goes $1 updating the level indicator $2'

        Parameters list:
              $1: dhcp16-state
              $2: dhcp16-indicator

        State change of a DHCP relay agent because all its servers are
        not accesibles."
    ::= { dhcpNotificationsPrefix 16 }


END
