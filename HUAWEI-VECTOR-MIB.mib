-- ============================================================================
-- Copyright (C) 2012 by  HUAWEI TECHNOLOGIES. All rights reserved.
-- Description:  This mib is used for defining huawei's vectoring management MIB objects.
--               The MIB is used for vectoring, vectoring is a transmission method that 
--               employs the coordination of line signals for reduction of crosstalk levels
--               and improvement of performance.
-- Reference:
-- Version: V1.03
--
-- ============================================================================

    HUAWEI-VECTOR-MIB DEFINITIONS ::= BEGIN

        IMPORTS
            enterprises, Integer32, Unsigned32, Gauge32, OBJECT-TYPE,
            MODULE-IDENTITY, OBJECT-IDENTITY, NOTIFICATION-TYPE
                FROM SNMPv2-SMI
            RowStatus, TruthValue, TEXTUAL-CONVENTION
                FROM SNMPv2-TC
            huaweiUtility
                FROM HUAWEI-MIB
            ifIndex
                FROM IF-MIB
            hwFrameIndex, hwSlotIndex, hwPortIndex, hwConfigChangeIP
                FROM HUAWEI-DEVICE-MIB
            Vdsl2Direction
                FROM   HUAWEI-VDSL2-LINE-TC-MIB
            hwXdslRequestID, hwXdslPortFrequentRetrainControlTimes
                FROM   HUAWEI-XDSL-COMMON-MIB;
             
            hwVectoringMIB MODULE-IDENTITY
            LAST-UPDATED "201301150000Z"
            ORGANIZATION
                "Huawei Technologies co.,Ltd."
            CONTACT-INFO                                        
                         "Huawei Industrial Base                
                          Bantian, Longgang                     
                          Shenzhen 518129                       
                          People's Republic of China            
                          Website: http://www.huawei.com        
                          Email: support@huawei.com             
                         "                                      
            DESCRIPTION
                "This mib is used for defining huawei's vectoring management MIB objects.
                 The MIB is used for vectoring, vectoring is a transmission method that 
                 employs the coordination of line signals for reduction of crosstalk levels
                 and improvement of performance.
                "

            --  Revision history
            
            REVISION     "201301150000Z"
            DESCRIPTION  "V1.03, changes in this revision:
                          Add the definition of the nodes: hwVectoringReceivedESRecoverAlarmTrap, hwVectoringPSConfigAbnormalAlarmTrap, 
                          hwVectoringPSConfigRecoverAlarmTrap in hwVectoringTraps.
                         "
                         
            REVISION     "201208260000Z"
            DESCRIPTION  "V1.02, changes in this revision:
                          Add leaf node hwVectoringLegacyCpeReservedBand and hwVectoringLegacyCpeToneBlackoutBand.
                          Create table hwVectoringFastJoinConfig and hwVectoringCrosstalkCouplingMatrixTable.
                          Add leaf node hwVectoringGroupProtectionOfNotReqBandsDs and hwVectoringGroupProtectionOfNotReqBandsUs.
                          Add leaf node hwVectoringLinkCPEType to get the CPE type connected to the port.
                          Add leaf node hwVectoringGlobalConfigChangeTrap to notify the change vectoring global configuration.
                          Create table hwVectoringCommonTraps to fetch the vectoring traps.
                          Add leaf node hwVectoringGlobalConfigChangeTrap.
                          Add leaf node hwVectoringVictCoefAbnormalVariationAlarmTrap, hwVectoringDistCoefAbnormalVariationAlarmTrap,
                          hwVectoringReceivedESAbnormalAlarmTrap, hwvdsl2LegacyCpeActivatedAlarmTrap and hwvdsl2FrequentlyRetrainTimesReachThresholdAlarmTrap.
                          Modify the node hwVectoringGroupIndex, hwVectoringLinkBelongedVceId 
                          and hwVectoringAutoGroupingGroupIndex.
                          Create table hwVectoringTrapsVbOids.
                          Add leaf node hwVectoringPortFrequentRetrainTimes.
                          delete unnecessary en dashes.
                          Add the definition of the table hwVectoringAutoGroupingTable, 
                          hwVectoringCrosstalkCouplingMatrixTable, hwVectoringAlarmTraps. 
                          add value forceFriendlyDsLimitUs(4) and forceFriendlyDsNoLimitUs(5) for hwVectoringLegacyCpeActivatePolicy and modify the description .                        
                         "
                        
            REVISION     "201202150000Z"
            DESCRIPTION  "V1.01, changes in this revision:
                          Add the definition of the table: hwVectoringGroupTable, hwVectoringConfProfTable, hwVectoringPortTable.
                          Add the definition of the nodes: hwVectoringLegacyCpeActivatePolicy in hwVectoringGlobalConfig.
                          Add the definition of the nodes: hwVectoringLinkBandPlanCompatible in hwVectoringPortTable.
                          Add the definition of the nodes: hwVectoringBandplanType, hwVectoringUs0Type, hwVectoringAnnexALimitMask in hwVectoringGlobalConfig.
                         "

            REVISION     "201109010000Z"                                                 
            DESCRIPTION  "V1.00, initial version" 

            ::= { huaweiUtility 171 }

--
-- Textual conventions
--

--
-- Vectoring table
--
        hwVectoringGlobalConfig OBJECT IDENTIFIER ::= { hwVectoringMIB 1 }
        
            hwVectoringSwitch OBJECT-TYPE
            SYNTAX INTEGER       
            {       
                enable(1),
                disable(2)     
            }       
            MAX-ACCESS  read-write       
            STATUS      current       
            DESCRIPTION       
                "Enable/Disable the global vectoring configuration. 
                 Default values:disable.
                 Options:
                 1. enable(1)  - Enables the global vectoring configuration
                 2. disable(2) - Disables the global vectoring configuration
                "
            ::= { hwVectoringGlobalConfig 1 }
            
        hwVectoringLegacyCpeActivatePolicy OBJECT-TYPE
            SYNTAX INTEGER       
            {       
                no-limit(1),
                block(2),
                limit(3),
                forceFriendlyDsLimitUs(4),
                forceFriendlyDsNoLimitUs(5)     
            }       
            MAX-ACCESS  read-write       
            STATUS      current       
            DESCRIPTION       
                "Vectoring legacy cpe activate policy. 
                 Default values:limit.
                 Options:
                 1. no-limit(1)                   - The legacy cpe is allowed to activated in G.993.2 operation mode
                 2. block(2)                      - The legacy cpe is not allowed to activated in G.993.2 operation mode
                 3. limit(3)                      - The legacy cpe is allowed to activated in G.993.2 operation mode, 
                                                    with PSD auto shaped to eliminate the self-FEXT to vectoring lines
                 4. forceFriendlyDsLimitUs(4)     - Force friendly is used in the downstream direction, and PSD automatic 
                                                    shaping is used in the upstream direction
                 5. forceFriendlyDsNoLimitUs(5)   - Force friendly is used in the downstream direction, and no restriction 
                                                    is set for the upstream direction
                "
            ::= { hwVectoringGlobalConfig 2 }
            
        hwVectoringBandplanType OBJECT-TYPE
            SYNTAX INTEGER
            {
                bandplanAnnexa(1),
                bandplanAnnexc(2),
                bandplan997e(3),
                bandplan998ade(4),
                bandplan998e(5),
                bandplanHPE(6)               
            }       
            MAX-ACCESS  read-write
            STATUS      current
            DESCRIPTION
                "Vectoring global frequency plan types.
                 Default values:bandplan998ade.
                 Options:
                 1. bandplanAnnexa(1)  - The frequency plan types for the vectoring feature is Annex A
                 2. bandplanAnnexc(2)  - The frequency plan types for the vectoring feature is Annex C
                 3. bandplan997e(3)    - The frequency plan types for the vectoring feature is 997E
                 4. bandplan998ade(4)  - The frequency plan types for the vectoring feature is 998ADE
                 5. bandplan998e(5)    - The frequency plan types for the vectoring feature is 998E
                 6. bandplanHPE(6)     - The frequency plan types for the vectoring feature is HPE
                "
            ::= { hwVectoringGlobalConfig 3 }
            
        hwVectoringUs0Type OBJECT-TYPE
            SYNTAX INTEGER
            {
                us0TypeA(1),
                us0TypeB(2),
                us0TypeM(3),
                us0TypeN(4),
                invalidValue(-1)
            }       
            MAX-ACCESS  read-write
            STATUS      current
            DESCRIPTION
                "Vectoring us0 type.
                 Default values:us0TypeA.
                 Options:
                 1. us0TypeA(1)      - US0 type is US0-type A
                 2. us0TypeB(2)      - US0 type is US0-type B
                 3. us0TypeM(3)      - US0 type is US0-type M
                 4. us0TypeN(4)      - US0 type is US0-type N/A
                 5. invalidValue(-1) - US0 type return -1 when vectoring frequency plan types is Annex A/Annex C
                 "
            ::= { hwVectoringGlobalConfig 4 }
            
        hwVectoringAnnexALimitMask OBJECT-TYPE
            SYNTAX INTEGER
            {
                d32(1),
                d48(2),
                d64(3),
                d128(4),
                invalidValue(-1)
            }       
            MAX-ACCESS  read-write
            STATUS      current
            DESCRIPTION
                "AnnexA limit mask.
                 Options:
                 1. d32(1)          - AnnexA limit mask is D-32
                 2. d48(2)          - AnnexA limit mask is D-48
                 3. d64(3)          - AnnexA limit mask is D-64
                 4. d128(4)         - AnnexA limit mask is D-128
                 5. invalidValue(-1) - AnnexA limit mask return -1 when vectoring frequency plan types is not Annex A
                "
            ::= { hwVectoringGlobalConfig 5 }            
            
        hwVectoringLegacyCpeReservedBand OBJECT-TYPE
            SYNTAX      OCTET STRING (SIZE(0..79))
            MAX-ACCESS  read-write
            STATUS      current
            DESCRIPTION
              "This object is used to set the reserved band of a legacy CPE. 
               This object takes effect when hwVectoringLegacyCpeActivatePolicy is set to limit. 
               Range of the subcarrier IDs: 0-6956. Two subcarriers are separated by a comma (,). 
               The format is: start subcarrier ID-end subcarrier ID. 
               The start subcarrier ID cannot be greater than the end subcarrier ID. 
               Only eight reserved band is supported, for example, 880-900,1000-1100.
               The settings of hwVectoringLegacyCpeReservedBand and 
               hwVectoringLegacyCpeToneBlackoutBand cannot overlap with each other.
              "
            ::= { hwVectoringGlobalConfig 6 }    
     
        hwVectoringLegacyCpeToneBlackoutBand OBJECT-TYPE
            SYNTAX      OCTET STRING (SIZE(0..79))
            MAX-ACCESS  read-write
            STATUS      current
            DESCRIPTION
               "This object is used to set the blackout band of a legacy CPE. 
                This object takes effect when hwVectoringLegacyCpeActivatePolicy is set to limit.
                Range of the subcarrier IDs: 0-6956. Two subcarriers are separated by a comma (,). 
                The format is: start subcarrier ID-end subcarrier ID.
                The start subcarrier ID cannot be greater than the end subcarrier ID. 
                Only eight tone blackout band is supported, for example, 1300-1320,1400-1500. 
                The settings of hwVectoringLegacyCpeReservedBand and 
                hwVectoringLegacyCpeToneBlackoutBand cannot overlap with each other.
                "
           ::= { hwVectoringGlobalConfig 7 } 
            
--       hwVectoringGroupTable        
    hwVectoringGroupTable OBJECT-TYPE
        SYNTAX SEQUENCE OF HwVectoringGroupEntry
        MAX-ACCESS not-accessible
        STATUS current
        DESCRIPTION
            "The table hwVectoringGroupTable contains the vectoring group
 	     configuration.
 	     The index of this table is hwVectoringGroupIndex.
 	    "
        ::= { hwVectoringMIB 2 }
        
     hwVectoringGroupEntry OBJECT-TYPE
        SYNTAX HwVectoringGroupEntry
        MAX-ACCESS not-accessible
        STATUS current
        DESCRIPTION
             "The table hwVectoringGroupTable contains the vectoring group
 	     configuration.
 	     The index of this entry is hwVectoringGroupIndex.
 	    "
        INDEX { hwVectoringGroupIndex }
        ::= { hwVectoringGroupTable 1 }
        
    HwVectoringGroupEntry ::=
        SEQUENCE 
            { 
                hwVectoringGroupIndex                      Unsigned32,
                hwVectoringGroupNotReqBandsUs              OCTET STRING,
                hwVectoringGroupNotReqBandsDs              OCTET STRING,
                hwVectoringGroupLinkList                   OCTET STRING,
                hwVectoringGroupRowStatus                  RowStatus,
                hwVectoringGroupProtectionOfNotReqBandsDs  INTEGER,
                hwVectoringGroupProtectionOfNotReqBandsUs  INTEGER            
            }    
        
    hwVectoringGroupIndex OBJECT-TYPE
        SYNTAX      Unsigned32 (1..96)
        MAX-ACCESS  not-accessible
        STATUS      current
        DESCRIPTION
            "This object identifies a row in this table."
        ::= { hwVectoringGroupEntry 1 }
   
    hwVectoringGroupNotReqBandsUs OBJECT-TYPE
        SYNTAX      OCTET STRING (SIZE(0..79))
        MAX-ACCESS  read-create
        STATUS      current
        DESCRIPTION
          "This configuration parameter shall be an array of pairs of 
	   sub-carrier indices for uptream . Each pair represents the
	   start and stop sub-carrier index of a frequency band in which
	   FEXT cancellation is not required. Up to 8 frequency bands may
	   be configured.
	   for example :880-900,1000-1020
	  "
        ::= { hwVectoringGroupEntry 2 }    

    hwVectoringGroupNotReqBandsDs OBJECT-TYPE
        SYNTAX      OCTET STRING (SIZE(0..79))
        MAX-ACCESS  read-create
        STATUS      current
        DESCRIPTION
	   "This configuration parameter shall be an array of pairs of 
	    sub-carrier indices for downstream . Each pair represents the
	    start and stop sub-carrier index of a frequency band in which
	    FEXT cancellation is not required. Up to 8 frequency bands may
	    be configured.
	    for example :1300-1320,1400-1450
	   "
        ::= { hwVectoringGroupEntry 3 } 
        
    hwVectoringGroupLinkList OBJECT-TYPE
        SYNTAX      OCTET STRING (SIZE (0..2048))
        MAX-ACCESS  read-create
        STATUS      current
        DESCRIPTION
            "This object defines the link list of the vectoring group.
             This is a string of 4 bytes of values indicates the port ifindex.
             It can contain as most as 512 link."
        ::= { hwVectoringGroupEntry 4 }
        
    hwVectoringGroupRowStatus OBJECT-TYPE
        SYNTAX      RowStatus
        MAX-ACCESS  read-create
        STATUS      current
        DESCRIPTION
            "This object is used to create a new row or delete an existing row 
             in this table.
            "
        ::= { hwVectoringGroupEntry 5 } 

    hwVectoringGroupProtectionOfNotReqBandsDs OBJECT-TYPE
        SYNTAX INTEGER {
                           enable (1),
                           disable (2)
                       }
        MAX-ACCESS  read-create
        STATUS      current
        DESCRIPTION
                   "This object enable/disable the protection of vectoring
                    lines downstream. 
                    Options:
                    1. enable(1)- The protection of vectoring lines downstream 
                                   is enabled
                    2. disable(2) - The protection of vectoring lines downstream
                                   is disabled
                   "         
        DEFVAL       { disable }
        ::= { hwVectoringGroupEntry 6 }     

    hwVectoringGroupProtectionOfNotReqBandsUs OBJECT-TYPE
        SYNTAX INTEGER {
                           enable (1),
                           disable (2)
                       }
        MAX-ACCESS  read-create
        STATUS      current
        DESCRIPTION
                   "This object enable/disable the protection of vectoring
                    lines upstream. 
                    Options:
                    1. enable(1)- The protection of vectoring lines upstream 
                                   is enabled
                    2. disable(2) - The protection of vectoring lines upstream
                                   is disabled
                   "         
        DEFVAL       { disable }
        ::= { hwVectoringGroupEntry 7 }          
                
--       hwVectoringConfProfTable        
    hwVectoringConfProfTable OBJECT-TYPE
        SYNTAX SEQUENCE OF HwVectoringConfProfEntry
        MAX-ACCESS not-accessible
        STATUS current
        DESCRIPTION
            "The table hwVectoringConfProfTable contains the vectoring profile
 	     configuration.
 	     A default profile with an index of 'DEFVAL' will always exist and 
 	     its parameters will be set to vendor-specific values, unless otherwise 
 	     specified in this document.
 	     The index of this table is hwVectoringProfName."
        ::= { hwVectoringMIB 3 }
        
     hwVectoringConfProfEntry OBJECT-TYPE
        SYNTAX HwVectoringConfProfEntry
        MAX-ACCESS not-accessible
        STATUS current
        DESCRIPTION
             "The table hwVectoringConfProfTable contains the vectoring profile
 	      configuration. 
 	      A default profile with an index of 'DEFVAL' will always exist and 
 	      its parameters will be set to vendor-specific values, unless otherwise 
 	      specified in this document.
 	      The index of this entry is hwVectoringProfName."
        INDEX { IMPLIED hwVectoringProfName }
        ::= { hwVectoringConfProfTable 1 }
        
    HwVectoringConfProfEntry ::=
        SEQUENCE 
            { 
                hwVectoringProfName                      OCTET STRING,
                hwVectoringEnableUs                      INTEGER,
                hwVectoringEnableDs                      INTEGER,
                hwVectoringProfRowStatus                 RowStatus
            }    
        
    hwVectoringProfName OBJECT-TYPE
        SYNTAX      OCTET STRING (SIZE(1..32))
        MAX-ACCESS  not-accessible
        STATUS      current
        DESCRIPTION
            "This object identifies a row in this table."
        ::= { hwVectoringConfProfEntry 1 }	      

    hwVectoringEnableUs OBJECT-TYPE
        SYNTAX INTEGER       
        {       
            enable(1),
            disable(2)     
        }
        MAX-ACCESS  read-create
        STATUS      current
        DESCRIPTION
            "Enable/Disable FEXT cancellation control upstream. 
             Default values: enable.
             Options:
             1. enable(1)  - Enable FEXT cancellation in the upstream direction from all the other vectoring lines into the line in the vectoring group
             2. disable(2) - Disable FEXT cancellation in the upstream direction from all the other vectoring lines into the line in the vectoring group."
        DEFVAL       { enable }
        ::= { hwVectoringConfProfEntry 2 }      
        
    hwVectoringEnableDs OBJECT-TYPE
        SYNTAX INTEGER       
        {       
            enable(1),
            disable(2)     
        }
        MAX-ACCESS  read-create
        STATUS      current
        DESCRIPTION
            "Enable/Disable FEXT cancellation control downstream. 
             Default values: enable.
             Options:
             1. enable(1)  - Enable FEXT cancellation in the downstream direction from all the other vectoring lines into the line in the vectoring group
             2. disable(2) - Disable FEXT cancellation in the downstream direction from all the other vectoring lines into the line in the vectoring group"
        DEFVAL       { enable }
        ::= { hwVectoringConfProfEntry 3 }       
        
    hwVectoringProfRowStatus OBJECT-TYPE
        SYNTAX      RowStatus
        MAX-ACCESS  read-create
        STATUS      current
        DESCRIPTION
            "This object is used to create a new row or delete an existing row 
             in this table. Before a profile can be deleted, it must be not 
             referenced from all VDSL ports."
        ::= { hwVectoringConfProfEntry 4 }
    
--       hwVectoringPortTable            
    hwVectoringPortTable OBJECT-TYPE
        SYNTAX SEQUENCE OF HwVectoringPortEntry
        MAX-ACCESS not-accessible
        STATUS current
        DESCRIPTION
            "The table hwVectoringPortTable contains port configuration about vectoring.
             The index of this table is ifIndex.
            "
        ::= { hwVectoringMIB 4 }
        
     hwVectoringPortEntry OBJECT-TYPE
        SYNTAX HwVectoringPortEntry
        MAX-ACCESS not-accessible
        STATUS current
        DESCRIPTION
             "The table hwVectoringPortTable contains port configuration about vectoring.
 	      The index of this entry is ifIndex."
        INDEX { ifIndex }
        ::= { hwVectoringPortTable 1 }
        
    HwVectoringPortEntry ::=
        SEQUENCE 
            { 
                hwVectoringLinkCfgProf                      OCTET STRING,
                hwVectoringLinkBelongedVceId                Unsigned32,
                hwVectoringLinkVcePortIndex                 Unsigned32,
                hwVectoringLinkBandPlanCompatible           INTEGER,
                hwVectoringLinkCPEType                      INTEGER
            }    
        
    hwVectoringLinkCfgProf OBJECT-TYPE
        SYNTAX      OCTET STRING (SIZE(0..32))
        MAX-ACCESS  read-write
        STATUS      current
        DESCRIPTION
            "This object configures the vectoring link profile name.
            "
        ::= { hwVectoringPortEntry 1 }        

    hwVectoringLinkBelongedVceId OBJECT-TYPE
        SYNTAX Unsigned32 (0..96)
        MAX-ACCESS  read-only
        STATUS      current
        DESCRIPTION
            "The VCE ID uniquely identifies the VCE that manages and controls
             the vectored group to which the line belongs. It consists of one 
             octet and valid ranges are from 1 to 96. The special value 0 means
             the line is not in a vectored group."
        ::= { hwVectoringPortEntry 2 }      
        
    hwVectoringLinkVcePortIndex OBJECT-TYPE
        SYNTAX Unsigned32 (0..512)
        MAX-ACCESS  read-only
        STATUS      current
        DESCRIPTION
            "The VCE port index is the physical index that uniquely identifies
             the VCE port to which the line is connected. It is an integer from
             1 to the maximum number of lines supported by the VCE. The special 
             value 0 means the VCE port index is not valid"
        ::= { hwVectoringPortEntry 3 }
        
    hwVectoringLinkBandPlanCompatible OBJECT-TYPE
         SYNTAX INTEGER       
        {       
            compatible(1),
            incompatible(2)     
        }
        MAX-ACCESS read-only
        STATUS current
        DESCRIPTION
            "Options:
             1. compatible(1)   - The vectoring line configured band plan is compatible with the vectoring band configuration
             2. incompatible(2) - The vectoring line configured band plan is not compatible with the vectoring band configuration"
        ::= { hwVectoringPortEntry 4 }   
         
    hwVectoringLinkCPEType  OBJECT-TYPE
        SYNTAX INTEGER
        {
            vectoring(1),
            fullFriendly(2),
            friendlyDs(3),
            legacyVdsl2(4),
            adsl(5),
            unknown(6)
        }
        MAX-ACCESS read-only
        STATUS current
        DESCRIPTION
            "Options:
             1. vectoring(1)     - The CPE type is vectoring
             2. fullFriendly(2)  - The CPE type is vectoring full friendly
             3. friendlyDs(3)    - The CPE type is vectoring friendly ds
             4. legacyVdsl2(4)   - The CPE type is vdsl2
             5. adsl(5)          - The CPE type is adsl/2/2+
             6. unknown(6)       - The CPE type is unknown
            "
        ::= { hwVectoringPortEntry 5 }   
                       
--       hwVectoringAutoGroupingTable            
    hwVectoringAutoGroupingTable OBJECT-TYPE
        SYNTAX SEQUENCE OF HwVectoringAutoGroupingEntry
        MAX-ACCESS not-accessible
        STATUS current
        DESCRIPTION
            "The table hwVectoringAutoGroupingTable contains the vectoring
             auto group result.
             The indexes of this table are hwVectoringGroupIndex and hwVectoringAutoGroupingGroupIndex.
            "
        ::= { hwVectoringMIB 5 }
        
     hwVectoringAutoGroupingEntry OBJECT-TYPE
        SYNTAX HwVectoringAutoGroupingEntry
        MAX-ACCESS not-accessible
        STATUS current
        DESCRIPTION
             "The table hwVectoringAutoGroupingTable contains the vectoring
              auto group result.
 	      The indexes of this entry are hwVectoringGroupIndex and hwVectoringAutoGroupingGroupIndex."
        INDEX { 
          hwVectoringGroupIndex,
          hwVectoringAutoGroupingGroupIndex
          }
        ::= { hwVectoringAutoGroupingTable 1 }
        
    HwVectoringAutoGroupingEntry ::=
        SEQUENCE 
            { 
                hwVectoringAutoGroupingGroupIndex           Unsigned32,
                hwVectoringAutoGroupingGroupLinkList        OCTET STRING
            }    
        
    hwVectoringAutoGroupingGroupIndex OBJECT-TYPE
        SYNTAX      Unsigned32 (1..96)
        MAX-ACCESS  not-accessible
        STATUS      current
        DESCRIPTION
            "This object identifies auto group index.
            "       
        ::= { hwVectoringAutoGroupingEntry 1 } 
        
    hwVectoringAutoGroupingGroupLinkList OBJECT-TYPE
        SYNTAX      OCTET STRING (SIZE (0..2048))
        MAX-ACCESS  read-only
        STATUS      current
        DESCRIPTION
            "This object defines the link list of the vectoring auto group.
             This is a string of 4 bytes of values indicates the port ifindex.
             It can contain as most as 512 link.
            "       
        ::= { hwVectoringAutoGroupingEntry 2 }
        
--   hwVectoringCrosstalkCouplingMatrixTable            
    hwVectoringCrosstalkCouplingMatrixTable OBJECT-TYPE
        SYNTAX SEQUENCE OF HwVectoringCrosstalkCouplingMatrixEntry
        MAX-ACCESS not-accessible
        STATUS current
        DESCRIPTION
            "The table hwVectoringCrosstalkCouplingMatrixTable contains information of vectoring 
             crosstalk coupling matrix about a port in a vectoring group.
             The indexes of this table are ifIndex and hwVectoringCrosstalkCouplingMatrixDirection.
            "
        ::= { hwVectoringMIB 6 }
        
     hwVectoringCrosstalkCouplingMatrixEntry OBJECT-TYPE
        SYNTAX HwVectoringCrosstalkCouplingMatrixEntry
        MAX-ACCESS not-accessible
        STATUS current
        DESCRIPTION
             "The table hwVectoringCrosstalkCouplingMatrixTable contains information of vectoring 
              crosstalk coupling matrix about a port in a vectoring group.
              The indexes of this entry are ifIndex and hwVectoringCrosstalkCouplingMatrixDirection.
             "
        INDEX { 
          ifIndex,
          hwVectoringCrosstalkCouplingMatrixDirection
          }
        ::= { hwVectoringCrosstalkCouplingMatrixTable 1 }
        
    HwVectoringCrosstalkCouplingMatrixEntry ::=
        SEQUENCE 
            { 
                hwVectoringCrosstalkCouplingMatrixDirection                 Vdsl2Direction,
                hwVectoringCrosstalkCoupingMatrixOperType                   INTEGER,
                hwVectoringCrosstalkCoupingMatrixOperResult                 INTEGER,
                hwVectoringCrosstalkCouplingMatrixPortIfindexList           OCTET STRING,
                hwVectoringCrosstalkCouplingMatrixAverageMagnitudeList      OCTET STRING,
                hwVectoringCrosstalkCouplingMatrixCancellationStatusList    OCTET STRING
            }    
        
    hwVectoringCrosstalkCouplingMatrixDirection OBJECT-TYPE
        SYNTAX      Vdsl2Direction
        MAX-ACCESS  not-accessible
        STATUS      current
        DESCRIPTION
            "The direction of the vectoring crosstalk coupling matrix 
             either upstream or downstream.
            "       
        ::= { hwVectoringCrosstalkCouplingMatrixEntry 1 } 
        
    hwVectoringCrosstalkCoupingMatrixOperType OBJECT-TYPE
        SYNTAX      INTEGER
        {
        start(1),
        stop(2)
        }
        MAX-ACCESS  read-write
        STATUS      current
        DESCRIPTION
            "This object is used to start the vectoring crosstalk coupling matrix.
             Options:
             1. start(1)            - start the vectoring crosstalk coupling matrix
             2. stop(2)             - stop the vectoring crosstalk coupling matrix
            "       
        ::= { hwVectoringCrosstalkCouplingMatrixEntry 2 } 
        
    hwVectoringCrosstalkCoupingMatrixOperResult OBJECT-TYPE
        SYNTAX      INTEGER
        {
        normal(1),
        fail(2)
        }
        MAX-ACCESS  accessible-for-notify
        STATUS      current
        DESCRIPTION
            "This object identifies the crosstalk coupling matrix operation result.
             Options:
             1. normal(1)           - The crosstalk coupling matrix operation result is normal.
             2. fail(2)             - The crosstalk coupling matrix operation result is fail.
            "       
        ::= { hwVectoringCrosstalkCouplingMatrixEntry 3 } 
        
    hwVectoringCrosstalkCouplingMatrixPortIfindexList OBJECT-TYPE
        SYNTAX      OCTET STRING (SIZE (0..2048))
        MAX-ACCESS  read-only
        STATUS      current
        DESCRIPTION
            "Ifindex list of port that effect another port in the same vectoring group.
             This is a string of 4 bytes of values indicates the port ifindex.
            "       
        ::= { hwVectoringCrosstalkCouplingMatrixEntry 4 } 
        
    hwVectoringCrosstalkCouplingMatrixAverageMagnitudeList OBJECT-TYPE
        SYNTAX      OCTET STRING (SIZE (0..2048))
        MAX-ACCESS  read-only
        STATUS      current
        DESCRIPTION
            "In this matrix must be seen all vectoring subscribers with disturberline.
             This is a string of 4 bytes of values indicates the port average magnitude.
             The units is 0.1 dBm/Hz.
            "       
        ::= { hwVectoringCrosstalkCouplingMatrixEntry 5 }
        
    hwVectoringCrosstalkCouplingMatrixCancellationStatusList OBJECT-TYPE
        SYNTAX      OCTET STRING (SIZE (0..512))
        MAX-ACCESS  read-only
        STATUS      current
        DESCRIPTION
            "This is a string of 1 bytes of values indicates the port crosstalk another.
             The byte value indicates:
             1. yes(1)            - counteract
             2. no(2)             - not counteract
             3. invalidValue(-1)  - invalid value
            "       
        ::= { hwVectoringCrosstalkCouplingMatrixEntry 6 }
              
--       hwVectoringBoardVectoringStateTable   
    hwVectoringBoardVectoringStateTable OBJECT-TYPE
        SYNTAX SEQUENCE OF HwVectoringBoardVectoringStateEntry
        MAX-ACCESS not-accessible
        STATUS current
        DESCRIPTION
            "The table hwVectoringBoardVectoringStateTable contains the vectoring current running information.
             The indexes of this table are hwFrameIndex and hwSlotIndex.
            "
        ::= { hwVectoringMIB 7 }
        
     hwVectoringBoardVectoringStateEntry OBJECT-TYPE
        SYNTAX HwVectoringBoardVectoringStateEntry
        MAX-ACCESS not-accessible
        STATUS current
        DESCRIPTION
             "The table hwVectoringBoardVectoringStateTable contains the vectoring current running information.
             The indexes of this entry are hwFrameIndex and hwSlotIndex.
             "
        INDEX { 
          hwFrameIndex,
          hwSlotIndex
          }
        ::= { hwVectoringBoardVectoringStateTable 1 }
        
    HwVectoringBoardVectoringStateEntry ::=
        SEQUENCE 
            { 
                hwVectoringVpVectoringInterfaceState        INTEGER,
                hwVectoringVdslVectoringInterfaceState      INTEGER,
                hwVectoringVdslVectoringSyncState           INTEGER
            }     
            
    hwVectoringVpVectoringInterfaceState OBJECT-TYPE
        SYNTAX      INTEGER
        {
        down(1),
        up(2),
        invalidValue(-1)
        }
        MAX-ACCESS  read-only
        STATUS      current
        DESCRIPTION
            "The object indicates VCE vectoring interface state.
             Options:
             1. down(1)           - vectoring interface state is abnormal
             2. up(2)             - vectoring interface state is normal
             3. invalidValue(-1)  - invalid value
            "       
        ::= { hwVectoringBoardVectoringStateEntry 1 }
        
    hwVectoringVdslVectoringInterfaceState OBJECT-TYPE
        SYNTAX      INTEGER
        {
        down(1),
        up(2),
        invalidValue(-1)
        }
        MAX-ACCESS  read-only
        STATUS      current
        DESCRIPTION
            "The object indicates VDSL vectoring interface state.
             Options:
             1. down(1)           - vectoring interface state is abnormal
             2. up(2)             - vectoring interface state is normal
             3. invalidValue(-1)  - invalid value
            "       
        ::= { hwVectoringBoardVectoringStateEntry 2 }
        
    hwVectoringVdslVectoringSyncState OBJECT-TYPE
        SYNTAX      INTEGER
        {
        noSync(1),
        sync(2),
        invalidValue(-1)
        }
        MAX-ACCESS  read-only
        STATUS      current
        DESCRIPTION
            "The object indicates Sync state between VCE and VDSL vectoring interface.
             Options:
             1. noSync(1)         - communication between VCE and VDSL is abnormal
             2. sync(2)           - communication between VCE and VDSL is normal
             3. invalidValue(-1)  - invalid value
            "       
        ::= { hwVectoringBoardVectoringStateEntry 3 }
        
-- Vectoring ALARM TRAP
 
        hwVectoringTraps OBJECT IDENTIFIER ::= { hwVectoringMIB 8 }
        hwVectoringAlarmTraps OBJECT IDENTIFIER  ::= { hwVectoringTraps 1 }
        hwVectoringAlarmTrapsPrefix OBJECT IDENTIFIER  ::= { hwVectoringAlarmTraps 1 }
        hwVectoringCommonTraps OBJECT IDENTIFIER  ::= { hwVectoringTraps 2 }
        hwVectoringCommonTrapsPrefix OBJECT IDENTIFIER  ::= { hwVectoringCommonTraps 1 }
        
        hwVectoringFaultAlarmTrap NOTIFICATION-TYPE
            OBJECTS 
                {
                hwFrameIndex,
                hwSlotIndex
                }
            STATUS current
            DESCRIPTION
               "This notification indicates that the vectoring service on the board fails.
               "
            ::= { hwVectoringAlarmTrapsPrefix 1 }
            
        hwVectoringRecoveryAlarmTrap NOTIFICATION-TYPE
            OBJECTS 
                {
                hwFrameIndex,
                hwSlotIndex
                }
            STATUS current
            DESCRIPTION
               "This notification indicates that the vectoring service on the board recovers.
               "
            ::= { hwVectoringAlarmTrapsPrefix 2 }
        
        hwVectoringVictCoefAbnormalVariationAlarmTrap NOTIFICATION-TYPE
            OBJECTS 
                {
                hwFrameIndex,
                hwSlotIndex,
                hwPortIndex
                }
            STATUS current
            DESCRIPTION
               "This notification indicates that the port receives abnormal crosstalk from
                other ports."
            ::= { hwVectoringAlarmTrapsPrefix 3 }

        hwVectoringDistCoefAbnormalVariationAlarmTrap NOTIFICATION-TYPE
            OBJECTS 
                {
                hwFrameIndex,
                hwSlotIndex,
                hwPortIndex
                }
            STATUS current
            DESCRIPTION
               "This notification indicates that the port causes abnormal crosstalk to
                other ports."
            ::= { hwVectoringAlarmTrapsPrefix 4 }

        hwVectoringReceivedESAbnormalAlarmTrap NOTIFICATION-TYPE
            OBJECTS 
                {
                hwFrameIndex,
                hwSlotIndex,
                hwPortIndex
                }
            STATUS current
            DESCRIPTION
               "This notification indicates that the port receives abnormal error sample
                messages."
            ::= { hwVectoringAlarmTrapsPrefix 5 }

        hwvdsl2LegacyCpeActivatedAlarmTrap NOTIFICATION-TYPE
            OBJECTS 
                {
                hwFrameIndex,
                hwSlotIndex,
                hwPortIndex,
                hwVectoringLinkCPEType,
                hwVectoringLegacyCpeActivatePolicy
                }
            STATUS current
            DESCRIPTION
               "This notification indicates that the port is activated in none-vectoring mode."
            ::= { hwVectoringAlarmTrapsPrefix 6 }

        hwvdsl2FrequentlyRetrainTimesReachThresholdAlarmTrap NOTIFICATION-TYPE
            OBJECTS 
                {
                hwFrameIndex,
                hwSlotIndex,
                hwPortIndex,
                hwXdslPortFrequentRetrainControlTimes,
                hwVectoringPortFrequentRetrainTimes
                }
            STATUS current
            DESCRIPTION
               "This notification indicates that the port frequently retrain times in
                15 minutes reach the threshold."
            ::= { hwVectoringAlarmTrapsPrefix 7 }
            
        hwVectoringReceivedESRecoverAlarmTrap NOTIFICATION-TYPE
            OBJECTS 
                {
                hwFrameIndex,
                hwSlotIndex,
                hwPortIndex
                }
            STATUS current
            DESCRIPTION
               "This notification indicates that the port error sample feedback recovers."
            ::= { hwVectoringAlarmTrapsPrefix 8 }
            
            
         hwVectoringPSConfigAbnormalAlarmTrap NOTIFICATION-TYPE
            OBJECTS 
                {
                hwFrameIndex,
                hwSlotIndex,
                hwPortIndex
                }
            STATUS current
            DESCRIPTION
               "This notification indicates that the port receives abnormal pilot Sequence
                messages."
            ::= { hwVectoringAlarmTrapsPrefix 9 }
            
         hwVectoringPSConfigRecoverAlarmTrap NOTIFICATION-TYPE
            OBJECTS 
                {
                hwFrameIndex,
                hwSlotIndex,
                hwPortIndex
                }
            STATUS current
            DESCRIPTION
               "This notification indicates that the port pilot sequence recovers."
            ::= { hwVectoringAlarmTrapsPrefix 10 }            
                                                            
        hwVectoringGlobalConfigChangeTrap NOTIFICATION-TYPE
            OBJECTS 
                {
                hwConfigChangeIP,
                hwVectoringSwitch,
                hwVectoringLegacyCpeActivatePolicy,
                hwVectoringBandplanType,
                hwVectoringUs0Type,
                hwVectoringAnnexALimitMask,
                hwVectoringLegacyCpeReservedBand,
                hwVectoringLegacyCpeToneBlackoutBand
                }
            STATUS current
            DESCRIPTION
               "This notification indicates that the vectoring global configuration is changed.
               "
            ::= { hwVectoringCommonTrapsPrefix 1 }
            
         hwVectoringCrosstalkCoupingMatrixOperResultTrap NOTIFICATION-TYPE
            OBJECTS 
                {
                hwXdslRequestID,
                ifIndex,
                hwVectoringCrosstalkCouplingMatrixDirection,
                hwVectoringCrosstalkCoupingMatrixOperResult
                }
            STATUS current
            DESCRIPTION
               "This notification indicates that the vectoring crosstalk coupling matrix calculation result.
               "
            ::= { hwVectoringCommonTrapsPrefix 2 }
                     
-- hwVectoringFastJoinConfig       
     
     hwVectoringFastJoinConfig OBJECT IDENTIFIER ::= { hwVectoringMIB 9 }
        
        hwVectoringGainPhase OBJECT-TYPE
            SYNTAX INTEGER       
            {       
                atInit(1),
                trigger(2),
                duringShowtime(3)    
            }       
            MAX-ACCESS  read-write       
            STATUS      current       
            DESCRIPTION       
                "This object is used to set the mode for obtaining the vectoring 
                 gain during port activation. Default values:atInit.
                 Options:
                 1. atInit(1)         - The vectoring gain is obtained during port 
                                        activation except board startup
                 2. trigger(2)        - The vectoring gain is obtained in some condition
                 3. duringShowtime(3) - The port is activated and then the vectoring 
                                        gain is obtained during tracking
                "
            ::= { hwVectoringFastJoinConfig 1 }            
            
        hwVectoringTriggerAfterBoardReset OBJECT-TYPE
            SYNTAX INTEGER       
            {       
                enable(1),
                disable(2),
                invalidValue(-1)  
            }       
            MAX-ACCESS  read-write       
            STATUS      current       
            DESCRIPTION       
                "The vectoring gain is not obtained during port activation 
                 in board reset, but obtained during tracking in SRA. 
                 Default values:enable.        
                 Options:
                 1. enable(1)         - Enables the vectoring gain achieved in showtime after board reset
                 2. disable(2)        - Disables the vectoring gain achieved in showtime after board reset
                 3. invalidValue(-1)  - invalid value         
                "
            ::= { hwVectoringFastJoinConfig 2 }
            
        hwVectoringTriggerDuringBulkNum OBJECT-TYPE
           SYNTAX Unsigned32 
            MAX-ACCESS  read-write
            STATUS      current
            DESCRIPTION
                "The vectoring gain achieved in showtime when the number of ports
                 join in at a time exceeds the configured bulk init number. It
                 ranges from 2 to 256. The invalid value  is 4294967295.
                 Default values:64.                
                "
            ::= { hwVectoringFastJoinConfig 3 }           
            
        hwVectoringJoinMaxWaitTime OBJECT-TYPE
            SYNTAX Unsigned32 (0..60) 
            UNITS       "seconds"    
            MAX-ACCESS  read-write       
            STATUS      current       
            DESCRIPTION       
                "This object is used to set the total time for a joined port 
                 to wait for other ports in the batch to join. 
                 Default values:15.                
                "
            ::= { hwVectoringFastJoinConfig 4 }
            
        hwVectoringJoinGapWaitTime OBJECT-TYPE
            SYNTAX Unsigned32 (0..60) 
            UNITS       "seconds"       
            MAX-ACCESS  read-write
            STATUS      current
            DESCRIPTION
                "This object is used to set the interval for a joined port to wait 
                 for a single port in the batch to join.
                 Default values:5.                 
                "
            ::= { hwVectoringFastJoinConfig 5 }
            
        hwVectoringTrackingPeriod OBJECT-TYPE
            SYNTAX Unsigned32 (0..240) 
            UNITS       "minute"   
            MAX-ACCESS  read-write
            STATUS      current
            DESCRIPTION
                "Vectoring tracking period. Default values:30.                
                "
            ::= { hwVectoringFastJoinConfig 6 }       

        hwVectoringHistoryCoefficient OBJECT-TYPE
            SYNTAX INTEGER
            {
                disable(1),
                upstream(2),
                downstream(3),
                both(4)
            }       
            MAX-ACCESS  read-write
            STATUS      current
            DESCRIPTION
                "This object is used to set whether to use a historical coefficient.
                 Default values:both.
                 Options:
                 1. disable(1)      - Indicates that a historical coefficient is not used
                 2. upstream(2)     - Indicates that a historical coefficient is used in upstream direction
                 3. downstream(3)   - Indicates that a historical coefficient is used in downstream direction
                 4. both(4)         - Indicates that a historical coefficient is used
                 "
            ::= { hwVectoringFastJoinConfig 7 }

-- hwVectoringTrapsVbOids            
        hwVectoringTrapsVbOids OBJECT IDENTIFIER ::= { hwVectoringMIB 10 }
    
        hwVectoringPortFrequentRetrainTimes OBJECT-TYPE
            SYNTAX Unsigned32
            MAX-ACCESS accessible-for-notify
            STATUS current
            DESCRIPTION
                "The times that Xdsl port frequent retrain in 15 minutes.  
 	            "
            ::= { hwVectoringTrapsVbOids 1}         
    END
--
-- HUAWEI-VECTOR-MIB.mib
--
