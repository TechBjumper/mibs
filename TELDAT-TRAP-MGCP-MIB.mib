-- file automatically created


TELDAT-TRAP-MGCP-MIB DEFINITIONS ::= BEGIN


IMPORTS
	MODULE-IDENTITY,OBJECT-TYPE,OBJECT-IDENTITY,NOTIFICATION-TYPE,Integer32,IpAddress
		FROM SNMPv2-SMI
	DisplayString
		FROM SNMPv2-TC
	telEventTraps
		FROM TELDAT-MIB;


mgcpTrapsMIB MODULE-IDENTITY
    LAST-UPDATED "201401200930Z"
    ORGANIZATION "Teldat, S.A."
    CONTACT-INFO 
        "Teldat, S.A.
        Customer Service

        Postal: Parque Tecnologico de Madrid
                Tres Cantos 28760
                Madrid, SPAIN

        Tel.: +34 918 076 565

        http://www.teldat.com"
    DESCRIPTION
        "This Module Information Base file is defined for managing received
        SNMP notifications generated by the MGCP event subsystem."
    REVISION "201401200930Z"
    DESCRIPTION "Initial implementation"
        ::= { telEventTraps 220 }


mgcpEventsGroup	OBJECT IDENTIFIER	::= { mgcpTrapsMIB 1 }

mgcpNotifications	OBJECT IDENTIFIER	::= { mgcpTrapsMIB 2 }
mgcpNotificationsPrefix	OBJECT IDENTIFIER	::= { mgcpNotifications 0 }

mgcpEventObjects1 OBJECT-IDENTITY
    STATUS current
    DESCRIPTION
        "Event MGCP.1
        MGCP Application error."
    ::= { mgcpEventsGroup 1 }

mgcp1-error OBJECT-TYPE
    SYNTAX DisplayString
    MAX-ACCESS accessible-for-notify
    STATUS current
    DESCRIPTION
        "Parameter 'error' in event MGCP.1"
    ::= { mgcpEventObjects1 1 }

mgcp1-endpoint OBJECT-TYPE
    SYNTAX DisplayString
    MAX-ACCESS accessible-for-notify
    STATUS current
    DESCRIPTION
        "Parameter 'endpoint' in event MGCP.1"
    ::= { mgcpEventObjects1 2 }

mgcpEventObjects2 OBJECT-IDENTITY
    STATUS current
    DESCRIPTION
        "Event MGCP.2
        MGCP Application information."
    ::= { mgcpEventsGroup 2 }

mgcp2-info OBJECT-TYPE
    SYNTAX DisplayString
    MAX-ACCESS accessible-for-notify
    STATUS current
    DESCRIPTION
        "Parameter 'info' in event MGCP.2"
    ::= { mgcpEventObjects2 1 }

mgcp2-endpoint OBJECT-TYPE
    SYNTAX DisplayString
    MAX-ACCESS accessible-for-notify
    STATUS current
    DESCRIPTION
        "Parameter 'endpoint' in event MGCP.2"
    ::= { mgcpEventObjects2 2 }

mgcpEventObjects3 OBJECT-IDENTITY
    STATUS current
    DESCRIPTION
        "Event MGCP.3
        MGCP Application warning."
    ::= { mgcpEventsGroup 3 }

mgcp3-warning OBJECT-TYPE
    SYNTAX DisplayString
    MAX-ACCESS accessible-for-notify
    STATUS current
    DESCRIPTION
        "Parameter 'warning' in event MGCP.3"
    ::= { mgcpEventObjects3 1 }

mgcp3-endpoint OBJECT-TYPE
    SYNTAX DisplayString
    MAX-ACCESS accessible-for-notify
    STATUS current
    DESCRIPTION
        "Parameter 'endpoint' in event MGCP.3"
    ::= { mgcpEventObjects3 2 }

mgcpEventObjects4 OBJECT-IDENTITY
    STATUS current
    DESCRIPTION
        "Event MGCP.4
        MGCP Application trace."
    ::= { mgcpEventsGroup 4 }

mgcp4-trace OBJECT-TYPE
    SYNTAX DisplayString
    MAX-ACCESS accessible-for-notify
    STATUS current
    DESCRIPTION
        "Parameter 'trace' in event MGCP.4"
    ::= { mgcpEventObjects4 1 }

mgcp4-endpoint OBJECT-TYPE
    SYNTAX DisplayString
    MAX-ACCESS accessible-for-notify
    STATUS current
    DESCRIPTION
        "Parameter 'endpoint' in event MGCP.4"
    ::= { mgcpEventObjects4 2 }

mgcpEventObjects5 OBJECT-IDENTITY
    STATUS current
    DESCRIPTION
        "Event MGCP.5
        Endpoint restart state."
    ::= { mgcpEventsGroup 5 }

mgcp5-state OBJECT-TYPE
    SYNTAX DisplayString
    MAX-ACCESS accessible-for-notify
    STATUS current
    DESCRIPTION
        "Parameter 'state' in event MGCP.5"
    ::= { mgcpEventObjects5 1 }

mgcp5-endpoint OBJECT-TYPE
    SYNTAX DisplayString
    MAX-ACCESS accessible-for-notify
    STATUS current
    DESCRIPTION
        "Parameter 'endpoint' in event MGCP.5"
    ::= { mgcpEventObjects5 2 }

mgcpEventObjects6 OBJECT-IDENTITY
    STATUS current
    DESCRIPTION
        "Event MGCP.6
        Restart In Progress command sent."
    ::= { mgcpEventsGroup 6 }

mgcp6-function OBJECT-TYPE
    SYNTAX DisplayString
    MAX-ACCESS accessible-for-notify
    STATUS current
    DESCRIPTION
        "Parameter 'function' in event MGCP.6"
    ::= { mgcpEventObjects6 1 }

mgcp6-method OBJECT-TYPE
    SYNTAX DisplayString
    MAX-ACCESS accessible-for-notify
    STATUS current
    DESCRIPTION
        "Parameter 'method' in event MGCP.6"
    ::= { mgcpEventObjects6 2 }

mgcp6-endpoint OBJECT-TYPE
    SYNTAX DisplayString
    MAX-ACCESS accessible-for-notify
    STATUS current
    DESCRIPTION
        "Parameter 'endpoint' in event MGCP.6"
    ::= { mgcpEventObjects6 3 }

mgcpEventObjects7 OBJECT-IDENTITY
    STATUS current
    DESCRIPTION
        "Event MGCP.7
        Notify command/response sent/rcvd."
    ::= { mgcpEventsGroup 7 }

mgcp7-event OBJECT-TYPE
    SYNTAX DisplayString
    MAX-ACCESS accessible-for-notify
    STATUS current
    DESCRIPTION
        "Parameter 'event' in event MGCP.7"
    ::= { mgcpEventObjects7 1 }

mgcp7-direction OBJECT-TYPE
    SYNTAX DisplayString
    MAX-ACCESS accessible-for-notify
    STATUS current
    DESCRIPTION
        "Parameter 'direction' in event MGCP.7"
    ::= { mgcpEventObjects7 2 }

mgcp7-endpoint OBJECT-TYPE
    SYNTAX DisplayString
    MAX-ACCESS accessible-for-notify
    STATUS current
    DESCRIPTION
        "Parameter 'endpoint' in event MGCP.7"
    ::= { mgcpEventObjects7 3 }

mgcpEventObjects8 OBJECT-IDENTITY
    STATUS current
    DESCRIPTION
        "Event MGCP.8
        Notification request command rcvd with required event and signal."
    ::= { mgcpEventsGroup 8 }

mgcp8-reqid OBJECT-TYPE
    SYNTAX DisplayString
    MAX-ACCESS accessible-for-notify
    STATUS current
    DESCRIPTION
        "Parameter 'reqid' in event MGCP.8"
    ::= { mgcpEventObjects8 1 }

mgcp8-embedded OBJECT-TYPE
    SYNTAX DisplayString
    MAX-ACCESS accessible-for-notify
    STATUS current
    DESCRIPTION
        "Parameter 'embedded' in event MGCP.8"
    ::= { mgcpEventObjects8 2 }

mgcp8-event OBJECT-TYPE
    SYNTAX DisplayString
    MAX-ACCESS accessible-for-notify
    STATUS current
    DESCRIPTION
        "Parameter 'event' in event MGCP.8"
    ::= { mgcpEventObjects8 3 }

mgcp8-signal OBJECT-TYPE
    SYNTAX DisplayString
    MAX-ACCESS accessible-for-notify
    STATUS current
    DESCRIPTION
        "Parameter 'signal' in event MGCP.8"
    ::= { mgcpEventObjects8 4 }

mgcp8-endpoint OBJECT-TYPE
    SYNTAX DisplayString
    MAX-ACCESS accessible-for-notify
    STATUS current
    DESCRIPTION
        "Parameter 'endpoint' in event MGCP.8"
    ::= { mgcpEventObjects8 5 }

mgcpEventObjects9 OBJECT-IDENTITY
    STATUS current
    DESCRIPTION
        "Event MGCP.9
        Create Connection command/response rcvd/sent."
    ::= { mgcpEventsGroup 9 }

mgcp9-command OBJECT-TYPE
    SYNTAX DisplayString
    MAX-ACCESS accessible-for-notify
    STATUS current
    DESCRIPTION
        "Parameter 'command' in event MGCP.9"
    ::= { mgcpEventObjects9 1 }

mgcp9-direction OBJECT-TYPE
    SYNTAX DisplayString
    MAX-ACCESS accessible-for-notify
    STATUS current
    DESCRIPTION
        "Parameter 'direction' in event MGCP.9"
    ::= { mgcpEventObjects9 2 }

mgcp9-endpoint OBJECT-TYPE
    SYNTAX DisplayString
    MAX-ACCESS accessible-for-notify
    STATUS current
    DESCRIPTION
        "Parameter 'endpoint' in event MGCP.9"
    ::= { mgcpEventObjects9 3 }

mgcpEventObjects10 OBJECT-IDENTITY
    STATUS current
    DESCRIPTION
        "Event MGCP.10
        Modify Connection command/response rcvd/sent."
    ::= { mgcpEventsGroup 10 }

mgcp10-command OBJECT-TYPE
    SYNTAX DisplayString
    MAX-ACCESS accessible-for-notify
    STATUS current
    DESCRIPTION
        "Parameter 'command' in event MGCP.10"
    ::= { mgcpEventObjects10 1 }

mgcp10-direction OBJECT-TYPE
    SYNTAX DisplayString
    MAX-ACCESS accessible-for-notify
    STATUS current
    DESCRIPTION
        "Parameter 'direction' in event MGCP.10"
    ::= { mgcpEventObjects10 2 }

mgcp10-endpoint OBJECT-TYPE
    SYNTAX DisplayString
    MAX-ACCESS accessible-for-notify
    STATUS current
    DESCRIPTION
        "Parameter 'endpoint' in event MGCP.10"
    ::= { mgcpEventObjects10 3 }

mgcpEventObjects11 OBJECT-IDENTITY
    STATUS current
    DESCRIPTION
        "Event MGCP.11
        Delete Connection command/response rcvd/sent."
    ::= { mgcpEventsGroup 11 }

mgcp11-command OBJECT-TYPE
    SYNTAX DisplayString
    MAX-ACCESS accessible-for-notify
    STATUS current
    DESCRIPTION
        "Parameter 'command' in event MGCP.11"
    ::= { mgcpEventObjects11 1 }

mgcp11-direction OBJECT-TYPE
    SYNTAX DisplayString
    MAX-ACCESS accessible-for-notify
    STATUS current
    DESCRIPTION
        "Parameter 'direction' in event MGCP.11"
    ::= { mgcpEventObjects11 2 }

mgcp11-endpoint OBJECT-TYPE
    SYNTAX DisplayString
    MAX-ACCESS accessible-for-notify
    STATUS current
    DESCRIPTION
        "Parameter 'endpoint' in event MGCP.11"
    ::= { mgcpEventObjects11 3 }

mgcpEventObjects12 OBJECT-IDENTITY
    STATUS current
    DESCRIPTION
        "Event MGCP.12
        Audit Endpoint command rcvd for endpoint."
    ::= { mgcpEventsGroup 12 }

mgcp12-endpoint OBJECT-TYPE
    SYNTAX DisplayString
    MAX-ACCESS accessible-for-notify
    STATUS current
    DESCRIPTION
        "Parameter 'endpoint' in event MGCP.12"
    ::= { mgcpEventObjects12 1 }

mgcpEventObjects13 OBJECT-IDENTITY
    STATUS current
    DESCRIPTION
        "Event MGCP.13
        Audit Connection command rcvd with connID."
    ::= { mgcpEventsGroup 13 }

mgcp13-connid OBJECT-TYPE
    SYNTAX DisplayString
    MAX-ACCESS accessible-for-notify
    STATUS current
    DESCRIPTION
        "Parameter 'connid' in event MGCP.13"
    ::= { mgcpEventObjects13 1 }

mgcp13-endpoint OBJECT-TYPE
    SYNTAX DisplayString
    MAX-ACCESS accessible-for-notify
    STATUS current
    DESCRIPTION
        "Parameter 'endpoint' in event MGCP.13"
    ::= { mgcpEventObjects13 2 }

mgcpEventObjects15 OBJECT-IDENTITY
    STATUS current
    DESCRIPTION
        "Event MGCP.15
        DTMF signal detected or to be generated at endpoint."
    ::= { mgcpEventsGroup 15 }

mgcp15-dtmf OBJECT-TYPE
    SYNTAX DisplayString
    MAX-ACCESS accessible-for-notify
    STATUS current
    DESCRIPTION
        "Parameter 'dtmf' in event MGCP.15"
    ::= { mgcpEventObjects15 1 }

mgcp15-action OBJECT-TYPE
    SYNTAX DisplayString
    MAX-ACCESS accessible-for-notify
    STATUS current
    DESCRIPTION
        "Parameter 'action' in event MGCP.15"
    ::= { mgcpEventObjects15 2 }

mgcp15-endpoint OBJECT-TYPE
    SYNTAX DisplayString
    MAX-ACCESS accessible-for-notify
    STATUS current
    DESCRIPTION
        "Parameter 'endpoint' in event MGCP.15"
    ::= { mgcpEventObjects15 3 }

mgcpEventObjects16 OBJECT-IDENTITY
    STATUS current
    DESCRIPTION
        "Event MGCP.16
        Generate or stop tone at endpoint."
    ::= { mgcpEventsGroup 16 }

mgcp16-tone OBJECT-TYPE
    SYNTAX DisplayString
    MAX-ACCESS accessible-for-notify
    STATUS current
    DESCRIPTION
        "Parameter 'tone' in event MGCP.16"
    ::= { mgcpEventObjects16 1 }

mgcp16-action OBJECT-TYPE
    SYNTAX DisplayString
    MAX-ACCESS accessible-for-notify
    STATUS current
    DESCRIPTION
        "Parameter 'action' in event MGCP.16"
    ::= { mgcpEventObjects16 2 }

mgcp16-endpoint OBJECT-TYPE
    SYNTAX DisplayString
    MAX-ACCESS accessible-for-notify
    STATUS current
    DESCRIPTION
        "Parameter 'endpoint' in event MGCP.16"
    ::= { mgcpEventObjects16 3 }

mgcpEventObjects17 OBJECT-IDENTITY
    STATUS current
    DESCRIPTION
        "Event MGCP.17
        Start or stop signal at endpoint."
    ::= { mgcpEventsGroup 17 }

mgcp17-signal OBJECT-TYPE
    SYNTAX DisplayString
    MAX-ACCESS accessible-for-notify
    STATUS current
    DESCRIPTION
        "Parameter 'signal' in event MGCP.17"
    ::= { mgcpEventObjects17 1 }

mgcp17-action OBJECT-TYPE
    SYNTAX DisplayString
    MAX-ACCESS accessible-for-notify
    STATUS current
    DESCRIPTION
        "Parameter 'action' in event MGCP.17"
    ::= { mgcpEventObjects17 2 }

mgcp17-endpoint OBJECT-TYPE
    SYNTAX DisplayString
    MAX-ACCESS accessible-for-notify
    STATUS current
    DESCRIPTION
        "Parameter 'endpoint' in event MGCP.17"
    ::= { mgcpEventObjects17 3 }

mgcpEventObjects19 OBJECT-IDENTITY
    STATUS current
    DESCRIPTION
        "Event MGCP.19
        MGCP Application error."
    ::= { mgcpEventsGroup 19 }

mgcp19-error OBJECT-TYPE
    SYNTAX DisplayString
    MAX-ACCESS accessible-for-notify
    STATUS current
    DESCRIPTION
        "Parameter 'error' in event MGCP.19"
    ::= { mgcpEventObjects19 1 }

mgcp19-ifc OBJECT-TYPE
    SYNTAX DisplayString
    MAX-ACCESS accessible-for-notify
    STATUS current
    DESCRIPTION
        "Parameter 'ifc' in event MGCP.19"
    ::= { mgcpEventObjects19 2 }

mgcpEventObjects20 OBJECT-IDENTITY
    STATUS current
    DESCRIPTION
        "Event MGCP.20
        MGCP Application information."
    ::= { mgcpEventsGroup 20 }

mgcp20-info OBJECT-TYPE
    SYNTAX DisplayString
    MAX-ACCESS accessible-for-notify
    STATUS current
    DESCRIPTION
        "Parameter 'info' in event MGCP.20"
    ::= { mgcpEventObjects20 1 }

mgcp20-ifc OBJECT-TYPE
    SYNTAX DisplayString
    MAX-ACCESS accessible-for-notify
    STATUS current
    DESCRIPTION
        "Parameter 'ifc' in event MGCP.20"
    ::= { mgcpEventObjects20 2 }

mgcpEventObjects21 OBJECT-IDENTITY
    STATUS current
    DESCRIPTION
        "Event MGCP.21
        MGCP Application warning."
    ::= { mgcpEventsGroup 21 }

mgcp21-warning OBJECT-TYPE
    SYNTAX DisplayString
    MAX-ACCESS accessible-for-notify
    STATUS current
    DESCRIPTION
        "Parameter 'warning' in event MGCP.21"
    ::= { mgcpEventObjects21 1 }

mgcp21-ifc OBJECT-TYPE
    SYNTAX DisplayString
    MAX-ACCESS accessible-for-notify
    STATUS current
    DESCRIPTION
        "Parameter 'ifc' in event MGCP.21"
    ::= { mgcpEventObjects21 2 }

mgcpEventObjects22 OBJECT-IDENTITY
    STATUS current
    DESCRIPTION
        "Event MGCP.22
        MGCP Application trace."
    ::= { mgcpEventsGroup 22 }

mgcp22-trace OBJECT-TYPE
    SYNTAX DisplayString
    MAX-ACCESS accessible-for-notify
    STATUS current
    DESCRIPTION
        "Parameter 'trace' in event MGCP.22"
    ::= { mgcpEventObjects22 1 }

mgcp22-ifc OBJECT-TYPE
    SYNTAX DisplayString
    MAX-ACCESS accessible-for-notify
    STATUS current
    DESCRIPTION
        "Parameter 'ifc' in event MGCP.22"
    ::= { mgcpEventObjects22 2 }

mgcpEventObjects23 OBJECT-IDENTITY
    STATUS current
    DESCRIPTION
        "Event MGCP.23
        Backhaul message with type, direction (Out or In), size and hrough the 
        ifc shown. If it has data it is shown as an HEX string."
    ::= { mgcpEventsGroup 23 }

mgcp23-type OBJECT-TYPE
    SYNTAX DisplayString
    MAX-ACCESS accessible-for-notify
    STATUS current
    DESCRIPTION
        "Parameter 'type' in event MGCP.23"
    ::= { mgcpEventObjects23 1 }

mgcp23-direction OBJECT-TYPE
    SYNTAX DisplayString
    MAX-ACCESS accessible-for-notify
    STATUS current
    DESCRIPTION
        "Parameter 'direction' in event MGCP.23"
    ::= { mgcpEventObjects23 2 }

mgcp23-size OBJECT-TYPE
    SYNTAX Integer32
    MAX-ACCESS accessible-for-notify
    STATUS current
    DESCRIPTION
        "Parameter 'size' in event MGCP.23"
    ::= { mgcpEventObjects23 3 }

mgcp23-ifc OBJECT-TYPE
    SYNTAX DisplayString
    MAX-ACCESS accessible-for-notify
    STATUS current
    DESCRIPTION
        "Parameter 'ifc' in event MGCP.23"
    ::= { mgcpEventObjects23 4 }

mgcp23-contents OBJECT-TYPE
    SYNTAX DisplayString
    MAX-ACCESS accessible-for-notify
    STATUS current
    DESCRIPTION
        "Parameter 'contents' in event MGCP.23"
    ::= { mgcpEventObjects23 5 }


mgcpNotification1 NOTIFICATION-TYPE
    OBJECTS { 
              mgcp1-error, 
              mgcp1-endpoint 
            }
    STATUS current
    DESCRIPTION
        "Notification of Event MGCP.1

        Message: 'App error: $1. Ep $2'

        Parameters list:
              $1: mgcp1-error
              $2: mgcp1-endpoint

        MGCP Application error."
    ::= { mgcpNotificationsPrefix 1 }

mgcpNotification2 NOTIFICATION-TYPE
    OBJECTS { 
              mgcp2-info, 
              mgcp2-endpoint 
            }
    STATUS current
    DESCRIPTION
        "Notification of Event MGCP.2

        Message: 'App info: $1. Ep $2'

        Parameters list:
              $1: mgcp2-info
              $2: mgcp2-endpoint

        MGCP Application information."
    ::= { mgcpNotificationsPrefix 2 }

mgcpNotification3 NOTIFICATION-TYPE
    OBJECTS { 
              mgcp3-warning, 
              mgcp3-endpoint 
            }
    STATUS current
    DESCRIPTION
        "Notification of Event MGCP.3

        Message: 'App warning: $1. Ep $2'

        Parameters list:
              $1: mgcp3-warning
              $2: mgcp3-endpoint

        MGCP Application warning."
    ::= { mgcpNotificationsPrefix 3 }

mgcpNotification4 NOTIFICATION-TYPE
    OBJECTS { 
              mgcp4-trace, 
              mgcp4-endpoint 
            }
    STATUS current
    DESCRIPTION
        "Notification of Event MGCP.4

        Message: 'App trace: $1. Ep $2'

        Parameters list:
              $1: mgcp4-trace
              $2: mgcp4-endpoint

        MGCP Application trace."
    ::= { mgcpNotificationsPrefix 4 }

mgcpNotification5 NOTIFICATION-TYPE
    OBJECTS { 
              mgcp5-state, 
              mgcp5-endpoint 
            }
    STATUS current
    DESCRIPTION
        "Notification of Event MGCP.5

        Message: 'Restart state: $1. Ep $2'

        Parameters list:
              $1: mgcp5-state
              $2: mgcp5-endpoint

        Endpoint restart state."
    ::= { mgcpNotificationsPrefix 5 }

mgcpNotification6 NOTIFICATION-TYPE
    OBJECTS { 
              mgcp6-function, 
              mgcp6-method,
              mgcp6-endpoint 
            }
    STATUS current
    DESCRIPTION
        "Notification of Event MGCP.6

        Message: 'Restart In Progress sent $1 with method $2. Ep $3'

        Parameters list:
              $1: mgcp6-function
              $2: mgcp6-method
              $3: mgcp6-endpoint

        Restart In Progress command sent."
    ::= { mgcpNotificationsPrefix 6 }

mgcpNotification7 NOTIFICATION-TYPE
    OBJECTS { 
              mgcp7-event, 
              mgcp7-direction,
              mgcp7-endpoint 
            }
    STATUS current
    DESCRIPTION
        "Notification of Event MGCP.7

        Message: 'Notify $1 $2. Ep $3'

        Parameters list:
              $1: mgcp7-event
              $2: mgcp7-direction
              $3: mgcp7-endpoint

        Notify command/response sent/rcvd."
    ::= { mgcpNotificationsPrefix 7 }

mgcpNotification8 NOTIFICATION-TYPE
    OBJECTS { 
              mgcp8-reqid, 
              mgcp8-embedded,
              mgcp8-event,
              mgcp8-signal,
              mgcp8-endpoint 
            }
    STATUS current
    DESCRIPTION
        "Notification of Event MGCP.8

        Message: 'Notification Request with id $1 $2 received with required event $3 and signal $4. Ep $5'

        Parameters list:
              $1: mgcp8-reqid
              $2: mgcp8-embedded
              $3: mgcp8-event
              $4: mgcp8-signal
              $5: mgcp8-endpoint

        Notification request command rcvd with required event and signal."
    ::= { mgcpNotificationsPrefix 8 }

mgcpNotification9 NOTIFICATION-TYPE
    OBJECTS { 
              mgcp9-command, 
              mgcp9-direction,
              mgcp9-endpoint 
            }
    STATUS current
    DESCRIPTION
        "Notification of Event MGCP.9

        Message: 'Create Conn $1 $2. Ep $3'

        Parameters list:
              $1: mgcp9-command
              $2: mgcp9-direction
              $3: mgcp9-endpoint

        Create Connection command/response rcvd/sent."
    ::= { mgcpNotificationsPrefix 9 }

mgcpNotification10 NOTIFICATION-TYPE
    OBJECTS { 
              mgcp10-command, 
              mgcp10-direction,
              mgcp10-endpoint 
            }
    STATUS current
    DESCRIPTION
        "Notification of Event MGCP.10

        Message: 'Modify Conn $1 $2. Ep $3'

        Parameters list:
              $1: mgcp10-command
              $2: mgcp10-direction
              $3: mgcp10-endpoint

        Modify Connection command/response rcvd/sent."
    ::= { mgcpNotificationsPrefix 10 }

mgcpNotification11 NOTIFICATION-TYPE
    OBJECTS { 
              mgcp11-command, 
              mgcp11-direction,
              mgcp11-endpoint 
            }
    STATUS current
    DESCRIPTION
        "Notification of Event MGCP.11

        Message: 'Delete Conn $1 $2. Ep $3'

        Parameters list:
              $1: mgcp11-command
              $2: mgcp11-direction
              $3: mgcp11-endpoint

        Delete Connection command/response rcvd/sent."
    ::= { mgcpNotificationsPrefix 11 }

mgcpNotification12 NOTIFICATION-TYPE
    OBJECTS { 
              mgcp12-endpoint 
            }
    STATUS current
    DESCRIPTION
        "Notification of Event MGCP.12

        Message: 'Audit Endpoint received. Ep $1'

        Parameters list:
              $1: mgcp12-endpoint

        Audit Endpoint command rcvd for endpoint."
    ::= { mgcpNotificationsPrefix 12 }

mgcpNotification13 NOTIFICATION-TYPE
    OBJECTS { 
              mgcp13-connid, 
              mgcp13-endpoint 
            }
    STATUS current
    DESCRIPTION
        "Notification of Event MGCP.13

        Message: 'Audit Connection received for connection with id $1. Ep $2'

        Parameters list:
              $1: mgcp13-connid
              $2: mgcp13-endpoint

        Audit Connection command rcvd with connID."
    ::= { mgcpNotificationsPrefix 13 }

mgcpNotification14 NOTIFICATION-TYPE
    STATUS current
    DESCRIPTION
        "Notification of Event MGCP.14

        Message: '---'

        Reserved for possible future use."
    ::= { mgcpNotificationsPrefix 14 }

mgcpNotification15 NOTIFICATION-TYPE
    OBJECTS { 
              mgcp15-dtmf, 
              mgcp15-action,
              mgcp15-endpoint 
            }
    STATUS current
    DESCRIPTION
        "Notification of Event MGCP.15

        Message: 'DTMF $1 $2. Ep $3'

        Parameters list:
              $1: mgcp15-dtmf
              $2: mgcp15-action
              $3: mgcp15-endpoint

        DTMF signal detected or to be generated at endpoint."
    ::= { mgcpNotificationsPrefix 15 }

mgcpNotification16 NOTIFICATION-TYPE
    OBJECTS { 
              mgcp16-tone, 
              mgcp16-action,
              mgcp16-endpoint 
            }
    STATUS current
    DESCRIPTION
        "Notification of Event MGCP.16

        Message: 'Generic Media tone $1 $2. Ep $3'

        Parameters list:
              $1: mgcp16-tone
              $2: mgcp16-action
              $3: mgcp16-endpoint

        Generate or stop tone at endpoint."
    ::= { mgcpNotificationsPrefix 16 }

mgcpNotification17 NOTIFICATION-TYPE
    OBJECTS { 
              mgcp17-signal, 
              mgcp17-action,
              mgcp17-endpoint 
            }
    STATUS current
    DESCRIPTION
        "Notification of Event MGCP.17

        Message: 'Line signal $1 $2. Ep $3'

        Parameters list:
              $1: mgcp17-signal
              $2: mgcp17-action
              $3: mgcp17-endpoint

        Start or stop signal at endpoint."
    ::= { mgcpNotificationsPrefix 17 }

mgcpNotification18 NOTIFICATION-TYPE
    STATUS current
    DESCRIPTION
        "Notification of Event MGCP.18

        Message: '---'

        Reserved for possible future use."
    ::= { mgcpNotificationsPrefix 18 }

mgcpNotification19 NOTIFICATION-TYPE
    OBJECTS { 
              mgcp19-error, 
              mgcp19-ifc 
            }
    STATUS current
    DESCRIPTION
        "Notification of Event MGCP.19

        Message: 'Backhaul error: $1. Ifc: $2'

        Parameters list:
              $1: mgcp19-error
              $2: mgcp19-ifc

        MGCP Application error."
    ::= { mgcpNotificationsPrefix 19 }

mgcpNotification20 NOTIFICATION-TYPE
    OBJECTS { 
              mgcp20-info, 
              mgcp20-ifc 
            }
    STATUS current
    DESCRIPTION
        "Notification of Event MGCP.20

        Message: 'Backhaul info: $1. Ifc: $2'

        Parameters list:
              $1: mgcp20-info
              $2: mgcp20-ifc

        MGCP Application information."
    ::= { mgcpNotificationsPrefix 20 }

mgcpNotification21 NOTIFICATION-TYPE
    OBJECTS { 
              mgcp21-warning, 
              mgcp21-ifc 
            }
    STATUS current
    DESCRIPTION
        "Notification of Event MGCP.21

        Message: 'Backhaul warning: $1. Ifc: $2'

        Parameters list:
              $1: mgcp21-warning
              $2: mgcp21-ifc

        MGCP Application warning."
    ::= { mgcpNotificationsPrefix 21 }

mgcpNotification22 NOTIFICATION-TYPE
    OBJECTS { 
              mgcp22-trace, 
              mgcp22-ifc 
            }
    STATUS current
    DESCRIPTION
        "Notification of Event MGCP.22

        Message: 'Backhaul trace: $1. Ifc: $2'

        Parameters list:
              $1: mgcp22-trace
              $2: mgcp22-ifc

        MGCP Application trace."
    ::= { mgcpNotificationsPrefix 22 }

mgcpNotification23 NOTIFICATION-TYPE
    OBJECTS { 
              mgcp23-type, 
              mgcp23-direction,
              mgcp23-size,
              mgcp23-ifc,
              mgcp23-contents 
            }
    STATUS current
    DESCRIPTION
        "Notification of Event MGCP.23

        Message: 'Backhaul msg $1, dir: $2, size $3, ifc: $4: $5'

        Parameters list:
              $1: mgcp23-type
              $2: mgcp23-direction
              $3: mgcp23-size
              $4: mgcp23-ifc
              $5: mgcp23-contents

        Backhaul message with type, direction (Out or In), size and hrough the 
        ifc shown. If it has data it is shown as an HEX string."
    ::= { mgcpNotificationsPrefix 23 }


END
