ACC-TUNNEL DEFINITIONS ::= BEGIN

    IMPORTS
		OBJECT-TYPE, IpAddress, TimeTicks, Gauge, Counter FROM RFC1155-SMI
		TRAP-TYPE FROM RFC-1215
 accTrapLogSeqNum FROM ACC-SYSTEM
	accBRG, DisplayString, IfIndex, SmdsAddress
             FROM ACC-MIB
	RowStatus FROM SNMPv2-TC;

-- Tunnel Group
    -- ACC TUNNEL branch
    accTunnel		OBJECT IDENTIFIER ::= { accBRG 72 }
    accTunnelScalars	OBJECT IDENTIFIER ::= { accTunnel 1 }
    --
    --  ACC general TUNNEL objects
    --
    --
    accTunnelPortCount  OBJECT-TYPE
        SYNTAX  INTEGER (0..65535)
        ACCESS  read-write
        STATUS  mandatory
        DESCRIPTION
             "Number of Tunnel ports available on the platform"
        ::= { accTunnelScalars 1 }
    --
    --  The Tunnel Port Table
    --
    accTunnelPortTable OBJECT-TYPE
	SYNTAX  SEQUENCE OF AccTunnelPortEntry
	ACCESS  	not-accessible
        STATUS          mandatory
        DESCRIPTION
             "Displays all active Tunnel Ports"
    ::= { accTunnel 2 }
    accTunnelPortEntry OBJECT-TYPE
        SYNTAX  AccTunnelPortEntry
        ACCESS  not-accessible
        STATUS  mandatory
        DESCRIPTION
             ""
        INDEX   { accTunnelPortTunnelIfIndex }
        ::= { accTunnelPortTable 1 }
    AccTunnelPortEntry ::= SEQUENCE {
	accTunnelPortTunnelIfIndex	INTEGER,
	accTunnelPortTunnelManager	INTEGER,
	accTunnelPortAdminState		INTEGER,
	accTunnelPortOperStatus		INTEGER,
	accTunnelPortAccessPartition	DisplayString,
	accTunnelPortCreate		INTEGER,
	accTunnelPortStatus		RowStatus
	}
	accTunnelPortTunnelIfIndex OBJECT-TYPE
	SYNTAX  INTEGER (0..4294967295)
	ACCESS  read-write
	STATUS  mandatory
	DESCRIPTION
	     "Interface index for a tunnel port"
	::= { accTunnelPortEntry 1 }
	accTunnelPortTunnelManager OBJECT-TYPE
	SYNTAX  INTEGER { 
			l2tp(1)
			}
	ACCESS  read-write
	STATUS  mandatory
	DESCRIPTION  
	     "Tunneling protocol used to manage the tunnel"
	DEFVAL { l2tp }
	::= { accTunnelPortEntry 2 }
	accTunnelPortAdminState OBJECT-TYPE
	SYNTAX  INTEGER {
		   enabled(1),
		   disabled(2)
		}
	ACCESS  read-write
	STATUS  mandatory
	DESCRIPTION
	     "Tunnel Adminstrative state"
	DEFVAL { disabled }
	::= { accTunnelPortEntry 3 }
	accTunnelPortOperStatus	OBJECT-TYPE
	SYNTAX  INTEGER {
		   up(1),
		   down(2)
		}
	ACCESS  read-only
	STATUS  mandatory
	DESCRIPTION
	     "Tunnel Operation status"
	::= { accTunnelPortEntry 4 }
	accTunnelPortAccessPartition	OBJECT-TYPE
	SYNTAX  DisplayString
	ACCESS  read-write
	STATUS  mandatory
	DESCRIPTION
	     "The access partition the tunnel belongs to"
	::= { accTunnelPortEntry 5 }
        accTunnelPortCreate    OBJECT-TYPE
        SYNTAX  INTEGER
        ACCESS  read-write
        STATUS  mandatory
        DESCRIPTION
             ""
        ::= { accTunnelPortEntry 6 }
        accTunnelPortStatus    OBJECT-TYPE
        SYNTAX  RowStatus
        ACCESS  read-write
        STATUS  mandatory
        DESCRIPTION
             "The current status of this entry."
        ::= { accTunnelPortEntry 7 }

END
