-- file automatically created


TELDAT-TRAP-HDLC-MIB DEFINITIONS ::= BEGIN


IMPORTS
	MODULE-IDENTITY,OBJECT-TYPE,OBJECT-IDENTITY,NOTIFICATION-TYPE,Integer32,IpAddress
		FROM SNMPv2-SMI
	DisplayString
		FROM SNMPv2-TC
	telEventTraps
		FROM TELDAT-MIB;


hdlcTrapsMIB MODULE-IDENTITY
    LAST-UPDATED "201401200930Z"
    ORGANIZATION "Teldat, S.A."
    CONTACT-INFO 
        "Teldat, S.A.
        Customer Service

        Postal: Parque Tecnologico de Madrid
                Tres Cantos 28760
                Madrid, SPAIN

        Tel.: +34 918 076 565

        http://www.teldat.com"
    DESCRIPTION
        "This Module Information Base file is defined for managing received
        SNMP notifications generated by the HDLC event subsystem."
    REVISION "201401200930Z"
    DESCRIPTION "Initial implementation"
        ::= { telEventTraps 190 }


hdlcEventsGroup	OBJECT IDENTIFIER	::= { hdlcTrapsMIB 1 }

hdlcNotifications	OBJECT IDENTIFIER	::= { hdlcTrapsMIB 2 }
hdlcNotificationsPrefix	OBJECT IDENTIFIER	::= { hdlcNotifications 0 }

hdlcEventObjects1 OBJECT-IDENTITY
    STATUS current
    DESCRIPTION
        "Event HDLC.1
        Frame transmitted."
    ::= { hdlcEventsGroup 1 }

hdlc1-address OBJECT-TYPE
    SYNTAX Integer32
    MAX-ACCESS accessible-for-notify
    STATUS current
    DESCRIPTION
        "Parameter 'address' in event HDLC.1"
    ::= { hdlcEventObjects1 1 }

hdlc1-control OBJECT-TYPE
    SYNTAX Integer32
    MAX-ACCESS accessible-for-notify
    STATUS current
    DESCRIPTION
        "Parameter 'control' in event HDLC.1"
    ::= { hdlcEventObjects1 2 }

hdlc1-protocol OBJECT-TYPE
    SYNTAX Integer32
    MAX-ACCESS accessible-for-notify
    STATUS current
    DESCRIPTION
        "Parameter 'protocol' in event HDLC.1"
    ::= { hdlcEventObjects1 3 }

hdlc1-len OBJECT-TYPE
    SYNTAX Integer32
    MAX-ACCESS accessible-for-notify
    STATUS current
    DESCRIPTION
        "Parameter 'len' in event HDLC.1"
    ::= { hdlcEventObjects1 4 }

hdlc1-ifc-name OBJECT-TYPE
    SYNTAX DisplayString
    MAX-ACCESS accessible-for-notify
    STATUS current
    DESCRIPTION
        "Parameter 'ifc-name' in event HDLC.1"
    ::= { hdlcEventObjects1 5 }

hdlcEventObjects2 OBJECT-IDENTITY
    STATUS current
    DESCRIPTION
        "Event HDLC.2
        Frame received."
    ::= { hdlcEventsGroup 2 }

hdlc2-address OBJECT-TYPE
    SYNTAX Integer32
    MAX-ACCESS accessible-for-notify
    STATUS current
    DESCRIPTION
        "Parameter 'address' in event HDLC.2"
    ::= { hdlcEventObjects2 1 }

hdlc2-control OBJECT-TYPE
    SYNTAX Integer32
    MAX-ACCESS accessible-for-notify
    STATUS current
    DESCRIPTION
        "Parameter 'control' in event HDLC.2"
    ::= { hdlcEventObjects2 2 }

hdlc2-protocol OBJECT-TYPE
    SYNTAX Integer32
    MAX-ACCESS accessible-for-notify
    STATUS current
    DESCRIPTION
        "Parameter 'protocol' in event HDLC.2"
    ::= { hdlcEventObjects2 3 }

hdlc2-len OBJECT-TYPE
    SYNTAX Integer32
    MAX-ACCESS accessible-for-notify
    STATUS current
    DESCRIPTION
        "Parameter 'len' in event HDLC.2"
    ::= { hdlcEventObjects2 4 }

hdlc2-ifc-name OBJECT-TYPE
    SYNTAX DisplayString
    MAX-ACCESS accessible-for-notify
    STATUS current
    DESCRIPTION
        "Parameter 'ifc-name' in event HDLC.2"
    ::= { hdlcEventObjects2 5 }

hdlcEventObjects3 OBJECT-IDENTITY
    STATUS current
    DESCRIPTION
        "Event HDLC.3
        Keepalive state change"
    ::= { hdlcEventsGroup 3 }

hdlc3-line-state OBJECT-TYPE
    SYNTAX DisplayString
    MAX-ACCESS accessible-for-notify
    STATUS current
    DESCRIPTION
        "Parameter 'line-state' in event HDLC.3"
    ::= { hdlcEventObjects3 1 }

hdlc3-ifc-name OBJECT-TYPE
    SYNTAX DisplayString
    MAX-ACCESS accessible-for-notify
    STATUS current
    DESCRIPTION
        "Parameter 'ifc-name' in event HDLC.3"
    ::= { hdlcEventObjects3 2 }

hdlcEventObjects4 OBJECT-IDENTITY
    STATUS current
    DESCRIPTION
        "Event HDLC.4
        Keepalive sequence transmitted. Status."
    ::= { hdlcEventsGroup 4 }

hdlc4-myseq OBJECT-TYPE
    SYNTAX Integer32
    MAX-ACCESS accessible-for-notify
    STATUS current
    DESCRIPTION
        "Parameter 'myseq' in event HDLC.4"
    ::= { hdlcEventObjects4 1 }

hdlc4-mineseen OBJECT-TYPE
    SYNTAX Integer32
    MAX-ACCESS accessible-for-notify
    STATUS current
    DESCRIPTION
        "Parameter 'mineseen' in event HDLC.4"
    ::= { hdlcEventObjects4 2 }

hdlc4-slarped OBJECT-TYPE
    SYNTAX DisplayString
    MAX-ACCESS accessible-for-notify
    STATUS current
    DESCRIPTION
        "Parameter 'slarped' in event HDLC.4"
    ::= { hdlcEventObjects4 3 }

hdlc4-yoursseen OBJECT-TYPE
    SYNTAX Integer32
    MAX-ACCESS accessible-for-notify
    STATUS current
    DESCRIPTION
        "Parameter 'yoursseen' in event HDLC.4"
    ::= { hdlcEventObjects4 4 }

hdlc4-line-state OBJECT-TYPE
    SYNTAX DisplayString
    MAX-ACCESS accessible-for-notify
    STATUS current
    DESCRIPTION
        "Parameter 'line-state' in event HDLC.4"
    ::= { hdlcEventObjects4 5 }

hdlc4-loop-state OBJECT-TYPE
    SYNTAX DisplayString
    MAX-ACCESS accessible-for-notify
    STATUS current
    DESCRIPTION
        "Parameter 'loop-state' in event HDLC.4"
    ::= { hdlcEventObjects4 6 }

hdlc4-ifc-name OBJECT-TYPE
    SYNTAX DisplayString
    MAX-ACCESS accessible-for-notify
    STATUS current
    DESCRIPTION
        "Parameter 'ifc-name' in event HDLC.4"
    ::= { hdlcEventObjects4 7 }

hdlcEventObjects5 OBJECT-IDENTITY
    STATUS current
    DESCRIPTION
        "Event HDLC.5
        Keepalive recived but none configured."
    ::= { hdlcEventsGroup 5 }

hdlc5-ifc-name OBJECT-TYPE
    SYNTAX DisplayString
    MAX-ACCESS accessible-for-notify
    STATUS current
    DESCRIPTION
        "Parameter 'ifc-name' in event HDLC.5"
    ::= { hdlcEventObjects5 1 }

hdlcEventObjects6 OBJECT-IDENTITY
    STATUS current
    DESCRIPTION
        "Event HDLC.6
        Keepalive time mismatch"
    ::= { hdlcEventsGroup 6 }

hdlc6-expected OBJECT-TYPE
    SYNTAX Integer32
    MAX-ACCESS accessible-for-notify
    STATUS current
    DESCRIPTION
        "Parameter 'expected' in event HDLC.6"
    ::= { hdlcEventObjects6 1 }

hdlc6-meassured OBJECT-TYPE
    SYNTAX Integer32
    MAX-ACCESS accessible-for-notify
    STATUS current
    DESCRIPTION
        "Parameter 'meassured' in event HDLC.6"
    ::= { hdlcEventObjects6 2 }

hdlc6-ifc-name OBJECT-TYPE
    SYNTAX DisplayString
    MAX-ACCESS accessible-for-notify
    STATUS current
    DESCRIPTION
        "Parameter 'ifc-name' in event HDLC.6"
    ::= { hdlcEventObjects6 3 }

hdlcEventObjects7 OBJECT-IDENTITY
    STATUS current
    DESCRIPTION
        "Event HDLC.7
        Invalid length of control packet."
    ::= { hdlcEventsGroup 7 }

hdlc7-len OBJECT-TYPE
    SYNTAX Integer32
    MAX-ACCESS accessible-for-notify
    STATUS current
    DESCRIPTION
        "Parameter 'len' in event HDLC.7"
    ::= { hdlcEventObjects7 1 }

hdlc7-ifc-name OBJECT-TYPE
    SYNTAX DisplayString
    MAX-ACCESS accessible-for-notify
    STATUS current
    DESCRIPTION
        "Parameter 'ifc-name' in event HDLC.7"
    ::= { hdlcEventObjects7 2 }

hdlcEventObjects8 OBJECT-IDENTITY
    STATUS current
    DESCRIPTION
        "Event HDLC.8
        Unexpected IP address reply."
    ::= { hdlcEventsGroup 8 }

hdlc8-ifc-name OBJECT-TYPE
    SYNTAX DisplayString
    MAX-ACCESS accessible-for-notify
    STATUS current
    DESCRIPTION
        "Parameter 'ifc-name' in event HDLC.8"
    ::= { hdlcEventObjects8 1 }

hdlcEventObjects9 OBJECT-IDENTITY
    STATUS current
    DESCRIPTION
        "Event HDLC.9
        IP address request."
    ::= { hdlcEventsGroup 9 }

hdlc9-ifc-name OBJECT-TYPE
    SYNTAX DisplayString
    MAX-ACCESS accessible-for-notify
    STATUS current
    DESCRIPTION
        "Parameter 'ifc-name' in event HDLC.9"
    ::= { hdlcEventObjects9 1 }

hdlcEventObjects10 OBJECT-IDENTITY
    STATUS current
    DESCRIPTION
        "Event HDLC.10
        Unsupported protocol."
    ::= { hdlcEventsGroup 10 }

hdlc10-protocol OBJECT-TYPE
    SYNTAX Integer32
    MAX-ACCESS accessible-for-notify
    STATUS current
    DESCRIPTION
        "Parameter 'protocol' in event HDLC.10"
    ::= { hdlcEventObjects10 1 }

hdlc10-ifc-name OBJECT-TYPE
    SYNTAX DisplayString
    MAX-ACCESS accessible-for-notify
    STATUS current
    DESCRIPTION
        "Parameter 'ifc-name' in event HDLC.10"
    ::= { hdlcEventObjects10 2 }

hdlcEventObjects11 OBJECT-IDENTITY
    STATUS current
    DESCRIPTION
        "Event HDLC.11
        Invalid addr of control packet."
    ::= { hdlcEventsGroup 11 }

hdlc11-bad-add OBJECT-TYPE
    SYNTAX Integer32
    MAX-ACCESS accessible-for-notify
    STATUS current
    DESCRIPTION
        "Parameter 'bad-add' in event HDLC.11"
    ::= { hdlcEventObjects11 1 }

hdlc11-ifc-name OBJECT-TYPE
    SYNTAX DisplayString
    MAX-ACCESS accessible-for-notify
    STATUS current
    DESCRIPTION
        "Parameter 'ifc-name' in event HDLC.11"
    ::= { hdlcEventObjects11 2 }

hdlcEventObjects12 OBJECT-IDENTITY
    STATUS current
    DESCRIPTION
        "Event HDLC.12
        Event received."
    ::= { hdlcEventsGroup 12 }

hdlc12-event OBJECT-TYPE
    SYNTAX Integer32
    MAX-ACCESS accessible-for-notify
    STATUS current
    DESCRIPTION
        "Parameter 'event' in event HDLC.12"
    ::= { hdlcEventObjects12 1 }

hdlc12-state OBJECT-TYPE
    SYNTAX Integer32
    MAX-ACCESS accessible-for-notify
    STATUS current
    DESCRIPTION
        "Parameter 'state' in event HDLC.12"
    ::= { hdlcEventObjects12 2 }

hdlc12-ifc-name OBJECT-TYPE
    SYNTAX DisplayString
    MAX-ACCESS accessible-for-notify
    STATUS current
    DESCRIPTION
        "Parameter 'ifc-name' in event HDLC.12"
    ::= { hdlcEventObjects12 3 }

hdlcEventObjects13 OBJECT-IDENTITY
    STATUS current
    DESCRIPTION
        "Event HDLC.13
        FSM state change."
    ::= { hdlcEventsGroup 13 }

hdlc13-old-state OBJECT-TYPE
    SYNTAX Integer32
    MAX-ACCESS accessible-for-notify
    STATUS current
    DESCRIPTION
        "Parameter 'old-state' in event HDLC.13"
    ::= { hdlcEventObjects13 1 }

hdlc13-new-state OBJECT-TYPE
    SYNTAX Integer32
    MAX-ACCESS accessible-for-notify
    STATUS current
    DESCRIPTION
        "Parameter 'new-state' in event HDLC.13"
    ::= { hdlcEventObjects13 2 }

hdlc13-ifc-name OBJECT-TYPE
    SYNTAX DisplayString
    MAX-ACCESS accessible-for-notify
    STATUS current
    DESCRIPTION
        "Parameter 'ifc-name' in event HDLC.13"
    ::= { hdlcEventObjects13 3 }

hdlcEventObjects14 OBJECT-IDENTITY
    STATUS current
    DESCRIPTION
        "Event HDLC.14
        Frame received dropped because Keepalive is down."
    ::= { hdlcEventsGroup 14 }

hdlc14-ifc-name OBJECT-TYPE
    SYNTAX DisplayString
    MAX-ACCESS accessible-for-notify
    STATUS current
    DESCRIPTION
        "Parameter 'ifc-name' in event HDLC.14"
    ::= { hdlcEventObjects14 1 }

hdlcEventObjects15 OBJECT-IDENTITY
    STATUS current
    DESCRIPTION
        "Event HDLC.15
        Debug indication."
    ::= { hdlcEventsGroup 15 }

hdlc15-Debug-string OBJECT-TYPE
    SYNTAX DisplayString
    MAX-ACCESS accessible-for-notify
    STATUS current
    DESCRIPTION
        "Parameter 'Debug-string' in event HDLC.15"
    ::= { hdlcEventObjects15 1 }

hdlc15-ifc-name OBJECT-TYPE
    SYNTAX DisplayString
    MAX-ACCESS accessible-for-notify
    STATUS current
    DESCRIPTION
        "Parameter 'ifc-name' in event HDLC.15"
    ::= { hdlcEventObjects15 2 }


hdlcNotification1 NOTIFICATION-TYPE
    OBJECTS { 
              hdlc1-address, 
              hdlc1-control,
              hdlc1-protocol,
              hdlc1-len,
              hdlc1-ifc-name 
            }
    STATUS current
    DESCRIPTION
        "Notification of Event HDLC.1

        Message: 'Transmit frame address $1 control $2 protocol $3 len $4 on interface $5'

        Parameters list:
              $1: hdlc1-address
              $2: hdlc1-control
              $3: hdlc1-protocol
              $4: hdlc1-len
              $5: hdlc1-ifc-name

        Frame transmitted."
    ::= { hdlcNotificationsPrefix 1 }

hdlcNotification2 NOTIFICATION-TYPE
    OBJECTS { 
              hdlc2-address, 
              hdlc2-control,
              hdlc2-protocol,
              hdlc2-len,
              hdlc2-ifc-name 
            }
    STATUS current
    DESCRIPTION
        "Notification of Event HDLC.2

        Message: 'Receive frame address $1 control $2 protocol $3 len $4 on interface $5'

        Parameters list:
              $1: hdlc2-address
              $2: hdlc2-control
              $3: hdlc2-protocol
              $4: hdlc2-len
              $5: hdlc2-ifc-name

        Frame received."
    ::= { hdlcNotificationsPrefix 2 }

hdlcNotification3 NOTIFICATION-TYPE
    OBJECTS { 
              hdlc3-line-state, 
              hdlc3-ifc-name 
            }
    STATUS current
    DESCRIPTION
        "Notification of Event HDLC.3

        Message: 'Keepalive change state to $1 on interface $2'

        Parameters list:
              $1: hdlc3-line-state
              $2: hdlc3-ifc-name

        Keepalive state change"
    ::= { hdlcNotificationsPrefix 3 }

hdlcNotification4 NOTIFICATION-TYPE
    OBJECTS { 
              hdlc4-myseq, 
              hdlc4-mineseen,
              hdlc4-slarped,
              hdlc4-yoursseen,
              hdlc4-line-state,
              hdlc4-loop-state,
              hdlc4-ifc-name 
            }
    STATUS current
    DESCRIPTION
        "Notification of Event HDLC.4

        Message: 'Keepalive myseq:$1 mineseen:$2$3 yoursseen:$4, line $5 $6 on interface $7'

        Parameters list:
              $1: hdlc4-myseq
              $2: hdlc4-mineseen
              $3: hdlc4-slarped
              $4: hdlc4-yoursseen
              $5: hdlc4-line-state
              $6: hdlc4-loop-state
              $7: hdlc4-ifc-name

        Keepalive sequence transmitted. Status."
    ::= { hdlcNotificationsPrefix 4 }

hdlcNotification5 NOTIFICATION-TYPE
    OBJECTS { 
              hdlc5-ifc-name 
            }
    STATUS current
    DESCRIPTION
        "Notification of Event HDLC.5

        Message: 'Got keepalive with none configured  on interface $1'

        Parameters list:
              $1: hdlc5-ifc-name

        Keepalive recived but none configured."
    ::= { hdlcNotificationsPrefix 5 }

hdlcNotification6 NOTIFICATION-TYPE
    OBJECTS { 
              hdlc6-expected, 
              hdlc6-meassured,
              hdlc6-ifc-name 
            }
    STATUS current
    DESCRIPTION
        "Notification of Event HDLC.6

        Message: 'Keepalive time mismatch - should be $1 secs, is $2  on interface $3'

        Parameters list:
              $1: hdlc6-expected
              $2: hdlc6-meassured
              $3: hdlc6-ifc-name

        Keepalive time mismatch"
    ::= { hdlcNotificationsPrefix 6 }

hdlcNotification7 NOTIFICATION-TYPE
    OBJECTS { 
              hdlc7-len, 
              hdlc7-ifc-name 
            }
    STATUS current
    DESCRIPTION
        "Notification of Event HDLC.7

        Message: 'Invalid length of control packet ($1 bytes) on interface $2'

        Parameters list:
              $1: hdlc7-len
              $2: hdlc7-ifc-name

        Invalid length of control packet."
    ::= { hdlcNotificationsPrefix 7 }

hdlcNotification8 NOTIFICATION-TYPE
    OBJECTS { 
              hdlc8-ifc-name 
            }
    STATUS current
    DESCRIPTION
        "Notification of Event HDLC.8

        Message: 'Unexpected IP address reply on interface $1'

        Parameters list:
              $1: hdlc8-ifc-name

        Unexpected IP address reply."
    ::= { hdlcNotificationsPrefix 8 }

hdlcNotification9 NOTIFICATION-TYPE
    OBJECTS { 
              hdlc9-ifc-name 
            }
    STATUS current
    DESCRIPTION
        "Notification of Event HDLC.9

        Message: 'IP address request on interface $1'

        Parameters list:
              $1: hdlc9-ifc-name

        IP address request."
    ::= { hdlcNotificationsPrefix 9 }

hdlcNotification10 NOTIFICATION-TYPE
    OBJECTS { 
              hdlc10-protocol, 
              hdlc10-ifc-name 
            }
    STATUS current
    DESCRIPTION
        "Notification of Event HDLC.10

        Message: 'Unsupported protocol $1 on interface $2'

        Parameters list:
              $1: hdlc10-protocol
              $2: hdlc10-ifc-name

        Unsupported protocol."
    ::= { hdlcNotificationsPrefix 10 }

hdlcNotification11 NOTIFICATION-TYPE
    OBJECTS { 
              hdlc11-bad-add, 
              hdlc11-ifc-name 
            }
    STATUS current
    DESCRIPTION
        "Notification of Event HDLC.11

        Message: 'Invalid address ($1) of control packet on interface $2'

        Parameters list:
              $1: hdlc11-bad-add
              $2: hdlc11-ifc-name

        Invalid addr of control packet."
    ::= { hdlcNotificationsPrefix 11 }

hdlcNotification12 NOTIFICATION-TYPE
    OBJECTS { 
              hdlc12-event, 
              hdlc12-state,
              hdlc12-ifc-name 
            }
    STATUS current
    DESCRIPTION
        "Notification of Event HDLC.12

        Message: 'Received event $1 on state $2 on interface $3'

        Parameters list:
              $1: hdlc12-event
              $2: hdlc12-state
              $3: hdlc12-ifc-name

        Event received."
    ::= { hdlcNotificationsPrefix 12 }

hdlcNotification13 NOTIFICATION-TYPE
    OBJECTS { 
              hdlc13-old-state, 
              hdlc13-new-state,
              hdlc13-ifc-name 
            }
    STATUS current
    DESCRIPTION
        "Notification of Event HDLC.13

        Message: 'FSM state change old state $1 new state $2 on interface $3'

        Parameters list:
              $1: hdlc13-old-state
              $2: hdlc13-new-state
              $3: hdlc13-ifc-name

        FSM state change."
    ::= { hdlcNotificationsPrefix 13 }

hdlcNotification14 NOTIFICATION-TYPE
    OBJECTS { 
              hdlc14-ifc-name 
            }
    STATUS current
    DESCRIPTION
        "Notification of Event HDLC.14

        Message: 'Drop frame on interface $1'

        Parameters list:
              $1: hdlc14-ifc-name

        Frame received dropped because Keepalive is down."
    ::= { hdlcNotificationsPrefix 14 }

hdlcNotification15 NOTIFICATION-TYPE
    OBJECTS { 
              hdlc15-Debug-string, 
              hdlc15-ifc-name 
            }
    STATUS current
    DESCRIPTION
        "Notification of Event HDLC.15

        Message: '$1 on interface $2'

        Parameters list:
              $1: hdlc15-Debug-string
              $2: hdlc15-ifc-name

        Debug indication."
    ::= { hdlcNotificationsPrefix 15 }


END
