-- file automatically created


TELDAT-TRAP-XN-MIB DEFINITIONS ::= BEGIN


IMPORTS
	MODULE-IDENTITY,OBJECT-TYPE,OBJECT-IDENTITY,NOTIFICATION-TYPE,Integer32,IpAddress
		FROM SNMPv2-SMI
	DisplayString
		FROM SNMPv2-TC
	telEventTraps
		FROM TELDAT-MIB;


xnTrapsMIB MODULE-IDENTITY
    LAST-UPDATED "201401200930Z"
    ORGANIZATION "Teldat, S.A."
    CONTACT-INFO 
        "Teldat, S.A.
        Customer Service

        Postal: Parque Tecnologico de Madrid
                Tres Cantos 28760
                Madrid, SPAIN

        Tel.: +34 918 076 565

        http://www.teldat.com"
    DESCRIPTION
        "This Module Information Base file is defined for managing received
        SNMP notifications generated by the XN event subsystem."
    REVISION "201401200930Z"
    DESCRIPTION "Initial implementation"
        ::= { telEventTraps 163 }


xnEventsGroup	OBJECT IDENTIFIER	::= { xnTrapsMIB 1 }

xnNotifications	OBJECT IDENTIFIER	::= { xnTrapsMIB 2 }
xnNotificationsPrefix	OBJECT IDENTIFIER	::= { xnNotifications 0 }

xnEventObjects1 OBJECT-IDENTITY
    STATUS current
    DESCRIPTION
        "Event XN.1
        This message is generated when a packet has an XNS packet length
        greater then the packets physical length."
    ::= { xnEventsGroup 1 }

xn1-protocol OBJECT-TYPE
    SYNTAX DisplayString
    MAX-ACCESS accessible-for-notify
    STATUS current
    DESCRIPTION
        "Parameter 'protocol' in event XN.1"
    ::= { xnEventObjects1 1 }

xn1-source-net OBJECT-TYPE
    SYNTAX Integer32
    MAX-ACCESS accessible-for-notify
    STATUS current
    DESCRIPTION
        "Parameter 'source-net' in event XN.1"
    ::= { xnEventObjects1 2 }

xn1-source-node OBJECT-TYPE
    SYNTAX DisplayString
    MAX-ACCESS accessible-for-notify
    STATUS current
    DESCRIPTION
        "Parameter 'source-node' in event XN.1"
    ::= { xnEventObjects1 3 }

xn1-length OBJECT-TYPE
    SYNTAX Integer32
    MAX-ACCESS accessible-for-notify
    STATUS current
    DESCRIPTION
        "Parameter 'length' in event XN.1"
    ::= { xnEventObjects1 4 }

xnEventObjects2 OBJECT-IDENTITY
    STATUS current
    DESCRIPTION
        "Event XN.2
        The reserved bits in the Transport Control field of the
        header were not zero. An Error (checksum) packet will be sent."
    ::= { xnEventsGroup 2 }

xn2-protocol OBJECT-TYPE
    SYNTAX DisplayString
    MAX-ACCESS accessible-for-notify
    STATUS current
    DESCRIPTION
        "Parameter 'protocol' in event XN.2"
    ::= { xnEventObjects2 1 }

xn2-source-net OBJECT-TYPE
    SYNTAX Integer32
    MAX-ACCESS accessible-for-notify
    STATUS current
    DESCRIPTION
        "Parameter 'source-net' in event XN.2"
    ::= { xnEventObjects2 2 }

xn2-source-node OBJECT-TYPE
    SYNTAX DisplayString
    MAX-ACCESS accessible-for-notify
    STATUS current
    DESCRIPTION
        "Parameter 'source-node' in event XN.2"
    ::= { xnEventObjects2 3 }

xn2-TC OBJECT-TYPE
    SYNTAX Integer32
    MAX-ACCESS accessible-for-notify
    STATUS current
    DESCRIPTION
        "Parameter 'TC' in event XN.2"
    ::= { xnEventObjects2 4 }

xnEventObjects3 OBJECT-IDENTITY
    STATUS current
    DESCRIPTION
        "Event XN.3
        This message is generated when the checksum in a packet being
        forwarded does not match the calculated checksum for the packet.
        An Error (checksum) packet will be sent."
    ::= { xnEventsGroup 3 }

xn3-protocol OBJECT-TYPE
    SYNTAX DisplayString
    MAX-ACCESS accessible-for-notify
    STATUS current
    DESCRIPTION
        "Parameter 'protocol' in event XN.3"
    ::= { xnEventObjects3 1 }

xn3-source-net OBJECT-TYPE
    SYNTAX Integer32
    MAX-ACCESS accessible-for-notify
    STATUS current
    DESCRIPTION
        "Parameter 'source-net' in event XN.3"
    ::= { xnEventObjects3 2 }

xn3-source-node OBJECT-TYPE
    SYNTAX DisplayString
    MAX-ACCESS accessible-for-notify
    STATUS current
    DESCRIPTION
        "Parameter 'source-node' in event XN.3"
    ::= { xnEventObjects3 3 }

xn3-cksum OBJECT-TYPE
    SYNTAX Integer32
    MAX-ACCESS accessible-for-notify
    STATUS current
    DESCRIPTION
        "Parameter 'cksum' in event XN.3"
    ::= { xnEventObjects3 4 }

xnEventObjects4 OBJECT-IDENTITY
    STATUS current
    DESCRIPTION
        "Event XN.4
        This message is generated when a packet's hop count counts up
        past 15 and overflows. An Error (hop count) packet will be sent."
    ::= { xnEventsGroup 4 }

xn4-protocol OBJECT-TYPE
    SYNTAX DisplayString
    MAX-ACCESS accessible-for-notify
    STATUS current
    DESCRIPTION
        "Parameter 'protocol' in event XN.4"
    ::= { xnEventObjects4 1 }

xn4-source-net OBJECT-TYPE
    SYNTAX Integer32
    MAX-ACCESS accessible-for-notify
    STATUS current
    DESCRIPTION
        "Parameter 'source-net' in event XN.4"
    ::= { xnEventObjects4 2 }

xn4-source-node OBJECT-TYPE
    SYNTAX DisplayString
    MAX-ACCESS accessible-for-notify
    STATUS current
    DESCRIPTION
        "Parameter 'source-node' in event XN.4"
    ::= { xnEventObjects4 3 }

xn4-destination-net OBJECT-TYPE
    SYNTAX Integer32
    MAX-ACCESS accessible-for-notify
    STATUS current
    DESCRIPTION
        "Parameter 'destination-net' in event XN.4"
    ::= { xnEventObjects4 4 }

xnEventObjects5 OBJECT-IDENTITY
    STATUS current
    DESCRIPTION
        "Event XN.5
        This message is generated when a packet cannot be forwarded
        because there is no gateway to the destination network.
        An Error (unreachable) packet will be sent."
    ::= { xnEventsGroup 5 }

xn5-protocol OBJECT-TYPE
    SYNTAX DisplayString
    MAX-ACCESS accessible-for-notify
    STATUS current
    DESCRIPTION
        "Parameter 'protocol' in event XN.5"
    ::= { xnEventObjects5 1 }

xn5-source-net OBJECT-TYPE
    SYNTAX Integer32
    MAX-ACCESS accessible-for-notify
    STATUS current
    DESCRIPTION
        "Parameter 'source-net' in event XN.5"
    ::= { xnEventObjects5 2 }

xn5-source-node OBJECT-TYPE
    SYNTAX DisplayString
    MAX-ACCESS accessible-for-notify
    STATUS current
    DESCRIPTION
        "Parameter 'source-node' in event XN.5"
    ::= { xnEventObjects5 3 }

xn5-destination-net OBJECT-TYPE
    SYNTAX Integer32
    MAX-ACCESS accessible-for-notify
    STATUS current
    DESCRIPTION
        "Parameter 'destination-net' in event XN.5"
    ::= { xnEventObjects5 4 }

xnEventObjects6 OBJECT-IDENTITY
    STATUS current
    DESCRIPTION
        "Event XN.6
        This packet is generated when a packet is being sent out
        the same network interface it arrived on. This router is
        not the best path off that network to the destination network."
    ::= { xnEventsGroup 6 }

xn6-protocol OBJECT-TYPE
    SYNTAX DisplayString
    MAX-ACCESS accessible-for-notify
    STATUS current
    DESCRIPTION
        "Parameter 'protocol' in event XN.6"
    ::= { xnEventObjects6 1 }

xn6-source-net OBJECT-TYPE
    SYNTAX Integer32
    MAX-ACCESS accessible-for-notify
    STATUS current
    DESCRIPTION
        "Parameter 'source-net' in event XN.6"
    ::= { xnEventObjects6 2 }

xn6-source-node OBJECT-TYPE
    SYNTAX DisplayString
    MAX-ACCESS accessible-for-notify
    STATUS current
    DESCRIPTION
        "Parameter 'source-node' in event XN.6"
    ::= { xnEventObjects6 3 }

xn6-destination-net OBJECT-TYPE
    SYNTAX Integer32
    MAX-ACCESS accessible-for-notify
    STATUS current
    DESCRIPTION
        "Parameter 'destination-net' in event XN.6"
    ::= { xnEventObjects6 4 }

xnEventObjects7 OBJECT-IDENTITY
    STATUS current
    DESCRIPTION
        "Event XN.7
        This message is generated when a packet is addressed to
        node 000000000000. This is an illegal host address.
        An Error (checksum) packet will be sent."
    ::= { xnEventsGroup 7 }

xn7-protocol OBJECT-TYPE
    SYNTAX DisplayString
    MAX-ACCESS accessible-for-notify
    STATUS current
    DESCRIPTION
        "Parameter 'protocol' in event XN.7"
    ::= { xnEventObjects7 1 }

xn7-source-net OBJECT-TYPE
    SYNTAX Integer32
    MAX-ACCESS accessible-for-notify
    STATUS current
    DESCRIPTION
        "Parameter 'source-net' in event XN.7"
    ::= { xnEventObjects7 2 }

xn7-source-node OBJECT-TYPE
    SYNTAX DisplayString
    MAX-ACCESS accessible-for-notify
    STATUS current
    DESCRIPTION
        "Parameter 'source-node' in event XN.7"
    ::= { xnEventObjects7 3 }

xn7-destination-net OBJECT-TYPE
    SYNTAX Integer32
    MAX-ACCESS accessible-for-notify
    STATUS current
    DESCRIPTION
        "Parameter 'destination-net' in event XN.7"
    ::= { xnEventObjects7 4 }

xnEventObjects8 OBJECT-IDENTITY
    STATUS current
    DESCRIPTION
        "Event XN.8
        This message is generated when a packet is forwarded."
    ::= { xnEventsGroup 8 }

xn8-protocol OBJECT-TYPE
    SYNTAX DisplayString
    MAX-ACCESS accessible-for-notify
    STATUS current
    DESCRIPTION
        "Parameter 'protocol' in event XN.8"
    ::= { xnEventObjects8 1 }

xn8-source-net OBJECT-TYPE
    SYNTAX Integer32
    MAX-ACCESS accessible-for-notify
    STATUS current
    DESCRIPTION
        "Parameter 'source-net' in event XN.8"
    ::= { xnEventObjects8 2 }

xn8-source-node OBJECT-TYPE
    SYNTAX DisplayString
    MAX-ACCESS accessible-for-notify
    STATUS current
    DESCRIPTION
        "Parameter 'source-node' in event XN.8"
    ::= { xnEventObjects8 3 }

xn8-dest-net OBJECT-TYPE
    SYNTAX Integer32
    MAX-ACCESS accessible-for-notify
    STATUS current
    DESCRIPTION
        "Parameter 'dest-net' in event XN.8"
    ::= { xnEventObjects8 4 }

xn8-dest-node OBJECT-TYPE
    SYNTAX DisplayString
    MAX-ACCESS accessible-for-notify
    STATUS current
    DESCRIPTION
        "Parameter 'dest-node' in event XN.8"
    ::= { xnEventObjects8 5 }

xnEventObjects9 OBJECT-IDENTITY
    STATUS current
    DESCRIPTION
        "Event XN.9
        The router cannot send out a forwarded packet to the required
        interface because it is too long. An Error (size) packet will be sent."
    ::= { xnEventsGroup 9 }

xn9-protocol OBJECT-TYPE
    SYNTAX DisplayString
    MAX-ACCESS accessible-for-notify
    STATUS current
    DESCRIPTION
        "Parameter 'protocol' in event XN.9"
    ::= { xnEventObjects9 1 }

xn9-pkt-size OBJECT-TYPE
    SYNTAX Integer32
    MAX-ACCESS accessible-for-notify
    STATUS current
    DESCRIPTION
        "Parameter 'pkt-size' in event XN.9"
    ::= { xnEventObjects9 2 }

xn9-max-size OBJECT-TYPE
    SYNTAX Integer32
    MAX-ACCESS accessible-for-notify
    STATUS current
    DESCRIPTION
        "Parameter 'max-size' in event XN.9"
    ::= { xnEventObjects9 3 }

xn9-interface OBJECT-TYPE
    SYNTAX DisplayString
    MAX-ACCESS accessible-for-notify
    STATUS current
    DESCRIPTION
        "Parameter 'interface' in event XN.9"
    ::= { xnEventObjects9 4 }

xn9-source-net OBJECT-TYPE
    SYNTAX Integer32
    MAX-ACCESS accessible-for-notify
    STATUS current
    DESCRIPTION
        "Parameter 'source-net' in event XN.9"
    ::= { xnEventObjects9 5 }

xn9-source-node OBJECT-TYPE
    SYNTAX DisplayString
    MAX-ACCESS accessible-for-notify
    STATUS current
    DESCRIPTION
        "Parameter 'source-node' in event XN.9"
    ::= { xnEventObjects9 6 }

xnEventObjects10 OBJECT-IDENTITY
    STATUS current
    DESCRIPTION
        "Event XN.10
        An outgoing packet was not successfully transmitted for the reason
        indicated by the error code."
    ::= { xnEventsGroup 10 }

xn10-protocol OBJECT-TYPE
    SYNTAX DisplayString
    MAX-ACCESS accessible-for-notify
    STATUS current
    DESCRIPTION
        "Parameter 'protocol' in event XN.10"
    ::= { xnEventObjects10 1 }

xn10-type OBJECT-TYPE
    SYNTAX Integer32
    MAX-ACCESS accessible-for-notify
    STATUS current
    DESCRIPTION
        "Parameter 'type' in event XN.10"
    ::= { xnEventObjects10 2 }

xn10-source-net OBJECT-TYPE
    SYNTAX Integer32
    MAX-ACCESS accessible-for-notify
    STATUS current
    DESCRIPTION
        "Parameter 'source-net' in event XN.10"
    ::= { xnEventObjects10 3 }

xn10-source-node OBJECT-TYPE
    SYNTAX DisplayString
    MAX-ACCESS accessible-for-notify
    STATUS current
    DESCRIPTION
        "Parameter 'source-node' in event XN.10"
    ::= { xnEventObjects10 4 }

xn10-dest-net OBJECT-TYPE
    SYNTAX Integer32
    MAX-ACCESS accessible-for-notify
    STATUS current
    DESCRIPTION
        "Parameter 'dest-net' in event XN.10"
    ::= { xnEventObjects10 5 }

xn10-dest-node OBJECT-TYPE
    SYNTAX DisplayString
    MAX-ACCESS accessible-for-notify
    STATUS current
    DESCRIPTION
        "Parameter 'dest-node' in event XN.10"
    ::= { xnEventObjects10 6 }

xn10-code OBJECT-TYPE
    SYNTAX Integer32
    MAX-ACCESS accessible-for-notify
    STATUS current
    DESCRIPTION
        "Parameter 'code' in event XN.10"
    ::= { xnEventObjects10 7 }

xnEventObjects11 OBJECT-IDENTITY
    STATUS current
    DESCRIPTION
        "Event XN.11
        The specified interface has come up, and has been enabled for
        the specified XNS protocol."
    ::= { xnEventsGroup 11 }

xn11-protocol OBJECT-TYPE
    SYNTAX DisplayString
    MAX-ACCESS accessible-for-notify
    STATUS current
    DESCRIPTION
        "Parameter 'protocol' in event XN.11"
    ::= { xnEventObjects11 1 }

xn11-network OBJECT-TYPE
    SYNTAX Integer32
    MAX-ACCESS accessible-for-notify
    STATUS current
    DESCRIPTION
        "Parameter 'network' in event XN.11"
    ::= { xnEventObjects11 2 }

xn11-node OBJECT-TYPE
    SYNTAX DisplayString
    MAX-ACCESS accessible-for-notify
    STATUS current
    DESCRIPTION
        "Parameter 'node' in event XN.11"
    ::= { xnEventObjects11 3 }

xn11-interface OBJECT-TYPE
    SYNTAX DisplayString
    MAX-ACCESS accessible-for-notify
    STATUS current
    DESCRIPTION
        "Parameter 'interface' in event XN.11"
    ::= { xnEventObjects11 4 }

xnEventObjects12 OBJECT-IDENTITY
    STATUS current
    DESCRIPTION
        "Event XN.12
        The specified route has been deleted because the first hop
        interface for that route has gone down."
    ::= { xnEventsGroup 12 }

xn12-protocol OBJECT-TYPE
    SYNTAX DisplayString
    MAX-ACCESS accessible-for-notify
    STATUS current
    DESCRIPTION
        "Parameter 'protocol' in event XN.12"
    ::= { xnEventObjects12 1 }

xn12-destination-net OBJECT-TYPE
    SYNTAX Integer32
    MAX-ACCESS accessible-for-notify
    STATUS current
    DESCRIPTION
        "Parameter 'destination-net' in event XN.12"
    ::= { xnEventObjects12 2 }

xn12-gateway OBJECT-TYPE
    SYNTAX DisplayString
    MAX-ACCESS accessible-for-notify
    STATUS current
    DESCRIPTION
        "Parameter 'gateway' in event XN.12"
    ::= { xnEventObjects12 3 }

xn12-interface OBJECT-TYPE
    SYNTAX DisplayString
    MAX-ACCESS accessible-for-notify
    STATUS current
    DESCRIPTION
        "Parameter 'interface' in event XN.12"
    ::= { xnEventObjects12 4 }

xnEventObjects13 OBJECT-IDENTITY
    STATUS current
    DESCRIPTION
        "Event XN.13
        This message is generated when a new entry cannot be made to
        routing table because it is already full."
    ::= { xnEventsGroup 13 }

xn13-protocol OBJECT-TYPE
    SYNTAX DisplayString
    MAX-ACCESS accessible-for-notify
    STATUS current
    DESCRIPTION
        "Parameter 'protocol' in event XN.13"
    ::= { xnEventObjects13 1 }

xn13-destination-net OBJECT-TYPE
    SYNTAX Integer32
    MAX-ACCESS accessible-for-notify
    STATUS current
    DESCRIPTION
        "Parameter 'destination-net' in event XN.13"
    ::= { xnEventObjects13 2 }

xnEventObjects14 OBJECT-IDENTITY
    STATUS current
    DESCRIPTION
        "Event XN.14
        A packet of the echo type has been received with the specified
        operation to the specified socket."
    ::= { xnEventsGroup 14 }

xn14-protocol OBJECT-TYPE
    SYNTAX DisplayString
    MAX-ACCESS accessible-for-notify
    STATUS current
    DESCRIPTION
        "Parameter 'protocol' in event XN.14"
    ::= { xnEventObjects14 1 }

xn14-operation OBJECT-TYPE
    SYNTAX Integer32
    MAX-ACCESS accessible-for-notify
    STATUS current
    DESCRIPTION
        "Parameter 'operation' in event XN.14"
    ::= { xnEventObjects14 2 }

xn14-socket OBJECT-TYPE
    SYNTAX Integer32
    MAX-ACCESS accessible-for-notify
    STATUS current
    DESCRIPTION
        "Parameter 'socket' in event XN.14"
    ::= { xnEventObjects14 3 }

xn14-source-net OBJECT-TYPE
    SYNTAX Integer32
    MAX-ACCESS accessible-for-notify
    STATUS current
    DESCRIPTION
        "Parameter 'source-net' in event XN.14"
    ::= { xnEventObjects14 4 }

xn14-source-node OBJECT-TYPE
    SYNTAX DisplayString
    MAX-ACCESS accessible-for-notify
    STATUS current
    DESCRIPTION
        "Parameter 'source-node' in event XN.14"
    ::= { xnEventObjects14 5 }

xnEventObjects15 OBJECT-IDENTITY
    STATUS current
    DESCRIPTION
        "Event XN.15
        A packet was being returned to the sender, but the sender
        node address was a multicast address or the illegal address
        000000000000. This can happen when sending an Echo reply,
        an Error packet, or replying to other queries. The packet
        will be discarded."
    ::= { xnEventsGroup 15 }

xn15-protocol OBJECT-TYPE
    SYNTAX DisplayString
    MAX-ACCESS accessible-for-notify
    STATUS current
    DESCRIPTION
        "Parameter 'protocol' in event XN.15"
    ::= { xnEventObjects15 1 }

xn15-source-net OBJECT-TYPE
    SYNTAX Integer32
    MAX-ACCESS accessible-for-notify
    STATUS current
    DESCRIPTION
        "Parameter 'source-net' in event XN.15"
    ::= { xnEventObjects15 2 }

xn15-source-node OBJECT-TYPE
    SYNTAX DisplayString
    MAX-ACCESS accessible-for-notify
    STATUS current
    DESCRIPTION
        "Parameter 'source-node' in event XN.15"
    ::= { xnEventObjects15 3 }

xn15-interface OBJECT-TYPE
    SYNTAX DisplayString
    MAX-ACCESS accessible-for-notify
    STATUS current
    DESCRIPTION
        "Parameter 'interface' in event XN.15"
    ::= { xnEventObjects15 4 }

xnEventObjects16 OBJECT-IDENTITY
    STATUS current
    DESCRIPTION
        "Event XN.16
        A packet was being returned to the sender, and the source network
        was zero, but the destination network was non-zero. This can
        happen when sending an Echo reply, an Error packet, or replying to
        other queries. The packet will be discarded."
    ::= { xnEventsGroup 16 }

xn16-protocol OBJECT-TYPE
    SYNTAX DisplayString
    MAX-ACCESS accessible-for-notify
    STATUS current
    DESCRIPTION
        "Parameter 'protocol' in event XN.16"
    ::= { xnEventObjects16 1 }

xn16-source-net OBJECT-TYPE
    SYNTAX Integer32
    MAX-ACCESS accessible-for-notify
    STATUS current
    DESCRIPTION
        "Parameter 'source-net' in event XN.16"
    ::= { xnEventObjects16 2 }

xn16-source-node OBJECT-TYPE
    SYNTAX DisplayString
    MAX-ACCESS accessible-for-notify
    STATUS current
    DESCRIPTION
        "Parameter 'source-node' in event XN.16"
    ::= { xnEventObjects16 3 }

xn16-dest-net OBJECT-TYPE
    SYNTAX Integer32
    MAX-ACCESS accessible-for-notify
    STATUS current
    DESCRIPTION
        "Parameter 'dest-net' in event XN.16"
    ::= { xnEventObjects16 4 }

xn16-dest-node OBJECT-TYPE
    SYNTAX DisplayString
    MAX-ACCESS accessible-for-notify
    STATUS current
    DESCRIPTION
        "Parameter 'dest-node' in event XN.16"
    ::= { xnEventObjects16 5 }

xnEventObjects17 OBJECT-IDENTITY
    STATUS current
    DESCRIPTION
        "Event XN.17
        This message is generated when no memory is available to copy the
        offending packet into an Error packet. An Error packet will not be sent."
    ::= { xnEventsGroup 17 }

xn17-protocol OBJECT-TYPE
    SYNTAX DisplayString
    MAX-ACCESS accessible-for-notify
    STATUS current
    DESCRIPTION
        "Parameter 'protocol' in event XN.17"
    ::= { xnEventObjects17 1 }

xnEventObjects18 OBJECT-IDENTITY
    STATUS current
    DESCRIPTION
        "Event XN.18
        This message is generated when a packet has a physical
        length shorter than the minimum 30 byte XNS, IPX, or DDS header length.
        The source-net and source-node may or may not be valid packet
        data, depending on how severe the truncation is."
    ::= { xnEventsGroup 18 }

xn18-protocol OBJECT-TYPE
    SYNTAX DisplayString
    MAX-ACCESS accessible-for-notify
    STATUS current
    DESCRIPTION
        "Parameter 'protocol' in event XN.18"
    ::= { xnEventObjects18 1 }

xn18-length OBJECT-TYPE
    SYNTAX Integer32
    MAX-ACCESS accessible-for-notify
    STATUS current
    DESCRIPTION
        "Parameter 'length' in event XN.18"
    ::= { xnEventObjects18 2 }

xn18-source-net OBJECT-TYPE
    SYNTAX Integer32
    MAX-ACCESS accessible-for-notify
    STATUS current
    DESCRIPTION
        "Parameter 'source-net' in event XN.18"
    ::= { xnEventObjects18 3 }

xn18-source-node OBJECT-TYPE
    SYNTAX DisplayString
    MAX-ACCESS accessible-for-notify
    STATUS current
    DESCRIPTION
        "Parameter 'source-node' in event XN.18"
    ::= { xnEventObjects18 4 }

xn18-interface OBJECT-TYPE
    SYNTAX DisplayString
    MAX-ACCESS accessible-for-notify
    STATUS current
    DESCRIPTION
        "Parameter 'interface' in event XN.18"
    ::= { xnEventObjects18 5 }

xnEventObjects19 OBJECT-IDENTITY
    STATUS current
    DESCRIPTION
        "Event XN.19
        This message is generated when an IPX packet is received with a source
        network number of 0. The router corrects this to be the network
        number of the interface the packet was received on."
    ::= { xnEventsGroup 19 }

xn19-protocol OBJECT-TYPE
    SYNTAX DisplayString
    MAX-ACCESS accessible-for-notify
    STATUS current
    DESCRIPTION
        "Parameter 'protocol' in event XN.19"
    ::= { xnEventObjects19 1 }

xn19-new-source-net OBJECT-TYPE
    SYNTAX Integer32
    MAX-ACCESS accessible-for-notify
    STATUS current
    DESCRIPTION
        "Parameter 'new-source-net' in event XN.19"
    ::= { xnEventObjects19 2 }

xn19-source-net OBJECT-TYPE
    SYNTAX Integer32
    MAX-ACCESS accessible-for-notify
    STATUS current
    DESCRIPTION
        "Parameter 'source-net' in event XN.19"
    ::= { xnEventObjects19 3 }

xn19-source-node OBJECT-TYPE
    SYNTAX DisplayString
    MAX-ACCESS accessible-for-notify
    STATUS current
    DESCRIPTION
        "Parameter 'source-node' in event XN.19"
    ::= { xnEventObjects19 4 }

xn19-dest-net OBJECT-TYPE
    SYNTAX Integer32
    MAX-ACCESS accessible-for-notify
    STATUS current
    DESCRIPTION
        "Parameter 'dest-net' in event XN.19"
    ::= { xnEventObjects19 5 }

xn19-dest-node OBJECT-TYPE
    SYNTAX DisplayString
    MAX-ACCESS accessible-for-notify
    STATUS current
    DESCRIPTION
        "Parameter 'dest-node' in event XN.19"
    ::= { xnEventObjects19 6 }

xnEventObjects20 OBJECT-IDENTITY
    STATUS current
    DESCRIPTION
        "Event XN.20
        This message is generated when an IPX packet is received with a source
        network number of 0, and the hop count (transport control) is non-zero.
        The source network number will not be corrected, since it is
        probably not the network it was received on. The dest-node
        will be unable to reply."
    ::= { xnEventsGroup 20 }

xn20-protocol OBJECT-TYPE
    SYNTAX DisplayString
    MAX-ACCESS accessible-for-notify
    STATUS current
    DESCRIPTION
        "Parameter 'protocol' in event XN.20"
    ::= { xnEventObjects20 1 }

xn20-hop-count OBJECT-TYPE
    SYNTAX Integer32
    MAX-ACCESS accessible-for-notify
    STATUS current
    DESCRIPTION
        "Parameter 'hop-count' in event XN.20"
    ::= { xnEventObjects20 2 }

xn20-source-net OBJECT-TYPE
    SYNTAX Integer32
    MAX-ACCESS accessible-for-notify
    STATUS current
    DESCRIPTION
        "Parameter 'source-net' in event XN.20"
    ::= { xnEventObjects20 3 }

xn20-source-node OBJECT-TYPE
    SYNTAX DisplayString
    MAX-ACCESS accessible-for-notify
    STATUS current
    DESCRIPTION
        "Parameter 'source-node' in event XN.20"
    ::= { xnEventObjects20 4 }

xn20-dest-net OBJECT-TYPE
    SYNTAX Integer32
    MAX-ACCESS accessible-for-notify
    STATUS current
    DESCRIPTION
        "Parameter 'dest-net' in event XN.20"
    ::= { xnEventObjects20 5 }

xn20-dest-node OBJECT-TYPE
    SYNTAX DisplayString
    MAX-ACCESS accessible-for-notify
    STATUS current
    DESCRIPTION
        "Parameter 'dest-node' in event XN.20"
    ::= { xnEventObjects20 6 }

xn20-interface OBJECT-TYPE
    SYNTAX DisplayString
    MAX-ACCESS accessible-for-notify
    STATUS current
    DESCRIPTION
        "Parameter 'interface' in event XN.20"
    ::= { xnEventObjects20 7 }

xnEventObjects21 OBJECT-IDENTITY
    STATUS current
    DESCRIPTION
        "Event XN.21
        This message is generated when a packet has a length field
        in the XNS, IPX or DDS network layer header that is shorter than
        the 30 byte minimum packet length."
    ::= { xnEventsGroup 21 }

xn21-protocol OBJECT-TYPE
    SYNTAX DisplayString
    MAX-ACCESS accessible-for-notify
    STATUS current
    DESCRIPTION
        "Parameter 'protocol' in event XN.21"
    ::= { xnEventObjects21 1 }

xn21-claimed-length OBJECT-TYPE
    SYNTAX Integer32
    MAX-ACCESS accessible-for-notify
    STATUS current
    DESCRIPTION
        "Parameter 'claimed-length' in event XN.21"
    ::= { xnEventObjects21 2 }

xn21-source-net OBJECT-TYPE
    SYNTAX Integer32
    MAX-ACCESS accessible-for-notify
    STATUS current
    DESCRIPTION
        "Parameter 'source-net' in event XN.21"
    ::= { xnEventObjects21 3 }

xn21-source-node OBJECT-TYPE
    SYNTAX DisplayString
    MAX-ACCESS accessible-for-notify
    STATUS current
    DESCRIPTION
        "Parameter 'source-node' in event XN.21"
    ::= { xnEventObjects21 4 }


xnNotification1 NOTIFICATION-TYPE
    OBJECTS { 
              xn1-protocol, 
              xn1-source-net,
              xn1-source-node,
              xn1-length,
              xn1-length 
            }
    STATUS current
    DESCRIPTION
        "Notification of Event XN.1

        Message: '$1 truncated packet from $2/$3; xns $4, physical $5'

        Parameters list:
              $1: xn1-protocol
              $2: xn1-source-net
              $3: xn1-source-node
              $4: xn1-length
              $5: xn1-length

        This message is generated when a packet has an XNS packet length
        greater then the packets physical length."
    ::= { xnNotificationsPrefix 1 }

xnNotification2 NOTIFICATION-TYPE
    OBJECTS { 
              xn2-protocol, 
              xn2-source-net,
              xn2-source-node,
              xn2-TC 
            }
    STATUS current
    DESCRIPTION
        "Notification of Event XN.2

        Message: '$1 non-zero transport control from $2/$3, $4'

        Parameters list:
              $1: xn2-protocol
              $2: xn2-source-net
              $3: xn2-source-node
              $4: xn2-TC

        The reserved bits in the Transport Control field of the
        header were not zero. An Error (checksum) packet will be sent."
    ::= { xnNotificationsPrefix 2 }

xnNotification3 NOTIFICATION-TYPE
    OBJECTS { 
              xn3-protocol, 
              xn3-source-net,
              xn3-source-node,
              xn3-cksum,
              xn3-cksum 
            }
    STATUS current
    DESCRIPTION
        "Notification of Event XN.3

        Message: '$1 bad routing checksum from $2/$3; received $4, compared $5'

        Parameters list:
              $1: xn3-protocol
              $2: xn3-source-net
              $3: xn3-source-node
              $4: xn3-cksum
              $5: xn3-cksum

        This message is generated when the checksum in a packet being
        forwarded does not match the calculated checksum for the packet.
        An Error (checksum) packet will be sent."
    ::= { xnNotificationsPrefix 3 }

xnNotification4 NOTIFICATION-TYPE
    OBJECTS { 
              xn4-protocol, 
              xn4-source-net,
              xn4-source-node,
              xn4-destination-net 
            }
    STATUS current
    DESCRIPTION
        "Notification of Event XN.4

        Message: '$1 hop count overflow from $2/$3 to $4'

        Parameters list:
              $1: xn4-protocol
              $2: xn4-source-net
              $3: xn4-source-node
              $4: xn4-destination-net

        This message is generated when a packet's hop count counts up
        past 15 and overflows. An Error (hop count) packet will be sent."
    ::= { xnNotificationsPrefix 4 }

xnNotification5 NOTIFICATION-TYPE
    OBJECTS { 
              xn5-protocol, 
              xn5-source-net,
              xn5-source-node,
              xn5-destination-net 
            }
    STATUS current
    DESCRIPTION
        "Notification of Event XN.5

        Message: '$1 no gateway from $2/$3 to $4'

        Parameters list:
              $1: xn5-protocol
              $2: xn5-source-net
              $3: xn5-source-node
              $4: xn5-destination-net

        This message is generated when a packet cannot be forwarded
        because there is no gateway to the destination network.
        An Error (unreachable) packet will be sent."
    ::= { xnNotificationsPrefix 5 }

xnNotification6 NOTIFICATION-TYPE
    OBJECTS { 
              xn6-protocol, 
              xn6-source-net,
              xn6-source-node,
              xn6-destination-net 
            }
    STATUS current
    DESCRIPTION
        "Notification of Event XN.6

        Message: '$1 wasted hop from $2/$3 to $4'

        Parameters list:
              $1: xn6-protocol
              $2: xn6-source-net
              $3: xn6-source-node
              $4: xn6-destination-net

        This packet is generated when a packet is being sent out
        the same network interface it arrived on. This router is
        not the best path off that network to the destination network."
    ::= { xnNotificationsPrefix 6 }

xnNotification7 NOTIFICATION-TYPE
    OBJECTS { 
              xn7-protocol, 
              xn7-source-net,
              xn7-source-node,
              xn7-destination-net 
            }
    STATUS current
    DESCRIPTION
        "Notification of Event XN.7

        Message: '$1 destination host 0 from $2/$3 to $4'

        Parameters list:
              $1: xn7-protocol
              $2: xn7-source-net
              $3: xn7-source-node
              $4: xn7-destination-net

        This message is generated when a packet is addressed to
        node 000000000000. This is an illegal host address.
        An Error (checksum) packet will be sent."
    ::= { xnNotificationsPrefix 7 }

xnNotification8 NOTIFICATION-TYPE
    OBJECTS { 
              xn8-protocol, 
              xn8-source-net,
              xn8-source-node,
              xn8-dest-net,
              xn8-dest-node 
            }
    STATUS current
    DESCRIPTION
        "Notification of Event XN.8

        Message: '$1 Packet received from $2/$3 for $4/$5'

        Parameters list:
              $1: xn8-protocol
              $2: xn8-source-net
              $3: xn8-source-node
              $4: xn8-dest-net
              $5: xn8-dest-node

        This message is generated when a packet is forwarded."
    ::= { xnNotificationsPrefix 8 }

xnNotification9 NOTIFICATION-TYPE
    OBJECTS { 
              xn9-protocol, 
              xn9-pkt-size,
              xn9-max-size,
              xn9-interface,
              xn9-source-net,
              xn9-source-node 
            }
    STATUS current
    DESCRIPTION
        "Notification of Event XN.9

        Message: '$1 packet too long to forward $2 > $3 interface $4 from $5/$6'

        Parameters list:
              $1: xn9-protocol
              $2: xn9-pkt-size
              $3: xn9-max-size
              $4: xn9-interface
              $5: xn9-source-net
              $6: xn9-source-node

        The router cannot send out a forwarded packet to the required
        interface because it is too long. An Error (size) packet will be sent."
    ::= { xnNotificationsPrefix 9 }

xnNotification10 NOTIFICATION-TYPE
    OBJECTS { 
              xn10-protocol, 
              xn10-type,
              xn10-source-net,
              xn10-source-node,
              xn10-dest-net,
              xn10-dest-node,
              xn10-code 
            }
    STATUS current
    DESCRIPTION
        "Notification of Event XN.10

        Message: '$1 $2 from $3/$4 for $5/$6 discarded for reason $7'

        Parameters list:
              $1: xn10-protocol
              $2: xn10-type
              $3: xn10-source-net
              $4: xn10-source-node
              $5: xn10-dest-net
              $6: xn10-dest-node
              $7: xn10-code

        An outgoing packet was not successfully transmitted for the reason
        indicated by the error code."
    ::= { xnNotificationsPrefix 10 }

xnNotification11 NOTIFICATION-TYPE
    OBJECTS { 
              xn11-protocol, 
              xn11-network,
              xn11-node,
              xn11-interface 
            }
    STATUS current
    DESCRIPTION
        "Notification of Event XN.11

        Message: '$1 interface $2/$3 interface $4 up'

        Parameters list:
              $1: xn11-protocol
              $2: xn11-network
              $3: xn11-node
              $4: xn11-interface

        The specified interface has come up, and has been enabled for
        the specified XNS protocol."
    ::= { xnNotificationsPrefix 11 }

xnNotification12 NOTIFICATION-TYPE
    OBJECTS { 
              xn12-protocol, 
              xn12-destination-net,
              xn12-gateway,
              xn12-interface 
            }
    STATUS current
    DESCRIPTION
        "Notification of Event XN.12

        Message: '$1 deleted net $2 route via $3 interface $4'

        Parameters list:
              $1: xn12-protocol
              $2: xn12-destination-net
              $3: xn12-gateway
              $4: xn12-interface

        The specified route has been deleted because the first hop
        interface for that route has gone down."
    ::= { xnNotificationsPrefix 12 }

xnNotification13 NOTIFICATION-TYPE
    OBJECTS { 
              xn13-protocol, 
              xn13-destination-net 
            }
    STATUS current
    DESCRIPTION
        "Notification of Event XN.13

        Message: '$1 Table overflow, destination $2'

        Parameters list:
              $1: xn13-protocol
              $2: xn13-destination-net

        This message is generated when a new entry cannot be made to
        routing table because it is already full."
    ::= { xnNotificationsPrefix 13 }

xnNotification14 NOTIFICATION-TYPE
    OBJECTS { 
              xn14-protocol, 
              xn14-operation,
              xn14-socket,
              xn14-source-net,
              xn14-source-node 
            }
    STATUS current
    DESCRIPTION
        "Notification of Event XN.14

        Message: '$1 Echo type $2 to socket $3 from $4/$5'

        Parameters list:
              $1: xn14-protocol
              $2: xn14-operation
              $3: xn14-socket
              $4: xn14-source-net
              $5: xn14-source-node

        A packet of the echo type has been received with the specified
        operation to the specified socket."
    ::= { xnNotificationsPrefix 14 }

xnNotification15 NOTIFICATION-TYPE
    OBJECTS { 
              xn15-protocol, 
              xn15-source-net,
              xn15-source-node,
              xn15-interface 
            }
    STATUS current
    DESCRIPTION
        "Notification of Event XN.15

        Message: '$1 bad source $2/$3 interface $4'

        Parameters list:
              $1: xn15-protocol
              $2: xn15-source-net
              $3: xn15-source-node
              $4: xn15-interface

        A packet was being returned to the sender, but the sender
        node address was a multicast address or the illegal address
        000000000000. This can happen when sending an Echo reply,
        an Error packet, or replying to other queries. The packet
        will be discarded."
    ::= { xnNotificationsPrefix 15 }

xnNotification16 NOTIFICATION-TYPE
    OBJECTS { 
              xn16-protocol, 
              xn16-source-net,
              xn16-source-node,
              xn16-dest-net,
              xn16-dest-node 
            }
    STATUS current
    DESCRIPTION
        "Notification of Event XN.16

        Message: '$1 bad source network 0 from $2/$3 for $4/$5'

        Parameters list:
              $1: xn16-protocol
              $2: xn16-source-net
              $3: xn16-source-node
              $4: xn16-dest-net
              $5: xn16-dest-node

        A packet was being returned to the sender, and the source network
        was zero, but the destination network was non-zero. This can
        happen when sending an Echo reply, an Error packet, or replying to
        other queries. The packet will be discarded."
    ::= { xnNotificationsPrefix 16 }

xnNotification17 NOTIFICATION-TYPE
    OBJECTS { 
              xn17-protocol 
            }
    STATUS current
    DESCRIPTION
        "Notification of Event XN.17

        Message: '$1 No memory for error packet'

        Parameters list:
              $1: xn17-protocol

        This message is generated when no memory is available to copy the
        offending packet into an Error packet. An Error packet will not be sent."
    ::= { xnNotificationsPrefix 17 }

xnNotification18 NOTIFICATION-TYPE
    OBJECTS { 
              xn18-protocol, 
              xn18-length,
              xn18-source-net,
              xn18-source-node,
              xn18-interface 
            }
    STATUS current
    DESCRIPTION
        "Notification of Event XN.18

        Message: '$1 short ($2) packet from $3/$4 (?) interface $5'

        Parameters list:
              $1: xn18-protocol
              $2: xn18-length
              $3: xn18-source-net
              $4: xn18-source-node
              $5: xn18-interface

        This message is generated when a packet has a physical
        length shorter than the minimum 30 byte XNS, IPX, or DDS header length.
        The source-net and source-node may or may not be valid packet
        data, depending on how severe the truncation is."
    ::= { xnNotificationsPrefix 18 }

xnNotification19 NOTIFICATION-TYPE
    OBJECTS { 
              xn19-protocol, 
              xn19-new-source-net,
              xn19-source-net,
              xn19-source-node,
              xn19-dest-net,
              xn19-dest-node 
            }
    STATUS current
    DESCRIPTION
        "Notification of Event XN.19

        Message: '$1 changing source network to $2 on packet received from $3/$4 for $5/$6'

        Parameters list:
              $1: xn19-protocol
              $2: xn19-new-source-net
              $3: xn19-source-net
              $4: xn19-source-node
              $5: xn19-dest-net
              $6: xn19-dest-node

        This message is generated when an IPX packet is received with a source
        network number of 0. The router corrects this to be the network
        number of the interface the packet was received on."
    ::= { xnNotificationsPrefix 19 }

xnNotification20 NOTIFICATION-TYPE
    OBJECTS { 
              xn20-protocol, 
              xn20-hop-count,
              xn20-source-net,
              xn20-source-node,
              xn20-dest-net,
              xn20-dest-node,
              xn20-interface 
            }
    STATUS current
    DESCRIPTION
        "Notification of Event XN.20

        Message: '$1 bad source network 0 with hop count $2 on packet received from $3/$4 for $5/$6 via interface $7'

        Parameters list:
              $1: xn20-protocol
              $2: xn20-hop-count
              $3: xn20-source-net
              $4: xn20-source-node
              $5: xn20-dest-net
              $6: xn20-dest-node
              $7: xn20-interface

        This message is generated when an IPX packet is received with a source
        network number of 0, and the hop count (transport control) is non-zero.
        The source network number will not be corrected, since it is
        probably not the network it was received on. The dest-node
        will be unable to reply."
    ::= { xnNotificationsPrefix 20 }

xnNotification21 NOTIFICATION-TYPE
    OBJECTS { 
              xn21-protocol, 
              xn21-claimed-length,
              xn21-source-net,
              xn21-source-node 
            }
    STATUS current
    DESCRIPTION
        "Notification of Event XN.21

        Message: '$1 invalid length ($2 bytes) from $3/$4'

        Parameters list:
              $1: xn21-protocol
              $2: xn21-claimed-length
              $3: xn21-source-net
              $4: xn21-source-node

        This message is generated when a packet has a length field
        in the XNS, IPX or DDS network layer header that is shorter than
        the 30 byte minimum packet length."
    ::= { xnNotificationsPrefix 21 }


END
