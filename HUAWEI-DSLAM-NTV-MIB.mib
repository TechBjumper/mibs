-- ========================================================================================================== 
-- Copyright (C) 2012 by  HUAWEI TECHNOLOGIES. All rights reserved.  
-- Description:   This MIB module defines the Multicast MIB objects. 
--                Multicast refers to the point-to-multipoint communication in which the multicast 
--                source sends the information to a certain subset of all the network nodes.
--                Controllable multicast allows an access device to determine 
--                if a user has the authority to watch programs by identifying the user request packets. 
--                In this way, the access device controls and forwards the multicast services.                             
-- Reference:                                                        
-- Version: V1.78                                               
-- =========================================================================================================== 

    HUAWEI-DSLAM-NTV-MIB DEFINITIONS ::= BEGIN
        IMPORTS    
            MODULE-IDENTITY, OBJECT-TYPE, OBJECT-IDENTITY, IpAddress, Integer32, Counter32, Unsigned32,NOTIFICATION-TYPE, Counter64
                FROM SNMPv2-SMI
            huaweiUtility
                FROM HUAWEI-MIB
            ifIndex, InterfaceIndex          
                FROM IF-MIB  
            hwConfigChangeIP
                FROM HUAWEI-DEVICE-MIB                                              
            RowStatus, DateAndTime, TruthValue, TEXTUAL-CONVENTION
                FROM SNMPv2-TC
            Ipv6Address                               
                FROM IPV6-TC                       
            InetAddressType, InetAddress
                FROM INET-ADDRESS-MIB;
                
        hwDslamNtv MODULE-IDENTITY
            LAST-UPDATED "201207030000Z"
            ORGANIZATION "Huawei Technologies co.,Ltd."
            CONTACT-INFO                                 
                         "Huawei Industrial Base         
                          Bantian, Longgang              
                          Shenzhen 518129                
                          People's Republic of China     
                          Website: http://www.huawei.com 
                          Email: support@huawei.com      
                         "                               
            DESCRIPTION
                "This MIB module defines the Multicast MIB objects. 
                 Multicast refers to the point-to-multipoint communication in which the multicast 
                 source sends the information to a certain subset of all the network nodes.
                 Controllable multicast allows an access device to determine 
                 if a user has the authority to watch programs by identifying the user request packets. 
                 In this way, the access device controls and forwards the multicast services."             
            
            --  Revision history
            REVISION     "201207030000Z"
            DESCRIPTION  "V1.78, Modified deccription of hwDslamNtvProgramNewIpCascadePortList.
	                 "
			 
            REVISION     "201206280000Z"
            DESCRIPTION  "V1.77, Modified deccription of hwDslamNtvDefaultUplinkPort.
                          Added hwDslamNtvBoardStatisticTable for the IPTV performance statistics of the specific board.
			  Added hwMulticastPortStatisticTable for the multicast port statistic.
                          Modified the value range of hwDslamNtvUserAuthority.
			  Modified deccription of hwDslamNtvProgramMask1 to hwDslamNtvProgramMask64.
                          Added hwDslamNtvChannelBandwidthCACTable for CAC of the channel.
                         "
            
            REVISION     "201204250000Z"
            DESCRIPTION  "V1.76, added hwDslamNtvProgramBTVUserPortList3 and hwDslamNtvProgramBTVUserPortList4 to
                          hwDslamNtvProgramTable.
                          Modified the value range of hwDslamntvIpCascadePortIndex from (1..2048) to (1..4096).
                          Modified the value range of hwDslamNtvFlowID.
                          Modified the value range of hwDslamNtvUserIgmpStatUserIndex from (0..4095) to (0..16383).
                         "                         
                           
            REVISION     "201203150000Z"
            DESCRIPTION  "V1.75, added hwDslamNtvMVLANIgmpDscpVaule, hwDslamNtvMVLANMldDscpVaule to hwDslamNtvMVLANTable.
                          Modified the value range of hwDslamNtvAssignBandwidth from (0..4294967295) to (-1|0..2147483647).
                          "
                         
            REVISION     "201203020000Z"
            DESCRIPTION  "V1.74, added hwDslamNtvMcastVlanTagTransformUserVlan and hwDslamNtvMVlanMembershipTable.
                          Added hwDslamNtvMcastVlanTagMode for the value of singleTranslate.
                          Added hwDslamNtvUserMldQueryVersion to hwDslamNtvUserTable.
                          Modified deccription of hwDslamNtvUserCurrentMldVersion.
                          Modified description of hwDslamNtvUserVpi, hwDslamNtvUserVci, hwDslamNtvUserUsedBandwidth,
                          hwDslamNtvUserUsdBwthPcntToPortRate, hwDslamNtvUserMatchPara, hwDslamNtvUserVideoVpi,
                          hwDslamNtvUserVideoVci, hwDslamNtvUserAncpVideoBandwidth, hwDslamNtvUserAncpMcastBandwidth,
                          hwDslamNtvUserMatchPara2, hwDslamNtvIpCascadePortMatchPara, hwDslamNtvIpCascadePortMatchPara2,
                          hwDslamNtvDefaultUplinkPort, hwDslamNtvMVLANIgmpQueryInterval, hwDslamNtvAssignBandwidth, 
                          hwDslamNtvAncpMcastBandwidth, hwDslamNtvAncpVideoBandwidth and hwDslamNtvMcastVlanTagMode.
                          Modified the value range of hwDslamNtvMFSExtMVlanId from (1..4093) to (1..4093|4097).
                          Added hwDslamNtvUserIgmpVersion to hwDslamNtvUserChangeTrap.
                          Added hwDslamNtvUserMldQueryVersion to hwDslamNtvUserChangeTrap.
                          "
                          
            REVISION     "201201100000Z"
            DESCRIPTION  "V1.73, modified the value range of hwDslamNtvAssignBandwidth from (512..2608857) to (0..4294967295).
                          Added hwDslamNtvMVlanIgmpStatV2JoinRcvdFromUser,hwDslamNtvMVlanIgmpStatV3JoinRcvdFromUser,
                          hwDslamNtvMVlanIgmpStatLeaveSentToNetwork and hwDslamNtvMVlanIgmpStatV3JoinSentToNetwork
                          to hwDslamNtvMVlanIgmpStatTable.
                          Added hwDslamNtvMVlanMldStatGenQueryRcvdFromNetwork,hwDslamNtvMVlanMldStatSpecQueryRcvdFromNetwork,
                          hwDslamNtvMVlanMldStatV1JoinRcvdFromUser,hwDslamNtvMVlanMldStatV2JoinRcvdFromUser,
                          hwDslamNtvMVlanMldStatLeaveRcvdFromUser,hwDslamNtvMVlanMldStatGenQuerySentToUser,
                          hwDslamNtvMVlanMldStatSpecQuerySentToUser,hwDslamNtvMVlanMldStatV2JoinSentToNetwork,
                          hwDslamNtvMVlanMldStatLeaveSentToNetwork and hwDslamNtvMVlanMldStatInvalidRcvdFromUser
                          to hwDslamNtvMVlanMldStatTable.
                          Added hwDslamNtvMFSExtTable for the multicast flow statistics from vlanid,IP address type,
                          program IP address and source IP address.
                          Modified description of hwDslamNtvMldStatisticTable and hwDslamNtvMVlanMldStatTable.
                          "
                         
            REVISION     "201112120000Z"
            DESCRIPTION  "V1.72, added hwDslamNtvGlobalCfg.
                          Added hwDslamNtvGlobalCfgPreviewRecognitionTime, hwDslamNtvGlobalCfgLogRecognitionTime,
                          hwDslamNtvGlobalCfgIgmpSyslog, hwDslamNtvGlobalCfgIgmpLogRecord and hwDslamNtvGlobalCfgIgmpRouterAlertToV2User
                          to hwDslamNtvGlobalCfg.
                          Modified description of hwDslamNtvUserIndex, hwDslamNtvProgramIndex, hwDslamNtvRightProfileIndex, 
                          hwDslamNtvUserMaxBandWidth and hwDslamNtvMVLANIndex.
                          Modified the value range of hwDslamNtvMVLANIndex from (1..256) to (-1|1..256).
                          Modified the value range of hwDslamNtvProgramIndex from (1..4096) to (-1|1..4096).
                          "
                         
            REVISION     "201109200000Z"
            DESCRIPTION  "V1.71, modified description of hwDslamNtvUserFlowType and hwDslamNtvUserFlowPara.
                         Added hwDslamNtvBandwidthCalcMode."

            REVISION     "201108220000Z"
            DESCRIPTION  "V1.70, added hwDslamNtvIgmpProcessPreferred."
            
            REVISION     "201107110000Z"
            DESCRIPTION  "V1.69, added hwDslamNtvMVLANSnoopingQueryProxy and hwDslamNtvMVLANGroupFilterMode
                          to hwDslamNtvMVLANTable.
                          Added hwDslamNtvMVlanIgmpStatJoinProgRcvUser, hwDslamNtvMVlanIgmpStatLeaveProgRcvUser
                          hwDslamNtvMVlanIgmpStatGenQuerySndUser, hwDslamNtvMVlanIgmpStatSpecQuerySndUser and 
                          hwDslamNtvMVlanIgmpStatInvalidRcvUser to hwDslamNtvMVlanIgmpStatTable.
                          Added hwDslamNtvUserIgmpStatSuccJoinProgRcv, hwDslamNtvUserIgmpStatErrJoinProgRcv
                          and hwDslamNtvUserIgmpStatLeaveProgRcv to hwDslamNtvUserIgmpStatTable.
                          Added hwDslamNtvMVLANDualPwSwitch, hwDslamNtvMVLANMldVer, hwDslamNtvMVLANMldUnsoliReportTime, hwDslamNtvMVLANMldPriority, 
                          hwDslamNtvMVLANMldMode, hwDslamNtvMVLANMldMatchMode, hwDslamNtvMVLANMldSnoopingReportSwitch, 
                          hwDslamNtvMVLANMldSnoopingLeaveSwitch, hwDslamNtvMldQueryInterval, hwDslamNtvMldV1QueryMaxResponseTime, 
                          hwDslamNtvMldV2QueryMaxResponseTime, hwDslamNtvMldRobustness, hwDslamNtvMVLANMldLastMemberQueryInterval, 
                          hwDslamNtvMldV1LastMemberQueryResponse, hwDslamNtvMldV2LastMemberQueryResponse, 
                          hwDslamNtvMVLANMldLastMemberQueryCount, hwDslamNtvMldInitialUnsolicitedReportInterval to 
                          hwDslamNtvMVLANTable.
                          Added hwDslamNtvProgramIPv6, hwDslamNtvProgramSourceIPv6 to hwDslamNtvProgramTable.
                          Added hwDslamNtvVUpportTblMldRouterVersion to hwDslamNtvVUpportTable.
                          Added hwDslamNtvUserCurrentMldVersion to hwDslamNtvUserTable.
                          Added hwDslamNtvMldStatisticTable, hwDslamNtvUserMldStatTable, hwDslamNtvMVlanMldStatTable, 
                          hwDslamNtvMVLANIPv6AddrRangeTable."
                          
            REVISION     "201105180000Z"
            DESCRIPTION  "V1.68, modified description of hwDslamNtvUserVideoFlowPara and hwDslamNtvUserFlowPara."
                          
            REVISION     "201012120000Z"
            DESCRIPTION  "V1.67, added hwDslamNtvMVLANIgmpQueryInterval, hwDslamNtvMVLANIgmpV2QueryMaxResponseTime,
                          hwDslamNtvMVLANIgmpV3QueryMaxResponseTime, hwDslamNtvMVLANIgmpRobustness,
                          hwDslamNtvMVLANIgmpLastMemberQueryInterval, hwDslamNtvMVLANIgmpV2LastMemberQueryResponse,
                          hwDslamNtvMVLANIgmpV3LastMemberQueryResponse, hwDslamNtvMVLANIgmpLastMemberQueryCount,
                          hwDslamNtvMVLANIgmpV2RouterTimerout and hwDslamNtvMVLANIgmpInitialUnsolicitedReportInterval
                          to hwDslamNtvMVLANTable."

            REVISION     "201012060000Z"
            DESCRIPTION  "V1.66, added hwDslamNtvIgmpUserStatCurrTable for the igmp statistic of current 15 minutes.
                          Added hwDslamNtvIgmpUserStatHistTable for the igmp statistic of history 15 minutes."

            REVISION     "201011270000Z"
            DESCRIPTION  "V1.65, added hwDslamNtvSourceIpAndGroupIpMode."

            REVISION     "201011250000Z"
            DESCRIPTION  "V1.64, added hwDslamNtvUserIgmpVersion to hwDslamNtvUserTable."
            
            REVISION     "201011220000Z"
            DESCRIPTION  "V1.63, modified description of leaves and the enumeration of hwDslamNtvUserFlowMode."
            
            REVISION     "201009140000Z"
            DESCRIPTION  "V1.62, added the range of hwDslamNtvProgramPriority's value,modified description.
                          Added hwDslamNtvMVLANIPAddrRangeTable."

            REVISION     "201007290000Z"
            DESCRIPTION  "V1.61, modified description."
             
            REVISION     "201006170000Z"
            DESCRIPTION  "V1.60, added hwDslamNtvIgmpAcceleratorMode and hwDslamNtvIgmpAcceleratorVlanPara."
            
            REVISION     "201006020000Z"
            DESCRIPTION  "V1.59, deleted the Chinese characters in this file.
                         Modified the OID which bound to the first parameter of hwDslamNtvUserChangeTrap 
                         and hwDslamNtvFlowMulticastPolicyChangeTrap.
                         Modified the value range of hwDslamNtvVUpportTblIndex from (1..1024) to (-1|1..1024)."
            
            REVISION     "201005200000Z"
            DESCRIPTION  "V1.58, added hwDslamNtvUserChangeTrap."
                        
            REVISION     "201005070000Z"
            DESCRIPTION  "V1.57, modified query-detect to queryDetect. Added hwDslamNtvUpportWorkMode enumerated value: Upport work mode support 'rrpp' mode."
            
            REVISION     "201004250000Z"
            DESCRIPTION  "V1.56, modified description of all leaves."
            
            REVISION     "201003100000Z"
            DESCRIPTION  "V1.55, modified enumeration format."
            
            REVISION     "200912311120Z"
            DESCRIPTION  "V1.53, added hwDslamNtvMVLANTrap and hwDslamNtvTrapsVbOids."
                      
            REVISION     "200912040000Z"
            DESCRIPTION  "V1.52, added hwDslamNtvUserStaticJoinTable for BTV simulation."
            
            REVISION     "200911190000Z"
            DESCRIPTION  "V1.51, added hwDslamNtvUserFlowTable,NTV user's flow management table, used for getting user index by flow. " 
            
            REVISION     "200911060000Z"
            DESCRIPTION  "V1.50, added hwDslamNtvUpportWorkMode enumerated value: upport work mode support 'RRPP' mode"
            
            REVISION     "200908070000Z"
            DESCRIPTION  "V1.49, added hwDslamNtvMcastVlanTagMode. The mode indicates 
                         how many tags of the multicast packet which is forwarded correctly. "            
            
            REVISION     "200906090000Z"
            DESCRIPTION  "V1.00, initial version."
                
            ::= { huaweiUtility 28} 
            
        PortList ::= TEXTUAL-CONVENTION
            STATUS current
            DESCRIPTION
                "
                Every sequence 16 octet group altogether represents ports of 
                one slot:
                  octet0  -- octet15  represents ports of slot0,
                  octet16 -- octet31  represents ports of slot1,
                  ......
                  octet112-- octet127 represents ports of slot7.
                
                Each octet specifies a set of eight ports, 
                with the first octet of a 16 octet group specifying ports 0 
                through 7 of the slot, the second octet of a 16 octet group
                specifying ports 8 through 15 of the slot, etc.
                Within each octet, the most significant bit represents 
                the lowest numbered port, and the least significant bit 
                represents the highest numbered port:
                   ------------------------------------------------
                  |bit in octet0:  7   6   5   4   3   2   1   0   |
                  |port in slot0:  0   1   2   3   4   5   6   7   |
                  |------------------------------------------------|
                   ......
                   ------------------------------------------------              
                  |bit in octet15: 7   6   5   4   3   2   1   0   |
                  |port in slot0: 120 121 122 123 124 125 126 127  |                  
                  |------------------------------------------------|                    
                  
                  
                   ------------------------------------------------
                  |bit in octet16: 7   6   5   4   3   2   1   0   |
                  |port in slot1:  0   1   2   3   4   5   6   7   |
                  |------------------------------------------------|
                  ......              
                   ------------------------------------------------
                  |bit in octet31: 7   6   5   4   3   2   1   0   |  
                  |port in slot1: 120 121 122 123 124 125 126 127  |  
                  |------------------------------------------------|
                  ......
                  ......
                
                Thus, each port of the DSLAN is represented by a single bit 
                within the value of this object. If that bit has a value of 
                '1' then that port is included in the set of ports; the port 
                is not included if its bit has a value of '0'."
            SYNTAX OCTET STRING (SIZE (0..128))
 
        hwDslamNtvMode   OBJECT-TYPE
            SYNTAX INTEGER
                {
                hmcp(1),
                igmpSnooping(2),
                igmpProxy(3),
                tvOff(4),
                oamGroupControl(5)
                }
            MAX-ACCESS   read-write
            STATUS       current
            DESCRIPTION
                "Indicates the IGMP mode. Currently, four modes in enumerated values are supported:
                 Options:
                 1. hmcp(1)            -indicates the IGMP mode is hmcp
                 2. igmpSnooping(2)    -indicates the IGMP mode is snooping
                 3. igmpProxy(3)       -indicates the IGMP mode is proxy
                 4. tvOff(4)           -indicates the IGMP mode is off
                 5. oamGroupControl(5) -indicates the IGMP mode is oamGroupControl
                 This leaf is valid in only the IGMP global mode. Default: tvOff(4).
                "
            ::= { hwDslamNtv 1 }
        
        hwDslamNtvVpi   OBJECT-TYPE
            SYNTAX       Integer32(0..255)
            MAX-ACCESS   read-write
            STATUS       current
            DESCRIPTION
                "Multicast vpi.
                 System multicast vpi. Value ranges from 0 to 255.If it is changed,
                 all the vpi of multicast pvcs are changed.
                 Default: 0                 
                "       
            ::= { hwDslamNtv 2 }
        
        hwDslamNtvVci   OBJECT-TYPE
            SYNTAX       Integer32(32..255)
            MAX-ACCESS   read-write
            STATUS       current
            DESCRIPTION
                "Multicast vci.
                 System multicast vci. Value from 0 to 65535.If it is changed,all the vci of multicast pvc are changed.
                 Default: 35
                "       
            ::= { hwDslamNtv 3 }
        
        hwDslamNtvQueryInterval   OBJECT-TYPE
            SYNTAX       Unsigned32 (30..5000)
            UNITS        "seconds"
            MAX-ACCESS   read-write
            STATUS       current
            DESCRIPTION
                "Sets/Queries the interval of an IGMP general group. 
                 Range: 30-5000 
                 Unit: second 
                 Default: 125
                "           
            ::= { hwDslamNtv 4 }
        
        hwDslamNtvQuerier   OBJECT-TYPE
            SYNTAX       IpAddress
            MAX-ACCESS   read-write
            STATUS       current
            DESCRIPTION
                "Indicates the source IP address of IGMP packets sent to the user side. 
                 Default: 192.168.1.1
                "
            ::= { hwDslamNtv 5 }   
        
        hwDslamNtvQueryMaxResponseTime   OBJECT-TYPE
            SYNTAX       Integer32 (1..255)
            UNITS        "0.1s"
            MAX-ACCESS   read-write
            STATUS       current
            DESCRIPTION
                "Indicates the maximum response time for an IGMPV2 general query.
                 Range: 1-255
                 Unit: 0.1s, that is, 0.1-25.5s.
                 Default: 10s (100)
                "         
            ::= { hwDslamNtv 6 }      
        
        hwDslamNtvLeaveDelay   OBJECT-TYPE
            SYNTAX       Integer32(5..2550)
            UNITS        "0.1s"
            MAX-ACCESS   read-write
            STATUS       current
            DESCRIPTION
                "Leave delay.
                 UNIT: 0.1s
                "
            ::= { hwDslamNtv 7 }
        
        hwDslamNtvMaxChannelNum   OBJECT-TYPE
            SYNTAX       Integer32(1..4096)
            MAX-ACCESS   read-only
            STATUS       current
            DESCRIPTION
                "Indicates the maximum number of programs supported by the system.
                "
            ::= { hwDslamNtv 8 }   
        
        hwDslamNtvSnoopingAdminStatus        OBJECT-TYPE
            SYNTAX       TruthValue
            MAX-ACCESS   read-write
            STATUS       current
            DESCRIPTION
                "Snooping administer state.
                 The administrative true(enable)/ false(disable) state for IGMP Snooping.
                 used to enable/disable IGMP Snooping to control whether MAC multicast 
                 forwarding table is created and maintained on Layer 2.
                "
            ::= { hwDslamNtv 9 }   
         
        hwDslamNtvLastChange   OBJECT-TYPE
            SYNTAX   INTEGER{
                              changed(1),
                              unchanged(2)
                            }
            MAX-ACCESS   read-only
            STATUS       current
            DESCRIPTION
                "NTV feature configure state.
                 The value of sysUpTime at the time when the system entered its current operational state. 
                 If the current state was entered prior to the last re-initialization of the local 
                 network management subsystem, then this object contains a zero value.
                 Options:
                 1. changed(1)   -indicates the NTV feature configure has changed
                 2. unchanged(2) -indicates the NTV feature configure has not changed
                "
            ::= { hwDslamNtv 10 }
        
        hwDslamNtvUpportInterface   OBJECT-TYPE
            SYNTAX       InterfaceIndex
            MAX-ACCESS   read-write
            STATUS       current
            DESCRIPTION
                "ifIndex of Main Up Port.
                "
            ::= { hwDslamNtv 11 } 
        
        hwDslamNtvUpportVlanId   OBJECT-TYPE
            SYNTAX       Integer32(1..4093)
            MAX-ACCESS   read-write
            STATUS       current
            DESCRIPTION
                "VlanId of Main Up Port.
                "
            ::= { hwDslamNtv 12 }
        
        hwDslamNtvRobustness        OBJECT-TYPE
            SYNTAX       Integer32(1..10)
            MAX-ACCESS   read-write
            STATUS       current
            DESCRIPTION
                "Indicates the system robustness variable. 
                 Range: 1-10 
                 Default: 2
                "           
            ::= { hwDslamNtv 13}
                
        hwDslamNtvUserTable    OBJECT-TYPE
            SYNTAX          SEQUENCE OF HwDslamNtvUserEntry
            MAX-ACCESS      not-accessible
            STATUS          current
            DESCRIPTION
                "Indicates the multicast user table.
                 The index of this table is hwDslamNtvUserIndex.
                "
            ::= { hwDslamNtv 16 }
        
        hwDslamNtvUserEntry    OBJECT-TYPE
            SYNTAX          HwDslamNtvUserEntry
            MAX-ACCESS      not-accessible
            STATUS          current
            DESCRIPTION
                "Indicates the multicast user table.
                 The index of this entry is hwDslamNtvUserIndex.
                "
            INDEX   
                { 
                hwDslamNtvUserIndex
                }
            ::= { hwDslamNtvUserTable  1 }
        
        HwDslamNtvUserEntry ::=
            SEQUENCE 
                { 
                hwDslamNtvUserAuthority
                    INTEGER,
                hwDslamNtvUserRightProfile
                    Integer32,
                hwDslamNtvUserRowStatus
                    RowStatus,
                hwDslamNtvUserOperStatus
                    INTEGER,
                hwDslamNtvUserAdminStatus
                    INTEGER,
                hwDslamNtvUserMaxChannel
                    Integer32,
                hwDslamNtvUserWatchingChannel1
                    BITS,
                hwDslamNtvUserWatchingChannel2
                    BITS,
                hwDslamNtvUserEnableLog
                    TruthValue,
                hwDslamNtvUserVpi
                    Integer32,
                hwDslamNtvUserVci
                    Integer32,
                hwDslamNtvUserVlan
                    Integer32,
                hwDslamNtvUserFlowType         
                    INTEGER,
                hwDslamNtvUserFlowPara         
                    Integer32,
                hwDslamNtvUserMode
                    INTEGER,
                hwDslamNtvUserAuthFailProcess
                    INTEGER,
                hwDslamNtvUserUsedBandwidth
                    Integer32,
                hwDslamNtvUserUsdBwthPcntToPortRate
                    Integer32,
                hwDslamNtvUserIfIndex
                    Integer32,
                hwDslamNtvUserIndex
                    Integer32,
                hwDslamNtvUserMatchPara
                    Integer32,
                hwDslamNtvUserMaxBandWidth
                    Unsigned32,
                hwDslamNtvUserQuickLeaveTime
                    Integer32,
                hwDslamNtvUserVideoVpi
                    Integer32,   
                hwDslamNtvUserVideoVci
                    Integer32,  
                hwDslamNtvUserVideoFlowType
                    INTEGER,          
                hwDslamNtvUserVideoFlowPara      
                    Integer32,
                hwDslamNtvUserQuickLeaveMode
                    INTEGER,                                               
                hwDslamNtvReceiveGlobalLeave
                    INTEGER,
                hwDslamNtvUserFlowMode
                    INTEGER,
                hwDslamNtvUserFlowID
                    Integer32,
                hwDslamNtvUserVideoFlowID
                    Integer32,
                hwDslamNtvUserVideoTagMode
                    INTEGER,
                hwDslamNtvUserVideoTagPara
                    Integer32,
                hwDslamNtvUserAncpVideoBandwidth
                    Integer32,
                hwDslamNtvUserAncpMcastBandwidth
                    Integer32,
                hwDslamNtvUserMatchPara2
                    Integer32,
                hwDslamNtvUserIgmpVersion
                    INTEGER,
                hwDslamNtvUserCurrentMldVersion
                    INTEGER,
                hwDslamNtvUserMldQueryVersion
                    INTEGER
                }
             
        hwDslamNtvUserAuthority        OBJECT-TYPE
            SYNTAX  INTEGER
                {
                auth(1),
                noauth(2),
		invalid(-1)
                }           
            MAX-ACCESS  read-create
            STATUS      current
            DESCRIPTION
                "Indicates the user authentication attribute. 
                 Options: 
                 1. auth(1)     -indicates the user authentication attribute is auth
                 2. noauth(2)   -indicates the user authentication attribute is noauth,
                                 the user has authority to watch all programs.
                 3. invalid(-1) -indicates the user authentication attribute is invalid
                 Default: noauth(2)
                "
            ::= { hwDslamNtvUserEntry 1}
                  
        hwDslamNtvUserRightProfile        OBJECT-TYPE
            SYNTAX       Integer32 (1..1024)
            MAX-ACCESS   read-create
            STATUS       current
            DESCRIPTION
                "Right profile.
                 The index of user right profile.When user select the right profile,
                 it can watch the program in the right profile only.
                "
            ::= { hwDslamNtvUserEntry 2}
        
        hwDslamNtvUserRowStatus      OBJECT-TYPE
            SYNTAX       RowStatus
            MAX-ACCESS   read-create
            STATUS       current
            DESCRIPTION
                "Row status, used to query, create, modify, and delete a multicast user. 
                 It supports the active(1), createAndGo(4), and destroy(6) operations.
                 During query, the value of this leaf is always active(1).
                 During deletion, specify the value of this leaf to destroy(6).
                 During creation, specify the value of this leaf to createAndGo(4).
                 To modify the parameters of a multicast user, this leaf need not be issued together.
                 Options:
                 1. active(1)      -indicates the query operation
                 2. createAndGo(4) -indicates the creating operation
                 3. destroy(6)     -indicates the deleting operation
                "
            ::= { hwDslamNtvUserEntry 3}
        
        hwDslamNtvUserOperStatus    OBJECT-TYPE
            SYNTAX INTEGER
                {
                online(1),
                offline(2),
                block(3)
                }  
            MAX-ACCESS   read-only
            STATUS       current
            DESCRIPTION
                "Indicates the current running status of a multicast user. This leaf supports only the query operation. 
                 When hwDslamNtvUserAdminStatus is block(1), this leaf must be block(3); when hwDslamNtvUserAdminStatus 
                 is unblock(2) and a user is watching a program, this leaf is online(1); when hwDslamNtvUserAdminStatus 
                 is unblock(2) and no user is watching programs, this leaf is offline(2). Options of hwDslamNtvUserOperStatus:
                 Options: 
                 1. online(1)  -indicates a user is watching program
                 2. offline(2) -indicates no user is watching program
                 3. block(3)   -indicates the leaf hwDslamNtvUserAdminStatus is block(1)
                "
            ::= { hwDslamNtvUserEntry 4}
        
        hwDslamNtvUserAdminStatus     OBJECT-TYPE
            SYNTAX INTEGER
                {
                block(1),
                unblock(2)
                }
            MAX-ACCESS  read-create
            STATUS      current
            DESCRIPTION
                "Indicates the management status of a multicast user. It is used to set whether allow a user to watch programs. 
                 Options: 
                 1. block(1)   -indicates a user can watch program
                 2. unblock(2) -indicates a user can watch program
                 Default: unblock(2). 
                "
            ::= { hwDslamNtvUserEntry 5}
        
        hwDslamNtvUserMaxChannel        OBJECT-TYPE
            SYNTAX      Integer32 (1..255)
            MAX-ACCESS  read-create
            STATUS      current
            DESCRIPTION
                "Indicates the maximum number of concurrent channels that can be watched by a user. 
                 Range: 1-255 
                 Default: 8
                "
            DEFVAL { 8 }
            ::= { hwDslamNtvUserEntry 6}
           
        hwDslamNtvUserWatchingChannel1        OBJECT-TYPE
            SYNTAX BITS
                {
                channel1(0),
                channel2(1),
                channel3(2),
                channel4(3),
                channel5(4),
                channel6(5),
                channel7(6),
                channel8(7),
                channel9(8),
                channel10(9),
                channel11(10),
                channel12(11),
                channel13(12),
                channel14(13),
                channel15(14),
                channel16(15),
                channel17(16),
                channel18(17),
                channel19(18),
                channel20(19),
                channel21(20),
                channel22(21),
                channel23(22),
                channel24(23),
                channel25(24),
                channel26(25),
                channel27(26),
                channel28(27),
                channel29(28),
                channel30(29),
                channel31(30),
                channel32(31),
                channel33(32),
                channel34(33),
                channel35(34),
                channel36(35),
                channel37(36),
                channel38(37),
                channel39(38),
                channel40(39),
                channel41(40),
                channel42(41),
                channel43(42),
                channel44(43),
                channel45(44),
                channel46(45),
                channel47(46),
                channel48(47),
                channel49(48),
                channel50(49),
                channel51(50),
                channel52(51),
                channel53(52),
                channel54(53),
                channel55(54),
                channel56(55),
                channel57(56),
                channel58(57),
                channel59(58),
                channel60(59),
                channel61(60),
                channel62(61),
                channel63(62),
                channel64(63),
                channel65(64),
                channel66(65),
                channel67(66),
                channel68(67),
                channel69(68),
                channel70(69),
                channel71(70),
                channel72(71),
                channel73(72),
                channel74(73),
                channel75(74),
                channel76(75),
                channel77(76),
                channel78(77),
                channel79(78),
                channel80(79),
                channel81(80),
                channel82(81),
                channel83(82),
                channel84(83),
                channel85(84),
                channel86(85),
                channel87(86),
                channel88(87),
                channel89(88),
                channel90(89),
                channel91(90),
                channel92(91),
                channel93(92),
                channel94(93),
                channel95(94),
                channel96(95),
                channel97(96),
                channel98(97),
                channel99(98),
                channel100(99),
                channel101(100),
                channel102(101),
                channel103(102),
                channel104(103),
                channel105(104),
                channel106(105),
                channel107(106),
                channel108(107),
                channel109(108),
                channel110(109),
                channel111(110),
                channel112(111),
                channel113(112),
                channel114(113),
                channel115(114),
                channel116(115),
                channel117(116),
                channel118(117),
                channel119(118),
                channel120(119),
                channel121(120),
                channel122(121),
                channel123(122),
                channel124(123),
                channel125(124),
                channel126(125),
                channel127(126),
                channel128(127)                       
                }           
            MAX-ACCESS   read-only
            STATUS       current
            DESCRIPTION
                "User watching channel.
                 The channels that a user is watching.
                "
            ::= { hwDslamNtvUserEntry 7}   
        
        hwDslamNtvUserWatchingChannel2        OBJECT-TYPE
            SYNTAX   BITS
                {
                channel129(0),
                channel130(1),
                channel131(2),
                channel132(3),
                channel133(4),
                channel134(5),
                channel135(6),
                channel136(7),
                channel137(8),
                channel138(9),
                channel139(10),
                channel140(11),
                channel141(12),
                channel142(13),
                channel143(14),
                channel144(15),
                channel145(16),
                channel146(17),
                channel147(18),
                channel148(19),
                channel149(20),
                channel150(21),
                channel151(22),
                channel152(23),
                channel153(24),
                channel154(25),
                channel155(26),
                channel156(27),
                channel157(28),
                channel158(29),
                channel159(30),
                channel160(31),
                channel161(32),
                channel162(33),
                channel163(34),
                channel164(35),
                channel165(36),
                channel166(37),
                channel167(38),
                channel168(39),
                channel169(40),
                channel170(41),
                channel171(42),
                channel172(43),
                channel173(44),
                channel174(45),
                channel175(46),
                channel176(47),
                channel177(48),
                channel178(49),
                channel179(50),
                channel180(51),
                channel181(52),
                channel182(53),
                channel183(54),
                channel184(55),
                channel185(56),
                channel186(57),
                channel187(58),
                channel188(59),
                channel189(60),
                channel190(61),
                channel191(62),
                channel192(63),
                channel193(64),
                channel194(65),
                channel195(66),
                channel196(67),
                channel197(68),
                channel198(69),
                channel199(70),
                channel200(71),
                channel201(72),
                channel202(73),
                channel203(74),
                channel204(75),
                channel205(76),
                channel206(77),
                channel207(78),
                channel208(79),
                channel209(80),
                channel210(81),
                channel211(82),
                channel212(83),
                channel213(84),
                channel214(85),
                channel215(86),
                channel216(87),
                channel217(88),
                channel218(89),
                channel219(90),
                channel220(91),
                channel221(92),
                channel222(93),
                channel223(94),
                channel224(95),
                channel225(96),
                channel226(97),
                channel227(98),
                channel228(99),
                channel229(100),
                channel230(101),
                channel231(102),
                channel232(103),
                channel233(104),
                channel234(105),
                channel235(106),
                channel236(107),
                channel237(108),
                channel238(109),
                channel239(110),
                channel240(111),
                channel241(112),
                channel242(113),
                channel243(114),
                channel244(115),
                channel245(116),
                channel246(117),
                channel247(118),
                channel248(119),
                channel249(120),
                channel250(121),
                channel251(122),
                channel252(123),
                channel253(124),
                channel254(125),
                channel255(126),
                channel256(127)
                }
            MAX-ACCESS   read-only
            STATUS       current
            DESCRIPTION
                "User watching channel.
                 The channels that a user is watching.
                "
            ::= { hwDslamNtvUserEntry 8}                  
        
        hwDslamNtvUserEnableLog OBJECT-TYPE
            SYNTAX TruthValue                
            MAX-ACCESS read-create
            STATUS current
            DESCRIPTION
                "Indicates the log switch. Options:
                 Options:
                 1. true(1)  -indicates the log switch is on
                 2. false(2) -indicates the log switch is off
                 Default: true(1)
                "
            DEFVAL { 1 }
            ::= { hwDslamNtvUserEntry 9 }
        
        hwDslamNtvUserVpi OBJECT-TYPE
            SYNTAX Integer32
            MAX-ACCESS read-create
            STATUS current
            DESCRIPTION
                "Indicates the VPI of the PVC carrying IGMP packets. This leaf 
                 and the VCI leaf together identify an xDSL user. The value range 
                 is determined by the xDSL line specifications. In a none-ATM type, 
                 the returned value for hwDslamNtvUserVpi is -1.
                "
            ::= { hwDslamNtvUserEntry 10 }

        hwDslamNtvUserVci OBJECT-TYPE
            SYNTAX Integer32
            MAX-ACCESS read-create
            STATUS current
            DESCRIPTION
                "Indicates the VCI of the PVC carrying IGMP packets. This leaf and 
                 the VPI leaf together identify an xDSL user. The value range is 
                 determined by the xDSL line specifications. In a none-ATM type, 
                 the returned value for hwDslamNtvUserVci is -1.
                "
            ::= { hwDslamNtvUserEntry 11 }

        hwDslamNtvUserVlan OBJECT-TYPE
            SYNTAX Integer32
            MAX-ACCESS read-create
            STATUS current
            DESCRIPTION
                "The VLAN which carries IGMP messages.
                "
            ::= { hwDslamNtvUserEntry 12 }
            
        hwDslamNtvUserFlowType OBJECT-TYPE
            SYNTAX INTEGER
                {
                byUserVlan(1),
                byEncap(2),
                by8021p(3),
                byUserVlanEtherType(4),
                otherType(255),
                singleFlow(-1)
                }
            MAX-ACCESS read-write
            STATUS current
            DESCRIPTION
                "Indicates the traffic stream type. If this leaf is not issued, it indicates the single-service traffic.
                 Options:
                 1. byUserVlan(1)          -indicates the traffic stream type is byUserVlan
                 2. byEncap(2)             -indicates the traffic stream type is byEncap
                 3. by8021p(3)             -indicates the traffic stream type is by8021p
                 4. byUserVlanEtherType(4) -indicates the traffic stream type is byUserVlanEtherType
                 5. otherType(255)         -indicates the traffic stream type is otherType
                 6. singleFlow(-1)         -indicates the traffic stream type is singleFlow
                "
            DEFVAL { 1 }
            ::= { hwDslamNtvUserEntry 17 }
    
        hwDslamNtvUserFlowPara OBJECT-TYPE
            SYNTAX Integer32
            MAX-ACCESS read-write
            STATUS current
            DESCRIPTION
                "Specifies the parameter value of the flow type. The parameter value varies with the flow type. In detail:
                 1. If the flow type is byUserVlan (1), the range of this parameter is 1-4095. If the flow type is untagged, 
                 this parameter is -1.
                 2. If the flow type is byEncap (2), the options of this parameter are ipv4oe(0), ipoe(1), pppoe(2) and ipv6oe(3).
                 3. If the flow type is by8021p (3), the range of this parameter is 0-7.
                 4. If the flow type is byUserVlanEtherType(4), the flow parameter is a combination of the EtherType and the user VLAN. 
                 5. If the flow type is otherType(255), the flow parameter is an invalid value, and this parameter is -1. 
                 The EtherType can be ipoe(1) or pppoe(2), and the user VLAN is in the range of 1-4095, 0 (priority-tagged), 
                 and untagged(-1). For the service flow of the byUserVlanEtherType(4) type, this leaf supports only reading, 
                 and does not support creation.                
                "
            DEFVAL { 1 }
            ::= { hwDslamNtvUserEntry 18 }
                 
        hwDslamNtvUserMode    OBJECT-TYPE
            SYNTAX INTEGER
                {
                snooping(0),
                discard(1),
                forwarding(2)
                }
            MAX-ACCESS    read-write
            STATUS        current
            DESCRIPTION
                "The status of the user port mode.
                 Options:
                 1. snooping(0)    -indicates the user port mode is snooping
                 2. discard(1)     -indicates the user port mode is discard
                 3. forwarding(2)  -indicates the user port mode is forwarding
                "
            ::= { hwDslamNtvUserEntry 19 }
            
        hwDslamNtvUserAuthFailProcess    OBJECT-TYPE
            SYNTAX INTEGER
                {
                discard(0),
                forward(1)
                }
            MAX-ACCESS    read-write
            STATUS        current
            DESCRIPTION
                "The process mode for the user when his authorization failed.
                 Options:
                 1. discard(0) -indicates process mode is discard
                 2. forward(1) -indicates process mode is forward
                "
            ::= { hwDslamNtvUserEntry 20 }  
            
        hwDslamNtvUserUsedBandwidth OBJECT-TYPE
            SYNTAX Integer32
            MAX-ACCESS read-only
            STATUS current
            DESCRIPTION
               "Indicates the used bandwidth of a user. When bandwidth management is disabled, 
               	the returned value for hwDslamNtvUserUsedBandwidth is -1.
                Unit: kbit/s.
               "
            ::= { hwDslamNtvUserEntry 21 }
                                                
        hwDslamNtvUserUsdBwthPcntToPortRate OBJECT-TYPE
            SYNTAX Integer32
            MAX-ACCESS read-only
            STATUS current
            DESCRIPTION
                "Indicates the percentage of the used bandwidth to the bandwidth allocated to the igmp user.
                 When bandwidth management is disabled or the bandwidth is not limited, the returned value 
                 for hwDslamNtvUserUsdBwthPcntToPortRate is -1.
                "
            ::= { hwDslamNtvUserEntry 22 }            

        hwDslamNtvUserIfIndex OBJECT-TYPE
            SYNTAX Integer32
            MAX-ACCESS read-write
            STATUS current
            DESCRIPTION
                "Indicates the port index, corresponding to the shelf ID and slot ID of the port. 
                 Its value and algorithm are the same as those of ifIndex.
                "
            ::= { hwDslamNtvUserEntry 23 }    

        hwDslamNtvUserIndex OBJECT-TYPE
            SYNTAX Integer32
            MAX-ACCESS read-only
            STATUS current
            DESCRIPTION
                "Indicates the unique index of a multicast user.
                 You can also fill -1 and the system will automatically allocate an index.
                "
            ::= { hwDslamNtvUserEntry 24 }    

        hwDslamNtvUserMatchPara OBJECT-TYPE
            SYNTAX Integer32
            MAX-ACCESS read-write
            STATUS current
            DESCRIPTION
                "Supported by only GPON and EPON. For an EPON port or a GPON port in the profile mode, 
                 it indicates ontid; for a GPON port in the non-profile mode, it indicates gemportid. 
                 The range is determined by the line specifications. In a none-xPON type, the returned 
                 value for hwDslamNtvUserMatchPara is -1.
                "
            ::= { hwDslamNtvUserEntry 25 }    
        
        hwDslamNtvUserMaxBandWidth OBJECT-TYPE
            SYNTAX Unsigned32
            MAX-ACCESS read-write
            STATUS current
            DESCRIPTION
                "Indicates the maximum multicast bandwidth. 
                 Range: 0-4294967295  
                 Unit: kbit/s 
                 Default: noLimit(4294967295)
                "
            ::= { hwDslamNtvUserEntry 26 }
                 
        hwDslamNtvUserQuickLeaveTime  OBJECT-TYPE
            SYNTAX       Integer32 (0..20)
            UNITS        "0.1s"
            MAX-ACCESS read-write
            STATUS current
            DESCRIPTION
                "The aging time of user in quick leave.
                 UNIT: 0.1s
                "
            ::= { hwDslamNtvUserEntry 30 }   
            
       hwDslamNtvUserVideoVpi OBJECT-TYPE
            SYNTAX Integer32
            MAX-ACCESS read-create
            STATUS current
            DESCRIPTION
                "Indicates the VPI of the traffic stream carrying the multicast video service. 
                 The range is determined by the xDSL line specifications. In a none-ATM type, 
                 the returned value for hwDslamNtvUserVideoVpi is -1.
                "
            ::= { hwDslamNtvUserEntry 31 }

        hwDslamNtvUserVideoVci OBJECT-TYPE
            SYNTAX Integer32
            MAX-ACCESS read-create
            STATUS current
            DESCRIPTION
                "Indicates the VCI of the traffic stream carrying the multicast video service. 
                 The range is determined by the xDSL line specifications. In a none-ATM type, 
                 the returned value for hwDslamNtvUserVideoVci is -1.
                "
            ::= { hwDslamNtvUserEntry 32 }
        
        hwDslamNtvUserVideoFlowType OBJECT-TYPE
            SYNTAX INTEGER
                {
                byUserVlan(1),
                byEncap(2),
                by8021p(3),
                byUserVlanEtherType(4),
                invalid(-1)
                }
            MAX-ACCESS read-write
            STATUS current
            DESCRIPTION
                "Indicates the flow type of the multicast video stream. 
                 If this leaf is not issued, it indicates the single-service traffic. 
                 Options:
                 1. byUserVlan(1)          -indicates the flow type of the multicast video stream is byUserVlan
                 2. byEncap(2)             -indicates the flow type of the multicast video stream is byEncap
                 3. by8021p(3)             -indicates the flow type of the multicast video stream is by8021p
                 4. byUserVlanEtherType(4) -indicates the flow type of the multicast video stream is byUserVlanEtherType
                 5. invalid(-1)            -indicates the flow type of the multicast video stream is invalid                                                                                                 
                "
            DEFVAL { 1 }
            ::= { hwDslamNtvUserEntry 33 }
    
        hwDslamNtvUserVideoFlowPara OBJECT-TYPE
            SYNTAX Integer32
            MAX-ACCESS read-write
            STATUS current
            DESCRIPTION
                "Specifies the parameter value of the flow carrying the multicast video service. 
                 The parameter value varies with the flow type. In detail:
                 1. If the flow type is byUserVlan (1), the range of this parameter is 1-4095. 
                 If the flow type is untagged, this parameter is -1.
                 2. If the flow type is byEncap (2), the options of this parameter are ipv4oe(0), ipoe(1), pppoe(2) and ipv6oe(3).
                 3. If the flow type is by8021p (3), the range of this parameter is 0-7.
                 4. If the flow type is byUserVlanEtherType(4), the flow parameter is a combination 
                 of the EtherType and the user VLAN. The EtherType can be ipoe(1) or pppoe(2), 
                 and the user VLAN is in the range of 1-4095, 0 (priority-tagged), and untagged(-1). 
                 For the service flow of the byUserVlanEtherType(4) type, this leaf supports only reading, 
                 and does not support creation.
                "
            DEFVAL { 1 }
            ::= { hwDslamNtvUserEntry 34 }    
            
        hwDslamNtvUserQuickLeaveMode OBJECT-TYPE
            SYNTAX INTEGER
                {
                immediate(1),
                macBased(2),
                disable(3)
                }
            MAX-ACCESS read-write
            STATUS current
            DESCRIPTION
                "Indicates the quick leave attribute of a user. Options:
                 1. immediate(1) -indicates the quick leave attribute of a user is immediate
                 2. macBased(2)  -indicates the quick leave attribute of a user is macBased
                 3. disable(3)   -indicates the quick leave attribute of a user is disable
                 In the OAM dynamic mode, the default value is disable(3); in other modes, 
                 the default value is macBased(2).
                "           
            ::= { hwDslamNtvUserEntry 35 }    
            
        hwDslamNtvReceiveGlobalLeave OBJECT-TYPE
            SYNTAX INTEGER{enable(1),disable(2)}
            MAX-ACCESS read-write
            STATUS current
            DESCRIPTION
                "Indicates the switch of whether to receive the global leave packet sent from the user side.
                 Options:
                 1. enable(1)  -indicates receive the global leave packet sent from the user side
                 2. disable(2) -indicates not receive the global leave packet sent from the user side
                 Default: disable(2). 
                "
            ::= { hwDslamNtvUserEntry 36 }               
                 
        hwDslamNtvUserFlowMode OBJECT-TYPE
            SYNTAX      INTEGER{ptm(1),atm(2),invalid(-1)}           
            MAX-ACCESS  read-write
            STATUS      current
            DESCRIPTION
                "Indicates the xDSL mode. The traffic stream on a non-xDSL board need not be issued with this leaf. 
                 Options:
                 1. ptm(1) -indicates the xDSL mode is ptm
                 2. atm(2) -indicates the xDSL mode is atm
                 3. invalid(-1) -indicates invalid xDSL mode 
                "
            ::= { hwDslamNtvUserEntry 37 }                                                          
    
        hwDslamNtvUserFlowID OBJECT-TYPE
            SYNTAX      Integer32
            MAX-ACCESS  read-create
            STATUS      current
            DESCRIPTION
                "Indicates the ID of the flow carrying the user IGMP protocol.
                "
            ::= { hwDslamNtvUserEntry 38 }
            
        hwDslamNtvUserVideoFlowID OBJECT-TYPE
            SYNTAX      Integer32
            MAX-ACCESS  read-create
            STATUS      current
            DESCRIPTION
                "Indicates the ID of the flow carrying the multicast video service. 
                "
            ::= { hwDslamNtvUserEntry 39 }
            
        hwDslamNtvUserVideoTagMode OBJECT-TYPE
            SYNTAX INTEGER
                {
                untagged(1),
                mvlan(2),
                vlan(3),
                withProgramVlan(4),
                invalid(-1)
                }           
            MAX-ACCESS  read-write
            STATUS      current
            DESCRIPTION
                "Indicates the video tag mode. 
                 Options:
                 1. untagged(1)        -indicates the video tag mode is untagged
                 2. mvlan(2)           -indicates the video tag mode is mvlan
                 3. vlan(3)            -indicates the video tag mode is vlan
                 4. withProgramVlan(4) -indicates the video tag mode is withProgramVlan
                 5. invalid(-1)        -indicates the video tag mode is invalid
                "
            DEFVAL { 1 }
            ::= { hwDslamNtvUserEntry 40 }  
                     
        hwDslamNtvUserVideoTagPara OBJECT-TYPE
            SYNTAX      Integer32           
            MAX-ACCESS  read-write
            STATUS      current
            DESCRIPTION
                 "Indicates video tag parameter.
                 "
            ::= { hwDslamNtvUserEntry 41 }  
        
        hwDslamNtvUserAncpVideoBandwidth OBJECT-TYPE
            SYNTAX      Integer32  
            UNITS       "kbps"         
            MAX-ACCESS  read-only
            STATUS      current
            DESCRIPTION
                "Indicates the total video bandwidth allocated by the ANCP server.
                 When ANCP CAC is disabled or the board does not support ANCP CAC, 
                 the returned value for hwDslamNtvUserAncpVideoBandwidth is -1.
                 Unit: kbit/s.
                "
            ::= { hwDslamNtvUserEntry 42 }  
        
        hwDslamNtvUserAncpMcastBandwidth OBJECT-TYPE
            SYNTAX      Integer32   
            UNITS       "kbps"        
            MAX-ACCESS  read-only
            STATUS      current
            DESCRIPTION
                 "Indicates the multicast bandwidth allocated by the ANCP server.
                  When ANCP CAC is disabled or the board does not support ANCP CAC, 
                  the returned value for hwDslamNtvUserAncpMcastBandwidth is -1.
                  Unit: kbit/s.
                 "
            ::= { hwDslamNtvUserEntry 43 }  
                    
        hwDslamNtvUserMatchPara2 OBJECT-TYPE
            SYNTAX Integer32
            MAX-ACCESS read-only
            STATUS current
            DESCRIPTION
                "Indicates the gemindex of a GPON port in the profile mode of a GPON board. 
                 This leaf need not be issued for a non-GPON board or in the GPON non-profile mode.
                 When the GPON mode is profile mode and the service board is a GPON board, the returned 
                 value for hwDslamNtvUserMatchPara2 is gemindex. Otherwise, the returned value is -1.
                "
            ::= { hwDslamNtvUserEntry 44 }    
            
        hwDslamNtvUserIgmpVersion OBJECT-TYPE
            SYNTAX INTEGER
                {
                v2(1),
                v3(2),
                v3Forced(3)
                }           
            MAX-ACCESS  read-write
            STATUS      current
            DESCRIPTION
                "Indicates the querier IGMP version of user . 
                 Options:
                 1. v2(1)       -indicates the querier IGMP version of user is v2.
                 2. v3(2)       -indicates the querier IGMP version of user is v3.
                 3. v3Forced(3) -indicates the querier IGMP version of user is v3Forced, which forced the query message version is v3.
                "
            DEFVAL { 2 }
            ::= { hwDslamNtvUserEntry 45 }    

        hwDslamNtvUserCurrentMldVersion OBJECT-TYPE
            SYNTAX INTEGER
                {
                v1(1),
                v2(2),
                invalid(-1)
                }           
            MAX-ACCESS  read-only
            STATUS      current
            DESCRIPTION
                "Indicates the querier MLD version of user . 
                 Options:
                 1. v1(1)       -indicates the current MLD version of user is v1.
                 2. v2(2)       -indicates the current MLD version of user is v2.
                 3. invalid(-1) -indicates the current MLD version of user is invalid.
                "
            ::= { hwDslamNtvUserEntry 46 }  
            
        hwDslamNtvUserMldQueryVersion OBJECT-TYPE
            SYNTAX INTEGER
                {
                v2(1),
                v2Special(2),
                invalid(-1)
                }           
            MAX-ACCESS  read-write
            STATUS      current
            DESCRIPTION
                "Indicates the querier MLD version of user . 
                 Options:
                 1. v2(1)              -indicates the querier MLD version of user is v2.
                 2. v2Special(2)       -indicates a version of query packet is determined by the version of the host.
                 3. invalid(-1)        -indicates the querier MLD version of user is invalid.
                "
            DEFVAL { 2 }
            ::= { hwDslamNtvUserEntry 47 }    
  
            
        hwDslamNtvChannelTable    OBJECT-TYPE
            SYNTAX             SEQUENCE OF HwDslamNtvChannelEntry
            MAX-ACCESS         not-accessible
            STATUS             current
            DESCRIPTION
                "Channel management table.
                 The index of this table is hwDslamNtvChannelIndex.
                "
            ::= { hwDslamNtv 17 }
        
        hwDslamNtvChannelEntry    OBJECT-TYPE
            SYNTAX         HwDslamNtvChannelEntry
            MAX-ACCESS         not-accessible
            STATUS         current
            DESCRIPTION
                "Channel management table.
                 The index of this entry is hwDslamNtvChannelIndex.
                "
            INDEX   
                { 
                hwDslamNtvChannelIndex
                }
            ::= { hwDslamNtvChannelTable  1 }

        HwDslamNtvChannelEntry    ::= 
            SEQUENCE  
                {
                hwDslamNtvChannelIndex    
                    Integer32,
                hwDslamNtvChannelFrame     
                    Integer32,
                hwDslamNtvChannelSlot    
                    Integer32,
                hwDslamNtvChannelPort      
                    Integer32,
                hwDslamNtvProgramIPAddr   
                    IpAddress,
                hwDslamNtvChannelType      
                    INTEGER,
                hwDslamNtvChannelRowStatus 
                    RowStatus,
                hwDslamNtvChannelAttrib   
                    INTEGER,
                hwDslamNtvChannelUserCount 
                    Integer32
                }
        
        hwDslamNtvChannelIndex        OBJECT-TYPE
            SYNTAX       Integer32(1..256)
            MAX-ACCESS   read-only
            STATUS       current
            DESCRIPTION
                "
                Channel index.
                "
            ::= { hwDslamNtvChannelEntry 1}
        
        hwDslamNtvChannelFrame        OBJECT-TYPE
            SYNTAX       Integer32 (0..255)
            MAX-ACCESS   read-create
            STATUS       current
            DESCRIPTION
                "Channel frame.
                 The frame ID of channel that indicates which frame the channel is on.
                "       
            ::= { hwDslamNtvChannelEntry 2}
        
        hwDslamNtvChannelSlot        OBJECT-TYPE
            SYNTAX       Integer32 (0..255)
            MAX-ACCESS   read-create
            STATUS       current
            DESCRIPTION
                "Channel slot.
                 The slot ID of channel that indicates which slot the channel is on.
                "
            ::= { hwDslamNtvChannelEntry 3}        
        
        hwDslamNtvChannelPort        OBJECT-TYPE
            SYNTAX       Integer32 (0..255)
            MAX-ACCESS   read-create
            STATUS       current
            DESCRIPTION
                "Channel port.
                 The port ID of channel that indicates which port the channel is on.
                "
            ::= { hwDslamNtvChannelEntry 4}        
        
        hwDslamNtvProgramIPAddr         OBJECT-TYPE
            SYNTAX       IpAddress
            MAX-ACCESS   read-create
            STATUS       current
            DESCRIPTION
                "Program IP address.
                 This address is the same as hwDslamNtvProgramIP in hwDslamNtvProgramTable.
                "
            ::= { hwDslamNtvChannelEntry 5}
        
        hwDslamNtvChannelType        OBJECT-TYPE
            SYNTAX       INTEGER
                         {
                             contral(1),
                             service(2)
                         }
            MAX-ACCESS   read-create
            STATUS       current
            DESCRIPTION
                "Channel type.
                 Options:
                 1. contral(1) -indicates the channel type is contral
                 2. service(2) -indicates the channel type is service
                "
            ::= { hwDslamNtvChannelEntry 6}    
        
        hwDslamNtvChannelRowStatus        OBJECT-TYPE
            SYNTAX       RowStatus
            MAX-ACCESS   read-create
            STATUS       current
            DESCRIPTION
                "Row status.
                 Add or delete a table item.
                 Options:
                 1. active(1)      -indicates the query operation
                 2. createAndGo(4) -indicates the adding operation
                 3. destroy(6)     -indicates the deleting operation
                "
            ::= { hwDslamNtvChannelEntry 7}
        
        hwDslamNtvChannelAttrib        OBJECT-TYPE
            SYNTAX   INTEGER
                {
                free(1),
                used(2)
                }
            MAX-ACCESS   read-only
            STATUS   current
            DESCRIPTION
                "Channel state.
                 The state of channel being used.If the user count is 0,t he value of the node is free(1).
                 If the user count isn't 0, the value of the node is used(2).
                 Options:
                 1. free(1) -indicates the channel is not used
                 2. used(2) -indicates the channel is being used
                "
            ::= { hwDslamNtvChannelEntry 8}
        
        hwDslamNtvChannelUserCount        OBJECT-TYPE
            SYNTAX       Integer32
            MAX-ACCESS   read-only
            STATUS       current
            DESCRIPTION
                "User Count.
                 Number of the users who are watching the channel.
                "
            ::= { hwDslamNtvChannelEntry 9}
        
        hwDslamNtvProgramTable    OBJECT-TYPE
            SYNTAX          SEQUENCE OF HwDslamNtvProgramEntry
            MAX-ACCESS      not-accessible
            STATUS          current
            DESCRIPTION
                "Indicates the multicast program table.
                 The index of this table is hwDslamNtvProgramIndex.
                "
            ::= { hwDslamNtv 18 }
        
        hwDslamNtvProgramEntry    OBJECT-TYPE
            SYNTAX          HwDslamNtvProgramEntry
            MAX-ACCESS      not-accessible
            STATUS          current
            DESCRIPTION
                "Indicates the multicast program table.
                 The index of this entry is hwDslamNtvProgramIndex.
                "
            INDEX 
                { 
                hwDslamNtvProgramIndex
                }
            ::= { hwDslamNtvProgramTable  1 }

        HwDslamNtvProgramEntry    ::= 
            SEQUENCE  
                {
                hwDslamNtvProgramIndex         
                    Integer32,
                hwDslamNtvProgramIP            
                    IpAddress,
                hwDslamNtvProgramRowStatus    
                    RowStatus,
                hwDslamNtvProgramName        
                    OCTET STRING,
                hwDslamNtvProfileMask         
                    BITS,   
                hwDslamNtvProgramUserCount     
                    Integer32,
                hwDslamNtvProgramUpport        
                    InterfaceIndex, 
                hwDslamNtvProgramUpportVlan    
                    Integer32, 
                hwDslamNtvProgramHostFun       
                    TruthValue,  
                hwDslamNtvProgramPrejoin      
                    TruthValue,
                hwDslamNtvProgramWatchingPortList1 
                    PortList,
                hwDslamNtvProgramWatchingPortList2 
                    PortList,
                hwDslamNtvProgramSourceIP          
                    IpAddress,
                hwDslamNtvProgramLogAttr           
                    TruthValue,
                hwDslamNtvProgramAcrossVlan     
                    TruthValue,
                hwDslamNtvProgramUnsolicited   
                    TruthValue,
                hwDslamNtvProgramBandWidth     
                    Integer32,
                hwDslamNtvProgramWatchingCount  
                    Integer32,
                hwDslamNtvProgramIpCascadePortList 
                    Integer32,
                hwDslamNtvProgramPreviewMaxTime
                    Integer32,
                hwDslamNtvProgramPreviewInterval
                    Integer32,
                hwDslamNtvProgramPreviewCount  
                    Integer32,
                hwDslamNtvProgramPriority      
                    Integer32,
                hwDslamNtvProgramHostIP        
                    IpAddress,
                hwDslamNtvProgramLastReporterIP 
                    IpAddress,
                hwDslamNtvProgramFoundElapse   
                    OCTET STRING,
                hwDslamNtvProgramExpireTime   
                    OCTET STRING,
                hwDslamNtvProgramBTVUserPortList
                    OCTET STRING,
                hwDslamNtvPreviewProfileID  
                    Integer32,
                hwDslamNtvProgramGrade      
                    Integer32 (0..255),
                hwDslamNtvProgramNewIpCascadePortList 
                    OCTET STRING,
                hwDslamNtvProgramMAC          
                    OCTET STRING,
                hwDslamNtvProgramBTVUserPortList2
                    OCTET STRING,
                hwDslamNtvProgramVideoTagVlan      
                    Integer32,
                hwDslamNtvProgramIPv6
                    Ipv6Address,
                hwDslamNtvProgramSourceIPv6
		    Ipv6Address,
		hwDslamNtvProgramBTVUserPortList3
		    OCTET STRING,
		hwDslamNtvProgramBTVUserPortList4
	            OCTET STRING
                }
                                        
        hwDslamNtvProgramIndex        OBJECT-TYPE
            SYNTAX       Integer32 (-1|1..4096)
            MAX-ACCESS   read-only
            STATUS       current
            DESCRIPTION
                "Indicates the index of a program.
                 Range: 1-4096,-1
                 You can also fill -1 and the system will automatically allocate an index.
                "
            ::= { hwDslamNtvProgramEntry 1}   
        
        hwDslamNtvProgramIP        OBJECT-TYPE
            SYNTAX       IpAddress
            MAX-ACCESS   read-create
            STATUS       current
            DESCRIPTION
                "Indicates the IP address of a program, the multicast address.
                "
            ::= { hwDslamNtvProgramEntry 2}
        
        hwDslamNtvProgramRowStatus        OBJECT-TYPE
            SYNTAX       RowStatus
            MAX-ACCESS   read-create
            STATUS       current
            DESCRIPTION
                "Row status, used to query, create, modify, and delete a multicast program. 
                 It supports the active(1), createAndGo(4), and destroy(6) operations.
                 During query, the value of this leaf is always active(1).
                 During deletion, specify the value of this leaf to destroy(6).
                 During creation, specify the value of this leaf to createAndGo(4).
                 To modify the parameters of a multicast program, this leaf need not be issued together.
                 Options:
                 1. active(1)      -indicates the query operation
                 2. createAndGo(4) -indicates the creating operation
                 3. destroy(6)     -indicates the deleting operation
                "
            ::= { hwDslamNtvProgramEntry 3}
        
        hwDslamNtvProgramName        OBJECT-TYPE
            SYNTAX       OCTET STRING (SIZE (1..16))
            MAX-ACCESS   read-create
            STATUS       current
            DESCRIPTION
                "Indicates the program name. Range: 1-16
                 It must be printable ASCII characters. 
                 Chinese characters are not supported. The name of a program must be unique. 
                 By default it is program-n. n indicates the index of the program. For example, 
                 the name of a program with the index of 4 is program-4.
                "
            ::= { hwDslamNtvProgramEntry 4}
        
        hwDslamNtvProfileMask        OBJECT-TYPE
            SYNTAX   BITS
                {
                profile1(0),
                profile2(1),
                profile3(2),
                profile4(3),
                profile5(4),
                profile6(5),
                profile7(6),
                profile8(7),
                profile9(8),
                profile10(9),
                profile11(10),
                profile12(11),
                profile13(12),
                profile14(13),
                profile15(14),
                profile16(15),
                profile17(16),
                profile18(17),
                profile19(18),
                profile20(19),
                profile21(20),
                profile22(21),
                profile23(22),
                profile24(23),
                profile25(24),
                profile26(25),
                profile27(26),
                profile28(27),
                profile29(28),
                profile30(29),
                profile31(30),
                profile32(31),
                profile33(32),
                profile34(33),
                profile35(34),
                profile36(35),
                profile37(36),
                profile38(37),
                profile39(38),
                profile40(39),
                profile41(40),
                profile42(41),
                profile43(42),
                profile44(43),
                profile45(44),
                profile46(45),
                profile47(46),
                profile48(47),
                profile49(48),
                profile50(49),
                profile51(50),
                profile52(51),
                profile53(52),
                profile54(53),
                profile55(54),
                profile56(55),
                profile57(56),
                profile58(57),
                profile59(58),
                profile60(59),
                profile61(60),
                profile62(61),
                profile63(62),
                profile64(63),
                profile65(64),
                profile66(65),
                profile67(66),
                profile68(67),
                profile69(68),
                profile70(69),
                profile71(70),
                profile72(71),
                profile73(72),
                profile74(73),
                profile75(74),
                profile76(75),
                profile77(76),
                profile78(77),
                profile79(78),
                profile80(79),
                profile81(80),
                profile82(81),
                profile83(82),
                profile84(83),
                profile85(84),
                profile86(85),
                profile87(86),
                profile88(87),
                profile89(88),
                profile90(89),
                profile91(90),
                profile92(91),
                profile93(92),
                profile94(93),
                profile95(94),
                profile96(95),
                profile97(96),
                profile98(97),
                profile99(98),
                profile100(99),
                profile101(100),
                profile102(101),
                profile103(102),
                profile104(103),
                profile105(104),
                profile106(105),
                profile107(106),
                profile108(107),
                profile109(108),
                profile110(109),
                profile111(110),
                profile112(111),
                profile113(112),
                profile114(113),
                profile115(114),
                profile116(115),
                profile117(116),
                profile118(117),
                profile119(118),
                profile120(119),
                profile121(120),
                profile122(121),
                profile123(122),
                profile124(123),
                profile125(124),
                profile126(125),
                profile127(126),
                profile128(127)                       
                }
            MAX-ACCESS   read-create
            STATUS       current
            DESCRIPTION
                "Right profile mask.
                 Right profile mask of program source. If program is included in the right profile,the mask is 1.
                 If program isn't included in the right profile,the mask is 0.
                "
            ::= { hwDslamNtvProgramEntry 5}
        
        hwDslamNtvProgramUserCount        OBJECT-TYPE
            SYNTAX       Integer32
            MAX-ACCESS   read-only
            STATUS       current
            DESCRIPTION
                "User count.
                 Count of the user which can watch the program. 
                "
            ::= { hwDslamNtvProgramEntry 6}
        
        hwDslamNtvProgramUpport   OBJECT-TYPE
            SYNTAX       InterfaceIndex
            MAX-ACCESS   read-create
            STATUS       current
            DESCRIPTION
                "ifIndex of Slave Up Port.
                "
            ::= { hwDslamNtvProgramEntry 7 }
        
        hwDslamNtvProgramUpportVlan   OBJECT-TYPE
            SYNTAX       Integer32 (1..4093)
            MAX-ACCESS   read-create
            STATUS       current
            DESCRIPTION
                "Indicates the VLAN where the program resides.
                "
            ::= { hwDslamNtvProgramEntry 8 }
        
        hwDslamNtvProgramHostFun     OBJECT-TYPE
            SYNTAX      TruthValue
            MAX-ACCESS  read-create
            STATUS      current
            DESCRIPTION
                "Indicates the host function of a program. 
                 Options:
                 1. true(1)  -indicates the host function of a program is true
                 2. false(2) -indicates the host function of a program is false
                 Default: true(1)
                "
            DEFVAL { 1 }
            ::= { hwDslamNtvProgramEntry 9}   
         
        hwDslamNtvProgramPrejoin     OBJECT-TYPE
            SYNTAX      TruthValue
            MAX-ACCESS  read-create
            STATUS      current
            DESCRIPTION
                "Indicates the pre-join function of a program. 
                 Options:
                 1. true(1)  -indicates the pre-join function of a program is true
                 2. false(2) -indicates the pre-join function of a program is false
                 Default: false(2).
                "
            DEFVAL { 2 }
         ::= { hwDslamNtvProgramEntry 10} 
         
        hwDslamNtvProgramWatchingPortList1 OBJECT-TYPE
            SYNTAX       PortList
            MAX-ACCESS   read-only
            STATUS       current
            DESCRIPTION
                "Port list of slot0 to slot7 who are watching the program.
                "
            ::= { hwDslamNtvProgramEntry 11 }
        
        hwDslamNtvProgramWatchingPortList2 OBJECT-TYPE
            SYNTAX       PortList
            MAX-ACCESS   read-only
            STATUS       current
            DESCRIPTION
                "Port list of slot8 to slot15 who are watching the program.
                "
              ::= { hwDslamNtvProgramEntry 12 }
           
        hwDslamNtvProgramSourceIP        OBJECT-TYPE
            SYNTAX       IpAddress
            MAX-ACCESS   read-create
            STATUS       current
            DESCRIPTION
                "Indicates the IP address of the program source.
                "
            ::= { hwDslamNtvProgramEntry 13}        
        
        hwDslamNtvProgramLogAttr OBJECT-TYPE
            SYNTAX TruthValue
            MAX-ACCESS read-create
            STATUS current
            DESCRIPTION
                "Indicates the log attribute of the program, that is, whether to collect the log statistics about the program.
                 Options:
                 1. true(1)  -indicates to collect the log statistics of the program
                 2. false(2) -indicates not to collect the log statistics of the program
                 Default: true(1)
                "
            DEFVAL { 1 }
            ::= { hwDslamNtvProgramEntry 14 }
        
        hwDslamNtvProgramAcrossVlan OBJECT-TYPE
            SYNTAX TruthValue
            MAX-ACCESS read-create
            STATUS current
            DESCRIPTION
                "Program is transferred by across VLAN.
                 Options:
                 1. true(1)  -indicates the program is transferred across VLAN
                 2. false(2) -indicates the program is not transferred across VLAN
                "
            DEFVAL { 1 }
            ::= { hwDslamNtvProgramEntry 15 }
        
        hwDslamNtvProgramUnsolicited OBJECT-TYPE
            SYNTAX TruthValue
            MAX-ACCESS read-create
            STATUS current
            DESCRIPTION
                "Indicates the active report attribute of a program. 
                 Options:
                 1. true(1)  -indicates the program can report actively
                 2. false(2) -indicates the program cannot report actively
                 Default: false(2)
                "
            DEFVAL { 2 }
            ::= { hwDslamNtvProgramEntry 16 }
        
        hwDslamNtvProgramBandWidth OBJECT-TYPE
            SYNTAX Integer32
            MAX-ACCESS read-create
            STATUS current
            DESCRIPTION
                "Indicates the program bandwidth limit. 
                 Default: 5000
                 Unit: kbit/s
                "
            ::= { hwDslamNtvProgramEntry 17 }
        
        hwDslamNtvProgramWatchingCount OBJECT-TYPE
            SYNTAX Integer32
            MAX-ACCESS read-only
            STATUS current
            DESCRIPTION
                "Indicates the number of users who are watching a program.
                "
            ::= { hwDslamNtvProgramEntry 18 }
        
        hwDslamNtvProgramIpCascadePortList OBJECT-TYPE
            SYNTAX Integer32
            MAX-ACCESS read-only
            STATUS current
            DESCRIPTION
                "IP cascade port list, 16bits. List of the IP cascade port which can watch the program.
                "
            ::= { hwDslamNtvProgramEntry 19 }
               
        hwDslamNtvProgramPreviewMaxTime OBJECT-TYPE
            SYNTAX Integer32 (10..6000)
            UNITS  "second"
            MAX-ACCESS read-write
            STATUS current
            DESCRIPTION
                "The max time of per preview.
                 Unit: second
                "
            DEFVAL { 120 }
                 ::= { hwDslamNtvProgramEntry 20 }
            
        hwDslamNtvProgramPreviewInterval OBJECT-TYPE
            SYNTAX Integer32 (0..7650)
            UNITS  "second"
            MAX-ACCESS read-write
            STATUS current
            DESCRIPTION
                "The interval time of preview the same program.
                 Unit: second
                "
            DEFVAL { 120 }
            ::= { hwDslamNtvProgramEntry 21 }
            
        hwDslamNtvProgramPreviewCount OBJECT-TYPE
            SYNTAX Integer32 (1..255)
            MAX-ACCESS read-write
            STATUS current
            DESCRIPTION
                "The times of preview.
                "
            DEFVAL { 8 }
            ::= { hwDslamNtvProgramEntry 22 }
        
        hwDslamNtvProgramPriority OBJECT-TYPE
            SYNTAX Integer32 (-1|0..7)
            MAX-ACCESS read-write
            STATUS current
            DESCRIPTION
                "Indicates the program priority, Setting priority as -1 is not permitted. 
                 Range: 0-7, -1 
                 Default: 7
                 0xffffffff(-1): Invalid priority
                "
            DEFVAL { 7 }
            ::= { hwDslamNtvProgramEntry 23 }
        
        hwDslamNtvProgramHostIP OBJECT-TYPE
            SYNTAX IpAddress
            MAX-ACCESS read-write
            STATUS current
            DESCRIPTION
                "Indicates the IP address of the host that requests the program.
                "
            ::= { hwDslamNtvProgramEntry 24 }
        
        hwDslamNtvProgramLastReporterIP OBJECT-TYPE
            SYNTAX IpAddress
            MAX-ACCESS read-only
            STATUS current
            DESCRIPTION
                "Indicates the IP address of the host that reports the last IGMP report packet.
                "
            ::= { hwDslamNtvProgramEntry 25 }
        hwDslamNtvProgramFoundElapse OBJECT-TYPE
            SYNTAX OCTET STRING
            MAX-ACCESS read-only
            STATUS current
            DESCRIPTION
                "Indicates the elapse time since the creation of a multicast group, displayed 
                 in ASCII. When it is shorter than a day, its precession is second in the form 
                 of HH:MM:SS. If it is longer than a day, its precision is day, in the form 
                 of n day(s), where, n indicates the number of days.
                "
            ::= { hwDslamNtvProgramEntry 26 }
        
        hwDslamNtvProgramExpireTime OBJECT-TYPE
            SYNTAX OCTET STRING
            MAX-ACCESS read-only
            STATUS current
            DESCRIPTION
                "Indicates the expiration time of the multicast group, displayed in ASCII. 
                 When it is shorter than a day, its precession is second in the form of HH:MM:SS. 
                 If it is longer than a day, its precision is day, in the form of n day(s), 
                 where, n indicates the number of days.
                "
            ::= { hwDslamNtvProgramEntry 27 }
                                     
        hwDslamNtvProgramBTVUserPortList OBJECT-TYPE
            SYNTAX OCTET STRING
            MAX-ACCESS read-only
            STATUS current
            DESCRIPTION
                "Indicates the mask of BTV users that are watching this program. It indicates users 
                 1-4096 and has 512 bytes in total (user indexes of bit0-bit7 are in ascending order). 
                 Each bit indicates whether a BTV user is watching the program.
                 Options: 
                  1. 1 -indicates that the user is watching the program
                  2. 0 -indicates that the user is not watching the program or the user does not exist
                "
            ::= { hwDslamNtvProgramEntry 28 }
                          
        hwDslamNtvPreviewProfileID  OBJECT-TYPE
            SYNTAX  Integer32
            MAX-ACCESS read-write
            STATUS current
            DESCRIPTION
                "Indicates the index of a preview profile. 
                 Range: 0-31 
                 Default: 0 
                "
            ::= { hwDslamNtvProgramEntry 29 }
        
        hwDslamNtvProgramGrade  OBJECT-TYPE
            SYNTAX  Integer32 (0..255)      
            MAX-ACCESS read-write
            STATUS current
            DESCRIPTION
                "Indicates the program grade. 
                 Range: 0-255 
                 Default: 255 
                "
            ::= { hwDslamNtvProgramEntry 30 }   
        
        hwDslamNtvProgramNewIpCascadePortList OBJECT-TYPE
            SYNTAX OCTET STRING
            MAX-ACCESS read-only
            STATUS current
            DESCRIPTION
                "Indicates the mask of cascade ports that are watching this program. There are 4096 bits in all,
                 that is, bit0-bit7 indicates the cascade ports with indexs 1-8(The index of the cascade port is 
                 in ascending order in one byte). Each bit indicates whether a cascade port is watching the program.
                 Options: 
                 1. 1 -watching this program
                 2. 0 -not watching this program or the cascade port does not exist
                 It can indicate 4096 cascade ports.
                "
            ::= { hwDslamNtvProgramEntry 31 }
               
        hwDslamNtvProgramMAC        OBJECT-TYPE
            SYNTAX       OCTET STRING 
            MAX-ACCESS   read-only
            STATUS       current
            DESCRIPTION
                "Indicates the MAC address of a program. It supports the read operation and does not 
                 support the modify or create operation. It is valid when the IGMP mode is oamGroupControl.
                "
            ::= { hwDslamNtvProgramEntry 32}   
        
        hwDslamNtvProgramBTVUserPortList2 OBJECT-TYPE
            SYNTAX OCTET STRING
            MAX-ACCESS read-only
            STATUS current
            DESCRIPTION
                "Indicates the mask of BTV users that are watching this program. It has 4096 bits. Each bit 
                 indicates whether a BTV user is watching the program.
                 Indicates a multicast port with an index in the range of 4097-8192, 512 bytes in total (user 
                 indexes of bit0-bit7 are in ascending order). 
                 Options: 
                 1. 1 -indicates that the user is watching the program
                 2. 0 -indicates that the user is not watching the program or the user does not exist
                "
            ::= { hwDslamNtvProgramEntry 33 }
        
        hwDslamNtvProgramVideoTagVlan OBJECT-TYPE
            SYNTAX Integer32 (0..4093)
            MAX-ACCESS read-write
            STATUS current
            DESCRIPTION
                "The video vlan of program.When set to 0,there will be no vlan in the video.
                "
            DEFVAL { 0 }
            ::= { hwDslamNtvProgramEntry 40 }
         
        hwDslamNtvProgramIPv6 OBJECT-TYPE
            SYNTAX Ipv6Address
            MAX-ACCESS read-create
            STATUS current
            DESCRIPTION
                "Indicates the IPv6 address of a program, the multicast address.
                "
            ::= { hwDslamNtvProgramEntry 41 }

        hwDslamNtvProgramSourceIPv6 OBJECT-TYPE
            SYNTAX Ipv6Address
            MAX-ACCESS read-create
            STATUS current
            DESCRIPTION
                "Indicates the IPv6 address of the program source.
                "
            ::= { hwDslamNtvProgramEntry 42 }

	hwDslamNtvProgramBTVUserPortList3 OBJECT-TYPE
	    SYNTAX OCTET STRING
	    MAX-ACCESS read-only
	    STATUS current
	    DESCRIPTION
                "Indicates the mask of BTV users that are watching this program. It has 4096 bits. Each bit 
                 indicates whether a BTV user is watching the program.
                 Indicates a multicast port with an index in the range of 8193-12288, 512 bytes in total (user 
                 indexes of bit0-bit7 are in ascending order). 
                 Options: 
                 1. 1 -indicates that the user is watching the program
                 2. 0 -indicates that the user is not watching the program or the user does not exist
                "  	        
	    ::= { hwDslamNtvProgramEntry 43 }
	    
	hwDslamNtvProgramBTVUserPortList4 OBJECT-TYPE
	    SYNTAX OCTET STRING
	    MAX-ACCESS read-only
	    STATUS current
	    DESCRIPTION
                "Indicates the mask of BTV users that are watching this program. It has 4096 bits. Each bit 
                 indicates whether a BTV user is watching the program.
                 Indicates a multicast port with an index in the range of 12289-16384, 512 bytes in total (user 
                 indexes of bit0-bit7 are in ascending order). 
                 Options: 
                 1. 1 -indicates that the user is watching the program
                 2. 0 -indicates that the user is not watching the program or the user does not exist
                "  	       
	    ::= { hwDslamNtvProgramEntry 44 }
	    
        hwDslamNtvRightProfileTable    OBJECT-TYPE
            SYNTAX          SEQUENCE OF HwDslamNtvRightProfileEntry
            MAX-ACCESS      not-accessible
            STATUS          current
            DESCRIPTION
                "Indicates the multicast authority profile table.
                 The index of this table is hwDslamNtvRightProfileIndex.
                "
            ::= { hwDslamNtv 19 }
        
        hwDslamNtvRightProfileEntry    OBJECT-TYPE
            SYNTAX         HwDslamNtvRightProfileEntry
            MAX-ACCESS     not-accessible
            STATUS         current
            DESCRIPTION
                "Indicates the multicast authority profile table.
                 The index of this entry is hwDslamNtvRightProfileIndex.
                "
            INDEX   
                { 
                hwDslamNtvRightProfileIndex
                }
            ::= { hwDslamNtvRightProfileTable  1 }
        
        HwDslamNtvRightProfileEntry    ::= 
            SEQUENCE  
                {
                hwDslamNtvRightProfileIndex       
                    Integer32,
                hwDslamNtvRightProfileName        
                    OCTET STRING,
                hwDslamNtvRightProfileRowStatus    
                    RowStatus,
                hwDslamNtvProgramMask1           
                    BITS,
                hwDslamNtvProgramMask2              
                    BITS,
                hwDslamNtvRightProfileCount       
                    Integer32,
                hwDslamNtvRightProfilePortList1   
                    PortList,
                hwDslamNtvRightProfilePortList2   
                    PortList,
                hwDslamNtvProgramMask3           
                    BITS,
                hwDslamNtvProgramMask4           
                    BITS,
                hwDslamNtvProgramMask5            
                    BITS,
                hwDslamNtvProgramMask6            
                    BITS,
                hwDslamNtvProgramMask7            
                    BITS,
                hwDslamNtvProgramMask8           
                    BITS,
                hwDslamNtvProgramMask9           
                    BITS,
                hwDslamNtvProgramMask10           
                    BITS,
                hwDslamNtvProgramMask11           
                    BITS,
                hwDslamNtvProgramMask12           
                    BITS,
                hwDslamNtvProgramMask13           
                    BITS,
                hwDslamNtvProgramMask14           
                    BITS,
                hwDslamNtvProgramMask15           
                    BITS,
                hwDslamNtvProgramMask16           
                    BITS,
                hwDslamNtvProgramMask17           
                    BITS,
                hwDslamNtvProgramMask18           
                    BITS,
                hwDslamNtvProgramMask19           
                    BITS,
                hwDslamNtvProgramMask20           
                    BITS,
                hwDslamNtvProgramMask21           
                    BITS,
                hwDslamNtvProgramMask22           
                    BITS,
                hwDslamNtvProgramMask23           
                    BITS,
                hwDslamNtvProgramMask24           
                    BITS,
                hwDslamNtvProgramMask25           
                    BITS,
                hwDslamNtvProgramMask26          
                    BITS,
                hwDslamNtvProgramMask27           
                    BITS,
                hwDslamNtvProgramMask28           
                    BITS,
                hwDslamNtvProgramMask29           
                    BITS,
                hwDslamNtvProgramMask30           
                    BITS,
                hwDslamNtvProgramMask31           
                    BITS,
                hwDslamNtvProgramMask32          
                    BITS,
                hwDslamNtvRightProfileUserRefCount
                    Integer32,
                hwDslamNtvProgramMask33           
                    BITS,
                hwDslamNtvProgramMask34           
                    BITS,
                hwDslamNtvProgramMask35           
                    BITS,
                hwDslamNtvProgramMask36          
                    BITS,
                hwDslamNtvProgramMask37           
                    BITS,
                hwDslamNtvProgramMask38           
                    BITS,
                hwDslamNtvProgramMask39           
                    BITS,
                hwDslamNtvProgramMask40           
                    BITS,
                hwDslamNtvProgramMask41          
                    BITS,
                hwDslamNtvProgramMask42           
                    BITS,
                hwDslamNtvProgramMask43           
                    BITS,
                hwDslamNtvProgramMask44           
                    BITS,
                hwDslamNtvProgramMask45           
                    BITS,
                hwDslamNtvProgramMask46           
                    BITS,
                hwDslamNtvProgramMask47            
                    BITS,
                hwDslamNtvProgramMask48           
                    BITS,
                hwDslamNtvProgramMask49          
                    BITS,
                hwDslamNtvProgramMask50          
                    BITS, 
                hwDslamNtvProgramMask51          
                    BITS,
                hwDslamNtvProgramMask52          
                    BITS,
                hwDslamNtvProgramMask53           
                    BITS,
                hwDslamNtvProgramMask54          
                    BITS,
                hwDslamNtvProgramMask55           
                    BITS,
                hwDslamNtvProgramMask56          
                    BITS,
                hwDslamNtvProgramMask57          
                    BITS,
                hwDslamNtvProgramMask58          
                    BITS,
                hwDslamNtvProgramMask59           
                    BITS,
                hwDslamNtvProgramMask60          
                    BITS,
                hwDslamNtvProgramMask61           
                    BITS,
                hwDslamNtvProgramMask62          
                    BITS,
                hwDslamNtvProgramMask63           
                    BITS,
                hwDslamNtvProgramMask64           
                    BITS                                
                }
        
        hwDslamNtvRightProfileIndex        OBJECT-TYPE
            SYNTAX       Integer32
            MAX-ACCESS   read-only
            STATUS       current
            DESCRIPTION
                "Indicates the index of an authority profile in the profile mode. 
                 Its value and algorithm in the user mode are the same as those of hwDslamNtvUserIndex.
                 You can also fill -1 and the system will automatically allocate an index.
                "
            ::= { hwDslamNtvRightProfileEntry 1}   
        
        hwDslamNtvRightProfileName      OBJECT-TYPE
            SYNTAX       OCTET STRING (SIZE (1..16))
            MAX-ACCESS   read-write
            STATUS       current
            DESCRIPTION
                "Indicates the name of an authority profile. 
                 Range: 1-16
                "
            ::= { hwDslamNtvRightProfileEntry 2}
        
        hwDslamNtvRightProfileRowStatus    OBJECT-TYPE
            SYNTAX       RowStatus
            MAX-ACCESS   read-create
            STATUS       current
            DESCRIPTION
                "Row status, used to query, create, modify, and delete a multicast authority profile. 
                 It supports the active(1), createAndGo(4), and destroy(6) operations.
                 During query, the value of this leaf is always active(1).
                 During deletion, specify the value of this leaf to destroy(6).
                 During creation, specify the value of this leaf to createAndGo(4).
                 To modify the parameters of a multicast authority profile, this leaf need not be issued together.
                 Options:
                 1. active(1)      -indicates the query operation
                 2. createAndGo(4) -indicates the creating operation
                 3. destroy(6)     -indicates the deleting operation
                "
            ::= { hwDslamNtvRightProfileEntry 3}   
        
        hwDslamNtvProgramMask1        OBJECT-TYPE
            SYNTAX   BITS
                {
                program1(0),
                program2(1),
                program3(2),
                program4(3),
                program5(4),
                program6(5),
                program7(6),
                program8(7),
                program9(8),
                program10(9),
                program11(10),
                program12(11),
                program13(12),
                program14(13),
                program15(14),
                program16(15),
                program17(16),
                program18(17),
                program19(18),
                program20(19),
                program21(20),
                program22(21),
                program23(22),
                program24(23),
                program25(24),
                program26(25),
                program27(26),
                program28(27),
                program29(28),
                program30(29),
                program31(30),
                program32(31),
                program33(32),
                program34(33),
                program35(34),
                program36(35),
                program37(36),
                program38(37),
                program39(38),
                program40(39),
                program41(40),
                program42(41),
                program43(42),
                program44(43),
                program45(44),
                program46(45),
                program47(46),
                program48(47),
                program49(48),
                program50(49),
                program51(50),
                program52(51),
                program53(52),
                program54(53),
                program55(54),
                program56(55),
                program57(56),
                program58(57),
                program59(58),
                program60(59),
                program61(60),
                program62(61),
                program63(62),
                program64(63),
                program65(64),
                program66(65),
                program67(66),
                program68(67),
                program69(68),
                program70(69),
                program71(70),
                program72(71),
                program73(72),
                program74(73),
                program75(74),
                program76(75),
                program77(76),
                program78(77),
                program79(78),
                program80(79),
                program81(80),
                program82(81),
                program83(82),
                program84(83),
                program85(84),
                program86(85),
                program87(86),
                program88(87),
                program89(88),
                program90(89),
                program91(90),
                program92(91),
                program93(92),
                program94(93),
                program95(94),
                program96(95),
                program97(96),
                program98(97),
                program99(98),
                program100(99),
                program101(100),
                program102(101),
                program103(102),
                program104(103),
                program105(104),
                program106(105),
                program107(106),
                program108(107),
                program109(108),
                program110(109),
                program111(110),
                program112(111),
                program113(112),
                program114(113),
                program115(114),
                program116(115),
                program117(116),
                program118(117),
                program119(118),
                program120(119),
                program121(120),
                program122(121),
                program123(122),
                program124(123),
                program125(124),
                program126(125),
                program127(126),
                program128(127)                       
                }
            MAX-ACCESS   read-write
            STATUS       current
            DESCRIPTION
                "Indicates the program mask. This leaf indicates the authority of programs with indexes 1-64, 
                 64 programs in total. The indication methods of other mast leaves are the same as this table.
                 Each two bits indicate the authority to a program. Meanings of a 2-bit mask:
                 1. Forbidden(11)
                 2. Watch(01)
                 3. Preview(10)
                 4. idle(00)
                "
            ::= { hwDslamNtvRightProfileEntry 4}
        
        hwDslamNtvProgramMask2        OBJECT-TYPE
            SYNTAX   BITS
                {
                program129(0),
                program130(1),
                program131(2),
                program132(3),
                program133(4),
                program134(5),
                program135(6),
                program136(7),
                program137(8),
                program138(9),
                program139(10),
                program140(11),
                program141(12),
                program142(13),
                program143(14),
                program144(15),
                program145(16),
                program146(17),
                program147(18),
                program148(19),
                program149(20),
                program150(21),
                program151(22),
                program152(23),
                program153(24),
                program154(25),
                program155(26),
                program156(27),
                program157(28),
                program158(29),
                program159(30),
                program160(31),
                program161(32),
                program162(33),
                program163(34),
                program164(35),
                program165(36),
                program166(37),
                program167(38),
                program168(39),
                program169(40),
                program170(41),
                program171(42),
                program172(43),
                program173(44),
                program174(45),
                program175(46),
                program176(47),
                program177(48),
                program178(49),
                program179(50),
                program180(51),
                program181(52),
                program182(53),
                program183(54),
                program184(55),
                program185(56),
                program186(57),
                program187(58),
                program188(59),
                program189(60),
                program190(61),
                program191(62),
                program192(63),
                program193(64),
                program194(65),
                program195(66),
                program196(67),
                program197(68),
                program198(69),
                program199(70),
                program200(71),
                program201(72),
                program202(73),
                program203(74),
                program204(75),
                program205(76),
                program206(77),
                program207(78),
                program208(79),
                program209(80),
                program210(81),
                program211(82),
                program212(83),
                program213(84),
                program214(85),
                program215(86),
                program216(87),
                program217(88),
                program218(89),
                program219(90),
                program220(91),
                program221(92),
                program222(93),
                program223(94),
                program224(95),
                program225(96),
                program226(97),
                program227(98),
                program228(99),
                program229(100),
                program230(101),
                program231(102),
                program232(103),
                program233(104),
                program234(105),
                program235(106),
                program236(107),
                program237(108),
                program238(109),
                program239(110),
                program240(111),
                program241(112),
                program242(113),
                program243(114),
                program244(115),
                program245(116),
                program246(117),
                program247(118),
                program248(119),
                program249(120),
                program250(121),
                program251(122),
                program252(123),
                program253(124),
                program254(125),
                program255(126),
                program256(127)
                }           
            MAX-ACCESS   read-write
            STATUS       current
            DESCRIPTION
                "Indicates the program mask. This leaf indicates the authority of programs with indexes 65-128, 
                 64 programs in total. The indication methods of other mast leaves are the same as this table.
                 Each two bits indicate the authority to a program. Meanings of a 2-bit mask:
                 1. Forbidden(11)
                 2. Watch(01)
                 3. Preview(10)
                 4. idle(00)
                "
            ::= { hwDslamNtvRightProfileEntry 5}
        
        hwDslamNtvRightProfileCount        OBJECT-TYPE
            SYNTAX       Integer32
            MAX-ACCESS   read-only
            STATUS       current
            DESCRIPTION
                "
                Right profile count.
                Count of the users who can watch the program in the right profile.
                "
            ::= { hwDslamNtvRightProfileEntry 6}
        
        hwDslamNtvRightProfilePortList1 OBJECT-TYPE
            SYNTAX       PortList
            MAX-ACCESS   read-only
            STATUS       current
            DESCRIPTION
                "Port list of slot0 to slot7 who can watch the program in the right profile.
                "
            ::= { hwDslamNtvRightProfileEntry 7 }
        
        hwDslamNtvRightProfilePortList2 OBJECT-TYPE
            SYNTAX       PortList
            MAX-ACCESS   read-only
            STATUS       current
            DESCRIPTION
                "Port list of slot8 to slot15 who can watch the program in the right profile.
                "
            ::= { hwDslamNtvRightProfileEntry 8 }
        
        hwDslamNtvProgramMask3 OBJECT-TYPE
            SYNTAX BITS
                {
                program257(0),
                program258(1),
                program259(2),
                program260(3),
                program261(4),
                program262(5),
                program263(6),
                program264(7),
                program265(8),
                program266(9),
                program267(10),
                program268(11),
                program269(12),
                program270(13),
                program271(14),
                program272(15),
                program273(16),
                program274(17),
                program275(18),
                program276(19),
                program277(20),
                program278(21),
                program279(22),
                program280(23),
                program281(24),
                program282(25),
                program283(26),
                program284(27),
                program285(28),
                program286(29),
                program287(30),
                program288(31),
                program289(32),
                program290(33),
                program291(34),
                program292(35),
                program293(36),
                program294(37),
                program295(38),
                program296(39),
                program297(40),
                program298(41),
                program299(42),
                program300(43),
                program301(44),
                program302(45),
                program303(46),
                program304(47),
                program305(48),
                program306(49),
                program307(50),
                program308(51),
                program309(52),
                program310(53),
                program311(54),
                program312(55),
                program313(56),
                program314(57),
                program315(58),
                program316(59),
                program317(60),
                program318(61),
                program319(62),
                program320(63),
                program321(64),
                program322(65),
                program323(66),
                program324(67),
                program325(68),
                program326(69),
                program327(70),
                program328(71),
                program329(72),
                program330(73),
                program331(74),
                program332(75),
                program333(76),
                program334(77),
                program335(78),
                program336(79),
                program337(80),
                program338(81),
                program339(82),
                program340(83),
                program341(84),
                program342(85),
                program343(86),
                program344(87),
                program345(88),
                program346(89),
                program347(90),
                program348(91),
                program349(92),
                program350(93),
                program351(94),
                program352(95),
                program353(96),
                program354(97),
                program355(98),
                program356(99),
                program357(100),
                program358(101),
                program359(102),
                program360(103),
                program361(104),
                program362(105),
                program363(106),
                program364(107),
                program365(108),
                program366(109),
                program367(110),
                program368(111),
                program369(112),
                program370(113),
                program371(114),
                program372(115),
                program373(116),
                program374(117),
                program375(118),
                program376(119),
                program377(120),
                program378(121),
                program379(122),
                program380(123),
                program381(124),
                program382(125),
                program383(126),
                program384(127)
                }
            MAX-ACCESS read-write
            STATUS current
            DESCRIPTION
                "Indicates the program mask. This leaf indicates the authority of programs with indexes 129-192, 
                 64 programs in total. The indication methods of other mast leaves are the same as this table.
                 Each two bits indicate the authority to a program. Meanings of a 2-bit mask:
                 1. Forbidden(11)
                 2. Watch(01)
                 3. Preview(10)
                 4. idle(00)
                "
            ::= { hwDslamNtvRightProfileEntry 9 }
            
        hwDslamNtvProgramMask4 OBJECT-TYPE
            SYNTAX BITS
                {
                program385(0),
                program386(1),
                program387(2),
                program388(3),
                program389(4),
                program390(5),
                program391(6),
                program392(7),
                program393(8),
                program394(9),
                program395(10),
                program396(11),
                program397(12),
                program398(13),
                program399(14),
                program400(15),
                program401(16),
                program402(17),
                program403(18),
                program404(19),
                program405(20),
                program406(21),
                program407(22),
                program408(23),
                program409(24),
                program410(25),
                program411(26),
                program412(27),
                program413(28),
                program414(29),
                program415(30),
                program416(31),
                program417(32),
                program418(33),
                program419(34),
                program420(35),
                program421(36),
                program422(37),
                program423(38),
                program424(39),
                program425(40),
                program426(41),
                program427(42),
                program428(43),
                program429(44),
                program430(45),
                program431(46),
                program432(47),
                program433(48),
                program434(49),
                program435(50),
                program436(51),
                program437(52),
                program438(53),
                program439(54),
                program440(55),
                program441(56),
                program442(57),
                program443(58),
                program444(59),
                program445(60),
                program446(61),
                program447(62),
                program448(63),
                program449(64),
                program450(65),
                program451(66),
                program452(67),
                program453(68),
                program454(69),
                program455(70),
                program456(71),
                program457(72),
                program458(73),
                program459(74),
                program460(75),
                program461(76),
                program462(77),
                program463(78),
                program464(79),
                program465(80),
                program466(81),
                program467(82),
                program468(83),
                program469(84),
                program470(85),
                program471(86),
                program472(87),
                program473(88),
                program474(89),
                program475(90),
                program476(91),
                program477(92),
                program478(93),
                program479(94),
                program480(95),
                program481(96),
                program482(97),
                program483(98),
                program484(99),
                program485(100),
                program486(101),
                program487(102),
                program488(103),
                program489(104),
                program490(105),
                program491(106),
                program492(107),
                program493(108),
                program494(109),
                program495(110),
                program496(111),
                program497(112),
                program498(113),
                program499(114),
                program500(115),
                program501(116),
                program502(117),
                program503(118),
                program504(119),
                program505(120),
                program506(121),
                program507(122),
                program508(123),
                program509(124),
                program510(125),
                program511(126),
                program512(127)
                }
            MAX-ACCESS read-write
            STATUS current
            DESCRIPTION
                "Indicates the program mask. This leaf indicates the authority of programs with indexes 193-256, 
                 64 programs in total. The indication methods of other mast leaves are the same as this table.
                 Each two bits indicate the authority to a program. Meanings of a 2-bit mask:
                 1. Forbidden(11)
                 2. Watch(01)
                 3. Preview(10)
                 4. idle(00)
                "
            ::= { hwDslamNtvRightProfileEntry 10 }
        
        hwDslamNtvProgramMask5 OBJECT-TYPE
            SYNTAX BITS
                {
                program513(0),
                program514(1),
                program515(2),
                program516(3),
                program517(4),
                program518(5),
                program519(6),
                program520(7),
                program521(8),
                program522(9),
                program523(10),
                program524(11),
                program525(12),
                program526(13),
                program527(14),
                program528(15),
                program529(16),
                program530(17),
                program531(18),
                program532(19),
                program533(20),
                program534(21),
                program535(22),
                program536(23),
                program537(24),
                program538(25),
                program539(26),
                program540(27),
                program541(28),
                program542(29),
                program543(30),
                program544(31),
                program545(32),
                program546(33),
                program547(34),
                program548(35),
                program549(36),
                program550(37),
                program551(38),
                program552(39),
                program553(40),
                program554(41),
                program555(42),
                program556(43),
                program557(44),
                program558(45),
                program559(46),
                program560(47),
                program561(48),
                program562(49),
                program563(50),
                program564(51),
                program565(52),
                program566(53),
                program567(54),
                program568(55),
                program569(56),
                program570(57),
                program571(58),
                program572(59),
                program573(60),
                program574(61),
                program575(62),
                program576(63),
                program577(64),
                program578(65),
                program579(66),
                program580(67),
                program581(68),
                program582(69),
                program583(70),
                program584(71),
                program585(72),
                program586(73),
                program587(74),
                program588(75),
                program589(76),
                program590(77),
                program591(78),
                program592(79),
                program593(80),
                program594(81),
                program595(82),
                program596(83),
                program597(84),
                program598(85),
                program599(86),
                program600(87),
                program601(88),
                program602(89),
                program603(90),
                program604(91),
                program605(92),
                program606(93),
                program607(94),
                program608(95),
                program609(96),
                program610(97),
                program611(98),
                program612(99),
                program613(100),
                program614(101),
                program615(102),
                program616(103),
                program617(104),
                program618(105),
                program619(106),
                program620(107),
                program621(108),
                program622(109),
                program623(110),
                program624(111),
                program625(112),
                program626(113),
                program627(114),
                program628(115),
                program629(116),
                program630(117),
                program631(118),
                program632(119),
                program633(120),
                program634(121),
                program635(122),
                program636(123),
                program637(124),
                program638(125),
                program639(126),
                program640(127)
                }
            MAX-ACCESS read-write
            STATUS current
            DESCRIPTION
                "Indicates the program mask. This leaf indicates the authority of programs with indexes 257-320, 
                 64 programs in total. The indication methods of other mast leaves are the same as this table.
                 Each two bits indicate the authority to a program. Meanings of a 2-bit mask:
                 1. Forbidden(11)
                 2. Watch(01)
                 3. Preview(10)
                 4. idle(00)
                "
            ::= { hwDslamNtvRightProfileEntry 11 }
        
        hwDslamNtvProgramMask6 OBJECT-TYPE
            SYNTAX BITS
                {
                program641(0),
                program642(1),
                program643(2),
                program644(3),
                program645(4),
                program646(5),
                program647(6),
                program648(7),
                program649(8),
                program650(9),
                program651(10),
                program652(11),
                program653(12),
                program654(13),
                program655(14),
                program656(15),
                program657(16),
                program658(17),
                program659(18),
                program660(19),
                program661(20),
                program662(21),
                program663(22),
                program664(23),
                program665(24),
                program666(25),
                program667(26),
                program668(27),
                program669(28),
                program670(29),
                program671(30),
                program672(31),
                program673(32),
                program674(33),
                program675(34),
                program676(35),
                program677(36),
                program678(37),
                program679(38),
                program680(39),
                program681(40),
                program682(41),
                program683(42),
                program684(43),
                program685(44),
                program686(45),
                program687(46),
                program688(47),
                program689(48),
                program690(49),
                program691(50),
                program692(51),
                program693(52),
                program694(53),
                program695(54),
                program696(55),
                program697(56),
                program698(57),
                program699(58),
                program700(59),
                program701(60),
                program702(61),
                program703(62),
                program704(63),
                program705(64),
                program706(65),
                program707(66),
                program708(67),
                program709(68),
                program710(69),
                program711(70),
                program712(71),
                program713(72),
                program714(73),
                program715(74),
                program716(75),
                program717(76),
                program718(77),
                program719(78),
                program720(79),
                program721(80),
                program722(81),
                program723(82),
                program724(83),
                program725(84),
                program726(85),
                program727(86),
                program728(87),
                program729(88),
                program730(89),
                program731(90),
                program732(91),
                program733(92),
                program734(93),
                program735(94),
                program736(95),
                program737(96),
                program738(97),
                program739(98),
                program740(99),
                program741(100),
                program742(101),
                program743(102),
                program744(103),
                program745(104),
                program746(105),
                program747(106),
                program748(107),
                program749(108),
                program750(109),
                program751(110),
                program752(111),
                program753(112),
                program754(113),
                program755(114),
                program756(115),
                program757(116),
                program758(117),
                program759(118),
                program760(119),
                program761(120),
                program762(121),
                program763(122),
                program764(123),
                program765(124),
                program766(125),
                program767(126),
                program768(127)
                }
            MAX-ACCESS read-write
            STATUS current
            DESCRIPTION
                "Indicates the program mask. This leaf indicates the authority of programs with indexes 321-384, 
                 64 programs in total. The indication methods of other mast leaves are the same as this table.
                 Each two bits indicate the authority to a program. Meanings of a 2-bit mask:
                 1. Forbidden(11)
                 2. Watch(01)
                 3. Preview(10)
                 4. idle(00)
                "
            ::= { hwDslamNtvRightProfileEntry 12 }
        
        hwDslamNtvProgramMask7 OBJECT-TYPE
            SYNTAX BITS
                {
                program769(0),
                program770(1),
                program771(2),
                program772(3),
                program773(4),
                program774(5),
                program775(6),
                program776(7),
                program777(8),
                program778(9),
                program779(10),
                program780(11),
                program781(12),
                program782(13),
                program783(14),
                program784(15),
                program785(16),
                program786(17),
                program787(18),
                program788(19),
                program789(20),
                program790(21),
                program791(22),
                program792(23),
                program793(24),
                program794(25),
                program795(26),
                program796(27),
                program797(28),
                program798(29),
                program799(30),
                program800(31),
                program801(32),
                program802(33),
                program803(34),
                program804(35),
                program805(36),
                program806(37),
                program807(38),
                program808(39),
                program809(40),
                program810(41),
                program811(42),
                program812(43),
                program813(44),
                program814(45),
                program815(46),
                program816(47),
                program817(48),
                program818(49),
                program819(50),
                program820(51),
                program821(52),
                program822(53),
                program823(54),
                program824(55),
                program825(56),
                program826(57),
                program827(58),
                program828(59),
                program829(60),
                program830(61),
                program831(62),
                program832(63),
                program833(64),
                program834(65),
                program835(66),
                program836(67),
                program837(68),
                program838(69),
                program839(70),
                program840(71),
                program841(72),
                program842(73),
                program843(74),
                program844(75),
                program845(76),
                program846(77),
                program847(78),
                program848(79),
                program849(80),
                program850(81),
                program851(82),
                program852(83),
                program853(84),
                program854(85),
                program855(86),
                program856(87),
                program857(88),
                program858(89),
                program859(90),
                program860(91),
                program861(92),
                program862(93),
                program863(94),
                program864(95),
                program865(96),
                program866(97),
                program867(98),
                program868(99),
                program869(100),
                program870(101),
                program871(102),
                program872(103),
                program873(104),
                program874(105),
                program875(106),
                program876(107),
                program877(108),
                program878(109),
                program879(110),
                program880(111),
                program881(112),
                program882(113),
                program883(114),
                program884(115),
                program885(116),
                program886(117),
                program887(118),
                program888(119),
                program889(120),
                program890(121),
                program891(122),
                program892(123),
                program893(124),
                program894(125),
                program895(126),
                program896(127)
                }
            MAX-ACCESS read-write
            STATUS current
            DESCRIPTION
                "Indicates the program mask. This leaf indicates the authority of programs with indexes 385-448, 
                 64 programs in total. The indication methods of other mast leaves are the same as this table.
                 Each two bits indicate the authority to a program. Meanings of a 2-bit mask:
                 1. Forbidden(11)
                 2. Watch(01)
                 3. Preview(10)
                 4. idle(00)
                "
            ::= { hwDslamNtvRightProfileEntry 13 }       
        
        hwDslamNtvProgramMask8 OBJECT-TYPE
            SYNTAX BITS
                {
                program897(0),
                program898(1),
                program899(2),
                program900(3),
                program901(4),
                program902(5),
                program903(6),
                program904(7),
                program905(8),
                program906(9),
                program907(10),
                program908(11),
                program909(12),
                program910(13),
                program911(14),
                program912(15),
                program913(16),
                program914(17),
                program915(18),
                program916(19),
                program917(20),
                program918(21),
                program919(22),
                program920(23),
                program921(24),
                program922(25),
                program923(26),
                program924(27),
                program925(28),
                program926(29),
                program927(30),
                program928(31),
                program929(32),
                program930(33),
                program931(34),
                program932(35),
                program933(36),
                program934(37),
                program935(38),
                program936(39),
                program937(40),
                program938(41),
                program939(42),
                program940(43),
                program941(44),
                program942(45),
                program943(46),
                program944(47),
                program945(48),
                program946(49),
                program947(50),
                program948(51),
                program949(52),
                program950(53),
                program951(54),
                program952(55),
                program953(56),
                program954(57),
                program955(58),
                program956(59),
                program957(60),
                program958(61),
                program959(62),
                program960(63),
                program961(64),
                program962(65),
                program963(66),
                program964(67),
                program965(68),
                program966(69),
                program967(70),
                program968(71),
                program969(72),
                program970(73),
                program971(74),
                program972(75),
                program973(76),
                program974(77),
                program975(78),
                program976(79),
                program977(80),
                program978(81),
                program979(82),
                program980(83),
                program981(84),
                program982(85),
                program983(86),
                program984(87),
                program985(88),
                program986(89),
                program987(90),
                program988(91),
                program989(92),
                program990(93),
                program991(94),
                program992(95),
                program993(96),
                program994(97),
                program995(98),
                program996(99),
                program997(100),
                program998(101),
                program999(102),
                program1000(103),
                program1001(104),
                program1002(105),
                program1003(106),
                program1004(107),
                program1005(108),
                program1006(109),
                program1007(110),
                program1008(111),
                program1009(112),
                program1010(113),
                program1011(114),
                program1012(115),
                program1013(116),
                program1014(117),
                program1015(118),
                program1016(119),
                program1017(120),
                program1018(121),
                program1019(122),
                program1020(123),
                program1021(124),
                program1022(125),
                program1023(126),
                program1024(127)
                }
            MAX-ACCESS read-write
            STATUS current
            DESCRIPTION
                "Indicates the program mask. This leaf indicates the authority of programs with indexes 449-512, 
                 64 programs in total. The indication methods of other mast leaves are the same as this table.
                 Each two bits indicate the authority to a program. Meanings of a 2-bit mask:
                 1. Forbidden(11)
                 2. Watch(01)
                 3. Preview(10)
                 4. idle(00)
                "
            ::= { hwDslamNtvRightProfileEntry 14 }        
        
        hwDslamNtvProgramMask9 OBJECT-TYPE
            SYNTAX BITS
                {
                program1025(0),
                program1026(1),
                program1027(2),
                program1028(3),
                program1029(4),
                program1030(5),
                program1031(6),
                program1032(7),
                program1033(8),
                program1034(9),
                program1035(10),
                program1036(11),
                program1037(12),
                program1038(13),
                program1039(14),
                program1040(15),
                program1041(16),
                program1042(17),
                program1043(18),
                program1044(19),
                program1045(20),
                program1046(21),
                program1047(22),
                program1048(23),
                program1049(24),
                program1050(25),
                program1051(26),
                program1052(27),
                program1053(28),
                program1054(29),
                program1055(30),
                program1056(31),
                program1057(32),
                program1058(33),
                program1059(34),
                program1060(35),
                program1061(36),
                program1062(37),
                program1063(38),
                program1064(39),
                program1065(40),
                program1066(41),
                program1067(42),
                program1068(43),
                program1069(44),
                program1070(45),
                program1071(46),
                program1072(47),
                program1073(48),
                program1074(49),
                program1075(50),
                program1076(51),
                program1077(52),
                program1078(53),
                program1079(54),
                program1080(55),
                program1081(56),
                program1082(57),
                program1083(58),
                program1084(59),
                program1085(60),
                program1086(61),
                program1087(62),
                program1088(63),
                program1089(64),
                program1090(65),
                program1091(66),
                program1092(67),
                program1093(68),
                program1094(69),
                program1095(70),
                program1096(71),
                program1097(72),
                program1098(73),
                program1099(74),
                program1100(75),
                program1101(76),
                program1102(77),
                program1103(78),
                program1104(79),
                program1105(80),
                program1106(81),
                program1107(82),
                program1108(83),
                program1109(84),
                program1110(85),
                program1111(86),
                program1112(87),
                program1113(88),
                program1114(89),
                program1115(90),
                program1116(91),
                program1117(92),
                program1118(93),
                program1119(94),
                program1120(95),
                program1121(96),
                program1122(97),
                program1123(98),
                program1124(99),
                program1125(100),
                program1126(101),
                program1127(102),
                program1128(103),
                program1129(104),
                program1130(105),
                program1131(106),
                program1132(107),
                program1133(108),
                program1134(109),
                program1135(110),
                program1136(111),
                program1137(112),
                program1138(113),
                program1139(114),
                program1140(115),
                program1141(116),
                program1142(117),
                program1143(118),
                program1144(119),
                program1145(120),
                program1146(121),
                program1147(122),
                program1148(123),
                program1149(124),
                program1150(125),
                program1151(126),
                program1152(127)
                }
            MAX-ACCESS read-write
            STATUS current
            DESCRIPTION
                "Indicates the program mask. This leaf indicates the authority of programs with indexes 513-576, 
                 64 programs in total. The indication methods of other mast leaves are the same as this table.
                 Each two bits indicate the authority to a program. Meanings of a 2-bit mask:
                 1. Forbidden(11)
                 2. Watch(01)
                 3. Preview(10)
                 4. idle(00)
                "
            ::= { hwDslamNtvRightProfileEntry 15 }
                
        hwDslamNtvProgramMask10 OBJECT-TYPE
            SYNTAX BITS
                {
                program1153(0),
                program1154(1),
                program1155(2),
                program1156(3),
                program1157(4),
                program1158(5),
                program1159(6),
                program1160(7),
                program1161(8),
                program1162(9),
                program1163(10),
                program1164(11),
                program1165(12),
                program1166(13),
                program1167(14),
                program1168(15),
                program1169(16),
                program1170(17),
                program1171(18),
                program1172(19),
                program1173(20),
                program1174(21),
                program1175(22),
                program1176(23),
                program1177(24),
                program1178(25),
                program1179(26),
                program1180(27),
                program1181(28),
                program1182(29),
                program1183(30),
                program1184(31),
                program1185(32),
                program1186(33),
                program1187(34),
                program1188(35),
                program1189(36),
                program1190(37),
                program1191(38),
                program1192(39),
                program1193(40),
                program1194(41),
                program1195(42),
                program1196(43),
                program1197(44),
                program1198(45),
                program1199(46),
                program1200(47),
                program1201(48),
                program1202(49),
                program1203(50),
                program1204(51),
                program1205(52),
                program1206(53),
                program1207(54),
                program1208(55),
                program1209(56),
                program1210(57),
                program1211(58),
                program1212(59),
                program1213(60),
                program1214(61),
                program1215(62),
                program1216(63),
                program1217(64),
                program1218(65),
                program1219(66),
                program1220(67),
                program1221(68),
                program1222(69),
                program1223(70),
                program1224(71),
                program1225(72),
                program1226(73),
                program1227(74),
                program1228(75),
                program1229(76),
                program1230(77),
                program1231(78),
                program1232(79),
                program1233(80),
                program1234(81),
                program1235(82),
                program1236(83),
                program1237(84),
                program1238(85),
                program1239(86),
                program1240(87),
                program1241(88),
                program1242(89),
                program1243(90),
                program1244(91),
                program1245(92),
                program1246(93),
                program1247(94),
                program1248(95),
                program1249(96),
                program1250(97),
                program1251(98),
                program1252(99),
                program1253(100),
                program1254(101),
                program1255(102),
                program1256(103),
                program1257(104),
                program1258(105),
                program1259(106),
                program1260(107),
                program1261(108),
                program1262(109),
                program1263(110),
                program1264(111),
                program1265(112),
                program1266(113),
                program1267(114),
                program1268(115),
                program1269(116),
                program1270(117),
                program1271(118),
                program1272(119),
                program1273(120),
                program1274(121),
                program1275(122),
                program1276(123),
                program1277(124),
                program1278(125),
                program1279(126),
                program1280(127)
                }
            MAX-ACCESS read-write
            STATUS current
            DESCRIPTION
                "Indicates the program mask. This leaf indicates the authority of programs with indexes 577-640, 
                 64 programs in total. The indication methods of other mast leaves are the same as this table.
                 Each two bits indicate the authority to a program. Meanings of a 2-bit mask:
                 1. Forbidden(11)
                 2. Watch(01)
                 3. Preview(10)
                 4. idle(00)
                "
            ::= { hwDslamNtvRightProfileEntry 16 }
        
        hwDslamNtvProgramMask11 OBJECT-TYPE
            SYNTAX BITS
                {
                program1281(0),
                program1282(1),
                program1283(2),
                program1284(3),
                program1285(4),
                program1286(5),
                program1287(6),
                program1288(7),
                program1289(8),
                program1290(9),
                program1291(10),
                program1292(11),
                program1293(12),
                program1294(13),
                program1295(14),
                program1296(15),
                program1297(16),
                program1298(17),
                program1299(18),
                program1300(19),
                program1301(20),
                program1302(21),
                program1303(22),
                program1304(23),
                program1305(24),
                program1306(25),
                program1307(26),
                program1308(27),
                program1309(28),
                program1310(29),
                program1311(30),
                program1312(31),
                program1313(32),
                program1314(33),
                program1315(34),
                program1316(35),
                program1317(36),
                program1318(37),
                program1319(38),
                program1320(39),
                program1321(40),
                program1322(41),
                program1323(42),
                program1324(43),
                program1325(44),
                program1326(45),
                program1327(46),
                program1328(47),
                program1329(48),
                program1330(49),
                program1331(50),
                program1332(51),
                program1333(52),
                program1334(53),
                program1335(54),
                program1336(55),
                program1337(56),
                program1338(57),
                program1339(58),
                program1340(59),
                program1341(60),
                program1342(61),
                program1343(62),
                program1344(63),
                program1345(64),
                program1346(65),
                program1347(66),
                program1348(67),
                program1349(68),
                program1350(69),
                program1351(70),
                program1352(71),
                program1353(72),
                program1354(73),
                program1355(74),
                program1356(75),
                program1357(76),
                program1358(77),
                program1359(78),
                program1360(79),
                program1361(80),
                program1362(81),
                program1363(82),
                program1364(83),
                program1365(84),
                program1366(85),
                program1367(86),
                program1368(87),
                program1369(88),
                program1370(89),
                program1371(90),
                program1372(91),
                program1373(92),
                program1374(93),
                program1375(94),
                program1376(95),
                program1377(96),
                program1378(97),
                program1379(98),
                program1380(99),
                program1381(100),
                program1382(101),
                program1383(102),
                program1384(103),
                program1385(104),
                program1386(105),
                program1387(106),
                program1388(107),
                program1389(108),
                program1390(109),
                program1391(110),
                program1392(111),
                program1393(112),
                program1394(113),
                program1395(114),
                program1396(115),
                program1397(116),
                program1398(117),
                program1399(118),
                program1400(119),
                program1401(120),
                program1402(121),
                program1403(122),
                program1404(123),
                program1405(124),
                program1406(125),
                program1407(126),
                program1408(127)
                }
            MAX-ACCESS read-write
            STATUS current
            DESCRIPTION
                "Indicates the program mask. This leaf indicates the authority of programs with indexes 641-704, 
                 64 programs in total. The indication methods of other mast leaves are the same as this table.
                 Each two bits indicate the authority to a program. Meanings of a 2-bit mask:
                 1. Forbidden(11)
                 2. Watch(01)
                 3. Preview(10)
                 4. idle(00)
                "
            ::= { hwDslamNtvRightProfileEntry 17 }        
        
        hwDslamNtvProgramMask12 OBJECT-TYPE
            SYNTAX BITS
                {
                program1409(0),
                program1410(1),
                program1411(2),
                program1412(3),
                program1413(4),
                program1414(5),
                program1415(6),
                program1416(7),
                program1417(8),
                program1418(9),
                program1419(10),
                program1420(11),
                program1421(12),
                program1422(13),
                program1423(14),
                program1424(15),
                program1425(16),
                program1426(17),
                program1427(18),
                program1428(19),
                program1429(20),
                program1430(21),
                program1431(22),
                program1432(23),
                program1433(24),
                program1434(25),
                program1435(26),
                program1436(27),
                program1437(28),
                program1438(29),
                program1439(30),
                program1440(31),
                program1441(32),
                program1442(33),
                program1443(34),
                program1444(35),
                program1445(36),
                program1446(37),
                program1447(38),
                program1448(39),
                program1449(40),
                program1450(41),
                program1451(42),
                program1452(43),
                program1453(44),
                program1454(45),
                program1455(46),
                program1456(47),
                program1457(48),
                program1458(49),
                program1459(50),
                program1460(51),
                program1461(52),
                program1462(53),
                program1463(54),
                program1464(55),
                program1465(56),
                program1466(57),
                program1467(58),
                program1468(59),
                program1469(60),
                program1470(61),
                program1471(62),
                program1472(63),
                program1473(64),
                program1474(65),
                program1475(66),
                program1476(67),
                program1477(68),
                program1478(69),
                program1479(70),
                program1480(71),
                program1481(72),
                program1482(73),
                program1483(74),
                program1484(75),
                program1485(76),
                program1486(77),
                program1487(78),
                program1488(79),
                program1489(80),
                program1490(81),
                program1491(82),
                program1492(83),
                program1493(84),
                program1494(85),
                program1495(86),
                program1496(87),
                program1497(88),
                program1498(89),
                program1499(90),
                program1500(91),
                program1501(92),
                program1502(93),
                program1503(94),
                program1504(95),
                program1505(96),
                program1506(97),
                program1507(98),
                program1508(99),
                program1509(100),
                program1510(101),
                program1511(102),
                program1512(103),
                program1513(104),
                program1514(105),
                program1515(106),
                program1516(107),
                program1517(108),
                program1518(109),
                program1519(110),
                program1520(111),
                program1521(112),
                program1522(113),
                program1523(114),
                program1524(115),
                program1525(116),
                program1526(117),
                program1527(118),
                program1528(119),
                program1529(120),
                program1530(121),
                program1531(122),
                program1532(123),
                program1533(124),
                program1534(125),
                program1535(126),
                program1536(127)
                }
            MAX-ACCESS read-write
            STATUS current
            DESCRIPTION
                "Indicates the program mask. This leaf indicates the authority of programs with indexes 705-768, 
                 64 programs in total. The indication methods of other mast leaves are the same as this table.
                 Each two bits indicate the authority to a program. Meanings of a 2-bit mask:
                 1. Forbidden(11)
                 2. Watch(01)
                 3. Preview(10)
                 4. idle(00)
                "
            ::= { hwDslamNtvRightProfileEntry 18 }      
      
        hwDslamNtvProgramMask13 OBJECT-TYPE
            SYNTAX BITS
                {
                program1537(0),
                program1538(1),
                program1539(2),
                program1540(3),
                program1541(4),
                program1542(5),
                program1543(6),
                program1544(7),
                program1545(8),
                program1546(9),
                program1547(10),
                program1548(11),
                program1549(12),
                program1550(13),
                program1551(14),
                program1552(15),
                program1553(16),
                program1554(17),
                program1555(18),
                program1556(19),
                program1557(20),
                program1558(21),
                program1559(22),
                program1560(23),
                program1561(24),
                program1562(25),
                program1563(26),
                program1564(27),
                program1565(28),
                program1566(29),
                program1567(30),
                program1568(31),
                program1569(32),
                program1570(33),
                program1571(34),
                program1572(35),
                program1573(36),
                program1574(37),
                program1575(38),
                program1576(39),
                program1577(40),
                program1578(41),
                program1579(42),
                program1580(43),
                program1581(44),
                program1582(45),
                program1583(46),
                program1584(47),
                program1585(48),
                program1586(49),
                program1587(50),
                program1588(51),
                program1589(52),
                program1590(53),
                program1591(54),
                program1592(55),
                program1593(56),
                program1594(57),
                program1595(58),
                program1596(59),
                program1597(60),
                program1598(61),
                program1599(62),
                program1600(63),
                program1601(64),
                program1602(65),
                program1603(66),
                program1604(67),
                program1605(68),
                program1606(69),
                program1607(70),
                program1608(71),
                program1609(72),
                program1610(73),
                program1611(74),
                program1612(75),
                program1613(76),
                program1614(77),
                program1615(78),
                program1616(79),
                program1617(80),
                program1618(81),
                program1619(82),
                program1620(83),
                program1621(84),
                program1622(85),
                program1623(86),
                program1624(87),
                program1625(88),
                program1626(89),
                program1627(90),
                program1628(91),
                program1629(92),
                program1630(93),
                program1631(94),
                program1632(95),
                program1633(96),
                program1634(97),
                program1635(98),
                program1636(99),
                program1637(100),
                program1638(101),
                program1639(102),
                program1640(103),
                program1641(104),
                program1642(105),
                program1643(106),
                program1644(107),
                program1645(108),
                program1646(109),
                program1647(110),
                program1648(111),
                program1649(112),
                program1650(113),
                program1651(114),
                program1652(115),
                program1653(116),
                program1654(117),
                program1655(118),
                program1656(119),
                program1657(120),
                program1658(121),
                program1659(122),
                program1660(123),
                program1661(124),
                program1662(125),
                program1663(126),
                program1664(127)
                }
            MAX-ACCESS read-write
            STATUS current
            DESCRIPTION
                "Indicates the program mask. This leaf indicates the authority of programs with indexes 769-832, 
                 64 programs in total. The indication methods of other mast leaves are the same as this table.
                 Each two bits indicate the authority to a program. Meanings of a 2-bit mask:
                 1. Forbidden(11)
                 2. Watch(01)
                 3. Preview(10)
                 4. idle(00)
                "
            ::= { hwDslamNtvRightProfileEntry 19 }         
        
        hwDslamNtvProgramMask14 OBJECT-TYPE
            SYNTAX BITS
                {
                program1665(0),
                program1666(1),
                program1667(2),
                program1668(3),
                program1669(4),
                program1670(5),
                program1671(6),
                program1672(7),
                program1673(8),
                program1674(9),
                program1675(10),
                program1676(11),
                program1677(12),
                program1678(13),
                program1679(14),
                program1680(15),
                program1681(16),
                program1682(17),
                program1683(18),
                program1684(19),
                program1685(20),
                program1686(21),
                program1687(22),
                program1688(23),
                program1689(24),
                program1690(25),
                program1691(26),
                program1692(27),
                program1693(28),
                program1694(29),
                program1695(30),
                program1696(31),
                program1697(32),
                program1698(33),
                program1699(34),
                program1700(35),
                program1701(36),
                program1702(37),
                program1703(38),
                program1704(39),
                program1705(40),
                program1706(41),
                program1707(42),
                program1708(43),
                program1709(44),
                program1710(45),
                program1711(46),
                program1712(47),
                program1713(48),
                program1714(49),
                program1715(50),
                program1716(51),
                program1717(52),
                program1718(53),
                program1719(54),
                program1720(55),
                program1721(56),
                program1722(57),
                program1723(58),
                program1724(59),
                program1725(60),
                program1726(61),
                program1727(62),
                program1728(63),
                program1729(64),
                program1730(65),
                program1731(66),
                program1732(67),
                program1733(68),
                program1734(69),
                program1735(70),
                program1736(71),
                program1737(72),
                program1738(73),
                program1739(74),
                program1740(75),
                program1741(76),
                program1742(77),
                program1743(78),
                program1744(79),
                program1745(80),
                program1746(81),
                program1747(82),
                program1748(83),
                program1749(84),
                program1750(85),
                program1751(86),
                program1752(87),
                program1753(88),
                program1754(89),
                program1755(90),
                program1756(91),
                program1757(92),
                program1758(93),
                program1759(94),
                program1760(95),
                program1761(96),
                program1762(97),
                program1763(98),
                program1764(99),
                program1765(100),
                program1766(101),
                program1767(102),
                program1768(103),
                program1769(104),
                program1770(105),
                program1771(106),
                program1772(107),
                program1773(108),
                program1774(109),
                program1775(110),
                program1776(111),
                program1777(112),
                program1778(113),
                program1779(114),
                program1780(115),
                program1781(116),
                program1782(117),
                program1783(118),
                program1784(119),
                program1785(120),
                program1786(121),
                program1787(122),
                program1788(123),
                program1789(124),
                program1790(125),
                program1791(126),
                program1792(127)
                }
            MAX-ACCESS read-write
            STATUS current
            DESCRIPTION
                "Indicates the program mask. This leaf indicates the authority of programs with indexes 833-896, 
                 64 programs in total. The indication methods of other mast leaves are the same as this table.
                 Each two bits indicate the authority to a program. Meanings of a 2-bit mask:
                 1. Forbidden(11)
                 2. Watch(01)
                 3. Preview(10)
                 4. idle(00)
                "
            ::= { hwDslamNtvRightProfileEntry 20 }                    
        
        hwDslamNtvProgramMask15 OBJECT-TYPE
            SYNTAX BITS
                {
                program1793(0),
                program1794(1),
                program1795(2),
                program1796(3),
                program1797(4),
                program1798(5),
                program1799(6),
                program1800(7),
                program1801(8),
                program1802(9),
                program1803(10),
                program1804(11),
                program1805(12),
                program1806(13),
                program1807(14),
                program1808(15),
                program1809(16),
                program1810(17),
                program1811(18),
                program1812(19),
                program1813(20),
                program1814(21),
                program1815(22),
                program1816(23),
                program1817(24),
                program1818(25),
                program1819(26),
                program1820(27),
                program1821(28),
                program1822(29),
                program1823(30),
                program1824(31),
                program1825(32),
                program1826(33),
                program1827(34),
                program1828(35),
                program1829(36),
                program1830(37),
                program1831(38),
                program1832(39),
                program1833(40),
                program1834(41),
                program1835(42),
                program1836(43),
                program1837(44),
                program1838(45),
                program1839(46),
                program1840(47),
                program1841(48),
                program1842(49),
                program1843(50),
                program1844(51),
                program1845(52),
                program1846(53),
                program1847(54),
                program1848(55),
                program1849(56),
                program1850(57),
                program1851(58),
                program1852(59),
                program1853(60),
                program1854(61),
                program1855(62),
                program1856(63),
                program1857(64),
                program1858(65),
                program1859(66),
                program1860(67),
                program1861(68),
                program1862(69),
                program1863(70),
                program1864(71),
                program1865(72),
                program1866(73),
                program1867(74),
                program1868(75),
                program1869(76),
                program1870(77),
                program1871(78),
                program1872(79),
                program1873(80),
                program1874(81),
                program1875(82),
                program1876(83),
                program1877(84),
                program1878(85),
                program1879(86),
                program1880(87),
                program1881(88),
                program1882(89),
                program1883(90),
                program1884(91),
                program1885(92),
                program1886(93),
                program1887(94),
                program1888(95),
                program1889(96),
                program1890(97),
                program1891(98),
                program1892(99),
                program1893(100),
                program1894(101),
                program1895(102),
                program1896(103),
                program1897(104),
                program1898(105),
                program1899(106),
                program1900(107),
                program1901(108),
                program1902(109),
                program1903(110),
                program1904(111),
                program1905(112),
                program1906(113),
                program1907(114),
                program1908(115),
                program1909(116),
                program1910(117),
                program1911(118),
                program1912(119),
                program1913(120),
                program1914(121),
                program1915(122),
                program1916(123),
                program1917(124),
                program1918(125),
                program1919(126),
                program1920(127)
                }
            MAX-ACCESS read-write
            STATUS current
            DESCRIPTION
                "Indicates the program mask. This leaf indicates the authority of programs with indexes 897-960, 
                 64 programs in total. The indication methods of other mast leaves are the same as this table.
                 Each two bits indicate the authority to a program. Meanings of a 2-bit mask:
                 1. Forbidden(11)
                 2. Watch(01)
                 3. Preview(10)
                 4. idle(00)
                "
            ::= { hwDslamNtvRightProfileEntry 21 }        
        
        hwDslamNtvProgramMask16 OBJECT-TYPE
            SYNTAX BITS
                {
                program1921(0),
                program1922(1),
                program1923(2),
                program1924(3),
                program1925(4),
                program1926(5),
                program1927(6),
                program1928(7),
                program1929(8),
                program1930(9),
                program1931(10),
                program1932(11),
                program1933(12),
                program1934(13),
                program1935(14),
                program1936(15),
                program1937(16),
                program1938(17),
                program1939(18),
                program1940(19),
                program1941(20),
                program1942(21),
                program1943(22),
                program1944(23),
                program1945(24),
                program1946(25),
                program1947(26),
                program1948(27),
                program1949(28),
                program1950(29),
                program1951(30),
                program1952(31),
                program1953(32),
                program1954(33),
                program1955(34),
                program1956(35),
                program1957(36),
                program1958(37),
                program1959(38),
                program1960(39),
                program1961(40),
                program1962(41),
                program1963(42),
                program1964(43),
                program1965(44),
                program1966(45),
                program1967(46),
                program1968(47),
                program1969(48),
                program1970(49),
                program1971(50),
                program1972(51),
                program1973(52),
                program1974(53),
                program1975(54),
                program1976(55),
                program1977(56),
                program1978(57),
                program1979(58),
                program1980(59),
                program1981(60),
                program1982(61),
                program1983(62),
                program1984(63),
                program1985(64),
                program1986(65),
                program1987(66),
                program1988(67),
                program1989(68),
                program1990(69),
                program1991(70),
                program1992(71),
                program1993(72),
                program1994(73),
                program1995(74),
                program1996(75),
                program1997(76),
                program1998(77),
                program1999(78),
                program2000(79),
                program2001(80),
                program2002(81),
                program2003(82),
                program2004(83),
                program2005(84),
                program2006(85),
                program2007(86),
                program2008(87),
                program2009(88),
                program2010(89),
                program2011(90),
                program2012(91),
                program2013(92),
                program2014(93),
                program2015(94),
                program2016(95),
                program2017(96),
                program2018(97),
                program2019(98),
                program2020(99),
                program2021(100),
                program2022(101),
                program2023(102),
                program2024(103),
                program2025(104),
                program2026(105),
                program2027(106),
                program2028(107),
                program2029(108),
                program2030(109),
                program2031(110),
                program2032(111),
                program2033(112),
                program2034(113),
                program2035(114),
                program2036(115),
                program2037(116),
                program2038(117),
                program2039(118),
                program2040(119),
                program2041(120),
                program2042(121),
                program2043(122),
                program2044(123),
                program2045(124),
                program2046(125),
                program2047(126),
                program2048(127)
                }
            MAX-ACCESS read-write
            STATUS current
            DESCRIPTION
                "Indicates the program mask. This leaf indicates the authority of programs with indexes 961-1024, 
                 64 programs in total. The indication methods of other mast leaves are the same as this table.
                 Each two bits indicate the authority to a program. Meanings of a 2-bit mask:
                 1. Forbidden(11)
                 2. Watch(01)
                 3. Preview(10)
                 4. idle(00)
                "
            ::= { hwDslamNtvRightProfileEntry 22 }        
        
        hwDslamNtvProgramMask17 OBJECT-TYPE
            SYNTAX BITS
                {
                program2049(0),
                program2050(1),
                program2051(2),
                program2052(3),
                program2053(4),
                program2054(5),
                program2055(6),
                program2056(7),
                program2057(8),
                program2058(9),
                program2059(10),
                program2060(11),
                program2061(12),
                program2062(13),
                program2063(14),
                program2064(15),
                program2065(16),
                program2066(17),
                program2067(18),
                program2068(19),
                program2069(20),
                program2070(21),
                program2071(22),
                program2072(23),
                program2073(24),
                program2074(25),
                program2075(26),
                program2076(27),
                program2077(28),
                program2078(29),
                program2079(30),
                program2080(31),
                program2081(32),
                program2082(33),
                program2083(34),
                program2084(35),
                program2085(36),
                program2086(37),
                program2087(38),
                program2088(39),
                program2089(40),
                program2090(41),
                program2091(42),
                program2092(43),
                program2093(44),
                program2094(45),
                program2095(46),
                program2096(47),
                program2097(48),
                program2098(49),
                program2099(50),
                program2100(51),
                program2101(52),
                program2102(53),
                program2103(54),
                program2104(55),
                program2105(56),
                program2106(57),
                program2107(58),
                program2108(59),
                program2109(60),
                program2110(61),
                program2111(62),
                program2112(63),
                program2113(64),
                program2114(65),
                program2115(66),
                program2116(67),
                program2117(68),
                program2118(69),
                program2119(70),
                program2120(71),
                program2121(72),
                program2122(73),
                program2123(74),
                program2124(75),
                program2125(76),
                program2126(77),
                program2127(78),
                program2128(79),
                program2129(80),
                program2130(81),
                program2131(82),
                program2132(83),
                program2133(84),
                program2134(85),
                program2135(86),
                program2136(87),
                program2137(88),
                program2138(89),
                program2139(90),
                program2140(91),
                program2141(92),
                program2142(93),
                program2143(94),
                program2144(95),
                program2145(96),
                program2146(97),
                program2147(98),
                program2148(99),
                program2149(100),
                program2150(101),
                program2151(102),
                program2152(103),
                program2153(104),
                program2154(105),
                program2155(106),
                program2156(107),
                program2157(108),
                program2158(109),
                program2159(110),
                program2160(111),
                program2161(112),
                program2162(113),
                program2163(114),
                program2164(115),
                program2165(116),
                program2166(117),
                program2167(118),
                program2168(119),
                program2169(120),
                program2170(121),
                program2171(122),
                program2172(123),
                program2173(124),
                program2174(125),
                program2175(126),
                program2176(127)
                }
            MAX-ACCESS read-write
            STATUS current
            DESCRIPTION
                "Indicates the program mask. This leaf indicates the authority of programs with indexes 1025-1088, 
                 64 programs in total. The indication methods of other mast leaves are the same as this table.
                 Each two bits indicate the authority to a program. Meanings of a 2-bit mask:
                 1. Forbidden(11)
                 2. Watch(01)
                 3. Preview(10)
                 4. idle(00)
                "
            ::= { hwDslamNtvRightProfileEntry 23 }        
        
        hwDslamNtvProgramMask18 OBJECT-TYPE
            SYNTAX BITS
                {
                program2177(0),
                program2178(1),
                program2179(2),
                program2180(3),
                program2181(4),
                program2182(5),
                program2183(6),
                program2184(7),
                program2185(8),
                program2186(9),
                program2187(10),
                program2188(11),
                program2189(12),
                program2190(13),
                program2191(14),
                program2192(15),
                program2193(16),
                program2194(17),
                program2195(18),
                program2196(19),
                program2197(20),
                program2198(21),
                program2199(22),
                program2200(23),
                program2201(24),
                program2202(25),
                program2203(26),
                program2204(27),
                program2205(28),
                program2206(29),
                program2207(30),
                program2208(31),
                program2209(32),
                program2210(33),
                program2211(34),
                program2212(35),
                program2213(36),
                program2214(37),
                program2215(38),
                program2216(39),
                program2217(40),
                program2218(41),
                program2219(42),
                program2220(43),
                program2221(44),
                program2222(45),
                program2223(46),
                program2224(47),
                program2225(48),
                program2226(49),
                program2227(50),
                program2228(51),
                program2229(52),
                program2230(53),
                program2231(54),
                program2232(55),
                program2233(56),
                program2234(57),
                program2235(58),
                program2236(59),
                program2237(60),
                program2238(61),
                program2239(62),
                program2240(63),
                program2241(64),
                program2242(65),
                program2243(66),
                program2244(67),
                program2245(68),
                program2246(69),
                program2247(70),
                program2248(71),
                program2249(72),
                program2250(73),
                program2251(74),
                program2252(75),
                program2253(76),
                program2254(77),
                program2255(78),
                program2256(79),
                program2257(80),
                program2258(81),
                program2259(82),
                program2260(83),
                program2261(84),
                program2262(85),
                program2263(86),
                program2264(87),
                program2265(88),
                program2266(89),
                program2267(90),
                program2268(91),
                program2269(92),
                program2270(93),
                program2271(94),
                program2272(95),
                program2273(96),
                program2274(97),
                program2275(98),
                program2276(99),
                program2277(100),
                program2278(101),
                program2279(102),
                program2280(103),
                program2281(104),
                program2282(105),
                program2283(106),
                program2284(107),
                program2285(108),
                program2286(109),
                program2287(110),
                program2288(111),
                program2289(112),
                program2290(113),
                program2291(114),
                program2292(115),
                program2293(116),
                program2294(117),
                program2295(118),
                program2296(119),
                program2297(120),
                program2298(121),
                program2299(122),
                program2300(123),
                program2301(124),
                program2302(125),
                program2303(126),
                program2304(127)
                }
            MAX-ACCESS read-write
            STATUS current
            DESCRIPTION
                "Indicates the program mask. This leaf indicates the authority of programs with indexes 1089-1152, 
                 64 programs in total. The indication methods of other mast leaves are the same as this table.
                 Each two bits indicate the authority to a program. Meanings of a 2-bit mask:
                 1. Forbidden(11)
                 2. Watch(01)
                 3. Preview(10)
                 4. idle(00)
                "
            ::= { hwDslamNtvRightProfileEntry 24 }        
        
        hwDslamNtvProgramMask19 OBJECT-TYPE
            SYNTAX BITS
                {
                program2305(0),
                program2306(1),
                program2307(2),
                program2308(3),
                program2309(4),
                program2310(5),
                program2311(6),
                program2312(7),
                program2313(8),
                program2314(9),
                program2315(10),
                program2316(11),
                program2317(12),
                program2318(13),
                program2319(14),
                program2320(15),
                program2321(16),
                program2322(17),
                program2323(18),
                program2324(19),
                program2325(20),
                program2326(21),
                program2327(22),
                program2328(23),
                program2329(24),
                program2330(25),
                program2331(26),
                program2332(27),
                program2333(28),
                program2334(29),
                program2335(30),
                program2336(31),
                program2337(32),
                program2338(33),
                program2339(34),
                program2340(35),
                program2341(36),
                program2342(37),
                program2343(38),
                program2344(39),
                program2345(40),
                program2346(41),
                program2347(42),
                program2348(43),
                program2349(44),
                program2350(45),
                program2351(46),
                program2352(47),
                program2353(48),
                program2354(49),
                program2355(50),
                program2356(51),
                program2357(52),
                program2358(53),
                program2359(54),
                program2360(55),
                program2361(56),
                program2362(57),
                program2363(58),
                program2364(59),
                program2365(60),
                program2366(61),
                program2367(62),
                program2368(63),
                program2369(64),
                program2370(65),
                program2371(66),
                program2372(67),
                program2373(68),
                program2374(69),
                program2375(70),
                program2376(71),
                program2377(72),
                program2378(73),
                program2379(74),
                program2380(75),
                program2381(76),
                program2382(77),
                program2383(78),
                program2384(79),
                program2385(80),
                program2386(81),
                program2387(82),
                program2388(83),
                program2389(84),
                program2390(85),
                program2391(86),
                program2392(87),
                program2393(88),
                program2394(89),
                program2395(90),
                program2396(91),
                program2397(92),
                program2398(93),
                program2399(94),
                program2400(95),
                program2401(96),
                program2402(97),
                program2403(98),
                program2404(99),
                program2405(100),
                program2406(101),
                program2407(102),
                program2408(103),
                program2409(104),
                program2410(105),
                program2411(106),
                program2412(107),
                program2413(108),
                program2414(109),
                program2415(110),
                program2416(111),
                program2417(112),
                program2418(113),
                program2419(114),
                program2420(115),
                program2421(116),
                program2422(117),
                program2423(118),
                program2424(119),
                program2425(120),
                program2426(121),
                program2427(122),
                program2428(123),
                program2429(124),
                program2430(125),
                program2431(126),
                program2432(127)
                }
            MAX-ACCESS read-write
            STATUS current
            DESCRIPTION
                "Indicates the program mask. This leaf indicates the authority of programs with indexes 1153-1216, 
                 64 programs in total. The indication methods of other mast leaves are the same as this table.
                 Each two bits indicate the authority to a program. Meanings of a 2-bit mask:
                 1. Forbidden(11)
                 2. Watch(01)
                 3. Preview(10)
                 4. idle(00)
                "
            ::= { hwDslamNtvRightProfileEntry 25 }
        
        
        hwDslamNtvProgramMask20 OBJECT-TYPE
            SYNTAX BITS
                {
                program2433(0),
                program2434(1),
                program2435(2),
                program2436(3),
                program2437(4),
                program2438(5),
                program2439(6),
                program2440(7),
                program2441(8),
                program2442(9),
                program2443(10),
                program2444(11),
                program2445(12),
                program2446(13),
                program2447(14),
                program2448(15),
                program2449(16),
                program2450(17),
                program2451(18),
                program2452(19),
                program2453(20),
                program2454(21),
                program2455(22),
                program2456(23),
                program2457(24),
                program2458(25),
                program2459(26),
                program2460(27),
                program2461(28),
                program2462(29),
                program2463(30),
                program2464(31),
                program2465(32),
                program2466(33),
                program2467(34),
                program2468(35),
                program2469(36),
                program2470(37),
                program2471(38),
                program2472(39),
                program2473(40),
                program2474(41),
                program2475(42),
                program2476(43),
                program2477(44),
                program2478(45),
                program2479(46),
                program2480(47),
                program2481(48),
                program2482(49),
                program2483(50),
                program2484(51),
                program2485(52),
                program2486(53),
                program2487(54),
                program2488(55),
                program2489(56),
                program2490(57),
                program2491(58),
                program2492(59),
                program2493(60),
                program2494(61),
                program2495(62),
                program2496(63),
                program2497(64),
                program2498(65),
                program2499(66),
                program2500(67),
                program2501(68),
                program2502(69),
                program2503(70),
                program2504(71),
                program2505(72),
                program2506(73),
                program2507(74),
                program2508(75),
                program2509(76),
                program2510(77),
                program2511(78),
                program2512(79),
                program2513(80),
                program2514(81),
                program2515(82),
                program2516(83),
                program2517(84),
                program2518(85),
                program2519(86),
                program2520(87),
                program2521(88),
                program2522(89),
                program2523(90),
                program2524(91),
                program2525(92),
                program2526(93),
                program2527(94),
                program2528(95),
                program2529(96),
                program2530(97),
                program2531(98),
                program2532(99),
                program2533(100),
                program2534(101),
                program2535(102),
                program2536(103),
                program2537(104),
                program2538(105),
                program2539(106),
                program2540(107),
                program2541(108),
                program2542(109),
                program2543(110),
                program2544(111),
                program2545(112),
                program2546(113),
                program2547(114),
                program2548(115),
                program2549(116),
                program2550(117),
                program2551(118),
                program2552(119),
                program2553(120),
                program2554(121),
                program2555(122),
                program2556(123),
                program2557(124),
                program2558(125),
                program2559(126),
                program2560(127)
                }
            MAX-ACCESS read-write
            STATUS current
            DESCRIPTION
                "Indicates the program mask. This leaf indicates the authority of programs with indexes 1217-1280, 
                 64 programs in total. The indication methods of other mast leaves are the same as this table.
                 Each two bits indicate the authority to a program. Meanings of a 2-bit mask:
                 1. Forbidden(11)
                 2. Watch(01)
                 3. Preview(10)
                 4. idle(00)
                "
            ::= { hwDslamNtvRightProfileEntry 26 }
        
        hwDslamNtvProgramMask21 OBJECT-TYPE
            SYNTAX BITS
                {
                program2561(0),
                program2562(1),
                program2563(2),
                program2564(3),
                program2565(4),
                program2566(5),
                program2567(6),
                program2568(7),
                program2569(8),
                program2570(9),
                program2571(10),
                program2572(11),
                program2573(12),
                program2574(13),
                program2575(14),
                program2576(15),
                program2577(16),
                program2578(17),
                program2579(18),
                program2580(19),
                program2581(20),
                program2582(21),
                program2583(22),
                program2584(23),
                program2585(24),
                program2586(25),
                program2587(26),
                program2588(27),
                program2589(28),
                program2590(29),
                program2591(30),
                program2592(31),
                program2593(32),
                program2594(33),
                program2595(34),
                program2596(35),
                program2597(36),
                program2598(37),
                program2599(38),
                program2600(39),
                program2601(40),
                program2602(41),
                program2603(42),
                program2604(43),
                program2605(44),
                program2606(45),
                program2607(46),
                program2608(47),
                program2609(48),
                program2610(49),
                program2611(50),
                program2612(51),
                program2613(52),
                program2614(53),
                program2615(54),
                program2616(55),
                program2617(56),
                program2618(57),
                program2619(58),
                program2620(59),
                program2621(60),
                program2622(61),
                program2623(62),
                program2624(63),
                program2625(64),
                program2626(65),
                program2627(66),
                program2628(67),
                program2629(68),
                program2630(69),
                program2631(70),
                program2632(71),
                program2633(72),
                program2634(73),
                program2635(74),
                program2636(75),
                program2637(76),
                program2638(77),
                program2639(78),
                program2640(79),
                program2641(80),
                program2642(81),
                program2643(82),
                program2644(83),
                program2645(84),
                program2646(85),
                program2647(86),
                program2648(87),
                program2649(88),
                program2650(89),
                program2651(90),
                program2652(91),
                program2653(92),
                program2654(93),
                program2655(94),
                program2656(95),
                program2657(96),
                program2658(97),
                program2659(98),
                program2660(99),
                program2661(100),
                program2662(101),
                program2663(102),
                program2664(103),
                program2665(104),
                program2666(105),
                program2667(106),
                program2668(107),
                program2669(108),
                program2670(109),
                program2671(110),
                program2672(111),
                program2673(112),
                program2674(113),
                program2675(114),
                program2676(115),
                program2677(116),
                program2678(117),
                program2679(118),
                program2680(119),
                program2681(120),
                program2682(121),
                program2683(122),
                program2684(123),
                program2685(124),
                program2686(125),
                program2687(126),
                program2688(127)
                }
            MAX-ACCESS read-write
            STATUS current
            DESCRIPTION
                "Indicates the program mask. This leaf indicates the authority of programs with indexes 1281-1344, 
                 64 programs in total. The indication methods of other mast leaves are the same as this table.
                 Each two bits indicate the authority to a program. Meanings of a 2-bit mask:
                 1. Forbidden(11)
                 2. Watch(01)
                 3. Preview(10)
                 4. idle(00)
                "
            ::= { hwDslamNtvRightProfileEntry 27 }
        
        hwDslamNtvProgramMask22 OBJECT-TYPE
            SYNTAX BITS
                {
                program2689(0),
                program2690(1),
                program2691(2),
                program2692(3),
                program2693(4),
                program2694(5),
                program2695(6),
                program2696(7),
                program2697(8),
                program2698(9),
                program2699(10),
                program2700(11),
                program2701(12),
                program2702(13),
                program2703(14),
                program2704(15),
                program2705(16),
                program2706(17),
                program2707(18),
                program2708(19),
                program2709(20),
                program2710(21),
                program2711(22),
                program2712(23),
                program2713(24),
                program2714(25),
                program2715(26),
                program2716(27),
                program2717(28),
                program2718(29),
                program2719(30),
                program2720(31),
                program2721(32),
                program2722(33),
                program2723(34),
                program2724(35),
                program2725(36),
                program2726(37),
                program2727(38),
                program2728(39),
                program2729(40),
                program2730(41),
                program2731(42),
                program2732(43),
                program2733(44),
                program2734(45),
                program2735(46),
                program2736(47),
                program2737(48),
                program2738(49),
                program2739(50),
                program2740(51),
                program2741(52),
                program2742(53),
                program2743(54),
                program2744(55),
                program2745(56),
                program2746(57),
                program2747(58),
                program2748(59),
                program2749(60),
                program2750(61),
                program2751(62),
                program2752(63),
                program2753(64),
                program2754(65),
                program2755(66),
                program2756(67),
                program2757(68),
                program2758(69),
                program2759(70),
                program2760(71),
                program2761(72),
                program2762(73),
                program2763(74),
                program2764(75),
                program2765(76),
                program2766(77),
                program2767(78),
                program2768(79),
                program2769(80),
                program2770(81),
                program2771(82),
                program2772(83),
                program2773(84),
                program2774(85),
                program2775(86),
                program2776(87),
                program2777(88),
                program2778(89),
                program2779(90),
                program2780(91),
                program2781(92),
                program2782(93),
                program2783(94),
                program2784(95),
                program2785(96),
                program2786(97),
                program2787(98),
                program2788(99),
                program2789(100),
                program2790(101),
                program2791(102),
                program2792(103),
                program2793(104),
                program2794(105),
                program2795(106),
                program2796(107),
                program2797(108),
                program2798(109),
                program2799(110),
                program2800(111),
                program2801(112),
                program2802(113),
                program2803(114),
                program2804(115),
                program2805(116),
                program2806(117),
                program2807(118),
                program2808(119),
                program2809(120),
                program2810(121),
                program2811(122),
                program2812(123),
                program2813(124),
                program2814(125),
                program2815(126),
                program2816(127)
                }
            MAX-ACCESS read-write
            STATUS current
            DESCRIPTION
                "Indicates the program mask. This leaf indicates the authority of programs with indexes 1345-1408, 
                 64 programs in total. The indication methods of other mast leaves are the same as this table.
                 Each two bits indicate the authority to a program. Meanings of a 2-bit mask:
                 1. Forbidden(11)
                 2. Watch(01)
                 3. Preview(10)
                 4. idle(00)
                "
            ::= { hwDslamNtvRightProfileEntry 28 }
        
        hwDslamNtvProgramMask23 OBJECT-TYPE
            SYNTAX BITS
                {
                program2817(0),
                program2818(1),
                program2819(2),
                program2820(3),
                program2821(4),
                program2822(5),
                program2823(6),
                program2824(7),
                program2825(8),
                program2826(9),
                program2827(10),
                program2828(11),
                program2829(12),
                program2830(13),
                program2831(14),
                program2832(15),
                program2833(16),
                program2834(17),
                program2835(18),
                program2836(19),
                program2837(20),
                program2838(21),
                program2839(22),
                program2840(23),
                program2841(24),
                program2842(25),
                program2843(26),
                program2844(27),
                program2845(28),
                program2846(29),
                program2847(30),
                program2848(31),
                program2849(32),
                program2850(33),
                program2851(34),
                program2852(35),
                program2853(36),
                program2854(37),
                program2855(38),
                program2856(39),
                program2857(40),
                program2858(41),
                program2859(42),
                program2860(43),
                program2861(44),
                program2862(45),
                program2863(46),
                program2864(47),
                program2865(48),
                program2866(49),
                program2867(50),
                program2868(51),
                program2869(52),
                program2870(53),
                program2871(54),
                program2872(55),
                program2873(56),
                program2874(57),
                program2875(58),
                program2876(59),
                program2877(60),
                program2878(61),
                program2879(62),
                program2880(63),
                program2881(64),
                program2882(65),
                program2883(66),
                program2884(67),
                program2885(68),
                program2886(69),
                program2887(70),
                program2888(71),
                program2889(72),
                program2890(73),
                program2891(74),
                program2892(75),
                program2893(76),
                program2894(77),
                program2895(78),
                program2896(79),
                program2897(80),
                program2898(81),
                program2899(82),
                program2900(83),
                program2901(84),
                program2902(85),
                program2903(86),
                program2904(87),
                program2905(88),
                program2906(89),
                program2907(90),
                program2908(91),
                program2909(92),
                program2910(93),
                program2911(94),
                program2912(95),
                program2913(96),
                program2914(97),
                program2915(98),
                program2916(99),
                program2917(100),
                program2918(101),
                program2919(102),
                program2920(103),
                program2921(104),
                program2922(105),
                program2923(106),
                program2924(107),
                program2925(108),
                program2926(109),
                program2927(110),
                program2928(111),
                program2929(112),
                program2930(113),
                program2931(114),
                program2932(115),
                program2933(116),
                program2934(117),
                program2935(118),
                program2936(119),
                program2937(120),
                program2938(121),
                program2939(122),
                program2940(123),
                program2941(124),
                program2942(125),
                program2943(126),
                program2944(127)
                }
            MAX-ACCESS read-write
            STATUS current
            DESCRIPTION
                "Indicates the program mask. This leaf indicates the authority of programs with indexes 1409-1472, 
                 64 programs in total. The indication methods of other mast leaves are the same as this table.
                 Each two bits indicate the authority to a program. Meanings of a 2-bit mask:
                 1. Forbidden(11)
                 2. Watch(01)
                 3. Preview(10)
                 4. idle(00)
                "
            ::= { hwDslamNtvRightProfileEntry 29 }        
        
        hwDslamNtvProgramMask24 OBJECT-TYPE
            SYNTAX BITS
                {
                program2945(0),
                program2946(1),
                program2947(2),
                program2948(3),
                program2949(4),
                program2950(5),
                program2951(6),
                program2952(7),
                program2953(8),
                program2954(9),
                program2955(10),
                program2956(11),
                program2957(12),
                program2958(13),
                program2959(14),
                program2960(15),
                program2961(16),
                program2962(17),
                program2963(18),
                program2964(19),
                program2965(20),
                program2966(21),
                program2967(22),
                program2968(23),
                program2969(24),
                program2970(25),
                program2971(26),
                program2972(27),
                program2973(28),
                program2974(29),
                program2975(30),
                program2976(31),
                program2977(32),
                program2978(33),
                program2979(34),
                program2980(35),
                program2981(36),
                program2982(37),
                program2983(38),
                program2984(39),
                program2985(40),
                program2986(41),
                program2987(42),
                program2988(43),
                program2989(44),
                program2990(45),
                program2991(46),
                program2992(47),
                program2993(48),
                program2994(49),
                program2995(50),
                program2996(51),
                program2997(52),
                program2998(53),
                program2999(54),
                program3000(55),
                program3001(56),
                program3002(57),
                program3003(58),
                program3004(59),
                program3005(60),
                program3006(61),
                program3007(62),
                program3008(63),
                program3009(64),
                program3010(65),
                program3011(66),
                program3012(67),
                program3013(68),
                program3014(69),
                program3015(70),
                program3016(71),
                program3017(72),
                program3018(73),
                program3019(74),
                program3020(75),
                program3021(76),
                program3022(77),
                program3023(78),
                program3024(79),
                program3025(80),
                program3026(81),
                program3027(82),
                program3028(83),
                program3029(84),
                program3030(85),
                program3031(86),
                program3032(87),
                program3033(88),
                program3034(89),
                program3035(90),
                program3036(91),
                program3037(92),
                program3038(93),
                program3039(94),
                program3040(95),
                program3041(96),
                program3042(97),
                program3043(98),
                program3044(99),
                program3045(100),
                program3046(101),
                program3047(102),
                program3048(103),
                program3049(104),
                program3050(105),
                program3051(106),
                program3052(107),
                program3053(108),
                program3054(109),
                program3055(110),
                program3056(111),
                program3057(112),
                program3058(113),
                program3059(114),
                program3060(115),
                program3061(116),
                program3062(117),
                program3063(118),
                program3064(119),
                program3065(120),
                program3066(121),
                program3067(122),
                program3068(123),
                program3069(124),
                program3070(125),
                program3071(126),
                program3072(127)
                }
            MAX-ACCESS read-write
            STATUS current
            DESCRIPTION
                "Indicates the program mask. This leaf indicates the authority of programs with indexes 1473-1536, 
                 64 programs in total. The indication methods of other mast leaves are the same as this table.
                 Each two bits indicate the authority to a program. Meanings of a 2-bit mask:
                 1. Forbidden(11)
                 2. Watch(01)
                 3. Preview(10)
                 4. idle(00)
                "
            ::= { hwDslamNtvRightProfileEntry 30 }        
        
        hwDslamNtvProgramMask25 OBJECT-TYPE
            SYNTAX BITS
                {
                program3073(0),
                program3074(1),
                program3075(2),
                program3076(3),
                program3077(4),
                program3078(5),
                program3079(6),
                program3080(7),
                program3081(8),
                program3082(9),
                program3083(10),
                program3084(11),
                program3085(12),
                program3086(13),
                program3087(14),
                program3088(15),
                program3089(16),
                program3090(17),
                program3091(18),
                program3092(19),
                program3093(20),
                program3094(21),
                program3095(22),
                program3096(23),
                program3097(24),
                program3098(25),
                program3099(26),
                program3100(27),
                program3101(28),
                program3102(29),
                program3103(30),
                program3104(31),
                program3105(32),
                program3106(33),
                program3107(34),
                program3108(35),
                program3109(36),
                program3110(37),
                program3111(38),
                program3112(39),
                program3113(40),
                program3114(41),
                program3115(42),
                program3116(43),
                program3117(44),
                program3118(45),
                program3119(46),
                program3120(47),
                program3121(48),
                program3122(49),
                program3123(50),
                program3124(51),
                program3125(52),
                program3126(53),
                program3127(54),
                program3128(55),
                program3129(56),
                program3130(57),
                program3131(58),
                program3132(59),
                program3133(60),
                program3134(61),
                program3135(62),
                program3136(63),
                program3137(64),
                program3138(65),
                program3139(66),
                program3140(67),
                program3141(68),
                program3142(69),
                program3143(70),
                program3144(71),
                program3145(72),
                program3146(73),
                program3147(74),
                program3148(75),
                program3149(76),
                program3150(77),
                program3151(78),
                program3152(79),
                program3153(80),
                program3154(81),
                program3155(82),
                program3156(83),
                program3157(84),
                program3158(85),
                program3159(86),
                program3160(87),
                program3161(88),
                program3162(89),
                program3163(90),
                program3164(91),
                program3165(92),
                program3166(93),
                program3167(94),
                program3168(95),
                program3169(96),
                program3170(97),
                program3171(98),
                program3172(99),
                program3173(100),
                program3174(101),
                program3175(102),
                program3176(103),
                program3177(104),
                program3178(105),
                program3179(106),
                program3180(107),
                program3181(108),
                program3182(109),
                program3183(110),
                program3184(111),
                program3185(112),
                program3186(113),
                program3187(114),
                program3188(115),
                program3189(116),
                program3190(117),
                program3191(118),
                program3192(119),
                program3193(120),
                program3194(121),
                program3195(122),
                program3196(123),
                program3197(124),
                program3198(125),
                program3199(126),
                program3200(127)
                }
            MAX-ACCESS read-write
            STATUS current
            DESCRIPTION
                "Indicates the program mask. This leaf indicates the authority of programs with indexes 1537-1600, 
                 64 programs in total. The indication methods of other mast leaves are the same as this table.
                 Each two bits indicate the authority to a program. Meanings of a 2-bit mask:
                 1. Forbidden(11)
                 2. Watch(01)
                 3. Preview(10)
                 4. idle(00)
                "
            ::= { hwDslamNtvRightProfileEntry 31 }        
        
        hwDslamNtvProgramMask26 OBJECT-TYPE
            SYNTAX BITS
                {
                program3201(0),
                program3202(1),
                program3203(2),
                program3204(3),
                program3205(4),
                program3206(5),
                program3207(6),
                program3208(7),
                program3209(8),
                program3210(9),
                program3211(10),
                program3212(11),
                program3213(12),
                program3214(13),
                program3215(14),
                program3216(15),
                program3217(16),
                program3218(17),
                program3219(18),
                program3220(19),
                program3221(20),
                program3222(21),
                program3223(22),
                program3224(23),
                program3225(24),
                program3226(25),
                program3227(26),
                program3228(27),
                program3229(28),
                program3230(29),
                program3231(30),
                program3232(31),
                program3233(32),
                program3234(33),
                program3235(34),
                program3236(35),
                program3237(36),
                program3238(37),
                program3239(38),
                program3240(39),
                program3241(40),
                program3242(41),
                program3243(42),
                program3244(43),
                program3245(44),
                program3246(45),
                program3247(46),
                program3248(47),
                program3249(48),
                program3250(49),
                program3251(50),
                program3252(51),
                program3253(52),
                program3254(53),
                program3255(54),
                program3256(55),
                program3257(56),
                program3258(57),
                program3259(58),
                program3260(59),
                program3261(60),
                program3262(61),
                program3263(62),
                program3264(63),
                program3265(64),
                program3266(65),
                program3267(66),
                program3268(67),
                program3269(68),
                program3270(69),
                program3271(70),
                program3272(71),
                program3273(72),
                program3274(73),
                program3275(74),
                program3276(75),
                program3277(76),
                program3278(77),
                program3279(78),
                program3280(79),
                program3281(80),
                program3282(81),
                program3283(82),
                program3284(83),
                program3285(84),
                program3286(85),
                program3287(86),
                program3288(87),
                program3289(88),
                program3290(89),
                program3291(90),
                program3292(91),
                program3293(92),
                program3294(93),
                program3295(94),
                program3296(95),
                program3297(96),
                program3298(97),
                program3299(98),
                program3300(99),
                program3301(100),
                program3302(101),
                program3303(102),
                program3304(103),
                program3305(104),
                program3306(105),
                program3307(106),
                program3308(107),
                program3309(108),
                program3310(109),
                program3311(110),
                program3312(111),
                program3313(112),
                program3314(113),
                program3315(114),
                program3316(115),
                program3317(116),
                program3318(117),
                program3319(118),
                program3320(119),
                program3321(120),
                program3322(121),
                program3323(122),
                program3324(123),
                program3325(124),
                program3326(125),
                program3327(126),
                program3328(127)
                }
            MAX-ACCESS read-write
            STATUS current
            DESCRIPTION
                "Indicates the program mask. This leaf indicates the authority of programs with indexes 1601-1664, 
                 64 programs in total. The indication methods of other mast leaves are the same as this table.
                 Each two bits indicate the authority to a program. Meanings of a 2-bit mask:
                 1. Forbidden(11)
                 2. Watch(01)
                 3. Preview(10)
                 4. idle(00)
                "
            ::= { hwDslamNtvRightProfileEntry 32 }        
        
        hwDslamNtvProgramMask27 OBJECT-TYPE
            SYNTAX BITS
                {
                program3329(0),
                program3330(1),
                program3331(2),
                program3332(3),
                program3333(4),
                program3334(5),
                program3335(6),
                program3336(7),
                program3337(8),
                program3338(9),
                program3339(10),
                program3340(11),
                program3341(12),
                program3342(13),
                program3343(14),
                program3344(15),
                program3345(16),
                program3346(17),
                program3347(18),
                program3348(19),
                program3349(20),
                program3350(21),
                program3351(22),
                program3352(23),
                program3353(24),
                program3354(25),
                program3355(26),
                program3356(27),
                program3357(28),
                program3358(29),
                program3359(30),
                program3360(31),
                program3361(32),
                program3362(33),
                program3363(34),
                program3364(35),
                program3365(36),
                program3366(37),
                program3367(38),
                program3368(39),
                program3369(40),
                program3370(41),
                program3371(42),
                program3372(43),
                program3373(44),
                program3374(45),
                program3375(46),
                program3376(47),
                program3377(48),
                program3378(49),
                program3379(50),
                program3380(51),
                program3381(52),
                program3382(53),
                program3383(54),
                program3384(55),
                program3385(56),
                program3386(57),
                program3387(58),
                program3388(59),
                program3389(60),
                program3390(61),
                program3391(62),
                program3392(63),
                program3393(64),
                program3394(65),
                program3395(66),
                program3396(67),
                program3397(68),
                program3398(69),
                program3399(70),
                program3400(71),
                program3401(72),
                program3402(73),
                program3403(74),
                program3404(75),
                program3405(76),
                program3406(77),
                program3407(78),
                program3408(79),
                program3409(80),
                program3410(81),
                program3411(82),
                program3412(83),
                program3413(84),
                program3414(85),
                program3415(86),
                program3416(87),
                program3417(88),
                program3418(89),
                program3419(90),
                program3420(91),
                program3421(92),
                program3422(93),
                program3423(94),
                program3424(95),
                program3425(96),
                program3426(97),
                program3427(98),
                program3428(99),
                program3429(100),
                program3430(101),
                program3431(102),
                program3432(103),
                program3433(104),
                program3434(105),
                program3435(106),
                program3436(107),
                program3437(108),
                program3438(109),
                program3439(110),
                program3440(111),
                program3441(112),
                program3442(113),
                program3443(114),
                program3444(115),
                program3445(116),
                program3446(117),
                program3447(118),
                program3448(119),
                program3449(120),
                program3450(121),
                program3451(122),
                program3452(123),
                program3453(124),
                program3454(125),
                program3455(126),
                program3456(127)
                }
            MAX-ACCESS read-write
            STATUS current
            DESCRIPTION
                "Indicates the program mask. This leaf indicates the authority of programs with indexes 1665-1728, 
                 64 programs in total. The indication methods of other mast leaves are the same as this table.
                 Each two bits indicate the authority to a program. Meanings of a 2-bit mask:
                 1. Forbidden(11)
                 2. Watch(01)
                 3. Preview(10)
                 4. idle(00)
                "
            ::= { hwDslamNtvRightProfileEntry 33 }        
        
        hwDslamNtvProgramMask28 OBJECT-TYPE
            SYNTAX BITS
                {
                program3457(0),
                program3458(1),
                program3459(2),
                program3460(3),
                program3461(4),
                program3462(5),
                program3463(6),
                program3464(7),
                program3465(8),
                program3466(9),
                program3467(10),
                program3468(11),
                program3469(12),
                program3470(13),
                program3471(14),
                program3472(15),
                program3473(16),
                program3474(17),
                program3475(18),
                program3476(19),
                program3477(20),
                program3478(21),
                program3479(22),
                program3480(23),
                program3481(24),
                program3482(25),
                program3483(26),
                program3484(27),
                program3485(28),
                program3486(29),
                program3487(30),
                program3488(31),
                program3489(32),
                program3490(33),
                program3491(34),
                program3492(35),
                program3493(36),
                program3494(37),
                program3495(38),
                program3496(39),
                program3497(40),
                program3498(41),
                program3499(42),
                program3500(43),
                program3501(44),
                program3502(45),
                program3503(46),
                program3504(47),
                program3505(48),
                program3506(49),
                program3507(50),
                program3508(51),
                program3509(52),
                program3510(53),
                program3511(54),
                program3512(55),
                program3513(56),
                program3514(57),
                program3515(58),
                program3516(59),
                program3517(60),
                program3518(61),
                program3519(62),
                program3520(63),
                program3521(64),
                program3522(65),
                program3523(66),
                program3524(67),
                program3525(68),
                program3526(69),
                program3527(70),
                program3528(71),
                program3529(72),
                program3530(73),
                program3531(74),
                program3532(75),
                program3533(76),
                program3534(77),
                program3535(78),
                program3536(79),
                program3537(80),
                program3538(81),
                program3539(82),
                program3540(83),
                program3541(84),
                program3542(85),
                program3543(86),
                program3544(87),
                program3545(88),
                program3546(89),
                program3547(90),
                program3548(91),
                program3549(92),
                program3550(93),
                program3551(94),
                program3552(95),
                program3553(96),
                program3554(97),
                program3555(98),
                program3556(99),
                program3557(100),
                program3558(101),
                program3559(102),
                program3560(103),
                program3561(104),
                program3562(105),
                program3563(106),
                program3564(107),
                program3565(108),
                program3566(109),
                program3567(110),
                program3568(111),
                program3569(112),
                program3570(113),
                program3571(114),
                program3572(115),
                program3573(116),
                program3574(117),
                program3575(118),
                program3576(119),
                program3577(120),
                program3578(121),
                program3579(122),
                program3580(123),
                program3581(124),
                program3582(125),
                program3583(126),
                program3584(127)
                }
            MAX-ACCESS read-write
            STATUS current
            DESCRIPTION
                "Indicates the program mask. This leaf indicates the authority of programs with indexes 1729-1792, 
                 64 programs in total. The indication methods of other mast leaves are the same as this table.
                 Each two bits indicate the authority to a program. Meanings of a 2-bit mask:
                 1. Forbidden(11)
                 2. Watch(01)
                 3. Preview(10)
                 4. idle(00)
                "
            ::= { hwDslamNtvRightProfileEntry 34 }        
        
        hwDslamNtvProgramMask29 OBJECT-TYPE
            SYNTAX BITS
                {
                program3585(0),
                program3586(1),
                program3587(2),
                program3588(3),
                program3589(4),
                program3590(5),
                program3591(6),
                program3592(7),
                program3593(8),
                program3594(9),
                program3595(10),
                program3596(11),
                program3597(12),
                program3598(13),
                program3599(14),
                program3600(15),
                program3601(16),
                program3602(17),
                program3603(18),
                program3604(19),
                program3605(20),
                program3606(21),
                program3607(22),
                program3608(23),
                program3609(24),
                program3610(25),
                program3611(26),
                program3612(27),
                program3613(28),
                program3614(29),
                program3615(30),
                program3616(31),
                program3617(32),
                program3618(33),
                program3619(34),
                program3620(35),
                program3621(36),
                program3622(37),
                program3623(38),
                program3624(39),
                program3625(40),
                program3626(41),
                program3627(42),
                program3628(43),
                program3629(44),
                program3630(45),
                program3631(46),
                program3632(47),
                program3633(48),
                program3634(49),
                program3635(50),
                program3636(51),
                program3637(52),
                program3638(53),
                program3639(54),
                program3640(55),
                program3641(56),
                program3642(57),
                program3643(58),
                program3644(59),
                program3645(60),
                program3646(61),
                program3647(62),
                program3648(63),
                program3649(64),
                program3650(65),
                program3651(66),
                program3652(67),
                program3653(68),
                program3654(69),
                program3655(70),
                program3656(71),
                program3657(72),
                program3658(73),
                program3659(74),
                program3660(75),
                program3661(76),
                program3662(77),
                program3663(78),
                program3664(79),
                program3665(80),
                program3666(81),
                program3667(82),
                program3668(83),
                program3669(84),
                program3670(85),
                program3671(86),
                program3672(87),
                program3673(88),
                program3674(89),
                program3675(90),
                program3676(91),
                program3677(92),
                program3678(93),
                program3679(94),
                program3680(95),
                program3681(96),
                program3682(97),
                program3683(98),
                program3684(99),
                program3685(100),
                program3686(101),
                program3687(102),
                program3688(103),
                program3689(104),
                program3690(105),
                program3691(106),
                program3692(107),
                program3693(108),
                program3694(109),
                program3695(110),
                program3696(111),
                program3697(112),
                program3698(113),
                program3699(114),
                program3700(115),
                program3701(116),
                program3702(117),
                program3703(118),
                program3704(119),
                program3705(120),
                program3706(121),
                program3707(122),
                program3708(123),
                program3709(124),
                program3710(125),
                program3711(126),
                program3712(127)
                }
            MAX-ACCESS read-write
            STATUS current
            DESCRIPTION
                "Indicates the program mask. This leaf indicates the authority of programs with indexes 1793-1856, 
                 64 programs in total. The indication methods of other mast leaves are the same as this table.
                 Each two bits indicate the authority to a program. Meanings of a 2-bit mask:
                 1. Forbidden(11)
                 2. Watch(01)
                 3. Preview(10)
                 4. idle(00)
                "
            ::= { hwDslamNtvRightProfileEntry 35 }        
        
        hwDslamNtvProgramMask30 OBJECT-TYPE
            SYNTAX BITS
                {
                program3713(0),
                program3714(1),
                program3715(2),
                program3716(3),
                program3717(4),
                program3718(5),
                program3719(6),
                program3720(7),
                program3721(8),
                program3722(9),
                program3723(10),
                program3724(11),
                program3725(12),
                program3726(13),
                program3727(14),
                program3728(15),
                program3729(16),
                program3730(17),
                program3731(18),
                program3732(19),
                program3733(20),
                program3734(21),
                program3735(22),
                program3736(23),
                program3737(24),
                program3738(25),
                program3739(26),
                program3740(27),
                program3741(28),
                program3742(29),
                program3743(30),
                program3744(31),
                program3745(32),
                program3746(33),
                program3747(34),
                program3748(35),
                program3749(36),
                program3750(37),
                program3751(38),
                program3752(39),
                program3753(40),
                program3754(41),
                program3755(42),
                program3756(43),
                program3757(44),
                program3758(45),
                program3759(46),
                program3760(47),
                program3761(48),
                program3762(49),
                program3763(50),
                program3764(51),
                program3765(52),
                program3766(53),
                program3767(54),
                program3768(55),
                program3769(56),
                program3770(57),
                program3771(58),
                program3772(59),
                program3773(60),
                program3774(61),
                program3775(62),
                program3776(63),
                program3777(64),
                program3778(65),
                program3779(66),
                program3780(67),
                program3781(68),
                program3782(69),
                program3783(70),
                program3784(71),
                program3785(72),
                program3786(73),
                program3787(74),
                program3788(75),
                program3789(76),
                program3790(77),
                program3791(78),
                program3792(79),
                program3793(80),
                program3794(81),
                program3795(82),
                program3796(83),
                program3797(84),
                program3798(85),
                program3799(86),
                program3800(87),
                program3801(88),
                program3802(89),
                program3803(90),
                program3804(91),
                program3805(92),
                program3806(93),
                program3807(94),
                program3808(95),
                program3809(96),
                program3810(97),
                program3811(98),
                program3812(99),
                program3813(100),
                program3814(101),
                program3815(102),
                program3816(103),
                program3817(104),
                program3818(105),
                program3819(106),
                program3820(107),
                program3821(108),
                program3822(109),
                program3823(110),
                program3824(111),
                program3825(112),
                program3826(113),
                program3827(114),
                program3828(115),
                program3829(116),
                program3830(117),
                program3831(118),
                program3832(119),
                program3833(120),
                program3834(121),
                program3835(122),
                program3836(123),
                program3837(124),
                program3838(125),
                program3839(126),
                program3840(127)
                }
            MAX-ACCESS read-write
            STATUS current
            DESCRIPTION
                "Indicates the program mask. This leaf indicates the authority of programs with indexes 1857-1920, 
                 64 programs in total. The indication methods of other mast leaves are the same as this table.
                 Each two bits indicate the authority to a program. Meanings of a 2-bit mask:
                 1. Forbidden(11)
                 2. Watch(01)
                 3. Preview(10)
                 4. idle(00)
                "
            ::= { hwDslamNtvRightProfileEntry 36 }        
        
        hwDslamNtvProgramMask31 OBJECT-TYPE
            SYNTAX BITS
                {
                program3841(0),
                program3842(1),
                program3843(2),
                program3844(3),
                program3845(4),
                program3846(5),
                program3847(6),
                program3848(7),
                program3849(8),
                program3850(9),
                program3851(10),
                program3852(11),
                program3853(12),
                program3854(13),
                program3855(14),
                program3856(15),
                program3857(16),
                program3858(17),
                program3859(18),
                program3860(19),
                program3861(20),
                program3862(21),
                program3863(22),
                program3864(23),
                program3865(24),
                program3866(25),
                program3867(26),
                program3868(27),
                program3869(28),
                program3870(29),
                program3871(30),
                program3872(31),
                program3873(32),
                program3874(33),
                program3875(34),
                program3876(35),
                program3877(36),
                program3878(37),
                program3879(38),
                program3880(39),
                program3881(40),
                program3882(41),
                program3883(42),
                program3884(43),
                program3885(44),
                program3886(45),
                program3887(46),
                program3888(47),
                program3889(48),
                program3890(49),
                program3891(50),
                program3892(51),
                program3893(52),
                program3894(53),
                program3895(54),
                program3896(55),
                program3897(56),
                program3898(57),
                program3899(58),
                program3900(59),
                program3901(60),
                program3902(61),
                program3903(62),
                program3904(63),
                program3905(64),
                program3906(65),
                program3907(66),
                program3908(67),
                program3909(68),
                program3910(69),
                program3911(70),
                program3912(71),
                program3913(72),
                program3914(73),
                program3915(74),
                program3916(75),
                program3917(76),
                program3918(77),
                program3919(78),
                program3920(79),
                program3921(80),
                program3922(81),
                program3923(82),
                program3924(83),
                program3925(84),
                program3926(85),
                program3927(86),
                program3928(87),
                program3929(88),
                program3930(89),
                program3931(90),
                program3932(91),
                program3933(92),
                program3934(93),
                program3935(94),
                program3936(95),
                program3937(96),
                program3938(97),
                program3939(98),
                program3940(99),
                program3941(100),
                program3942(101),
                program3943(102),
                program3944(103),
                program3945(104),
                program3946(105),
                program3947(106),
                program3948(107),
                program3949(108),
                program3950(109),
                program3951(110),
                program3952(111),
                program3953(112),
                program3954(113),
                program3955(114),
                program3956(115),
                program3957(116),
                program3958(117),
                program3959(118),
                program3960(119),
                program3961(120),
                program3962(121),
                program3963(122),
                program3964(123),
                program3965(124),
                program3966(125),
                program3967(126),
                program3968(127)
                }
            MAX-ACCESS read-write
            STATUS current
            DESCRIPTION
                "Indicates the program mask. This leaf indicates the authority of programs with indexes 1921-1984, 
                 64 programs in total. The indication methods of other mast leaves are the same as this table.
                 Each two bits indicate the authority to a program. Meanings of a 2-bit mask:
                 1. Forbidden(11)
                 2. Watch(01)
                 3. Preview(10)
                 4. idle(00)
                "
            ::= { hwDslamNtvRightProfileEntry 37 }
        
        hwDslamNtvProgramMask32 OBJECT-TYPE
            SYNTAX BITS
                {
                program3969(0),
                program3970(1),
                program3971(2),
                program3972(3),
                program3973(4),
                program3974(5),
                program3975(6),
                program3976(7),
                program3977(8),
                program3978(9),
                program3979(10),
                program3980(11),
                program3981(12),
                program3982(13),
                program3983(14),
                program3984(15),
                program3985(16),
                program3986(17),
                program3987(18),
                program3988(19),
                program3989(20),
                program3990(21),
                program3991(22),
                program3992(23),
                program3993(24),
                program3994(25),
                program3995(26),
                program3996(27),
                program3997(28),
                program3998(29),
                program3999(30),
                program4000(31),
                program4001(32),
                program4002(33),
                program4003(34),
                program4004(35),
                program4005(36),
                program4006(37),
                program4007(38),
                program4008(39),
                program4009(40),
                program4010(41),
                program4011(42),
                program4012(43),
                program4013(44),
                program4014(45),
                program4015(46),
                program4016(47),
                program4017(48),
                program4018(49),
                program4019(50),
                program4020(51),
                program4021(52),
                program4022(53),
                program4023(54),
                program4024(55),
                program4025(56),
                program4026(57),
                program4027(58),
                program4028(59),
                program4029(60),
                program4030(61),
                program4031(62),
                program4032(63),
                program4033(64),
                program4034(65),
                program4035(66),
                program4036(67),
                program4037(68),
                program4038(69),
                program4039(70),
                program4040(71),
                program4041(72),
                program4042(73),
                program4043(74),
                program4044(75),
                program4045(76),
                program4046(77),
                program4047(78),
                program4048(79),
                program4049(80),
                program4050(81),
                program4051(82),
                program4052(83),
                program4053(84),
                program4054(85),
                program4055(86),
                program4056(87),
                program4057(88),
                program4058(89),
                program4059(90),
                program4060(91),
                program4061(92),
                program4062(93),
                program4063(94),
                program4064(95),
                program4065(96),
                program4066(97),
                program4067(98),
                program4068(99),
                program4069(100),
                program4070(101),
                program4071(102),
                program4072(103),
                program4073(104),
                program4074(105),
                program4075(106),
                program4076(107),
                program4077(108),
                program4078(109),
                program4079(110),
                program4080(111),
                program4081(112),
                program4082(113),
                program4083(114),
                program4084(115),
                program4085(116),
                program4086(117),
                program4087(118),
                program4088(119),
                program4089(120),
                program4090(121),
                program4091(122),
                program4092(123),
                program4093(124),
                program4094(125),
                program4095(126),
                program4096(127)
                }
            MAX-ACCESS read-write
            STATUS current
            DESCRIPTION
                "Indicates the program mask. This leaf indicates the authority of programs with indexes 1985-2048, 
                 64 programs in total. The indication methods of other mast leaves are the same as this table.
                 Each two bits indicate the authority to a program. Meanings of a 2-bit mask:
                 1. Forbidden(11)
                 2. Watch(01)
                 3. Preview(10)
                 4. idle(00)
                "
            ::= { hwDslamNtvRightProfileEntry 38 }                    
        
        hwDslamNtvRightProfileUserRefCount OBJECT-TYPE
            SYNTAX Integer32
            MAX-ACCESS read-only
            STATUS current
            DESCRIPTION
                "Indicates the number of users bound to the profile.
                "
            ::= { hwDslamNtvRightProfileEntry 39 }
            
        hwDslamNtvProgramMask33 OBJECT-TYPE
            SYNTAX BITS
                {
                program4097(0),  
                program4098(1),  
                program4099(2),  
                program4100(3),  
                program4101(4),  
                program4102(5),  
                program4103(6),  
                program4104(7),  
                program4105(8),  
                program4106(9),  
                program4107(10), 
                program4108(11), 
                program4109(12), 
                program4110(13), 
                program4111(14), 
                program4112(15), 
                program4113(16), 
                program4114(17), 
                program4115(18), 
                program4116(19), 
                program4117(20), 
                program4118(21), 
                program4119(22), 
                program4120(23), 
                program4121(24), 
                program4122(25), 
                program4123(26), 
                program4124(27), 
                program4125(28), 
                program4126(29), 
                program4127(30), 
                program4128(31), 
                program4129(32), 
                program4130(33), 
                program4131(34), 
                program4132(35), 
                program4133(36), 
                program4134(37), 
                program4135(38), 
                program4136(39), 
                program4137(40), 
                program4138(41), 
                program4139(42), 
                program4140(43), 
                program4141(44), 
                program4142(45), 
                program4143(46), 
                program4144(47), 
                program4145(48), 
                program4146(49), 
                program4147(50), 
                program4148(51), 
                program4149(52), 
                program4150(53), 
                program4151(54), 
                program4152(55), 
                program4153(56), 
                program4154(57), 
                program4155(58), 
                program4156(59), 
                program4157(60), 
                program4158(61), 
                program4159(62), 
                program4160(63), 
                program4161(64), 
                program4162(65), 
                program4163(66), 
                program4164(67), 
                program4165(68), 
                program4166(69), 
                program4167(70), 
                program4168(71), 
                program4169(72), 
                program4170(73), 
                program4171(74), 
                program4172(75), 
                program4173(76), 
                program4174(77), 
                program4175(78), 
                program4176(79), 
                program4177(80), 
                program4178(81), 
                program4179(82), 
                program4180(83), 
                program4181(84), 
                program4182(85), 
                program4183(86), 
                program4184(87), 
                program4185(88), 
                program4186(89), 
                program4187(90), 
                program4188(91), 
                program4189(92), 
                program4190(93), 
                program4191(94), 
                program4192(95), 
                program4193(96), 
                program4194(97), 
                program4195(98), 
                program4196(99), 
                program4200(103),
                program4197(100),
                program4198(101),
                program4199(102),
                program4201(104),
                program4202(105),
                program4203(106),
                program4204(107),
                program4205(108),
                program4206(109),
                program4207(110),
                program4208(111),
                program4209(112),
                program4210(113),
                program4211(114),
                program4212(115),
                program4213(116),
                program4214(117),
                program4215(118),
                program4216(119),
                program4217(120),
                program4218(121),
                program4219(122),
                program4220(123),
                program4221(124),
                program4222(125),
                program4223(126),
                program4224(127)         
                }
            MAX-ACCESS read-write
            STATUS current
            DESCRIPTION
                "Indicates the program mask. This leaf indicates the authority of programs with indexes 2049-2112, 
                 64 programs in total. The indication methods of other mast leaves are the same as this table.
                 Each two bits indicate the authority to a program. Meanings of a 2-bit mask:
                 1. Forbidden(11)
                 2. Watch(01)
                 3. Preview(10)
                 4. idle(00)
                "
            ::= { hwDslamNtvRightProfileEntry 40 }    
              
        hwDslamNtvProgramMask34 OBJECT-TYPE
            SYNTAX BITS
                {
                program4225(0),  
                program4226(1),  
                program4227(2),  
                program4228(3),  
                program4229(4),  
                program4230(5),  
                program4231(6),  
                program4232(7),  
                program4233(8),  
                program4234(9),  
                program4235(10), 
                program4236(11), 
                program4237(12), 
                program4238(13), 
                program4239(14), 
                program4240(15), 
                program4241(16), 
                program4242(17), 
                program4243(18), 
                program4244(19), 
                program4245(20), 
                program4246(21), 
                program4247(22), 
                program4248(23), 
                program4249(24), 
                program4250(25), 
                program4251(26), 
                program4252(27), 
                program4253(28), 
                program4254(29), 
                program4255(30), 
                program4256(31), 
                program4257(32), 
                program4258(33), 
                program4259(34), 
                program4260(35), 
                program4261(36), 
                program4262(37), 
                program4263(38), 
                program4264(39), 
                program4265(40), 
                program4266(41), 
                program4267(42), 
                program4268(43), 
                program4269(44), 
                program4270(45), 
                program4271(46), 
                program4272(47), 
                program4273(48), 
                program4274(49), 
                program4275(50), 
                program4276(51), 
                program4277(52), 
                program4278(53), 
                program4279(54), 
                program4280(55), 
                program4281(56), 
                program4282(57), 
                program4283(58), 
                program4284(59), 
                program4285(60), 
                program4286(61), 
                program4287(62), 
                program4288(63), 
                program4289(64), 
                program4290(65), 
                program4291(66), 
                program4292(67), 
                program4293(68), 
                program4294(69), 
                program4295(70), 
                program4296(71), 
                program4297(72), 
                program4298(73), 
                program4299(74), 
                program4300(75), 
                program4301(76), 
                program4302(77), 
                program4303(78), 
                program4304(79), 
                program4305(80), 
                program4306(81), 
                program4307(82), 
                program4308(83), 
                program4309(84), 
                program4310(85), 
                program4311(86), 
                program4312(87), 
                program4313(88), 
                program4314(89), 
                program4315(90), 
                program4316(91), 
                program4317(92), 
                program4318(93), 
                program4319(94), 
                program4320(95), 
                program4321(96), 
                program4322(97), 
                program4323(98), 
                program4324(99), 
                program4325(100),
                program4326(101),
                program4327(102),
                program4328(103),
                program4329(104),
                program4330(105),
                program4331(106),
                program4332(107),
                program4333(108),
                program4334(109),
                program4335(110),
                program4336(111),
                program4337(112),
                program4338(113),
                program4339(114),
                program4340(115),
                program4341(116),
                program4342(117),
                program4343(118),
                program4344(119),
                program4345(120),
                program4346(121),
                program4347(122),
                program4348(123),
                program4349(124),
                program4350(125),
                program4351(126),           
                program4352(127)        
                }
            MAX-ACCESS read-write
            STATUS current
            DESCRIPTION
                "Indicates the program mask. This leaf indicates the authority of programs with indexes 2113-2176, 
                 64 programs in total. The indication methods of other mast leaves are the same as this table.
                 Each two bits indicate the authority to a program. Meanings of a 2-bit mask:
                 1. Forbidden(11)
                 2. Watch(01)
                 3. Preview(10)
                 4. idle(00)
                "
            ::= { hwDslamNtvRightProfileEntry 41 }    
              
        hwDslamNtvProgramMask35 OBJECT-TYPE
            SYNTAX BITS
                {
                program4353(0),  
                program4354(1),  
                program4355(2),  
                program4356(3),  
                program4357(4),  
                program4358(5),  
                program4359(6),  
                program4360(7),  
                program4361(8),  
                program4362(9),  
                program4363(10), 
                program4364(11), 
                program4365(12), 
                program4366(13), 
                program4367(14), 
                program4368(15), 
                program4369(16), 
                program4370(17), 
                program4371(18), 
                program4372(19), 
                program4373(20), 
                program4374(21), 
                program4375(22), 
                program4376(23), 
                program4377(24), 
                program4378(25), 
                program4379(26), 
                program4380(27), 
                program4381(28), 
                program4382(29), 
                program4383(30), 
                program4384(31), 
                program4385(32), 
                program4386(33), 
                program4387(34), 
                program4388(35), 
                program4389(36), 
                program4390(37), 
                program4391(38), 
                program4392(39), 
                program4393(40), 
                program4394(41), 
                program4395(42), 
                program4396(43), 
                program4397(44), 
                program4398(45), 
                program4399(46), 
                program4400(47), 
                program4401(48), 
                program4402(49), 
                program4403(50), 
                program4404(51), 
                program4405(52), 
                program4406(53), 
                program4407(54), 
                program4408(55), 
                program4409(56), 
                program4410(57), 
                program4411(58), 
                program4412(59), 
                program4413(60), 
                program4414(61), 
                program4415(62), 
                program4416(63), 
                program4417(64), 
                program4418(65), 
                program4419(66), 
                program4420(67), 
                program4421(68), 
                program4422(69), 
                program4423(70), 
                program4424(71), 
                program4425(72), 
                program4426(73), 
                program4427(74), 
                program4428(75), 
                program4429(76), 
                program4430(77), 
                program4431(78), 
                program4432(79), 
                program4433(80), 
                program4434(81), 
                program4435(82), 
                program4436(83), 
                program4437(84), 
                program4438(85), 
                program4439(86), 
                program4440(87), 
                program4441(88), 
                program4442(89), 
                program4443(90), 
                program4444(91), 
                program4445(92), 
                program4446(93), 
                program4447(94), 
                program4448(95), 
                program4449(96), 
                program4450(97), 
                program4451(98), 
                program4452(99), 
                program4453(100),
                program4454(101),
                program4455(102),
                program4456(103),
                program4457(104),
                program4458(105),
                program4459(106),
                program4460(107),
                program4461(108),
                program4462(109),
                program4463(110),
                program4464(111),
                program4465(112),
                program4466(113),
                program4467(114),
                program4468(115),
                program4469(116),
                program4470(117),
                program4471(118),
                program4472(119),
                program4473(120),
                program4474(121),
                program4475(122),
                program4476(123),
                program4477(124),
                program4478(125),
                program4479(126),
                program4480(127)         
                }
            MAX-ACCESS read-write
            STATUS current
            DESCRIPTION
                "Indicates the program mask. This leaf indicates the authority of programs with indexes 2177-2240, 
                 64 programs in total. The indication methods of other mast leaves are the same as this table.
                 Each two bits indicate the authority to a program. Meanings of a 2-bit mask:
                 1. Forbidden(11)
                 2. Watch(01)
                 3. Preview(10)
                 4. idle(00)
                "
            ::= { hwDslamNtvRightProfileEntry 42 }    
              
        hwDslamNtvProgramMask36 OBJECT-TYPE
            SYNTAX BITS
                {
                program4481(0),  
                program4482(1),  
                program4483(2),  
                program4484(3),  
                program4485(4),  
                program4486(5),  
                program4487(6),  
                program4488(7),  
                program4489(8),  
                program4490(9),  
                program4491(10), 
                program4492(11), 
                program4493(12), 
                program4494(13), 
                program4495(14), 
                program4496(15), 
                program4497(16), 
                program4498(17), 
                program4499(18), 
                program4500(19), 
                program4501(20), 
                program4502(21), 
                program4503(22), 
                program4504(23), 
                program4505(24), 
                program4506(25), 
                program4507(26), 
                program4508(27), 
                program4509(28), 
                program4510(29), 
                program4511(30), 
                program4512(31), 
                program4513(32), 
                program4514(33), 
                program4515(34), 
                program4516(35), 
                program4517(36), 
                program4518(37), 
                program4519(38), 
                program4520(39), 
                program4521(40), 
                program4522(41), 
                program4523(42), 
                program4524(43), 
                program4525(44), 
                program4526(45), 
                program4527(46), 
                program4528(47), 
                program4529(48), 
                program4530(49), 
                program4531(50), 
                program4532(51), 
                program4533(52), 
                program4534(53), 
                program4535(54), 
                program4536(55), 
                program4537(56), 
                program4538(57), 
                program4539(58), 
                program4540(59), 
                program4541(60), 
                program4542(61), 
                program4543(62), 
                program4544(63), 
                program4545(64), 
                program4546(65), 
                program4547(66), 
                program4548(67), 
                program4549(68), 
                program4550(69), 
                program4551(70), 
                program4552(71), 
                program4553(72), 
                program4554(73), 
                program4555(74), 
                program4556(75), 
                program4557(76), 
                program4558(77), 
                program4559(78), 
                program4560(79), 
                program4561(80), 
                program4562(81), 
                program4563(82), 
                program4564(83), 
                program4565(84), 
                program4566(85), 
                program4567(86), 
                program4568(87), 
                program4569(88), 
                program4570(89), 
                program4571(90), 
                program4572(91), 
                program4573(92), 
                program4574(93), 
                program4575(94), 
                program4576(95), 
                program4577(96), 
                program4578(97), 
                program4579(98), 
                program4580(99), 
                program4581(100),
                program4582(101),
                program4583(102),
                program4584(103),
                program4585(104),
                program4586(105),
                program4587(106),
                program4588(107),
                program4589(108),
                program4590(109),
                program4591(110),
                program4592(111),
                program4593(112),
                program4594(113),
                program4595(114),
                program4596(115),
                program4597(116),
                program4598(117),
                program4599(118),
                program4600(119),
                program4601(120),
                program4602(121),
                program4603(122),
                program4604(123),
                program4605(124),
                program4606(125),
                program4607(126),
                program4608(127)         
                }
            MAX-ACCESS read-write
            STATUS current
            DESCRIPTION
                "Indicates the program mask. This leaf indicates the authority of programs with indexes 2241-2304, 
                 64 programs in total. The indication methods of other mast leaves are the same as this table.
                 Each two bits indicate the authority to a program. Meanings of a 2-bit mask:
                 1. Forbidden(11)
                 2. Watch(01)
                 3. Preview(10)
                 4. idle(00)
                "
            ::= { hwDslamNtvRightProfileEntry 43 }    
              
        hwDslamNtvProgramMask37 OBJECT-TYPE
            SYNTAX BITS
                {
                program4609(0),  
                program4610(1),  
                program4611(2),  
                program4612(3),  
                program4613(4),  
                program4614(5),  
                program4615(6),  
                program4616(7),  
                program4617(8),  
                program4618(9),  
                program4619(10), 
                program4620(11), 
                program4621(12), 
                program4622(13), 
                program4623(14), 
                program4624(15), 
                program4625(16), 
                program4626(17), 
                program4627(18), 
                program4628(19), 
                program4629(20), 
                program4630(21), 
                program4631(22), 
                program4632(23), 
                program4633(24), 
                program4634(25), 
                program4635(26), 
                program4636(27), 
                program4637(28), 
                program4638(29), 
                program4639(30), 
                program4640(31), 
                program4641(32), 
                program4642(33), 
                program4643(34), 
                program4644(35), 
                program4645(36), 
                program4646(37), 
                program4647(38), 
                program4648(39), 
                program4649(40), 
                program4650(41), 
                program4651(42), 
                program4652(43), 
                program4653(44), 
                program4654(45), 
                program4655(46), 
                program4656(47), 
                program4657(48), 
                program4658(49), 
                program4659(50), 
                program4660(51), 
                program4661(52), 
                program4662(53), 
                program4663(54), 
                program4664(55), 
                program4665(56), 
                program4666(57), 
                program4667(58), 
                program4668(59), 
                program4669(60), 
                program4670(61), 
                program4671(62), 
                program4672(63), 
                program4673(64), 
                program4674(65), 
                program4675(66), 
                program4676(67), 
                program4677(68), 
                program4678(69), 
                program4679(70), 
                program4680(71), 
                program4681(72), 
                program4682(73), 
                program4683(74), 
                program4684(75), 
                program4685(76), 
                program4686(77), 
                program4687(78), 
                program4688(79), 
                program4689(80), 
                program4690(81), 
                program4691(82), 
                program4692(83), 
                program4693(84), 
                program4694(85), 
                program4695(86), 
                program4696(87), 
                program4697(88), 
                program4698(89), 
                program4699(90), 
                program4700(91), 
                program4701(92), 
                program4702(93), 
                program4703(94), 
                program4704(95), 
                program4705(96), 
                program4706(97), 
                program4707(98), 
                program4708(99), 
                program4709(100),
                program4710(101),
                program4711(102),
                program4712(103),
                program4713(104),
                program4714(105),
                program4715(106),
                program4716(107),
                program4717(108),
                program4718(109),
                program4719(110),
                program4720(111),
                program4721(112),
                program4722(113),
                program4723(114),
                program4724(115),
                program4725(116),
                program4726(117),
                program4727(118),
                program4728(119),
                program4729(120),
                program4730(121),
                program4731(122),
                program4732(123),
                program4733(124),
                program4734(125),
                program4735(126),
                program4736(127)         
                }
            MAX-ACCESS read-write
            STATUS current
            DESCRIPTION
                "Indicates the program mask. This leaf indicates the authority of programs with indexes 2305-2368, 
                 64 programs in total. The indication methods of other mast leaves are the same as this table.
                 Each two bits indicate the authority to a program. Meanings of a 2-bit mask:
                 1. Forbidden(11)
                 2. Watch(01)
                 3. Preview(10)
                 4. idle(00)
                "
            ::= { hwDslamNtvRightProfileEntry 44 }    
              
        hwDslamNtvProgramMask38 OBJECT-TYPE
            SYNTAX BITS
                {
                program4737(0),  
                program4738(1),  
                program4739(2),  
                program4740(3),  
                program4741(4),  
                program4742(5),  
                program4743(6),  
                program4744(7),  
                program4745(8),  
                program4746(9),  
                program4747(10), 
                program4748(11), 
                program4749(12), 
                program4750(13), 
                program4751(14), 
                program4752(15), 
                program4753(16), 
                program4754(17), 
                program4755(18), 
                program4756(19), 
                program4757(20), 
                program4758(21), 
                program4759(22), 
                program4760(23), 
                program4761(24), 
                program4762(25), 
                program4763(26), 
                program4764(27), 
                program4765(28), 
                program4766(29), 
                program4767(30), 
                program4768(31), 
                program4769(32), 
                program4770(33), 
                program4771(34), 
                program4772(35), 
                program4773(36), 
                program4774(37), 
                program4775(38), 
                program4776(39), 
                program4777(40), 
                program4778(41), 
                program4779(42), 
                program4780(43), 
                program4781(44), 
                program4782(45), 
                program4783(46), 
                program4784(47), 
                program4785(48), 
                program4786(49), 
                program4787(50), 
                program4788(51), 
                program4789(52), 
                program4790(53), 
                program4791(54), 
                program4792(55), 
                program4793(56), 
                program4794(57), 
                program4795(58), 
                program4796(59), 
                program4797(60), 
                program4798(61), 
                program4799(62), 
                program4800(63), 
                program4801(64), 
                program4802(65), 
                program4803(66), 
                program4804(67), 
                program4805(68), 
                program4806(69), 
                program4807(70), 
                program4808(71), 
                program4809(72), 
                program4810(73), 
                program4811(74), 
                program4812(75), 
                program4813(76), 
                program4814(77), 
                program4815(78), 
                program4816(79), 
                program4817(80), 
                program4818(81), 
                program4819(82), 
                program4820(83), 
                program4821(84), 
                program4822(85), 
                program4823(86), 
                program4824(87), 
                program4825(88), 
                program4826(89), 
                program4827(90), 
                program4828(91), 
                program4829(92), 
                program4830(93), 
                program4831(94), 
                program4832(95), 
                program4833(96), 
                program4834(97), 
                program4835(98), 
                program4836(99), 
                program4837(100),
                program4838(101),
                program4839(102),
                program4840(103),
                program4841(104),
                program4842(105),
                program4843(106),
                program4844(107),
                program4845(108),
                program4846(109),
                program4847(110),
                program4848(111),
                program4849(112),
                program4850(113),
                program4851(114),
                program4852(115),
                program4853(116),
                program4854(117),
                program4855(118),
                program4856(119),
                program4857(120),
                program4858(121),
                program4859(122),
                program4860(123),
                program4861(124),
                program4862(125),
                program4863(126),
                program4864(127)         
                }
            MAX-ACCESS read-write
            STATUS current
            DESCRIPTION
                "Indicates the program mask. This leaf indicates the authority of programs with indexes 2369-2432, 
                 64 programs in total. The indication methods of other mast leaves are the same as this table.
                 Each two bits indicate the authority to a program. Meanings of a 2-bit mask:
                 1. Forbidden(11)
                 2. Watch(01)
                 3. Preview(10)
                 4. idle(00)
                "
            ::= { hwDslamNtvRightProfileEntry 45 }    
              
        hwDslamNtvProgramMask39 OBJECT-TYPE
            SYNTAX BITS
                {
                program4865(0),  
                program4866(1),  
                program4867(2),  
                program4868(3),  
                program4869(4),  
                program4870(5),  
                program4871(6),  
                program4872(7),  
                program4873(8),  
                program4874(9),  
                program4875(10), 
                program4876(11), 
                program4877(12), 
                program4878(13), 
                program4879(14), 
                program4880(15), 
                program4881(16), 
                program4882(17), 
                program4883(18), 
                program4884(19), 
                program4885(20), 
                program4886(21), 
                program4887(22), 
                program4888(23), 
                program4889(24), 
                program4890(25), 
                program4891(26), 
                program4892(27), 
                program4893(28), 
                program4894(29), 
                program4895(30), 
                program4896(31), 
                program4897(32), 
                program4898(33), 
                program4899(34), 
                program4900(35), 
                program4901(36), 
                program4902(37), 
                program4903(38), 
                program4904(39), 
                program4905(40), 
                program4906(41), 
                program4907(42), 
                program4908(43), 
                program4909(44), 
                program4910(45), 
                program4911(46), 
                program4912(47), 
                program4913(48), 
                program4914(49), 
                program4915(50), 
                program4916(51), 
                program4917(52), 
                program4918(53), 
                program4919(54), 
                program4920(55), 
                program4921(56), 
                program4922(57), 
                program4923(58), 
                program4924(59), 
                program4925(60), 
                program4926(61), 
                program4927(62), 
                program4928(63), 
                program4929(64), 
                program4930(65), 
                program4931(66), 
                program4932(67), 
                program4933(68), 
                program4934(69), 
                program4935(70), 
                program4936(71), 
                program4937(72), 
                program4938(73), 
                program4939(74), 
                program4940(75), 
                program4941(76), 
                program4942(77), 
                program4943(78), 
                program4944(79), 
                program4945(80), 
                program4946(81), 
                program4947(82), 
                program4948(83), 
                program4949(84), 
                program4950(85), 
                program4951(86), 
                program4952(87), 
                program4953(88), 
                program4954(89), 
                program4955(90), 
                program4956(91), 
                program4957(92), 
                program4958(93), 
                program4959(94), 
                program4960(95), 
                program4961(96), 
                program4962(97), 
                program4963(98), 
                program4964(99), 
                program4965(100),
                program4966(101),
                program4967(102),
                program4968(103),
                program4969(104),
                program4970(105),
                program4971(106),
                program4972(107),
                program4973(108),
                program4974(109),
                program4975(110),
                program4976(111),
                program4977(112),
                program4978(113),
                program4979(114),
                program4980(115),
                program4981(116),
                program4982(117),
                program4983(118),
                program4984(119),
                program4985(120),
                program4986(121),
                program4987(122),
                program4988(123),
                program4989(124),
                program4990(125),
                program4991(126),
                program4992(127)         
                }
            MAX-ACCESS read-write
            STATUS current
            DESCRIPTION
                "Indicates the program mask. This leaf indicates the authority of programs with indexes 2433-2496, 
                 64 programs in total. The indication methods of other mast leaves are the same as this table.
                 Each two bits indicate the authority to a program. Meanings of a 2-bit mask:
                 1. Forbidden(11)
                 2. Watch(01)
                 3. Preview(10)
                 4. idle(00)
                "
            ::= { hwDslamNtvRightProfileEntry 46 }    
              
        hwDslamNtvProgramMask40 OBJECT-TYPE
            SYNTAX BITS
                {
                program4993(0),  
                program4994(1),  
                program4995(2),  
                program4996(3),  
                program4997(4),  
                program4998(5),  
                program4999(6),  
                program5000(7),  
                program5001(8),  
                program5002(9),  
                program5003(10), 
                program5004(11), 
                program5005(12), 
                program5006(13), 
                program5007(14), 
                program5008(15), 
                program5009(16), 
                program5010(17), 
                program5011(18), 
                program5012(19), 
                program5013(20), 
                program5014(21), 
                program5015(22), 
                program5016(23), 
                program5017(24), 
                program5018(25), 
                program5019(26), 
                program5020(27), 
                program5021(28), 
                program5022(29), 
                program5023(30), 
                program5024(31), 
                program5025(32), 
                program5026(33), 
                program5027(34), 
                program5028(35), 
                program5029(36), 
                program5030(37), 
                program5031(38), 
                program5032(39), 
                program5033(40), 
                program5034(41), 
                program5035(42), 
                program5036(43), 
                program5037(44), 
                program5038(45), 
                program5039(46), 
                program5040(47), 
                program5041(48), 
                program5042(49), 
                program5043(50), 
                program5044(51), 
                program5045(52), 
                program5046(53), 
                program5047(54), 
                program5048(55), 
                program5049(56), 
                program5050(57), 
                program5051(58), 
                program5052(59), 
                program5053(60), 
                program5054(61), 
                program5055(62), 
                program5056(63), 
                program5057(64), 
                program5058(65), 
                program5059(66), 
                program5060(67), 
                program5061(68), 
                program5062(69), 
                program5063(70), 
                program5064(71), 
                program5065(72), 
                program5066(73), 
                program5067(74), 
                program5068(75), 
                program5069(76), 
                program5070(77), 
                program5071(78), 
                program5072(79), 
                program5073(80), 
                program5074(81), 
                program5075(82), 
                program5076(83), 
                program5077(84), 
                program5078(85), 
                program5079(86), 
                program5080(87), 
                program5081(88), 
                program5082(89), 
                program5083(90), 
                program5084(91), 
                program5085(92), 
                program5086(93), 
                program5087(94), 
                program5088(95), 
                program5089(96), 
                program5090(97), 
                program5091(98), 
                program5092(99), 
                program5093(100),
                program5094(101),
                program5095(102),
                program5096(103),
                program5097(104),
                program5098(105),
                program5099(106),
                program5100(107),
                program5101(108),
                program5102(109),
                program5103(110),
                program5104(111),
                program5105(112),
                program5106(113),
                program5107(114),
                program5108(115),
                program5109(116),
                program5110(117),
                program5111(118),
                program5112(119),
                program5113(120),
                program5114(121),
                program5115(122),
                program5116(123),
                program5117(124),
                program5118(125),
                program5119(126),
                program5120(127)         
                }
            MAX-ACCESS read-write
            STATUS current
            DESCRIPTION
                "Indicates the program mask. This leaf indicates the authority of programs with indexes 2497-2560, 
                 64 programs in total. The indication methods of other mast leaves are the same as this table.
                 Each two bits indicate the authority to a program. Meanings of a 2-bit mask:
                 1. Forbidden(11)
                 2. Watch(01)
                 3. Preview(10)
                 4. idle(00)
                "
            ::= { hwDslamNtvRightProfileEntry 47 }    
            
        hwDslamNtvProgramMask41 OBJECT-TYPE
            SYNTAX BITS
                {
                program5121(0),  
                program5122(1),  
                program5123(2),  
                program5124(3),  
                program5125(4),  
                program5126(5),  
                program5127(6),  
                program5128(7),  
                program5129(8),  
                program5130(9),  
                program5131(10), 
                program5132(11), 
                program5133(12), 
                program5134(13), 
                program5135(14), 
                program5136(15), 
                program5137(16), 
                program5138(17), 
                program5139(18), 
                program5140(19), 
                program5141(20), 
                program5142(21), 
                program5143(22), 
                program5144(23), 
                program5145(24), 
                program5146(25), 
                program5147(26), 
                program5148(27), 
                program5149(28), 
                program5150(29), 
                program5151(30), 
                program5152(31), 
                program5153(32), 
                program5154(33), 
                program5155(34), 
                program5156(35), 
                program5157(36), 
                program5158(37), 
                program5159(38), 
                program5160(39), 
                program5161(40), 
                program5162(41), 
                program5163(42), 
                program5164(43), 
                program5165(44), 
                program5166(45), 
                program5167(46), 
                program5168(47), 
                program5169(48), 
                program5170(49), 
                program5171(50), 
                program5172(51), 
                program5173(52), 
                program5174(53), 
                program5175(54), 
                program5176(55), 
                program5177(56), 
                program5178(57), 
                program5179(58), 
                program5180(59), 
                program5181(60), 
                program5182(61), 
                program5183(62), 
                program5184(63), 
                program5185(64), 
                program5186(65), 
                program5187(66), 
                program5188(67), 
                program5189(68), 
                program5190(69), 
                program5191(70), 
                program5192(71), 
                program5193(72), 
                program5194(73), 
                program5195(74), 
                program5196(75), 
                program5197(76), 
                program5198(77), 
                program5199(78), 
                program5200(79), 
                program5201(80), 
                program5202(81), 
                program5203(82), 
                program5204(83), 
                program5205(84), 
                program5206(85), 
                program5207(86), 
                program5208(87), 
                program5209(88), 
                program5210(89), 
                program5211(90), 
                program5212(91), 
                program5213(92), 
                program5214(93), 
                program5215(94), 
                program5216(95), 
                program5217(96), 
                program5218(97), 
                program5219(98), 
                program5220(99), 
                program5221(100),
                program5222(101),
                program5223(102),
                program5224(103),
                program5225(104),
                program5226(105),
                program5227(106),
                program5228(107),
                program5229(108),
                program5230(109),
                program5231(110),
                program5232(111),
                program5233(112),
                program5234(113),
                program5235(114),
                program5236(115),
                program5237(116),
                program5238(117),
                program5239(118),
                program5240(119),
                program5241(120),
                program5242(121),
                program5243(122),
                program5244(123),
                program5245(124),
                program5246(125),
                program5247(126),
                program5248(127) 
                }
            MAX-ACCESS read-write
            STATUS current
            DESCRIPTION
                "Indicates the program mask. This leaf indicates the authority of programs with indexes 2561-2624, 
                 64 programs in total. The indication methods of other mast leaves are the same as this table.
                 Each two bits indicate the authority to a program. Meanings of a 2-bit mask:
                 1. Forbidden(11)
                 2. Watch(01)
                 3. Preview(10)
                 4. idle(00)
                "
            ::= { hwDslamNtvRightProfileEntry 48 }    
            
        hwDslamNtvProgramMask42 OBJECT-TYPE
            SYNTAX BITS
                {
                program5249(0),  
                program5250(1),  
                program5251(2),  
                program5252(3),  
                program5253(4),  
                program5254(5),  
                program5255(6),  
                program5256(7),  
                program5257(8),  
                program5258(9),  
                program5259(10), 
                program5260(11), 
                program5261(12), 
                program5262(13), 
                program5263(14), 
                program5264(15), 
                program5265(16), 
                program5266(17), 
                program5267(18), 
                program5268(19), 
                program5269(20), 
                program5270(21), 
                program5271(22), 
                program5272(23), 
                program5273(24), 
                program5274(25), 
                program5275(26), 
                program5276(27), 
                program5277(28), 
                program5278(29), 
                program5279(30), 
                program5280(31), 
                program5281(32), 
                program5282(33), 
                program5283(34), 
                program5284(35), 
                program5285(36), 
                program5286(37), 
                program5287(38), 
                program5288(39), 
                program5289(40), 
                program5290(41), 
                program5291(42), 
                program5292(43), 
                program5293(44), 
                program5294(45), 
                program5295(46), 
                program5296(47), 
                program5297(48), 
                program5298(49), 
                program5299(50), 
                program5300(51), 
                program5301(52), 
                program5302(53), 
                program5303(54), 
                program5304(55), 
                program5305(56), 
                program5306(57), 
                program5307(58), 
                program5308(59), 
                program5309(60), 
                program5310(61), 
                program5311(62), 
                program5312(63), 
                program5313(64), 
                program5314(65), 
                program5315(66), 
                program5316(67), 
                program5317(68), 
                program5318(69), 
                program5319(70), 
                program5320(71), 
                program5321(72), 
                program5322(73), 
                program5323(74), 
                program5324(75), 
                program5325(76), 
                program5326(77), 
                program5327(78), 
                program5328(79), 
                program5329(80), 
                program5330(81), 
                program5331(82), 
                program5332(83), 
                program5333(84), 
                program5334(85), 
                program5335(86), 
                program5336(87), 
                program5337(88), 
                program5338(89), 
                program5339(90), 
                program5340(91), 
                program5341(92), 
                program5342(93), 
                program5343(94), 
                program5344(95), 
                program5345(96), 
                program5346(97), 
                program5347(98), 
                program5348(99), 
                program5349(100),
                program5350(101),
                program5351(102),
                program5352(103),
                program5353(104),
                program5354(105),
                program5355(106),
                program5356(107),
                program5357(108),
                program5358(109),
                program5359(110),
                program5360(111),
                program5361(112),
                program5362(113),
                program5363(114),
                program5364(115),
                program5365(116),
                program5366(117),
                program5367(118),
                program5368(119),
                program5369(120),
                program5370(121),
                program5371(122),
                program5372(123),
                program5373(124),
                program5374(125),
                program5375(126),
                program5376(127) 
                }
            MAX-ACCESS read-write
            STATUS current
            DESCRIPTION
                "Indicates the program mask. This leaf indicates the authority of programs with indexes 2625-2688, 
                 64 programs in total. The indication methods of other mast leaves are the same as this table.
                 Each two bits indicate the authority to a program. Meanings of a 2-bit mask:
                 1. Forbidden(11)
                 2. Watch(01)
                 3. Preview(10)
                 4. idle(00)
                "
            ::= { hwDslamNtvRightProfileEntry 49 }    
            
        hwDslamNtvProgramMask43 OBJECT-TYPE
            SYNTAX BITS
                {
                program5377(0),  
                program5378(1),  
                program5379(2),  
                program5380(3),  
                program5381(4),  
                program5382(5),  
                program5383(6),  
                program5384(7),  
                program5385(8),  
                program5386(9),  
                program5387(10), 
                program5388(11), 
                program5389(12), 
                program5390(13), 
                program5391(14), 
                program5392(15), 
                program5393(16), 
                program5394(17), 
                program5395(18), 
                program5396(19), 
                program5397(20), 
                program5398(21), 
                program5399(22), 
                program5400(23), 
                program5401(24), 
                program5402(25), 
                program5403(26), 
                program5404(27), 
                program5405(28), 
                program5406(29), 
                program5407(30), 
                program5408(31), 
                program5409(32), 
                program5410(33), 
                program5411(34), 
                program5412(35), 
                program5413(36), 
                program5414(37), 
                program5415(38), 
                program5416(39), 
                program5417(40), 
                program5418(41), 
                program5419(42), 
                program5420(43), 
                program5421(44), 
                program5422(45), 
                program5423(46), 
                program5424(47), 
                program5425(48), 
                program5426(49), 
                program5427(50), 
                program5428(51), 
                program5429(52), 
                program5430(53), 
                program5431(54), 
                program5432(55), 
                program5433(56), 
                program5434(57), 
                program5435(58), 
                program5436(59), 
                program5437(60), 
                program5438(61), 
                program5439(62), 
                program5440(63), 
                program5441(64), 
                program5442(65), 
                program5443(66), 
                program5444(67), 
                program5445(68), 
                program5446(69), 
                program5447(70), 
                program5448(71), 
                program5449(72), 
                program5450(73), 
                program5451(74), 
                program5452(75), 
                program5453(76), 
                program5454(77), 
                program5455(78), 
                program5456(79), 
                program5457(80), 
                program5458(81), 
                program5459(82), 
                program5460(83), 
                program5461(84), 
                program5462(85), 
                program5463(86), 
                program5464(87), 
                program5465(88), 
                program5466(89), 
                program5467(90), 
                program5468(91), 
                program5469(92), 
                program5470(93), 
                program5471(94), 
                program5472(95), 
                program5473(96), 
                program5474(97), 
                program5475(98), 
                program5476(99), 
                program5477(100),
                program5478(101),
                program5479(102),
                program5480(103),
                program5481(104),
                program5482(105),
                program5483(106),
                program5484(107),
                program5485(108),
                program5486(109),
                program5487(110),
                program5488(111),
                program5489(112),
                program5490(113),
                program5491(114),
                program5492(115),
                program5493(116),
                program5494(117),
                program5495(118),
                program5496(119),
                program5497(120),
                program5498(121),
                program5499(122),
                program5500(123),
                program5501(124),
                program5502(125),
                program5503(126),
                program5504(127) 
                }
            MAX-ACCESS read-write
            STATUS current
            DESCRIPTION
                "Indicates the program mask. This leaf indicates the authority of programs with indexes 2689-2752, 
                 64 programs in total. The indication methods of other mast leaves are the same as this table.
                 Each two bits indicate the authority to a program. Meanings of a 2-bit mask:
                 1. Forbidden(11)
                 2. Watch(01)
                 3. Preview(10)
                 4. idle(00)
                "
            ::= { hwDslamNtvRightProfileEntry 50 }    
            
        hwDslamNtvProgramMask44 OBJECT-TYPE
            SYNTAX BITS
                {
                program5505(0),  
                program5506(1),  
                program5507(2),  
                program5508(3),  
                program5509(4),  
                program5510(5),  
                program5511(6),  
                program5512(7),  
                program5513(8),  
                program5514(9),  
                program5515(10), 
                program5516(11), 
                program5517(12), 
                program5518(13), 
                program5519(14), 
                program5520(15), 
                program5521(16), 
                program5522(17), 
                program5523(18), 
                program5524(19), 
                program5525(20), 
                program5526(21), 
                program5527(22), 
                program5528(23), 
                program5529(24), 
                program5530(25), 
                program5531(26), 
                program5532(27), 
                program5533(28), 
                program5534(29), 
                program5535(30), 
                program5536(31), 
                program5537(32), 
                program5538(33), 
                program5539(34), 
                program5540(35), 
                program5541(36), 
                program5542(37), 
                program5543(38), 
                program5544(39), 
                program5545(40), 
                program5546(41), 
                program5547(42), 
                program5548(43), 
                program5549(44), 
                program5550(45), 
                program5551(46), 
                program5552(47), 
                program5553(48), 
                program5554(49), 
                program5555(50), 
                program5556(51), 
                program5557(52), 
                program5558(53), 
                program5559(54), 
                program5560(55), 
                program5561(56), 
                program5562(57), 
                program5563(58), 
                program5564(59), 
                program5565(60), 
                program5566(61), 
                program5567(62), 
                program5568(63), 
                program5569(64), 
                program5570(65), 
                program5571(66), 
                program5572(67), 
                program5573(68), 
                program5574(69), 
                program5575(70), 
                program5576(71), 
                program5577(72), 
                program5578(73), 
                program5579(74), 
                program5580(75), 
                program5581(76), 
                program5582(77), 
                program5583(78), 
                program5584(79), 
                program5585(80), 
                program5586(81), 
                program5587(82), 
                program5588(83), 
                program5589(84), 
                program5590(85), 
                program5591(86), 
                program5592(87), 
                program5593(88), 
                program5594(89), 
                program5595(90), 
                program5596(91), 
                program5597(92), 
                program5598(93), 
                program5599(94), 
                program5600(95), 
                program5601(96), 
                program5602(97), 
                program5603(98), 
                program5604(99), 
                program5605(100),
                program5606(101),
                program5607(102),
                program5608(103),
                program5609(104),
                program5610(105),
                program5611(106),
                program5612(107),
                program5613(108),
                program5614(109),
                program5615(110),
                program5616(111),
                program5617(112),
                program5618(113),
                program5619(114),
                program5620(115),
                program5621(116),
                program5622(117),
                program5623(118),
                program5624(119),
                program5625(120),
                program5626(121),
                program5627(122),
                program5628(123),
                program5629(124),
                program5630(125),
                program5631(126),
                program5632(127) 
                }
            MAX-ACCESS read-write
            STATUS current
            DESCRIPTION
                "Indicates the program mask. This leaf indicates the authority of programs with indexes 2753-2816, 
                 64 programs in total. The indication methods of other mast leaves are the same as this table.
                 Each two bits indicate the authority to a program. Meanings of a 2-bit mask:
                 1. Forbidden(11)
                 2. Watch(01)
                 3. Preview(10)
                 4. idle(00)
                "
            ::= { hwDslamNtvRightProfileEntry 51 }        
            
        hwDslamNtvProgramMask45 OBJECT-TYPE
            SYNTAX BITS
                {
                program5633(0),  
                program5634(1),  
                program5635(2),  
                program5636(3),  
                program5637(4),  
                program5638(5),  
                program5639(6),  
                program5640(7),  
                program5641(8),  
                program5642(9),  
                program5643(10), 
                program5644(11), 
                program5645(12), 
                program5646(13), 
                program5647(14), 
                program5648(15), 
                program5649(16), 
                program5650(17), 
                program5651(18), 
                program5652(19), 
                program5653(20), 
                program5654(21), 
                program5655(22), 
                program5656(23), 
                program5657(24), 
                program5658(25), 
                program5659(26), 
                program5660(27), 
                program5661(28), 
                program5662(29), 
                program5663(30), 
                program5664(31), 
                program5665(32), 
                program5666(33), 
                program5667(34), 
                program5668(35), 
                program5669(36), 
                program5670(37), 
                program5671(38), 
                program5672(39), 
                program5673(40), 
                program5674(41), 
                program5675(42), 
                program5676(43), 
                program5677(44), 
                program5678(45), 
                program5679(46), 
                program5680(47), 
                program5681(48), 
                program5682(49), 
                program5683(50), 
                program5684(51), 
                program5685(52), 
                program5686(53), 
                program5687(54), 
                program5688(55), 
                program5689(56), 
                program5690(57), 
                program5691(58), 
                program5692(59), 
                program5693(60), 
                program5694(61), 
                program5695(62), 
                program5696(63), 
                program5697(64), 
                program5698(65), 
                program5699(66), 
                program5700(67), 
                program5701(68), 
                program5702(69), 
                program5703(70), 
                program5704(71), 
                program5705(72), 
                program5706(73), 
                program5707(74), 
                program5708(75), 
                program5709(76), 
                program5710(77), 
                program5711(78), 
                program5712(79), 
                program5713(80), 
                program5714(81), 
                program5715(82), 
                program5716(83), 
                program5717(84), 
                program5718(85), 
                program5719(86), 
                program5720(87), 
                program5721(88), 
                program5722(89), 
                program5723(90), 
                program5724(91), 
                program5725(92), 
                program5726(93), 
                program5727(94), 
                program5728(95), 
                program5729(96), 
                program5730(97), 
                program5731(98), 
                program5732(99), 
                program5733(100),
                program5734(101),
                program5735(102),
                program5736(103),
                program5737(104),
                program5738(105),
                program5739(106),
                program5740(107),
                program5741(108),
                program5742(109),
                program5743(110),
                program5744(111),
                program5745(112),
                program5746(113),
                program5747(114),
                program5748(115),
                program5749(116),
                program5750(117),
                program5751(118),
                program5752(119),
                program5753(120),
                program5754(121),
                program5755(122),
                program5756(123),
                program5757(124),
                program5758(125),
                program5759(126),
                program5760(127) 
                }
            MAX-ACCESS read-write
            STATUS current
            DESCRIPTION
                "Indicates the program mask. This leaf indicates the authority of programs with indexes 2817-2880, 
                 64 programs in total. The indication methods of other mast leaves are the same as this table.
                 Each two bits indicate the authority to a program. Meanings of a 2-bit mask:
                 1. Forbidden(11)
                 2. Watch(01)
                 3. Preview(10)
                 4. idle(00)
                "
            ::= { hwDslamNtvRightProfileEntry 52 }    
            
        hwDslamNtvProgramMask46 OBJECT-TYPE
            SYNTAX BITS
                {
                program5761(0),  
                program5762(1),  
                program5763(2),  
                program5764(3),  
                program5765(4),  
                program5766(5),  
                program5767(6),  
                program5768(7),  
                program5769(8),  
                program5770(9),  
                program5771(10), 
                program5772(11), 
                program5773(12), 
                program5774(13), 
                program5775(14), 
                program5776(15), 
                program5777(16), 
                program5778(17), 
                program5779(18), 
                program5780(19), 
                program5781(20), 
                program5782(21), 
                program5783(22), 
                program5784(23), 
                program5785(24), 
                program5786(25), 
                program5787(26), 
                program5788(27), 
                program5789(28), 
                program5790(29), 
                program5791(30), 
                program5792(31), 
                program5793(32), 
                program5794(33), 
                program5795(34), 
                program5796(35), 
                program5797(36), 
                program5798(37), 
                program5799(38), 
                program5800(39), 
                program5801(40), 
                program5802(41), 
                program5803(42), 
                program5804(43), 
                program5805(44), 
                program5806(45), 
                program5807(46), 
                program5808(47), 
                program5809(48), 
                program5810(49), 
                program5811(50), 
                program5812(51), 
                program5813(52), 
                program5814(53), 
                program5815(54), 
                program5816(55), 
                program5817(56), 
                program5818(57), 
                program5819(58), 
                program5820(59), 
                program5821(60), 
                program5822(61), 
                program5823(62), 
                program5824(63), 
                program5825(64), 
                program5826(65), 
                program5827(66), 
                program5828(67), 
                program5829(68), 
                program5830(69), 
                program5831(70), 
                program5832(71), 
                program5833(72), 
                program5834(73), 
                program5835(74), 
                program5836(75), 
                program5837(76), 
                program5838(77), 
                program5839(78), 
                program5840(79), 
                program5841(80), 
                program5842(81), 
                program5843(82), 
                program5844(83), 
                program5845(84), 
                program5846(85), 
                program5847(86), 
                program5848(87), 
                program5849(88), 
                program5850(89), 
                program5851(90), 
                program5852(91), 
                program5853(92), 
                program5854(93), 
                program5855(94), 
                program5856(95), 
                program5857(96), 
                program5858(97), 
                program5859(98), 
                program5860(99), 
                program5861(100),
                program5862(101),
                program5863(102),
                program5864(103),
                program5865(104),
                program5866(105),
                program5867(106),
                program5868(107),
                program5869(108),
                program5870(109),
                program5871(110),
                program5872(111),
                program5873(112),
                program5874(113),
                program5875(114),
                program5876(115),
                program5877(116),
                program5878(117),
                program5879(118),
                program5880(119),
                program5881(120),
                program5882(121),
                program5883(122),
                program5884(123),
                program5885(124),
                program5886(125),
                program5887(126),
                program5888(127) 
                }
            MAX-ACCESS read-write
            STATUS current
            DESCRIPTION
                "Indicates the program mask. This leaf indicates the authority of programs with indexes 2881-2944, 
                 64 programs in total. The indication methods of other mast leaves are the same as this table.
                 Each two bits indicate the authority to a program. Meanings of a 2-bit mask:
                 1. Forbidden(11)
                 2. Watch(01)
                 3. Preview(10)
                 4. idle(00)
                "
            ::= { hwDslamNtvRightProfileEntry 53 }        
            
        hwDslamNtvProgramMask47 OBJECT-TYPE
            SYNTAX BITS
                {
                program5889(0),  
                program5890(1),  
                program5891(2),  
                program5892(3),  
                program5893(4),  
                program5894(5),  
                program5895(6),  
                program5896(7),  
                program5897(8),  
                program5898(9),  
                program5899(10), 
                program5900(11), 
                program5901(12), 
                program5902(13), 
                program5903(14), 
                program5904(15), 
                program5905(16), 
                program5906(17), 
                program5907(18), 
                program5908(19), 
                program5909(20), 
                program5910(21), 
                program5911(22), 
                program5912(23), 
                program5913(24), 
                program5914(25), 
                program5915(26), 
                program5916(27), 
                program5917(28), 
                program5918(29), 
                program5919(30), 
                program5920(31), 
                program5921(32), 
                program5922(33), 
                program5923(34), 
                program5924(35), 
                program5925(36), 
                program5926(37), 
                program5927(38), 
                program5928(39), 
                program5929(40), 
                program5930(41), 
                program5931(42), 
                program5932(43), 
                program5933(44), 
                program5934(45), 
                program5935(46), 
                program5936(47), 
                program5937(48), 
                program5938(49), 
                program5939(50), 
                program5940(51), 
                program5941(52), 
                program5942(53), 
                program5943(54), 
                program5944(55), 
                program5945(56), 
                program5946(57), 
                program5947(58), 
                program5948(59), 
                program5949(60), 
                program5950(61), 
                program5951(62), 
                program5952(63), 
                program5953(64), 
                program5954(65), 
                program5955(66), 
                program5956(67), 
                program5957(68), 
                program5958(69), 
                program5959(70), 
                program5960(71), 
                program5961(72), 
                program5962(73), 
                program5963(74), 
                program5964(75), 
                program5965(76), 
                program5966(77), 
                program5967(78), 
                program5968(79), 
                program5969(80), 
                program5970(81), 
                program5971(82), 
                program5972(83), 
                program5973(84), 
                program5974(85), 
                program5975(86), 
                program5976(87), 
                program5977(88), 
                program5978(89), 
                program5979(90), 
                program5980(91), 
                program5981(92), 
                program5982(93), 
                program5983(94), 
                program5984(95), 
                program5985(96), 
                program5986(97), 
                program5987(98), 
                program5988(99), 
                program5989(100),
                program5990(101),
                program5991(102),
                program5992(103),
                program5993(104),
                program5994(105),
                program5995(106),
                program5996(107),
                program5997(108),
                program5998(109),
                program5999(110),
                program6000(111),
                program6001(112),
                program6002(113),
                program6003(114),
                program6004(115),
                program6005(116),
                program6006(117),
                program6007(118),
                program6008(119),
                program6009(120),
                program6010(121),
                program6011(122),
                program6012(123),
                program6013(124),
                program6014(125),
                program6015(126),
                program6016(127) 
                }
            MAX-ACCESS read-write
            STATUS current
            DESCRIPTION
                "Indicates the program mask. This leaf indicates the authority of programs with indexes 2945-3008, 
                 64 programs in total. The indication methods of other mast leaves are the same as this table.
                 Each two bits indicate the authority to a program. Meanings of a 2-bit mask:
                 1. Forbidden(11)
                 2. Watch(01)
                 3. Preview(10)
                 4. idle(00)
                "
            ::= { hwDslamNtvRightProfileEntry 54 }    
            
        hwDslamNtvProgramMask48 OBJECT-TYPE
            SYNTAX BITS
                {
                program6017(0),  
                program6018(1),  
                program6019(2),  
                program6020(3),  
                program6021(4),  
                program6022(5),  
                program6023(6),  
                program6024(7),  
                program6025(8),  
                program6026(9),  
                program6027(10), 
                program6028(11), 
                program6029(12), 
                program6030(13), 
                program6031(14), 
                program6032(15), 
                program6033(16), 
                program6034(17), 
                program6035(18), 
                program6036(19), 
                program6037(20), 
                program6038(21), 
                program6039(22), 
                program6040(23), 
                program6041(24), 
                program6042(25), 
                program6043(26), 
                program6044(27), 
                program6045(28), 
                program6046(29), 
                program6047(30), 
                program6048(31), 
                program6049(32), 
                program6050(33), 
                program6051(34), 
                program6052(35), 
                program6053(36), 
                program6054(37), 
                program6055(38), 
                program6056(39), 
                program6057(40), 
                program6058(41), 
                program6059(42), 
                program6060(43), 
                program6061(44), 
                program6062(45), 
                program6063(46), 
                program6064(47), 
                program6065(48), 
                program6066(49), 
                program6067(50), 
                program6068(51), 
                program6069(52), 
                program6070(53), 
                program6071(54), 
                program6072(55), 
                program6073(56), 
                program6074(57), 
                program6075(58), 
                program6076(59), 
                program6077(60), 
                program6078(61), 
                program6079(62), 
                program6080(63), 
                program6081(64), 
                program6082(65), 
                program6083(66), 
                program6084(67), 
                program6085(68), 
                program6086(69), 
                program6087(70), 
                program6088(71), 
                program6089(72), 
                program6090(73), 
                program6091(74), 
                program6092(75), 
                program6093(76), 
                program6094(77), 
                program6095(78), 
                program6096(79), 
                program6097(80), 
                program6098(81), 
                program6099(82), 
                program6100(83), 
                program6101(84), 
                program6102(85), 
                program6103(86), 
                program6104(87), 
                program6105(88), 
                program6106(89), 
                program6107(90), 
                program6108(91), 
                program6109(92), 
                program6110(93), 
                program6111(94), 
                program6112(95), 
                program6113(96), 
                program6114(97), 
                program6115(98), 
                program6116(99), 
                program6117(100),
                program6118(101),
                program6119(102),
                program6120(103),
                program6121(104),
                program6122(105),
                program6123(106),
                program6124(107),
                program6125(108),
                program6126(109),
                program6127(110),
                program6128(111),
                program6129(112),
                program6130(113),
                program6131(114),
                program6132(115),
                program6133(116),
                program6134(117),
                program6135(118),
                program6136(119),
                program6137(120),
                program6138(121),
                program6139(122),
                program6140(123),
                program6141(124),
                program6142(125),
                program6143(126),
                program6144(127) 
                }
            MAX-ACCESS read-write
            STATUS current
            DESCRIPTION
                "Indicates the program mask. This leaf indicates the authority of programs with indexes 3009-3072, 
                 64 programs in total. The indication methods of other mast leaves are the same as this table.
                 Each two bits indicate the authority to a program. Meanings of a 2-bit mask:
                 1. Forbidden(11)
                 2. Watch(01)
                 3. Preview(10)
                 4. idle(00)
                "
            ::= { hwDslamNtvRightProfileEntry 55 }    
            
        hwDslamNtvProgramMask49 OBJECT-TYPE
            SYNTAX BITS
                {
                program6145(0),  
                program6146(1),  
                program6147(2),  
                program6148(3),  
                program6149(4),  
                program6150(5),  
                program6151(6),  
                program6152(7),  
                program6153(8),  
                program6154(9),  
                program6155(10), 
                program6156(11), 
                program6157(12), 
                program6158(13), 
                program6159(14), 
                program6160(15), 
                program6161(16), 
                program6162(17), 
                program6163(18), 
                program6164(19), 
                program6165(20), 
                program6166(21), 
                program6167(22), 
                program6168(23), 
                program6169(24), 
                program6170(25), 
                program6171(26), 
                program6172(27), 
                program6173(28), 
                program6174(29), 
                program6175(30), 
                program6176(31), 
                program6177(32), 
                program6178(33), 
                program6179(34), 
                program6180(35), 
                program6181(36), 
                program6182(37), 
                program6183(38), 
                program6184(39), 
                program6185(40), 
                program6186(41), 
                program6187(42), 
                program6188(43), 
                program6189(44), 
                program6190(45), 
                program6191(46), 
                program6192(47), 
                program6193(48), 
                program6194(49), 
                program6195(50), 
                program6196(51), 
                program6197(52), 
                program6198(53), 
                program6199(54), 
                program6200(55), 
                program6201(56), 
                program6202(57), 
                program6203(58), 
                program6204(59), 
                program6205(60), 
                program6206(61), 
                program6207(62), 
                program6208(63), 
                program6209(64), 
                program6210(65), 
                program6211(66), 
                program6212(67), 
                program6213(68), 
                program6214(69), 
                program6215(70), 
                program6216(71), 
                program6217(72), 
                program6218(73), 
                program6219(74), 
                program6220(75), 
                program6221(76), 
                program6222(77), 
                program6223(78), 
                program6224(79), 
                program6225(80), 
                program6226(81), 
                program6227(82), 
                program6228(83), 
                program6229(84), 
                program6230(85), 
                program6231(86), 
                program6232(87), 
                program6233(88), 
                program6234(89), 
                program6235(90), 
                program6236(91), 
                program6237(92), 
                program6238(93), 
                program6239(94), 
                program6240(95), 
                program6241(96), 
                program6242(97), 
                program6243(98), 
                program6244(99), 
                program6245(100),
                program6246(101),
                program6247(102),
                program6248(103),
                program6249(104),
                program6250(105),
                program6251(106),
                program6252(107),
                program6253(108),
                program6254(109),
                program6255(110),
                program6256(111),
                program6257(112),
                program6258(113),
                program6259(114),
                program6260(115),
                program6261(116),
                program6262(117),
                program6263(118),
                program6264(119),
                program6265(120),
                program6266(121),
                program6267(122),
                program6268(123),
                program6269(124),
                program6270(125),
                program6271(126),
                program6272(127) 
                }
            MAX-ACCESS read-write
            STATUS current
            DESCRIPTION
                "Indicates the program mask. This leaf indicates the authority of programs with indexes 3073-3136, 
                 64 programs in total. The indication methods of other mast leaves are the same as this table.
                 Each two bits indicate the authority to a program. Meanings of a 2-bit mask:
                 1. Forbidden(11)
                 2. Watch(01)
                 3. Preview(10)
                 4. idle(00)
                "
            ::= { hwDslamNtvRightProfileEntry 56 }        
            
        hwDslamNtvProgramMask50 OBJECT-TYPE
            SYNTAX BITS
                {
                program6273(0),  
                program6274(1),  
                program6275(2),  
                program6276(3),  
                program6277(4),  
                program6278(5),  
                program6279(6),  
                program6280(7),  
                program6281(8),  
                program6282(9),  
                program6283(10), 
                program6284(11), 
                program6285(12), 
                program6286(13), 
                program6287(14), 
                program6288(15), 
                program6289(16), 
                program6290(17), 
                program6291(18), 
                program6292(19), 
                program6293(20), 
                program6294(21), 
                program6295(22), 
                program6296(23), 
                program6297(24), 
                program6298(25), 
                program6299(26), 
                program6300(27), 
                program6301(28), 
                program6302(29), 
                program6303(30), 
                program6304(31), 
                program6305(32), 
                program6306(33), 
                program6307(34), 
                program6308(35), 
                program6309(36), 
                program6310(37), 
                program6311(38), 
                program6312(39), 
                program6313(40), 
                program6314(41), 
                program6315(42), 
                program6316(43), 
                program6317(44), 
                program6318(45), 
                program6319(46), 
                program6320(47), 
                program6321(48), 
                program6322(49), 
                program6323(50), 
                program6324(51), 
                program6325(52), 
                program6326(53), 
                program6327(54), 
                program6328(55), 
                program6329(56), 
                program6330(57), 
                program6331(58), 
                program6332(59), 
                program6333(60), 
                program6334(61), 
                program6335(62), 
                program6336(63), 
                program6337(64), 
                program6338(65), 
                program6339(66), 
                program6340(67), 
                program6341(68), 
                program6342(69), 
                program6343(70), 
                program6344(71), 
                program6345(72), 
                program6346(73), 
                program6347(74), 
                program6348(75), 
                program6349(76), 
                program6350(77), 
                program6351(78), 
                program6352(79), 
                program6353(80), 
                program6354(81), 
                program6355(82), 
                program6356(83), 
                program6357(84), 
                program6358(85), 
                program6359(86), 
                program6360(87), 
                program6361(88), 
                program6362(89), 
                program6363(90), 
                program6364(91), 
                program6365(92), 
                program6366(93), 
                program6367(94), 
                program6368(95), 
                program6369(96), 
                program6370(97), 
                program6371(98), 
                program6372(99), 
                program6373(100),
                program6374(101),
                program6375(102),
                program6376(103),
                program6377(104),
                program6378(105),
                program6379(106),
                program6380(107),
                program6381(108),
                program6382(109),
                program6383(110),
                program6384(111),
                program6385(112),
                program6386(113),
                program6387(114),
                program6388(115),
                program6389(116),
                program6390(117),
                program6391(118),
                program6392(119),
                program6393(120),
                program6394(121),
                program6395(122),
                program6396(123),
                program6397(124),
                program6398(125),
                program6399(126),
                program6400(127)
                }
            MAX-ACCESS read-write
            STATUS current
            DESCRIPTION
                "Indicates the program mask. This leaf indicates the authority of programs with indexes 3137-3200, 
                 64 programs in total. The indication methods of other mast leaves are the same as this table.
                 Each two bits indicate the authority to a program. Meanings of a 2-bit mask:
                 1. Forbidden(11)
                 2. Watch(01)
                 3. Preview(10)
                 4. idle(00)
                "
            ::= { hwDslamNtvRightProfileEntry 57 }    
            
        hwDslamNtvProgramMask51 OBJECT-TYPE
            SYNTAX BITS
                {
                program6401(0),  
                program6402(1),  
                program6403(2),  
                program6404(3),  
                program6405(4),  
                program6406(5),  
                program6407(6),  
                program6408(7),  
                program6409(8),  
                program6410(9),  
                program6411(10), 
                program6412(11), 
                program6413(12), 
                program6414(13), 
                program6415(14), 
                program6416(15), 
                program6417(16), 
                program6418(17), 
                program6419(18), 
                program6420(19), 
                program6421(20), 
                program6422(21), 
                program6423(22), 
                program6424(23), 
                program6425(24), 
                program6426(25), 
                program6427(26), 
                program6428(27), 
                program6429(28), 
                program6430(29), 
                program6431(30), 
                program6432(31), 
                program6433(32), 
                program6434(33), 
                program6435(34), 
                program6436(35), 
                program6437(36), 
                program6438(37), 
                program6439(38), 
                program6440(39), 
                program6441(40), 
                program6442(41), 
                program6443(42), 
                program6444(43), 
                program6445(44), 
                program6446(45), 
                program6447(46), 
                program6448(47), 
                program6449(48), 
                program6450(49), 
                program6451(50), 
                program6452(51), 
                program6453(52), 
                program6454(53), 
                program6455(54), 
                program6456(55), 
                program6457(56), 
                program6458(57), 
                program6459(58), 
                program6460(59), 
                program6461(60), 
                program6462(61), 
                program6463(62), 
                program6464(63), 
                program6465(64), 
                program6466(65), 
                program6467(66), 
                program6468(67), 
                program6469(68), 
                program6470(69), 
                program6471(70), 
                program6472(71), 
                program6473(72), 
                program6474(73), 
                program6475(74), 
                program6476(75), 
                program6477(76), 
                program6478(77), 
                program6479(78), 
                program6480(79), 
                program6481(80), 
                program6482(81), 
                program6483(82), 
                program6484(83), 
                program6485(84), 
                program6486(85), 
                program6487(86), 
                program6488(87), 
                program6489(88), 
                program6490(89), 
                program6491(90), 
                program6492(91), 
                program6493(92), 
                program6494(93), 
                program6495(94), 
                program6496(95), 
                program6497(96), 
                program6498(97), 
                program6499(98), 
                program6500(99), 
                program6501(100),
                program6502(101),
                program6503(102),
                program6504(103),
                program6505(104),
                program6506(105),
                program6507(106),
                program6508(107),
                program6509(108),
                program6510(109),
                program6511(110),
                program6512(111),
                program6513(112),
                program6514(113),
                program6515(114),
                program6516(115),
                program6517(116),
                program6518(117),
                program6519(118),
                program6520(119),
                program6521(120),
                program6522(121),
                program6523(122),
                program6524(123),
                program6525(124),
                program6526(125),
                program6527(126),
                program6528(127) 
                }
            MAX-ACCESS read-write
            STATUS current
            DESCRIPTION
                "Indicates the program mask. This leaf indicates the authority of programs with indexes 3201-3264, 
                 64 programs in total. The indication methods of other mast leaves are the same as this table.
                 Each two bits indicate the authority to a program. Meanings of a 2-bit mask:
                 1. Forbidden(11)
                 2. Watch(01)
                 3. Preview(10)
                 4. idle(00)
                "
            ::= { hwDslamNtvRightProfileEntry 58 }    
            
        hwDslamNtvProgramMask52 OBJECT-TYPE
            SYNTAX BITS
                {
                program6529(0),  
                program6530(1),  
                program6531(2),  
                program6532(3),  
                program6533(4),  
                program6534(5),  
                program6535(6),  
                program6536(7),  
                program6537(8),  
                program6538(9),  
                program6539(10), 
                program6540(11), 
                program6541(12), 
                program6542(13), 
                program6543(14), 
                program6544(15), 
                program6545(16), 
                program6546(17), 
                program6547(18), 
                program6548(19), 
                program6549(20), 
                program6550(21), 
                program6551(22), 
                program6552(23), 
                program6553(24), 
                program6554(25), 
                program6555(26), 
                program6556(27), 
                program6557(28), 
                program6558(29), 
                program6559(30), 
                program6560(31), 
                program6561(32), 
                program6562(33), 
                program6563(34), 
                program6564(35), 
                program6565(36), 
                program6566(37), 
                program6567(38), 
                program6568(39), 
                program6569(40), 
                program6570(41), 
                program6571(42), 
                program6572(43), 
                program6573(44), 
                program6574(45), 
                program6575(46), 
                program6576(47), 
                program6577(48), 
                program6578(49), 
                program6579(50), 
                program6580(51), 
                program6581(52), 
                program6582(53), 
                program6583(54), 
                program6584(55), 
                program6585(56), 
                program6586(57), 
                program6587(58), 
                program6588(59), 
                program6589(60), 
                program6590(61), 
                program6591(62), 
                program6592(63), 
                program6593(64), 
                program6594(65), 
                program6595(66), 
                program6596(67), 
                program6597(68), 
                program6598(69), 
                program6599(70), 
                program6600(71), 
                program6601(72), 
                program6602(73), 
                program6603(74), 
                program6604(75), 
                program6605(76), 
                program6606(77), 
                program6607(78), 
                program6608(79), 
                program6609(80), 
                program6610(81), 
                program6611(82), 
                program6612(83), 
                program6613(84), 
                program6614(85), 
                program6615(86), 
                program6616(87), 
                program6617(88), 
                program6618(89), 
                program6619(90), 
                program6620(91), 
                program6621(92), 
                program6622(93), 
                program6623(94), 
                program6624(95), 
                program6625(96), 
                program6626(97), 
                program6627(98), 
                program6628(99), 
                program6629(100),
                program6630(101),
                program6631(102),
                program6632(103),
                program6633(104),
                program6634(105),
                program6635(106),
                program6636(107),
                program6637(108),
                program6638(109),
                program6639(110),
                program6640(111),
                program6641(112),
                program6642(113),
                program6643(114),
                program6644(115),
                program6645(116),
                program6646(117),
                program6647(118),
                program6648(119),
                program6649(120),
                program6650(121),
                program6651(122),
                program6652(123),
                program6653(124),
                program6654(125),
                program6655(126),
                program6656(127) 
                }
            MAX-ACCESS read-write
            STATUS current
            DESCRIPTION
                "Indicates the program mask. This leaf indicates the authority of programs with indexes 3265-3328, 
                 64 programs in total. The indication methods of other mast leaves are the same as this table.
                 Each two bits indicate the authority to a program. Meanings of a 2-bit mask:
                 1. Forbidden(11)
                 2. Watch(01)
                 3. Preview(10)
                 4. idle(00)
                "
            ::= { hwDslamNtvRightProfileEntry 59 }
            
        hwDslamNtvProgramMask53 OBJECT-TYPE
            SYNTAX BITS
                {
                program6657(0),  
                program6658(1),  
                program6659(2),  
                program6660(3),  
                program6661(4),  
                program6662(5),  
                program6663(6),  
                program6664(7),  
                program6665(8),  
                program6666(9),  
                program6667(10), 
                program6668(11), 
                program6669(12), 
                program6670(13), 
                program6671(14), 
                program6672(15), 
                program6673(16), 
                program6674(17), 
                program6675(18), 
                program6676(19), 
                program6677(20), 
                program6678(21), 
                program6679(22), 
                program6680(23), 
                program6681(24), 
                program6682(25), 
                program6683(26), 
                program6684(27), 
                program6685(28), 
                program6686(29), 
                program6687(30), 
                program6688(31), 
                program6689(32), 
                program6690(33), 
                program6691(34), 
                program6692(35), 
                program6693(36), 
                program6694(37), 
                program6695(38), 
                program6696(39), 
                program6697(40), 
                program6698(41), 
                program6699(42), 
                program6700(43), 
                program6701(44), 
                program6702(45), 
                program6703(46), 
                program6704(47), 
                program6705(48), 
                program6706(49), 
                program6707(50), 
                program6708(51), 
                program6709(52), 
                program6710(53), 
                program6711(54), 
                program6712(55), 
                program6713(56), 
                program6714(57), 
                program6715(58), 
                program6716(59), 
                program6717(60), 
                program6718(61), 
                program6719(62), 
                program6720(63), 
                program6721(64), 
                program6722(65), 
                program6723(66), 
                program6724(67), 
                program6725(68), 
                program6726(69), 
                program6727(70), 
                program6728(71), 
                program6729(72), 
                program6730(73), 
                program6731(74), 
                program6732(75), 
                program6733(76), 
                program6734(77), 
                program6735(78), 
                program6736(79), 
                program6737(80), 
                program6738(81), 
                program6739(82), 
                program6740(83), 
                program6741(84), 
                program6742(85), 
                program6743(86), 
                program6744(87), 
                program6745(88), 
                program6746(89), 
                program6747(90), 
                program6748(91), 
                program6749(92), 
                program6750(93), 
                program6751(94), 
                program6752(95), 
                program6753(96), 
                program6754(97), 
                program6755(98), 
                program6756(99), 
                program6757(100),
                program6758(101),
                program6759(102),
                program6760(103),
                program6761(104),
                program6762(105),
                program6763(106),
                program6764(107),
                program6765(108),
                program6766(109),
                program6767(110),
                program6768(111),
                program6769(112),
                program6770(113),
                program6771(114),
                program6772(115),
                program6773(116),
                program6774(117),
                program6775(118),
                program6776(119),
                program6777(120),
                program6778(121),
                program6779(122),
                program6780(123),
                program6781(124),
                program6782(125),
                program6783(126),
                program6784(127) 
                }
            MAX-ACCESS read-write
            STATUS current
            DESCRIPTION
                "Indicates the program mask. This leaf indicates the authority of programs with indexes 3329-3392, 
                 64 programs in total. The indication methods of other mast leaves are the same as this table.
                 Each two bits indicate the authority to a program. Meanings of a 2-bit mask:
                 1. Forbidden(11)
                 2. Watch(01)
                 3. Preview(10)
                 4. idle(00)
                "
            ::= { hwDslamNtvRightProfileEntry 60 }    
            
        hwDslamNtvProgramMask54 OBJECT-TYPE
            SYNTAX BITS
                {
                program6785(0),  
                program6786(1),  
                program6787(2),  
                program6788(3),  
                program6789(4),  
                program6790(5),  
                program6791(6),  
                program6792(7),  
                program6793(8),  
                program6794(9),  
                program6795(10), 
                program6796(11), 
                program6797(12), 
                program6798(13), 
                program6799(14), 
                program6800(15), 
                program6801(16), 
                program6802(17), 
                program6803(18), 
                program6804(19), 
                program6805(20), 
                program6806(21), 
                program6807(22), 
                program6808(23), 
                program6809(24), 
                program6810(25), 
                program6811(26), 
                program6812(27), 
                program6813(28), 
                program6814(29), 
                program6815(30), 
                program6816(31), 
                program6817(32), 
                program6818(33), 
                program6819(34), 
                program6820(35), 
                program6821(36), 
                program6822(37), 
                program6823(38), 
                program6824(39), 
                program6825(40), 
                program6826(41), 
                program6827(42), 
                program6828(43), 
                program6829(44), 
                program6830(45), 
                program6831(46), 
                program6832(47), 
                program6833(48), 
                program6834(49), 
                program6835(50), 
                program6836(51), 
                program6837(52), 
                program6838(53), 
                program6839(54), 
                program6840(55), 
                program6841(56), 
                program6842(57), 
                program6843(58), 
                program6844(59), 
                program6845(60), 
                program6846(61), 
                program6847(62), 
                program6848(63), 
                program6849(64), 
                program6850(65), 
                program6851(66), 
                program6852(67), 
                program6853(68), 
                program6854(69), 
                program6855(70), 
                program6856(71), 
                program6857(72), 
                program6858(73), 
                program6859(74), 
                program6860(75), 
                program6861(76), 
                program6862(77), 
                program6863(78), 
                program6864(79), 
                program6865(80), 
                program6866(81), 
                program6867(82), 
                program6868(83), 
                program6869(84), 
                program6870(85), 
                program6871(86), 
                program6872(87), 
                program6873(88), 
                program6874(89), 
                program6875(90), 
                program6876(91), 
                program6877(92), 
                program6878(93), 
                program6879(94), 
                program6880(95), 
                program6881(96), 
                program6882(97), 
                program6883(98), 
                program6884(99), 
                program6885(100),
                program6886(101),
                program6887(102),
                program6888(103),
                program6889(104),
                program6890(105),
                program6891(106),
                program6892(107),
                program6893(108),
                program6894(109),
                program6895(110),
                program6896(111),
                program6897(112),
                program6898(113),
                program6899(114),
                program6900(115),
                program6901(116),
                program6902(117),
                program6903(118),
                program6904(119),
                program6905(120),
                program6906(121),
                program6907(122),
                program6908(123),
                program6909(124),
                program6910(125),
                program6911(126),
                program6912(127) 
                }
            MAX-ACCESS read-write
            STATUS current
            DESCRIPTION
                "Indicates the program mask. This leaf indicates the authority of programs with indexes 3393-3456, 
                 64 programs in total. The indication methods of other mast leaves are the same as this table.
                 Each two bits indicate the authority to a program. Meanings of a 2-bit mask:
                 1. Forbidden(11)
                 2. Watch(01)
                 3. Preview(10)
                 4. idle(00)
                "
            ::= { hwDslamNtvRightProfileEntry 61 }        
            
        hwDslamNtvProgramMask55 OBJECT-TYPE
            SYNTAX BITS
                {
                program6913(0),  
                program6914(1),  
                program6915(2),  
                program6916(3),  
                program6917(4),  
                program6918(5),  
                program6919(6),  
                program6920(7),  
                program6921(8),  
                program6922(9),  
                program6923(10), 
                program6924(11), 
                program6925(12), 
                program6926(13), 
                program6927(14), 
                program6928(15), 
                program6929(16), 
                program6930(17), 
                program6931(18), 
                program6932(19), 
                program6933(20), 
                program6934(21), 
                program6935(22), 
                program6936(23), 
                program6937(24), 
                program6938(25), 
                program6939(26), 
                program6940(27), 
                program6941(28), 
                program6942(29), 
                program6943(30), 
                program6944(31), 
                program6945(32), 
                program6946(33), 
                program6947(34), 
                program6948(35), 
                program6949(36), 
                program6950(37), 
                program6951(38), 
                program6952(39), 
                program6953(40), 
                program6954(41), 
                program6955(42), 
                program6956(43), 
                program6957(44), 
                program6958(45), 
                program6959(46), 
                program6960(47), 
                program6961(48), 
                program6962(49), 
                program6963(50), 
                program6964(51), 
                program6965(52), 
                program6966(53), 
                program6967(54), 
                program6968(55), 
                program6969(56), 
                program6970(57), 
                program6971(58), 
                program6972(59), 
                program6973(60), 
                program6974(61), 
                program6975(62), 
                program6976(63), 
                program6977(64), 
                program6978(65), 
                program6979(66), 
                program6980(67), 
                program6981(68), 
                program6982(69), 
                program6983(70), 
                program6984(71), 
                program6985(72), 
                program6986(73), 
                program6987(74), 
                program6988(75), 
                program6989(76), 
                program6990(77), 
                program6991(78), 
                program6992(79), 
                program6993(80), 
                program6994(81), 
                program6995(82), 
                program6996(83), 
                program6997(84), 
                program6998(85), 
                program6999(86), 
                program7000(87), 
                program7001(88), 
                program7002(89), 
                program7003(90), 
                program7004(91), 
                program7005(92), 
                program7006(93), 
                program7007(94), 
                program7008(95), 
                program7009(96), 
                program7010(97), 
                program7011(98), 
                program7012(99), 
                program7013(100),
                program7014(101),
                program7015(102),
                program7016(103),
                program7017(104),
                program7018(105),
                program7019(106),
                program7020(107),
                program7021(108),
                program7022(109),
                program7023(110),
                program7024(111),
                program7025(112),
                program7026(113),
                program7027(114),
                program7028(115),
                program7029(116),
                program7030(117),
                program7031(118),
                program7032(119),
                program7033(120),
                program7034(121),
                program7035(122),
                program7036(123),
                program7037(124),
                program7038(125),
                program7039(126),
                program7040(127) 
                }
            MAX-ACCESS read-write
            STATUS current
            DESCRIPTION
                "Indicates the program mask. This leaf indicates the authority of programs with indexes 3457-3520, 
                 64 programs in total. The indication methods of other mast leaves are the same as this table.
                 Each two bits indicate the authority to a program. Meanings of a 2-bit mask:
                 1. Forbidden(11)
                 2. Watch(01)
                 3. Preview(10)
                 4. idle(00)
                "
            ::= { hwDslamNtvRightProfileEntry 62 }    
            
        hwDslamNtvProgramMask56 OBJECT-TYPE
            SYNTAX BITS
                {
                program7041(0),  
                program7042(1),  
                program7043(2),  
                program7044(3),  
                program7045(4),  
                program7046(5),  
                program7047(6),  
                program7048(7),  
                program7049(8),  
                program7050(9),  
                program7051(10), 
                program7052(11), 
                program7053(12), 
                program7054(13), 
                program7055(14), 
                program7056(15), 
                program7057(16), 
                program7058(17), 
                program7059(18), 
                program7060(19), 
                program7061(20), 
                program7062(21), 
                program7063(22), 
                program7064(23), 
                program7065(24), 
                program7066(25), 
                program7067(26), 
                program7068(27), 
                program7069(28), 
                program7070(29), 
                program7071(30), 
                program7072(31), 
                program7073(32), 
                program7074(33), 
                program7075(34), 
                program7076(35), 
                program7077(36), 
                program7078(37), 
                program7079(38), 
                program7080(39), 
                program7081(40), 
                program7082(41), 
                program7083(42), 
                program7084(43), 
                program7085(44), 
                program7086(45), 
                program7087(46), 
                program7088(47), 
                program7089(48), 
                program7090(49), 
                program7091(50), 
                program7092(51), 
                program7093(52), 
                program7094(53), 
                program7095(54), 
                program7096(55), 
                program7097(56), 
                program7098(57), 
                program7099(58), 
                program7100(59), 
                program7101(60), 
                program7102(61), 
                program7103(62), 
                program7104(63), 
                program7105(64), 
                program7106(65), 
                program7107(66), 
                program7108(67), 
                program7109(68), 
                program7110(69), 
                program7111(70), 
                program7112(71), 
                program7113(72), 
                program7114(73), 
                program7115(74), 
                program7116(75), 
                program7117(76), 
                program7118(77), 
                program7119(78), 
                program7120(79), 
                program7121(80), 
                program7122(81), 
                program7123(82), 
                program7124(83), 
                program7125(84), 
                program7126(85), 
                program7127(86), 
                program7128(87), 
                program7129(88), 
                program7130(89), 
                program7131(90), 
                program7132(91), 
                program7133(92), 
                program7134(93), 
                program7135(94), 
                program7136(95), 
                program7137(96), 
                program7138(97), 
                program7139(98), 
                program7140(99), 
                program7141(100),
                program7142(101),
                program7143(102),
                program7144(103),
                program7145(104),
                program7146(105),
                program7147(106),
                program7148(107),
                program7149(108),
                program7150(109),
                program7151(110),
                program7152(111),
                program7153(112),
                program7154(113),
                program7155(114),
                program7156(115),
                program7157(116),
                program7158(117),
                program7159(118),
                program7160(119),
                program7161(120),
                program7162(121),
                program7163(122),
                program7164(123),
                program7165(124),
                program7166(125),
                program7167(126),
                program7168(127)
                }
            MAX-ACCESS read-write
            STATUS current
            DESCRIPTION
                "Indicates the program mask. This leaf indicates the authority of programs with indexes 3521-3584, 
                 64 programs in total. The indication methods of other mast leaves are the same as this table.
                 Each two bits indicate the authority to a program. Meanings of a 2-bit mask:
                 1. Forbidden(11)
                 2. Watch(01)
                 3. Preview(10)
                 4. idle(00)
                "
            ::= { hwDslamNtvRightProfileEntry 63 }    
            
        hwDslamNtvProgramMask57 OBJECT-TYPE
            SYNTAX BITS
                {
                program7169(0),  
                program7170(1),  
                program7171(2),  
                program7172(3),  
                program7173(4),  
                program7174(5),  
                program7175(6),  
                program7176(7),  
                program7177(8),  
                program7178(9),  
                program7179(10), 
                program7180(11), 
                program7181(12), 
                program7182(13), 
                program7183(14), 
                program7184(15), 
                program7185(16), 
                program7186(17), 
                program7187(18), 
                program7188(19), 
                program7189(20), 
                program7190(21), 
                program7191(22), 
                program7192(23), 
                program7193(24), 
                program7194(25), 
                program7195(26), 
                program7196(27), 
                program7197(28), 
                program7198(29), 
                program7199(30), 
                program7200(31), 
                program7201(32), 
                program7202(33), 
                program7203(34), 
                program7204(35), 
                program7205(36), 
                program7206(37), 
                program7207(38), 
                program7208(39), 
                program7209(40), 
                program7210(41), 
                program7211(42), 
                program7212(43), 
                program7213(44), 
                program7214(45), 
                program7215(46), 
                program7216(47), 
                program7217(48), 
                program7218(49), 
                program7219(50), 
                program7220(51), 
                program7221(52), 
                program7222(53), 
                program7223(54), 
                program7224(55), 
                program7225(56), 
                program7226(57), 
                program7227(58), 
                program7228(59), 
                program7229(60), 
                program7230(61), 
                program7231(62), 
                program7232(63), 
                program7233(64), 
                program7234(65), 
                program7235(66), 
                program7236(67), 
                program7237(68), 
                program7238(69), 
                program7239(70), 
                program7240(71), 
                program7241(72), 
                program7242(73), 
                program7243(74), 
                program7244(75), 
                program7245(76), 
                program7246(77), 
                program7247(78), 
                program7248(79), 
                program7249(80), 
                program7250(81), 
                program7251(82), 
                program7252(83), 
                program7253(84), 
                program7254(85), 
                program7255(86), 
                program7256(87), 
                program7257(88), 
                program7258(89), 
                program7259(90), 
                program7260(91), 
                program7261(92), 
                program7262(93), 
                program7263(94), 
                program7264(95), 
                program7265(96), 
                program7266(97), 
                program7267(98), 
                program7268(99), 
                program7269(100),
                program7270(101),
                program7271(102),
                program7272(103),
                program7273(104),
                program7274(105),
                program7275(106),
                program7276(107),
                program7277(108),
                program7278(109),
                program7279(110),
                program7280(111),
                program7281(112),
                program7282(113),
                program7283(114),
                program7284(115),
                program7285(116),
                program7286(117),
                program7287(118),
                program7288(119),
                program7289(120),
                program7290(121),
                program7291(122),
                program7292(123),
                program7293(124),
                program7294(125),
                program7295(126),
                program7296(127) 
                }
            MAX-ACCESS read-write
            STATUS current
            DESCRIPTION
                "Indicates the program mask. This leaf indicates the authority of programs with indexes 3585-3648, 
                 64 programs in total. The indication methods of other mast leaves are the same as this table.
                 Each two bits indicate the authority to a program. Meanings of a 2-bit mask:
                 1. Forbidden(11)
                 2. Watch(01)
                 3. Preview(10)
                 4. idle(00)
                "
            ::= { hwDslamNtvRightProfileEntry 64 }        
            
        hwDslamNtvProgramMask58 OBJECT-TYPE
            SYNTAX BITS
                {
                program7297(0),  
                program7298(1),  
                program7299(2),  
                program7300(3),  
                program7301(4),  
                program7302(5),  
                program7303(6),  
                program7304(7),  
                program7305(8),  
                program7306(9),  
                program7307(10), 
                program7308(11), 
                program7309(12), 
                program7310(13), 
                program7311(14), 
                program7312(15), 
                program7313(16), 
                program7314(17), 
                program7315(18), 
                program7316(19), 
                program7317(20), 
                program7318(21), 
                program7319(22), 
                program7320(23), 
                program7321(24), 
                program7322(25), 
                program7323(26), 
                program7324(27), 
                program7325(28), 
                program7326(29), 
                program7327(30), 
                program7328(31), 
                program7329(32), 
                program7330(33), 
                program7331(34), 
                program7332(35), 
                program7333(36), 
                program7334(37), 
                program7335(38), 
                program7336(39), 
                program7337(40), 
                program7338(41), 
                program7339(42), 
                program7340(43), 
                program7341(44), 
                program7342(45), 
                program7343(46), 
                program7344(47), 
                program7345(48), 
                program7346(49), 
                program7347(50), 
                program7348(51), 
                program7349(52), 
                program7350(53), 
                program7351(54), 
                program7352(55), 
                program7353(56), 
                program7354(57), 
                program7355(58), 
                program7356(59), 
                program7357(60), 
                program7358(61), 
                program7359(62), 
                program7360(63), 
                program7361(64), 
                program7362(65), 
                program7363(66), 
                program7364(67), 
                program7365(68), 
                program7366(69), 
                program7367(70), 
                program7368(71), 
                program7369(72), 
                program7370(73), 
                program7371(74), 
                program7372(75), 
                program7373(76), 
                program7374(77), 
                program7375(78), 
                program7376(79), 
                program7377(80), 
                program7378(81), 
                program7379(82), 
                program7380(83), 
                program7381(84), 
                program7382(85), 
                program7383(86), 
                program7384(87), 
                program7385(88), 
                program7386(89), 
                program7387(90), 
                program7388(91), 
                program7389(92), 
                program7390(93), 
                program7391(94), 
                program7392(95), 
                program7393(96), 
                program7394(97), 
                program7395(98), 
                program7396(99), 
                program7397(100),
                program7398(101),
                program7399(102),
                program7400(103),
                program7401(104),
                program7402(105),
                program7403(106),
                program7404(107),
                program7405(108),
                program7406(109),
                program7407(110),
                program7408(111),
                program7409(112),
                program7410(113),
                program7411(114),
                program7412(115),
                program7413(116),
                program7414(117),
                program7415(118),
                program7416(119),
                program7417(120),
                program7418(121),
                program7419(122),
                program7420(123),
                program7421(124),
                program7422(125),
                program7423(126),
                program7424(127) 
                }
            MAX-ACCESS read-write
            STATUS current
            DESCRIPTION
                "Indicates the program mask. This leaf indicates the authority of programs with indexes 3649-3712, 
                 64 programs in total. The indication methods of other mast leaves are the same as this table.
                 Each two bits indicate the authority to a program. Meanings of a 2-bit mask:
                 1. Forbidden(11)
                 2. Watch(01)
                 3. Preview(10)
                 4. idle(00)
                "
            ::= { hwDslamNtvRightProfileEntry 65 }        
            
        hwDslamNtvProgramMask59 OBJECT-TYPE
            SYNTAX BITS
                {
                program7425(0),  
                program7426(1),  
                program7427(2),  
                program7428(3),  
                program7429(4),  
                program7430(5),  
                program7431(6),  
                program7432(7),  
                program7433(8),  
                program7434(9),  
                program7435(10), 
                program7436(11), 
                program7437(12), 
                program7438(13), 
                program7439(14), 
                program7440(15), 
                program7441(16), 
                program7442(17), 
                program7443(18), 
                program7444(19), 
                program7445(20), 
                program7446(21), 
                program7447(22), 
                program7448(23), 
                program7449(24), 
                program7450(25), 
                program7451(26), 
                program7452(27), 
                program7453(28), 
                program7454(29), 
                program7455(30), 
                program7456(31), 
                program7457(32), 
                program7458(33), 
                program7459(34), 
                program7460(35), 
                program7461(36), 
                program7462(37), 
                program7463(38), 
                program7464(39), 
                program7465(40), 
                program7466(41), 
                program7467(42), 
                program7468(43), 
                program7469(44), 
                program7470(45), 
                program7471(46), 
                program7472(47), 
                program7473(48), 
                program7474(49), 
                program7475(50), 
                program7476(51), 
                program7477(52), 
                program7478(53), 
                program7479(54), 
                program7480(55), 
                program7481(56), 
                program7482(57), 
                program7483(58), 
                program7484(59), 
                program7485(60), 
                program7486(61), 
                program7487(62), 
                program7488(63), 
                program7489(64), 
                program7490(65), 
                program7491(66), 
                program7492(67), 
                program7493(68), 
                program7494(69), 
                program7495(70), 
                program7496(71), 
                program7497(72), 
                program7498(73), 
                program7499(74), 
                program7500(75), 
                program7501(76), 
                program7502(77), 
                program7503(78), 
                program7504(79), 
                program7505(80), 
                program7506(81), 
                program7507(82), 
                program7508(83), 
                program7509(84), 
                program7510(85), 
                program7511(86), 
                program7512(87), 
                program7513(88), 
                program7514(89), 
                program7515(90), 
                program7516(91), 
                program7517(92), 
                program7518(93), 
                program7519(94), 
                program7520(95), 
                program7521(96), 
                program7522(97), 
                program7523(98), 
                program7524(99), 
                program7525(100),
                program7526(101),
                program7527(102),
                program7528(103),
                program7529(104),
                program7530(105),
                program7531(106),
                program7532(107),
                program7533(108),
                program7534(109),
                program7535(110),
                program7536(111),
                program7537(112),
                program7538(113),
                program7539(114),
                program7540(115),
                program7541(116),
                program7542(117),
                program7543(118),
                program7544(119),
                program7545(120),
                program7546(121),
                program7547(122),
                program7548(123),
                program7549(124),
                program7550(125),
                program7551(126),
                program7552(127)
                }
            MAX-ACCESS read-write
            STATUS current
            DESCRIPTION
                "Indicates the program mask. This leaf indicates the authority of programs with indexes 3713-3776, 
                 64 programs in total. The indication methods of other mast leaves are the same as this table.
                 Each two bits indicate the authority to a program. Meanings of a 2-bit mask:
                 1. Forbidden(11)
                 2. Watch(01)
                 3. Preview(10)
                 4. idle(00)
                "
            ::= { hwDslamNtvRightProfileEntry 66 }    
            
        hwDslamNtvProgramMask60 OBJECT-TYPE
            SYNTAX BITS
                {
                program7553(0),  
                program7554(1),  
                program7555(2),  
                program7556(3),  
                program7557(4),  
                program7558(5),  
                program7559(6),  
                program7560(7),  
                program7561(8),  
                program7562(9),  
                program7563(10), 
                program7564(11), 
                program7565(12), 
                program7566(13), 
                program7567(14), 
                program7568(15), 
                program7569(16), 
                program7570(17), 
                program7571(18), 
                program7572(19), 
                program7573(20), 
                program7574(21), 
                program7575(22), 
                program7576(23), 
                program7577(24), 
                program7578(25), 
                program7579(26), 
                program7580(27), 
                program7581(28), 
                program7582(29), 
                program7583(30), 
                program7584(31), 
                program7585(32), 
                program7586(33), 
                program7587(34), 
                program7588(35), 
                program7589(36), 
                program7590(37), 
                program7591(38), 
                program7592(39), 
                program7593(40), 
                program7594(41), 
                program7595(42), 
                program7596(43), 
                program7597(44), 
                program7598(45), 
                program7599(46), 
                program7600(47), 
                program7601(48), 
                program7602(49), 
                program7603(50), 
                program7604(51), 
                program7605(52), 
                program7606(53), 
                program7607(54), 
                program7608(55), 
                program7609(56), 
                program7610(57), 
                program7611(58), 
                program7612(59), 
                program7613(60), 
                program7614(61), 
                program7615(62), 
                program7616(63), 
                program7617(64), 
                program7618(65), 
                program7619(66), 
                program7620(67), 
                program7621(68), 
                program7622(69), 
                program7623(70), 
                program7624(71), 
                program7625(72), 
                program7626(73), 
                program7627(74), 
                program7628(75), 
                program7629(76), 
                program7630(77), 
                program7631(78), 
                program7632(79), 
                program7633(80), 
                program7634(81), 
                program7635(82), 
                program7636(83), 
                program7637(84), 
                program7638(85), 
                program7639(86), 
                program7640(87), 
                program7641(88), 
                program7642(89), 
                program7643(90), 
                program7644(91), 
                program7645(92), 
                program7646(93), 
                program7647(94), 
                program7648(95), 
                program7649(96), 
                program7650(97), 
                program7651(98), 
                program7652(99), 
                program7653(100),
                program7654(101),
                program7655(102),
                program7656(103),
                program7657(104),
                program7658(105),
                program7659(106),
                program7660(107),
                program7661(108),
                program7662(109),
                program7663(110),
                program7664(111),
                program7665(112),
                program7666(113),
                program7667(114),
                program7668(115),
                program7669(116),
                program7670(117),
                program7671(118),
                program7672(119),
                program7673(120),
                program7674(121),
                program7675(122),
                program7676(123),
                program7677(124),
                program7678(125),
                program7679(126),
                program7680(127)
                }
            MAX-ACCESS read-write
            STATUS current
            DESCRIPTION
                "Indicates the program mask. This leaf indicates the authority of programs with indexes 3777-3840, 
                 64 programs in total. The indication methods of other mast leaves are the same as this table.
                 Each two bits indicate the authority to a program. Meanings of a 2-bit mask:
                 1. Forbidden(11)
                 2. Watch(01)
                 3. Preview(10)
                 4. idle(00)
                "
            ::= { hwDslamNtvRightProfileEntry 67 }    
            
        hwDslamNtvProgramMask61 OBJECT-TYPE
            SYNTAX BITS
                {
                program7681(0),  
                program7682(1),  
                program7683(2),  
                program7684(3),  
                program7685(4),  
                program7686(5),  
                program7687(6),  
                program7688(7),  
                program7689(8),  
                program7690(9),  
                program7691(10), 
                program7692(11), 
                program7693(12), 
                program7694(13), 
                program7695(14), 
                program7696(15), 
                program7697(16), 
                program7698(17), 
                program7699(18), 
                program7700(19), 
                program7701(20), 
                program7702(21), 
                program7703(22), 
                program7704(23), 
                program7705(24), 
                program7706(25), 
                program7707(26), 
                program7708(27), 
                program7709(28), 
                program7710(29), 
                program7711(30), 
                program7712(31), 
                program7713(32), 
                program7714(33), 
                program7715(34), 
                program7716(35), 
                program7717(36), 
                program7718(37), 
                program7719(38), 
                program7720(39), 
                program7721(40), 
                program7722(41), 
                program7723(42), 
                program7724(43), 
                program7725(44), 
                program7726(45), 
                program7727(46), 
                program7728(47), 
                program7729(48), 
                program7730(49), 
                program7731(50), 
                program7732(51), 
                program7733(52), 
                program7734(53), 
                program7735(54), 
                program7736(55), 
                program7737(56), 
                program7738(57), 
                program7739(58), 
                program7740(59), 
                program7741(60), 
                program7742(61), 
                program7743(62), 
                program7744(63), 
                program7745(64), 
                program7746(65), 
                program7747(66), 
                program7748(67), 
                program7749(68), 
                program7750(69), 
                program7751(70), 
                program7752(71), 
                program7753(72), 
                program7754(73), 
                program7755(74), 
                program7756(75), 
                program7757(76), 
                program7758(77), 
                program7759(78), 
                program7760(79), 
                program7761(80), 
                program7762(81), 
                program7763(82), 
                program7764(83), 
                program7765(84), 
                program7766(85), 
                program7767(86), 
                program7768(87), 
                program7769(88), 
                program7770(89), 
                program7771(90), 
                program7772(91), 
                program7773(92), 
                program7774(93), 
                program7775(94), 
                program7776(95), 
                program7777(96), 
                program7778(97), 
                program7779(98), 
                program7780(99), 
                program7781(100),
                program7782(101),
                program7783(102),
                program7784(103),
                program7785(104),
                program7786(105),
                program7787(106),
                program7788(107),
                program7789(108),
                program7790(109),
                program7791(110),
                program7792(111),
                program7793(112),
                program7794(113),
                program7795(114),
                program7796(115),
                program7797(116),
                program7798(117),
                program7799(118),
                program7800(119),
                program7801(120),
                program7802(121),
                program7803(122),
                program7804(123),
                program7805(124),
                program7806(125),
                program7807(126),
                program7808(127)
                }
            MAX-ACCESS read-write
            STATUS current
            DESCRIPTION
                "Indicates the program mask. This leaf indicates the authority of programs with indexes 3841-3904, 
                 64 programs in total. The indication methods of other mast leaves are the same as this table.
                 Each two bits indicate the authority to a program. Meanings of a 2-bit mask:
                 1. Forbidden(11)
                 2. Watch(01)
                 3. Preview(10)
                 4. idle(00)
                "
            ::= { hwDslamNtvRightProfileEntry 68 }        
            
        hwDslamNtvProgramMask62 OBJECT-TYPE
            SYNTAX BITS
                {
                program7809(0),  
                program7810(1),  
                program7811(2),  
                program7812(3),  
                program7813(4),  
                program7814(5),  
                program7815(6),  
                program7816(7),  
                program7817(8),  
                program7818(9),  
                program7819(10), 
                program7820(11), 
                program7821(12), 
                program7822(13), 
                program7823(14), 
                program7824(15), 
                program7825(16), 
                program7826(17), 
                program7827(18), 
                program7828(19), 
                program7829(20), 
                program7830(21), 
                program7831(22), 
                program7832(23), 
                program7833(24), 
                program7834(25), 
                program7835(26), 
                program7836(27), 
                program7837(28), 
                program7838(29), 
                program7839(30), 
                program7840(31), 
                program7841(32), 
                program7842(33), 
                program7843(34), 
                program7844(35), 
                program7845(36), 
                program7846(37), 
                program7847(38), 
                program7848(39), 
                program7849(40), 
                program7850(41), 
                program7851(42), 
                program7852(43), 
                program7853(44), 
                program7854(45), 
                program7855(46), 
                program7856(47), 
                program7857(48), 
                program7858(49), 
                program7859(50), 
                program7860(51), 
                program7861(52), 
                program7862(53), 
                program7863(54), 
                program7864(55), 
                program7865(56), 
                program7866(57), 
                program7867(58), 
                program7868(59), 
                program7869(60), 
                program7870(61), 
                program7871(62), 
                program7872(63), 
                program7873(64), 
                program7874(65), 
                program7875(66), 
                program7876(67), 
                program7877(68), 
                program7878(69), 
                program7879(70), 
                program7880(71), 
                program7881(72), 
                program7882(73), 
                program7883(74), 
                program7884(75), 
                program7885(76), 
                program7886(77), 
                program7887(78), 
                program7888(79), 
                program7889(80), 
                program7890(81), 
                program7891(82), 
                program7892(83), 
                program7893(84), 
                program7894(85), 
                program7895(86), 
                program7896(87), 
                program7897(88), 
                program7898(89), 
                program7899(90), 
                program7900(91), 
                program7901(92), 
                program7902(93), 
                program7903(94), 
                program7904(95), 
                program7905(96), 
                program7906(97), 
                program7907(98), 
                program7908(99), 
                program7909(100),
                program7910(101),
                program7911(102),
                program7912(103),
                program7913(104),
                program7914(105),
                program7915(106),
                program7916(107),
                program7917(108),
                program7918(109),
                program7919(110),
                program7920(111),
                program7921(112),
                program7922(113),
                program7923(114),
                program7924(115),
                program7925(116),
                program7926(117),
                program7927(118),
                program7928(119),
                program7929(120),
                program7930(121),
                program7931(122),
                program7932(123),
                program7933(124),
                program7934(125),
                program7935(126),
                program7936(127)
                }
            MAX-ACCESS read-write
            STATUS current
            DESCRIPTION
                "Indicates the program mask. This leaf indicates the authority of programs with indexes 3905-3968, 
                 64 programs in total. The indication methods of other mast leaves are the same as this table.
                 Each two bits indicate the authority to a program. Meanings of a 2-bit mask:
                 1. Forbidden(11)
                 2. Watch(01)
                 3. Preview(10)
                 4. idle(00)
                "
            ::= { hwDslamNtvRightProfileEntry 69 }    
            
        hwDslamNtvProgramMask63 OBJECT-TYPE
            SYNTAX BITS
                {
                program7937(0),  
                program7938(1),  
                program7939(2),  
                program7940(3),  
                program7941(4),  
                program7942(5),  
                program7943(6),  
                program7944(7),  
                program7945(8),  
                program7946(9),  
                program7947(10), 
                program7948(11), 
                program7949(12), 
                program7950(13), 
                program7951(14), 
                program7952(15), 
                program7953(16), 
                program7954(17), 
                program7955(18), 
                program7956(19), 
                program7957(20), 
                program7958(21), 
                program7959(22), 
                program7960(23), 
                program7961(24), 
                program7962(25), 
                program7963(26), 
                program7964(27), 
                program7965(28), 
                program7966(29), 
                program7967(30), 
                program7968(31), 
                program7969(32), 
                program7970(33), 
                program7971(34), 
                program7972(35), 
                program7973(36), 
                program7974(37), 
                program7975(38), 
                program7976(39), 
                program7977(40), 
                program7978(41), 
                program7979(42), 
                program7980(43), 
                program7981(44), 
                program7982(45), 
                program7983(46), 
                program7984(47), 
                program7985(48), 
                program7986(49), 
                program7987(50), 
                program7988(51), 
                program7989(52), 
                program7990(53), 
                program7991(54), 
                program7992(55), 
                program7993(56), 
                program7994(57), 
                program7995(58), 
                program7996(59), 
                program7997(60), 
                program7998(61), 
                program7999(62), 
                program8000(63),
                program8001(64), 
                program8002(65), 
                program8003(66), 
                program8004(67), 
                program8005(68), 
                program8006(69), 
                program8007(70), 
                program8008(71), 
                program8009(72), 
                program8010(73), 
                program8011(74), 
                program8012(75), 
                program8013(76), 
                program8014(77), 
                program8015(78), 
                program8016(79), 
                program8017(80), 
                program8018(81), 
                program8019(82), 
                program8020(83), 
                program8021(84), 
                program8022(85), 
                program8023(86), 
                program8024(87), 
                program8025(88), 
                program8026(89), 
                program8027(90), 
                program8028(91), 
                program8029(92), 
                program8030(93), 
                program8031(94), 
                program8032(95), 
                program8033(96), 
                program8034(97), 
                program8035(98), 
                program8036(99), 
                program8037(100),
                program8038(101),
                program8039(102),
                program8040(103),
                program8041(104),
                program8042(105),
                program8043(106),
                program8044(107),
                program8045(108),
                program8046(109),
                program8047(110),
                program8048(111),
                program8049(112),
                program8050(113),
                program8051(114),
                program8052(115),
                program8053(116),
                program8054(117),
                program8055(118),
                program8056(119),
                program8057(120),
                program8058(121),
                program8059(122),
                program8060(123),
                program8061(124),
                program8062(125),
                program8063(126),
                program8064(127)                     
                }
            MAX-ACCESS read-write
            STATUS current
            DESCRIPTION
                "Indicates the program mask. This leaf indicates the authority of programs with indexes 3969-4032, 
                 64 programs in total. The indication methods of other mast leaves are the same as this table.
                 Each two bits indicate the authority to a program. Meanings of a 2-bit mask:
                 1. Forbidden(11)
                 2. Watch(01)
                 3. Preview(10)
                 4. idle(00)
                "
            ::= { hwDslamNtvRightProfileEntry 70 }    
            
        hwDslamNtvProgramMask64 OBJECT-TYPE
            SYNTAX BITS
                {
                program8065(0),  
                program8066(1),  
                program8067(2),  
                program8068(3),  
                program8069(4),  
                program8070(5),  
                program8071(6),  
                program8072(7),  
                program8073(8),  
                program8074(9),  
                program8075(10), 
                program8076(11), 
                program8077(12), 
                program8078(13), 
                program8079(14), 
                program8080(15), 
                program8081(16), 
                program8082(17), 
                program8083(18), 
                program8084(19), 
                program8085(20), 
                program8086(21), 
                program8087(22), 
                program8088(23), 
                program8089(24), 
                program8090(25), 
                program8091(26), 
                program8092(27), 
                program8093(28), 
                program8094(29), 
                program8095(30), 
                program8096(31), 
                program8097(32), 
                program8098(33), 
                program8099(34), 
                program8100(35), 
                program8101(36), 
                program8102(37), 
                program8103(38), 
                program8104(39), 
                program8105(40), 
                program8106(41), 
                program8107(42), 
                program8108(43), 
                program8109(44), 
                program8110(45), 
                program8111(46), 
                program8112(47), 
                program8113(48), 
                program8114(49), 
                program8115(50), 
                program8116(51), 
                program8117(52), 
                program8118(53), 
                program8119(54), 
                program8120(55), 
                program8121(56), 
                program8122(57), 
                program8123(58), 
                program8124(59), 
                program8125(60), 
                program8126(61), 
                program8127(62), 
                program8128(63), 
                program8129(64), 
                program8130(65), 
                program8131(66), 
                program8132(67), 
                program8133(68), 
                program8134(69), 
                program8135(70), 
                program8136(71), 
                program8137(72), 
                program8138(73), 
                program8139(74), 
                program8140(75), 
                program8141(76), 
                program8142(77), 
                program8143(78), 
                program8144(79), 
                program8145(80), 
                program8146(81), 
                program8147(82), 
                program8148(83), 
                program8149(84), 
                program8150(85), 
                program8151(86), 
                program8152(87), 
                program8153(88), 
                program8154(89), 
                program8155(90), 
                program8156(91), 
                program8157(92), 
                program8158(93), 
                program8159(94), 
                program8160(95), 
                program8161(96), 
                program8162(97), 
                program8163(98), 
                program8164(99), 
                program8165(100),
                program8166(101),
                program8167(102),
                program8168(103),
                program8169(104),
                program8170(105),
                program8171(106),
                program8172(107),
                program8173(108),
                program8174(109),
                program8175(110),
                program8176(111),
                program8177(112),
                program8178(113),
                program8179(114),
                program8180(115),
                program8181(116),
                program8182(117),
                program8183(118),
                program8184(119),
                program8185(120),
                program8186(121),
                program8187(122),
                program8188(123),
                program8189(124),
                program8190(125),
                program8191(126),
                program8192(127)                      
                }
            MAX-ACCESS read-write
            STATUS current
            DESCRIPTION
                "Indicates the program mask. This leaf indicates the authority of programs with indexes 4033-4096, 
                 64 programs in total. The indication methods of other mast leaves are the same as this table.
                 Each two bits indicate the authority to a program. Meanings of a 2-bit mask:
                 1. Forbidden(11)
                 2. Watch(01)
                 3. Preview(10)
                 4. idle(00)
                "
            ::= { hwDslamNtvRightProfileEntry 71 }                
 
        hwDslamNtvChannelTrafficTable    OBJECT-TYPE
            SYNTAX          SEQUENCE OF HwDslamNtvChannelTrafficEntry
            MAX-ACCESS      not-accessible
            STATUS          current
            DESCRIPTION
                "Traffic statistics table.
                 The index of this table is hwDslamNtvChannelIndex.
                "
            ::= { hwDslamNtv 20 }
        
        hwDslamNtvChannelTrafficEntry    OBJECT-TYPE
             SYNTAX             HwDslamNtvChannelTrafficEntry
             MAX-ACCESS         not-accessible
             STATUS             current
             DESCRIPTION
                 "Traffic statistics table.
                  The index of this entry is hwDslamNtvChannelIndex.
                 "
             INDEX   
                 { 
                 hwDslamNtvChannelIndex
                 }
             ::= { hwDslamNtvChannelTrafficTable  1 }
        
        HwDslamNtvChannelTrafficEntry    ::= 
            SEQUENCE  
                {
                hwDslamNtvAdminStatus       
                    INTEGER,
                hwDslamNtvTrafficValue     
                    Integer32
                }
        
        hwDslamNtvAdminStatus       OBJECT-TYPE
            SYNTAX  INTEGER
                {
                up(1),
                down(2)
                }
            MAX-ACCESS   read-write
            STATUS       current
            DESCRIPTION
                "Administration state.
                 The Administration state of video multicast traffic statistics.
                 Options:
                 1. up(1)   -indicates the administration state is up
                 2. down(2) -indicates the administration state is down
                "
            ::= { hwDslamNtvChannelTrafficEntry 1}
        
        hwDslamNtvTrafficValue        OBJECT-TYPE
            SYNTAX       Integer32
            UNITS        "kbps"           
            MAX-ACCESS   read-only
            STATUS       current
            DESCRIPTION
                "Traffic Value.
                 The value of video multicast traffic statistics.
                 UNIT: kbit/s
                "
            ::= { hwDslamNtvChannelTrafficEntry 2}       
        
        hwDslamNtvIgmpConfigTable    OBJECT-TYPE
            SYNTAX          SEQUENCE OF HwDslamNtvIgmpConfigEntry
            MAX-ACCESS      not-accessible
            STATUS          current
            DESCRIPTION
                "Port IGMP Parameter config table.
                 The index of this table is hwDslamNtvUserIndex.
                "
            ::= { hwDslamNtv 21 }
    
        hwDslamNtvIgmpConfigEntry    OBJECT-TYPE
            SYNTAX          HwDslamNtvIgmpConfigEntry
            MAX-ACCESS      not-accessible
            STATUS          current
            DESCRIPTION
                "Port IGMP Parameter config table.
                 The index of this entry is hwDslamNtvUserIndex.
                "
            INDEX   
                { 
                hwDslamNtvUserIndex 
                }
            ::= { hwDslamNtvIgmpConfigTable  1 }
        
        HwDslamNtvIgmpConfigEntry    ::= 
            SEQUENCE  
                {
                hwDslamNtvIgmpQuickLeave          
                    TruthValue            
                }
        
        hwDslamNtvIgmpQuickLeave        OBJECT-TYPE
            SYNTAX      TruthValue    
            MAX-ACCESS  read-write
            STATUS      current
            DESCRIPTION
                "Quick Leave.
                 When Quick Leave is true,IGMP-Proxy make user 
                 offline as soon as receiving Leave packet instead 
                 of sending  specific queries.
                 Options:
                 1. true(1)  -indicates the user can leave as soon as receiving Leave packet instead 
                              of sending  specific queries 
                 2. false(1) -indicates the user can leave after sending specific queries
                "
            DEFVAL { 2 }
            ::= { hwDslamNtvIgmpConfigEntry 1}
        
        hwDslamNtvProgramLogTable    OBJECT-TYPE
            SYNTAX          SEQUENCE OF HwDslamNtvProgramLogEntry
            MAX-ACCESS      not-accessible
            STATUS          current
            DESCRIPTION
                "Program Log statistics table.
                 The indexes of this table are hwDslamNtvProgramLogStartTime, hwDslamNtvProgramLogEndTime and hwDslamNtvProgramLogIP.
                "
            ::= { hwDslamNtv 22 }
        
        hwDslamNtvProgramLogEntry    OBJECT-TYPE
            SYNTAX             HwDslamNtvProgramLogEntry
            MAX-ACCESS         not-accessible
            STATUS             current
            DESCRIPTION
                "Program Log statistics table.
                 The indexes of this entry are hwDslamNtvProgramLogStartTime, hwDslamNtvProgramLogEndTime and hwDslamNtvProgramLogIP.
                "
            INDEX   
                { 
                hwDslamNtvProgramLogStartTime,
                hwDslamNtvProgramLogEndTime,
                hwDslamNtvProgramLogIP
                }
            ::= { hwDslamNtvProgramLogTable  1 }
        
        HwDslamNtvProgramLogEntry    ::= 
            SEQUENCE  
                {
                hwDslamNtvProgramLogStartTime 
                    DateAndTime,
                hwDslamNtvProgramLogEndTime   
                    DateAndTime,
                hwDslamNtvProgramLogIP        
                    IpAddress,
                hwDslamNtvProgramLogUserNum   
                    Integer32, 
                hwDslamNtvProgramLogTotalTime  
                    Integer32
               }
        
        hwDslamNtvProgramLogStartTime       OBJECT-TYPE
            SYNTAX       DateAndTime
            MAX-ACCESS   read-only
            STATUS       current
            DESCRIPTION
                "Start time.
                 Start time of the program log Statistics.
                "
            ::= { hwDslamNtvProgramLogEntry 1}
        
        hwDslamNtvProgramLogEndTime       OBJECT-TYPE
            SYNTAX       DateAndTime
            MAX-ACCESS   read-only
            STATUS       current
            DESCRIPTION
                "End time.
                 End time of the program log Statistics.
                "
            ::= { hwDslamNtvProgramLogEntry 2}  
        
        hwDslamNtvProgramLogIP        OBJECT-TYPE
            SYNTAX       IpAddress
            MAX-ACCESS   read-only
            STATUS       current
            DESCRIPTION
                "Program IP address.
                "
            ::= { hwDslamNtvProgramLogEntry 3}     
        
        hwDslamNtvProgramLogUserNum        OBJECT-TYPE
            SYNTAX       Integer32
            MAX-ACCESS   read-only
            STATUS       current
            DESCRIPTION
                "Total user number.
                "
            ::= { hwDslamNtvProgramLogEntry 4}    
        
        hwDslamNtvProgramLogTotalTime        OBJECT-TYPE
            SYNTAX       Integer32
            MAX-ACCESS   read-only
            STATUS       current
            DESCRIPTION
                "Total time.
                "
            ::= { hwDslamNtvProgramLogEntry 5} 
        
        hwDslamNtvUpportTable    OBJECT-TYPE
            SYNTAX          SEQUENCE OF HwDslamNtvUpportEntry
            MAX-ACCESS      not-accessible
            STATUS          current
            DESCRIPTION
                "Upport management table.
                 The index of this table is hwDslamNtvUpportTblIndex.
                "
            ::= { hwDslamNtv 23 }
        
        hwDslamNtvUpportEntry    OBJECT-TYPE
            SYNTAX          HwDslamNtvUpportEntry
            MAX-ACCESS      not-accessible
            STATUS          current
            DESCRIPTION
                "Upport management table.
                 The index of this entry is hwDslamNtvUpportTblIndex.
                "
            INDEX 
                { 
                hwDslamNtvUpportTblIndex
                }
            ::= { hwDslamNtvUpportTable  1 }
        
        HwDslamNtvUpportEntry    ::= 
            SEQUENCE  
                {
                hwDslamNtvUpportTblIndex     
                    Integer32,
                hwDslamNtvUpportTblRowStatus  
                    RowStatus, 
                hwDslamNtvUpportTblInter      
                    Integer32, 
                hwDslamNtvUpportTblVlan      
                    Integer32,
                hwDslamNtvUpportTblHostIP    
                    IpAddress,
                hwDslamNtvUpportTblRouterVersion
                    Integer32,
                hwDslamNtvUpportTblAllocBandwidth 
                    Integer32,
                hwDslamNtvUpportTblUsedBandwidth
                    OCTET STRING,     
                hwDslamNtvUpportTblPortSpeed  
                    Integer32,
                hwDslamNtvUpportTblMFSResult   
                    Integer32         
              }
                                        
        hwDslamNtvUpportTblIndex        OBJECT-TYPE
            SYNTAX       Integer32(1..1024)
            MAX-ACCESS   read-create
            STATUS       current
            DESCRIPTION
                "Upport index.
                "
            ::= { hwDslamNtvUpportEntry 1}   
        
        hwDslamNtvUpportTblRowStatus        OBJECT-TYPE
            SYNTAX       RowStatus
            MAX-ACCESS   read-create
            STATUS       current
            DESCRIPTION
                "Row status.
                 Add or delete a table item.
                 Options:
                 1. active(1)      -indicates the query operation
                 2. createAndGo(4) -indicates the creating operation
                 3. destroy(6)     -indicates the deleting operation
                "
            ::= { hwDslamNtvUpportEntry 2}   
        
        hwDslamNtvUpportTblInter   OBJECT-TYPE
            SYNTAX       Integer32
            MAX-ACCESS   read-create
            STATUS       current
            DESCRIPTION
                "Up Port.Frame/Slot/Port.
                "
            ::= { hwDslamNtvUpportEntry 3 }
        
        hwDslamNtvUpportTblVlan   OBJECT-TYPE
            SYNTAX       Integer32 (1..4093)
            MAX-ACCESS   read-create
            STATUS       current
            DESCRIPTION
                "VlanId of Up Port.
                "
            ::= { hwDslamNtvUpportEntry 4 }
        
        hwDslamNtvUpportTblHostIP        OBJECT-TYPE
            SYNTAX       IpAddress
            MAX-ACCESS   read-create
            STATUS       current
            DESCRIPTION
                "IGMP host IP address.
                 If IP address of Upport-interface is not configured,
                 IGMP-host-IP-address will be used to send IGMP packets.
                "
            ::= { hwDslamNtvUpportEntry 5}
        
        hwDslamNtvUpportTblRouterVersion  OBJECT-TYPE
            SYNTAX       Integer32 (1..3)
            MAX-ACCESS   read-only
            STATUS       current
            DESCRIPTION
                "The current IGMP Version of  up port.It is include V1/V2/V3 version.
                "
        ::= { hwDslamNtvUpportEntry 6}
        
        hwDslamNtvUpportTblAllocBandwidth OBJECT-TYPE
            SYNTAX       Integer32 (1..100)
            MAX-ACCESS   read-create
            STATUS       current
            DESCRIPTION
                "The uplink port allocates multicast bandwidth. unit:kbps.
                "
            ::= { hwDslamNtvUpportEntry 7}
        
        hwDslamNtvUpportTblUsedBandwidth OBJECT-TYPE
            SYNTAX       OCTET STRING
            MAX-ACCESS   read-only
            STATUS       current
            DESCRIPTION
                "It has been used multicase bandwidth of up port. unit:kbps.
                "
            ::= { hwDslamNtvUpportEntry 8}  
        
        hwDslamNtvUpportTblPortSpeed OBJECT-TYPE
            SYNTAX       Integer32
            MAX-ACCESS   read-only
            STATUS       current
            DESCRIPTION
                "The ethernet port speed. unit:kbps
                "
            ::= { hwDslamNtvUpportEntry 9}
                   
        hwDslamNtvUpportTblMFSResult OBJECT-TYPE
            SYNTAX Integer32
            MAX-ACCESS read-only
            STATUS current
            DESCRIPTION
                "Get the Multicast Flow Statics result of an appointed uplink port.
                "
            ::= { hwDslamNtvUpportEntry 10 } 
        
        hwDslamNtvIpCascadeTable    OBJECT-TYPE
            SYNTAX          SEQUENCE OF HwDslamNtvIpCascadeEntry
            MAX-ACCESS      not-accessible
            STATUS          current
            DESCRIPTION
                "Indicates the multicast subtending port table.
                 The index of this table is hwDslamntvIpCascadePortIndex.
                "
            ::= { hwDslamNtv 24 }
        
        hwDslamNtvIpCascadeEntry    OBJECT-TYPE
            SYNTAX          HwDslamNtvIpCascadeEntry
            MAX-ACCESS      not-accessible
            STATUS          current
            DESCRIPTION
                "Indicates the multicast subtending port table.
                 The index of this entry is hwDslamntvIpCascadePortIndex.
                "
            INDEX 
                { 
                hwDslamntvIpCascadePortIndex
                }
            ::= { hwDslamNtvIpCascadeTable  1 }
        
        HwDslamNtvIpCascadeEntry    ::= 
            SEQUENCE  
                {
                hwDslamntvIpCascadePortIndex         
                    Integer32,
                hwDslamNtvIpCascadePortRowStatus     
                    RowStatus, 
                hwDslamntvIpCascadePortFrameSlotPort  
                    Integer32, 
                hwDslamntvIpCascadeProgramWatchingCount
                    Integer32,     
                hwDslamntvIpCascadePortStaticJoin    
                    TruthValue,
                hwDslamntvIpCascadePortQuickLeave     
                    TruthValue,
                hwDslamntvIpCascadePortMode         
                    INTEGER,
                hwDslamntvIpCascadePortProcAfterMismatch 
                    INTEGER,
                hwDslamNtvIpCascadePortMatchPara     
                    Integer32,
                hwDslamntvIpCascadePortControlWord   
                    TruthValue,
                hwDslamNtvIpCascadePortMatchPara2    
                    Integer32
              }
                                        
        hwDslamntvIpCascadePortIndex        OBJECT-TYPE
            SYNTAX       Integer32 (1..4096)
            MAX-ACCESS read-only
            STATUS       current
            DESCRIPTION
                "Indicates the index of a multicast subtending port.
                "
            ::= { hwDslamNtvIpCascadeEntry 1}   
        
        hwDslamNtvIpCascadePortRowStatus        OBJECT-TYPE
            SYNTAX       RowStatus
            MAX-ACCESS   read-create
            STATUS       current
            DESCRIPTION
                "Row status, used to query, create, modify, and delete a multicast subtending port. 
                 It supports the active(1), createAndGo(4), and destroy(6) operations.
                 During query, the value of this leaf is always active(1).
                 During deletion, specify the value of this leaf to destroy(6).
                 During creation, specify the value of this leaf to createAndGo(4).
                 To modify the parameters of a multicast subtending port, this leaf need not be issued together.
                 Options:
                 1. active(1)      -indicates the query operation
                 2. createAndGo(4) -indicates the creating operation
                 3. destroy(6)     -indicates the deleting operation
                "
            ::= { hwDslamNtvIpCascadeEntry 2}   
        
        hwDslamntvIpCascadePortFrameSlotPort   OBJECT-TYPE
            SYNTAX       Integer32
            MAX-ACCESS   read-create
            STATUS       current
            DESCRIPTION
                "Indicates the shelf/slot/port ID of the bandwidth management upstream port. 
                 It is not a port index. The most significant 8 bits indicate the shelf ID, 
                 the next 8 bits indicate the slot ID, and the last 16 bits indicate the port ID.
                "
            ::= { hwDslamNtvIpCascadeEntry 3}   
        
        hwDslamntvIpCascadeProgramWatchingCount   OBJECT-TYPE
            SYNTAX       Integer32
            MAX-ACCESS   read-only
            STATUS       current
            DESCRIPTION
                "Indicates the number of programs being watched by an IP subtending port.
                "
            ::= { hwDslamNtvIpCascadeEntry 4 }
        
        hwDslamntvIpCascadePortStaticJoin   OBJECT-TYPE
            SYNTAX TruthValue
            MAX-ACCESS read-create
            STATUS current
            DESCRIPTION
                "Indicates the static pre-join attribute of an IP subtending port.
                 Options:
                 1. true(1)  -indicates the static pre-join attribute of an IP subtending port is on
                 2. false(2) -indicates the static pre-join attribute of an IP subtending port is off
                 Default: false(2).
                "
               ::= { hwDslamNtvIpCascadeEntry 5 }
            
        hwDslamntvIpCascadePortQuickLeave   OBJECT-TYPE
            SYNTAX TruthValue
            MAX-ACCESS read-create
            STATUS current
            DESCRIPTION
                "Indicates the quick leave attribute of an IP subtending port.
                 Options:
                 1. true(1)  -indicates the IP subtending port can leave quickly
                 2. false(2) -indicates the IP subtending port cannot leave quickly
                 Default: false(2).
                "
            ::= { hwDslamNtvIpCascadeEntry 6 }
                 
        hwDslamntvIpCascadePortMode   OBJECT-TYPE
            SYNTAX INTEGER
                {
                snooping(0),
                discard(1),
                forwarding(2)
                }
            MAX-ACCESS read-create
            STATUS current
            DESCRIPTION
                "Snooping mode of the IP cascade port.
                 Options:
                 1. snooping(0)   -indicates the snooping mode of the IP cascade port is snooping
                 2. discard(1)    -indicates the discard mode of the IP cascade port is discard
                 3. forwarding(2) -indicates the discard mode of the IP cascade port is forwarding
                "
            ::= { hwDslamNtvIpCascadeEntry 7 }
        
        hwDslamntvIpCascadePortProcAfterMismatch   OBJECT-TYPE
            SYNTAX INTEGER
                {
                transparent(0),
                discard(1)
                }
            MAX-ACCESS read-create
            STATUS current
            DESCRIPTION
                "Indicates the processing mode when matching of an IP subtending port fails.
                 Options:
                 1. transparent(0) -indicates the process mode is transparent
                 2. discard(1)     -indicates the process mode is discard
                 Default: transparent(0).
                "
            ::= { hwDslamNtvIpCascadeEntry 8 }
                 
        hwDslamNtvIpCascadePortMatchPara OBJECT-TYPE
            SYNTAX Integer32
            MAX-ACCESS read-write
            STATUS current
            DESCRIPTION
                "Indicates the first extended key parameter of a subtending port, 
                 supported by only the GPON and EPON ports. It indicates ontid for 
                 an EPON port or a GPON port in the profile mode; it indicates 
                 gemportid for a GPON port in the non-profile mode. The range is 
                 determined by the line specifications. If the cascade port is a 
                 GE cascade port, the returned value for hwDslamNtvIpCascadePortMatchPara is -1.
                "
            ::= { hwDslamNtvIpCascadeEntry 9 }   
            
        hwDslamntvIpCascadePortControlWord OBJECT-TYPE
            SYNTAX TruthValue
            MAX-ACCESS read-create
            STATUS current
            DESCRIPTION
                "Indicates whether to concern about the VLAN contained in the packet sent from the IP subtending port. 
                 Options:
                 1. true(1)  -indicates to concern about the VLAN contained in the packet sent from the IP subtending port
                 2. false(2) -indicates not to concern about the VLAN contained in the packet sent from the IP subtending port
                 Default: true(1).                
                "
            ::= { hwDslamNtvIpCascadeEntry 10 }
                 
        hwDslamNtvIpCascadePortMatchPara2 OBJECT-TYPE
            SYNTAX Integer32
            MAX-ACCESS read-write
            STATUS current
            DESCRIPTION
                "Indicates the second extended key parameter of a GPON subtending port. It is supported by only a 
                 GPON product in the profile. It indicates gemindex of a GPON port. The range is determined by the 
                 line specifications. If the cascade port is a GE cascade port, the returned value for 
                 hwDslamNtvIpCascadePortMatchPara2 is -1.
                "
            ::= { hwDslamNtvIpCascadeEntry 11 }   
           
        hwDslamNtvUserRunStateTable OBJECT-TYPE
            SYNTAX SEQUENCE OF HwDslamNtvUserRunStateEntry
            MAX-ACCESS not-accessible
            STATUS current
            DESCRIPTION
                "Indicates the online status of a multicast user.
                 The indexes of this table are hwDslamNtvUserIndex and hwDslamNtvUserRunStateProgramIndex.
                "
            ::= { hwDslamNtv 25 }
        
        hwDslamNtvUserRunStateEntry OBJECT-TYPE
            SYNTAX HwDslamNtvUserRunStateEntry
            MAX-ACCESS not-accessible
            STATUS current
            DESCRIPTION
                "Indicates the online status of a multicast user.
                 The indexes of this entry are hwDslamNtvUserIndex and hwDslamNtvUserRunStateProgramIndex.
                "
            INDEX 
                { 
                hwDslamNtvUserIndex,
                hwDslamNtvUserRunStateProgramIndex
                }
            ::= { hwDslamNtvUserRunStateTable 1 }
        
        HwDslamNtvUserRunStateEntry ::=
            SEQUENCE 
                { 
                hwDslamNtvUserRunStateProgramIndex        Integer32,
                hwDslamNtvUserRunStateProgramStatus        INTEGER
                }
        
        hwDslamNtvUserRunStateProgramIndex OBJECT-TYPE
            SYNTAX Integer32 (1..4096)
            MAX-ACCESS read-only
            STATUS current
            DESCRIPTION
                "Indicates the program index, corresponding to hwDslamNtvProgramIndex.
                "
            ::= { hwDslamNtvUserRunStateEntry 1 }
                    
        hwDslamNtvUserRunStateProgramStatus OBJECT-TYPE
            SYNTAX INTEGER { watch(1),preview(2),invalid(3) }
            MAX-ACCESS read-create
            STATUS current
            DESCRIPTION
                "Indicates the program status. 
                 Options: 
                 1. watch(1)   -indicates the program status is watch
                 2. preview(2) -indicates the program status is preview
                 3. invalid(3) -indicates the program status is invalid
                "
            ::= { hwDslamNtvUserRunStateEntry 2 }  
        
        hwDslamNtvUserProfileTable    OBJECT-TYPE
            SYNTAX          SEQUENCE OF HwDslamNtvUserProfileEntry
            MAX-ACCESS      not-accessible
            STATUS          current
            DESCRIPTION
                "Indicates the binding relationship between a user and a profile in the profile mode.
                 The indexes of this table are hwDslamNtvUserIndex and hwDslamNtvUserProfileIndex.
                "
            ::= { hwDslamNtv 26 }
        
        hwDslamNtvUserProfileEntry    OBJECT-TYPE
            SYNTAX          HwDslamNtvUserProfileEntry
            MAX-ACCESS      not-accessible
            STATUS          current
            DESCRIPTION
                "Indicates the binding relationship between a user and a profile in the profile mode.
                 The indexes of this entry are hwDslamNtvUserIndex and hwDslamNtvUserProfileIndex.
                "
            INDEX 
                { 
                hwDslamNtvUserIndex,
                hwDslamNtvUserProfileIndex
                }
            ::= { hwDslamNtvUserProfileTable  1 }
        
        HwDslamNtvUserProfileEntry    ::= 
            SEQUENCE  
                {
                hwDslamNtvUserProfileIndex         
                    Integer32,
                hwDslamNtvUserProfileTblRowStatus  
                    RowStatus
                }
        
        hwDslamNtvUserProfileIndex        OBJECT-TYPE
            SYNTAX       Integer32(1..2000)
            MAX-ACCESS   read-only
            STATUS       current
            DESCRIPTION
                "Indicates the index of an authority profile. 
                 Range: 1-2000
                "
            ::= { hwDslamNtvUserProfileEntry 1}
        
        hwDslamNtvUserProfileTblRowStatus      OBJECT-TYPE
            SYNTAX       RowStatus
            MAX-ACCESS   read-create
            STATUS       current
            DESCRIPTION
                "Row status, used to query, create, modify, and delete the binding between 
                 a multicast user and a profile. It supports the active(1), createAndGo(4), 
                 and destroy(6) operations.
                 During query, the value of this leaf is always active(1).
                 During deletion, specify the value of this leaf to destroy(6).
                 During creation, specify the value of this leaf to createAndGo(4).
                 Options:
                  1. active(1)      -indicates the query operation
                  2. createAndGo(4) -indicates the creating operation
                  3. destroy(6)     -indicates the deleting operation
                "
            ::= { hwDslamNtvUserProfileEntry 2} 
        
        hwDslamNtvAttrProfileTable    OBJECT-TYPE
            SYNTAX          SEQUENCE OF HwDslamNtvAttrProfileEntry
            MAX-ACCESS      not-accessible
            STATUS          current
            DESCRIPTION
                "User Attribute profile management table.
                 The index of this table is hwDslamNtvAttrProfileIndex.
                "
            ::= { hwDslamNtv 27 }
        
        hwDslamNtvAttrProfileEntry    OBJECT-TYPE
            SYNTAX         HwDslamNtvAttrProfileEntry
            MAX-ACCESS     not-accessible
            STATUS         current
            DESCRIPTION
                "User Attribute profile management table.
                 The index of this entry is hwDslamNtvAttrProfileIndex.
                "
            INDEX   
                { 
                hwDslamNtvAttrProfileIndex
                }
            ::= { hwDslamNtvAttrProfileTable  1 }
        
        HwDslamNtvAttrProfileEntry    ::= 
            SEQUENCE
                {
                hwDslamNtvAttrProfileIndex       
                    Integer32,
                hwDslamNtvAttrProfileName        
                    OCTET STRING,
                hwDslamNtvAttrProfileQuickLeave  
                    TruthValue,
                hwDslamNtvAttrProfileAuthorization
                    Integer32,
                hwDslamNtvAttrProfileMaxBandwidth
                    Integer32,
                hwDslamNtvAttrProfileMaxGroups   
                    Integer32,
                hwDslamNtvAttrProfileEnableLog   
                    Integer32,
                hwDslamNtvAttrProfileAuthFailCut  
                    Integer32,
                hwDslamNtvAttrProfilePacketMode  
                    Integer32
            }
        
        hwDslamNtvAttrProfileIndex        OBJECT-TYPE
            SYNTAX       Integer32
            MAX-ACCESS   read-only
            STATUS       current
            DESCRIPTION
                "The user attribute profile index.
                "
            ::= { hwDslamNtvAttrProfileEntry 1}
        
        hwDslamNtvAttrProfileName        OBJECT-TYPE
            SYNTAX       OCTET STRING
            MAX-ACCESS   read-create
            STATUS       current
            DESCRIPTION
                "The user attribute profile name,It is the keywords of attribute profile.
                "
            ::= { hwDslamNtvAttrProfileEntry 2}
        
        hwDslamNtvAttrProfileQuickLeave    OBJECT-TYPE
            SYNTAX       TruthValue
            MAX-ACCESS   read-create
            STATUS       current
            DESCRIPTION
                "When the user sends igmp leave packet,if the value is true(1),then the multicast table is delete,
                 and the system does not send the special query packet to user.if the value is false(2),then the system need 
                 send the special query packet to user.
                 Options:
                 1. true(1)  -indicates the system need not send the special query packet to user
                 2. false(2) -indicates the system needs to send the special query packet to user
                "
            ::= { hwDslamNtvAttrProfileEntry 3}
        
        hwDslamNtvAttrProfileAuthorization    OBJECT-TYPE
            SYNTAX       Integer32
            MAX-ACCESS   read-create
            STATUS       current
            DESCRIPTION
                "The user's authorization ,{ auth(0),no-auth(1) }
                "
            ::= { hwDslamNtvAttrProfileEntry 4}
        
        hwDslamNtvAttrProfileMaxBandwidth    OBJECT-TYPE
            SYNTAX       Integer32
            MAX-ACCESS   read-create
            STATUS       current
            DESCRIPTION
                "The user permita the max bandwidth to traffic multicast.
                "
            ::= { hwDslamNtvAttrProfileEntry 5}
        
        hwDslamNtvAttrProfileMaxGroups    OBJECT-TYPE
            SYNTAX       Integer32
            MAX-ACCESS   read-create
            STATUS       current
            DESCRIPTION
                "The max channel number that a user can watch at the same time.
                "
            ::= { hwDslamNtvAttrProfileEntry 6}
        
        hwDslamNtvAttrProfileEnableLog    OBJECT-TYPE
            SYNTAX       Integer32
            MAX-ACCESS   read-create
            STATUS       current
            DESCRIPTION
                "Log switch. When the log switch is on(1), 
                 the system will record the events of starting or stopping watching programs of the user.
                 When the log switch is off(2), the system will stop recording.
                "
            ::= { hwDslamNtvAttrProfileEntry 7}
        
        hwDslamNtvAttrProfileAuthFailCut    OBJECT-TYPE
            SYNTAX       Integer32
            MAX-ACCESS   read-create
            STATUS       current
            DESCRIPTION
                "When the user authorization fails,if the value is discard(0), the user's igmp packet is discard,
                 and if the value is forward(1),the user's igmp packet is sent to upper router }
                "
            ::= { hwDslamNtvAttrProfileEntry 8}
        
        hwDslamNtvAttrProfilePacketMode    OBJECT-TYPE
            SYNTAX       Integer32
            MAX-ACCESS   read-only
            STATUS       current
            DESCRIPTION
                "The packet process mode when receive the user's igmp packet,if snooping(0),then config the user multicast
                 table,and send this igmp packet to upper router. if discard(1), then discard the user's igmp packet.
                 if forwarding(2),the send user's igmp packet to upper router,do not configure user multicast table.
                "
            ::= { hwDslamNtvAttrProfileEntry 9}
        
         hwDslamNtvSourceCheck        OBJECT-TYPE
             SYNTAX       TruthValue
             MAX-ACCESS   read-write
             STATUS       current
             DESCRIPTION
                 "Source-IP-check administer state.
                  The true(enable)/ false(disable) state for Source-IP-check.
                  Used to enable/disable Source-IP-check to control whether source-IP 
                  must be match when forwarding multicast data.
                  Options:
                  1. true(1)  -indicates the Soure-IP-check is enabled
                  2. false(2) -indicates the Soure-IP-check is disabled
                 "
             ::= { hwDslamNtv 31} 
        
        hwDslamNtvDefaultSource        OBJECT-TYPE
            SYNTAX       IpAddress
            MAX-ACCESS   read-write
            STATUS       current
            DESCRIPTION
                "Default multicast-source for program.
                 The program which is not bind to multicast-source when added to 
                 program room will be bind to this default source.
                "
            ::= { hwDslamNtv 32}
         
        hwDslamNtvReportInterval   OBJECT-TYPE
            SYNTAX       Integer32(1..5000)
            UNITS        "seconds"
            MAX-ACCESS   read-write
            STATUS       current
            DESCRIPTION
                "Unsolicited report interval.
                 The frequency at which Unsolicited IGMP Host-Report packets 
                 are transmitted to up-device.
                 Default: 10
                 Unit: second
                "     
            ::= { hwDslamNtv 33 }
        
        hwDslamNtvUpportWorkMode   OBJECT-TYPE
            SYNTAX       INTEGER 
                { 
                program(1),
                mstp(2),
                broadcast(3),
                protect(4),
                default(5),
                queryDetect(6),
                rrpp(7) 
                }
            MAX-ACCESS   read-write
            STATUS       current
            DESCRIPTION
                "Sets/Queries the working mode of an upstream port. When the upstream port works in 
                 the pim-ssm mode, this leaf does not support the modify operation. 
                 Options: 
                 1. program(1)     -indicates the working mode of an upstream port is program
                 2. mstp(2)        -indicates the working mode of an upstream port is mstp
                 3. broadcast(3)   -indicates the working mode of an upstream port is broadcast
                 4. protect(4)     -indicates the working mode of an upstream port is protect
                 5. default(5)     -indicates the working mode of an upstream port is default
                 6. queryDetect(6) -indicates the working mode of an upstream port is queryDetect
                 7. rrpp(7)        -indicates the working mode of an upstream port is rrpp
                 Default: default(5)
                "
            ::= { hwDslamNtv 34 }
        
        hwDslamNtvV1RouterTimerout   OBJECT-TYPE
            SYNTAX       Integer32(1..5000)
            UNITS        "seconds"
            MAX-ACCESS   read-write
            STATUS       current
            DESCRIPTION
                "The Version 1 Router Present Timeout is how long a host must wait
                 after hearing a Version 1 Query before it may send any IGMPv2
                 messages.
                 Default: 400
                 Unit: second
                "      
            ::= { hwDslamNtv 35 }
        
        hwDslamNtvLastMemberQueryCount   OBJECT-TYPE
            SYNTAX       Integer32(1..10)
            MAX-ACCESS   read-write
            STATUS       current
            DESCRIPTION
                "Sets/Queries the number of IGMPv2 group-specific queries. 
                 Range: 1-10 
                 The default value is equal to hwDslamNtvRobustness.
                "       
            ::= { hwDslamNtv 36 }
        
        hwDslamNtvLastMemberQueryInterval   OBJECT-TYPE
            SYNTAX       Integer32(1..50000)
            UNITS        "0.1s"
            MAX-ACCESS   read-write
            STATUS       current
            DESCRIPTION
                "Sets/Queries the interval of IGMPv2 group-specific queries.
                 Range: 1-50000.
                 Unit: 0.1s, that is, 0.1-5000s. By default, it is 10 (that is, 1 second). 
                 The group-specific query interval must be longer than the group-specific 
                 query response. When a user goes offline without sending the report packet, 
                 if the system does not receive the report packet from the user within the 
                 maximum response time after the general query packet is sent, the system 
                 sends the general query packets for N-1 times based on the interval for 
                 the general query (N indicates the robustness variable). If the system 
                 does not receive the report packet within the maximum response time after 
                 the last general query is sent, it indicates that the user is offline. 
                 Aging time of a subscriber = General query interval x Robustness 
                 variable + Response time of the general query.
                "     
            ::= { hwDslamNtv 37 }
        
       hwDslamNtvLastMemberQueryResponse OBJECT-TYPE
           SYNTAX Integer32 (1..255)
           UNITS "0.1s"
           MAX-ACCESS read-write
           STATUS current
           DESCRIPTION
               "Sets/Queries the maximum response time for an IGMPV2 group-specific query.
                Range: 1-255.
                Unit: 0.1s, that is, 0.1-25.5s. By default, it is 8 (namely 0.8s). 
                The group-specific query response must be shorter than the group-specific 
                query interval. If the system does not receive the report packet within 
                the maximum response time after the group-specific query packet is sent, 
                the system sends the group-specific query packets for specified times 
                (times of the group-specific query) based on the interval for the group-specific 
                query. If the system does not receive the report packet within the specified 
                time (maximum response time to the group-specific query) after the last 
                group-specific query packet is sent, it indicates that the user is offline. 
                User aging time = Interval for group-specific query x Times of group-specific 
                query + Maximum response time to group-specific query.
               "            
           ::= { hwDslamNtv 38 }    
        
       hwDslamNtvAuthorizeSwitch OBJECT-TYPE
           SYNTAX      TruthValue
           MAX-ACCESS  read-write
           STATUS      current
           DESCRIPTION
               "Indicates the authentication switch. 
                Options:
                1. true(1)  -indicates the autentication switch is on
                2. false(2) -indicates the autentication switch is off
                Default: true(1)
               "
           ::= { hwDslamNtv 39 }
        
        hwDslamNtvPreviewSwitch  OBJECT-TYPE
            SYNTAX      TruthValue
            MAX-ACCESS  read-write
            STATUS      current
            DESCRIPTION
                "Indicates the system preview switch. 
                 Options:
                 1. true(1)  -indicates the system preview switch is on
                 2. false(2) -indicates the system preview switch is off
                 Default: true(1)
                "
            ::= { hwDslamNtv 40 }
        
        hwDslamNtvRecognitionTime  OBJECT-TYPE
            SYNTAX      Integer32 (1..120)
            UNITS        "second"
            MAX-ACCESS  read-write
            STATUS      current
            DESCRIPTION
                "Indicates the system recognition time. 
                 Range: 1-120s
                 Default: 30s
                 Unit: second
                "
            ::= { hwDslamNtv 41 }
        
        hwDslamNtvClearPreviewCount  OBJECT-TYPE
            SYNTAX       RowStatus
            MAX-ACCESS   read-write
            STATUS      current
            DESCRIPTION
                "Clears the preview count of all users. 
                 Options: 
                 1. active(1) -clear the preview count of all users
                "
            ::= { hwDslamNtv 42 }
        
        hwDslamNtvTimeClearPreviewCount  OBJECT-TYPE
            SYNTAX       DateAndTime
            MAX-ACCESS   read-write
            STATUS      current
            DESCRIPTION
                "Clears the preview count of all users regularly. By default, 
                 the system clears the preview count of all users at 4:00 a.m.
                "
            ::= { hwDslamNtv 43 }
        
        hwDslamNtvRightAssignMode   OBJECT-TYPE
            SYNTAX  INTEGER
                {  
                user-based(1), 
                profile-based(2) 
                }
            MAX-ACCESS   read-write
            STATUS       current
            DESCRIPTION
                "Right assigned mode.
                 Options:
                 1. user-based(1)    -indicates the right assigned mode is user-based
                 2. profile-based(2) -indicates the right assigned mode is profile-based
                "
            ::= { hwDslamNtv 44 }
        
        hwDslamNtvLogReportInterval   OBJECT-TYPE
            SYNTAX   Integer32 (0..12)
            UNITS        "hour"
            MAX-ACCESS   read-write
            STATUS       current
            DESCRIPTION
                "Indicates the interval for active report of user demand log. 
                 Range: 0-12                  
                 Default: 2
                 Unit: hour 
                 0 indicates disabling the active report of user demand log.
                "
            ::= { hwDslamNtv 45 }
        
        hwDslamNtvLogOperation   OBJECT-TYPE
            SYNTAX   INTEGER
                {  
                logReportStart(1), 
                logReportStop(2),
                invalid(-1)  
                }
            MAX-ACCESS   read-write
            STATUS       current
            DESCRIPTION
                "Sets the multicast log report function.
                 Options:
                 1. logReportStart(1) -immediately report all current logs.
                 2. logReportStop(2)  -stop reporting logs.
                 3. invalid(-1)       -indicates invalid.
                "
            ::= { hwDslamNtv 46 }
                 
        hwDslamNtvBandwidthManagementSwitch OBJECT-TYPE
            SYNTAX      TruthValue
            MAX-ACCESS  read-write
            STATUS      current
            DESCRIPTION
                "Indicates the bandwidth management and CAC switch. 
                 Options:
                 1. true(1)  -indicates the bandwidth management and CAC switch is on
                 2. false(2) -indicates the bandwidth management and CAC switch is off
                 Default: true(1)
                "
            ::= { hwDslamNtv 47 }    
        
        hwDslamNtvLogSwitch OBJECT-TYPE
            SYNTAX      TruthValue
            MAX-ACCESS  read-write
            STATUS      current
            DESCRIPTION
                "Indicates the global log switch. 
                 Options:
                 1. true(1)  -indicates the global log switch is on
                 2. false(2) -indicates the global log switch is off
                 Default: true(1)
                "
            ::= { hwDslamNtv 48 }    
        hwDslamNtvFlow8021p OBJECT-TYPE
            SYNTAX Integer32 (0..7)
            MAX-ACCESS read-write
            STATUS current
            DESCRIPTION
                "priority of    802.1p
                 Default: 6
                "
            ::= { hwDslamNtv 52 }
        
        hwDslamNtvFlowVlanid  OBJECT-TYPE
            SYNTAX Integer32 (1..4093)
            MAX-ACCESS read-write
            STATUS current
            DESCRIPTION
                "Vlan id.
                 Default:1                 
                "
            ::= { hwDslamNtv 53 }
        
        hwDslamNtvFlowEncap  OBJECT-TYPE
            SYNTAX INTEGER
                {
                ipoe(1),
                pppoe(2)
                }
            MAX-ACCESS read-write
            STATUS current
            DESCRIPTION
                "encapsulation type
                 Options:
                 1. ipoe(1)  -indicates the encapsulation type is ipoe
                 2. pppoe(2) -indicates the encapsulation type is pppoe
                 Default: ipoe
                "
            ::= { hwDslamNtv 54 }
        
        hwDslamNtvQuerySwitch   OBJECT-TYPE
            SYNTAX       TruthValue
            MAX-ACCESS   read-write
            STATUS       current
            DESCRIPTION
                "IGMP user querier switch.When enable, device may send igmp query to 
                 user sequentially, else, just forward query from upper router to user.
                "
            ::= { hwDslamNtv 55} 
        
        hwDslamNtvReportProxySwitch OBJECT-TYPE
            SYNTAX       TruthValue
            MAX-ACCESS   read-write
            STATUS       current
            DESCRIPTION
                "Indicates the proxy switch for the report packets in the IGMP snooping mode. 
                 Options:
                 1. true(1)  -indicates the proxy switch for the report packets in the 
                              IGMP snooping mode is on
                 2. false(2) -indicates the proxy switch for the report packets in the 
                              IGMP snooping mode is off
                 Default: false(2)
                "
            ::= { hwDslamNtv 56}
        
        hwDslamNtvLeaveProxySwitch    OBJECT-TYPE
             SYNTAX      TruthValue
             MAX-ACCESS    read-write
             STATUS        current
             DESCRIPTION
                 "Indicates the proxy switch for the leave packets in the IGMP snooping mode. 
                  Options:
                  1. true(1)  -indicates the proxy switch for the leave packets in the 
                               IGMP snooping mode is on
                  2. false(2) -indicates the proxy switch for the leave packets in the 
                               IGMP snooping mode is off
                  Default: false(2)
                 "
             ::= { hwDslamNtv 57}
        
        hwDslamNtvSnoopingUserAgingTime    OBJECT-TYPE
            SYNTAX      Integer32(10..1200)
            UNITS       "1s"
            MAX-ACCESS  read-write
            STATUS      current
            DESCRIPTION
                "The aging time configuration for IGMP over PPPoE user under the IGMP 
                 Snooping mode.
                 Unit: 1s
                "
            ::= { hwDslamNtv 58}
         
        hwDslamUnkownMulticastTunnelSwitch OBJECT-TYPE
            SYNTAX       TruthValue
            MAX-ACCESS   read-write
            STATUS       current
            DESCRIPTION
                "Unknown multicast tunneling switch.
                Options:
                1. true(1)  -indicates the unknown multicast tunneling switch is on
                2. false(2) -indicates the unknown multicast tunneling switch is off
                Default: false(2)
                " 
            ::= { hwDslamNtv 59}
         
         hwDslamNtvUserAllocBwthPercent  OBJECT-TYPE
             SYNTAX Integer32 (1..100)
             MAX-ACCESS read-write
             STATUS current
             DESCRIPTION
                 "The bandwidth percentage assigned for user. Default:100%
                 "
             ::= { hwDslamNtv 60 } 
                  
         hwDslamNtvMFSTable OBJECT-TYPE
             SYNTAX SEQUENCE OF HwDslamNtvMFSEntry
             MAX-ACCESS not-accessible
             STATUS current
             DESCRIPTION
                 "Indicates the multicast traffic statistic table.
                  The index of this table is hwDslamNtvMFSProgramIndex.
                 "
             ::= { hwDslamNtv 61 }
            
        hwDslamNtvMFSEntry OBJECT-TYPE
            SYNTAX HwDslamNtvMFSEntry
            MAX-ACCESS not-accessible
            STATUS current
            DESCRIPTION
                "Indicates the multicast traffic statistic table.
                 The index of this entry is hwDslamNtvMFSProgramIndex.
                "
            INDEX { hwDslamNtvMFSProgramIndex }
            ::= { hwDslamNtvMFSTable 1 }
            
        HwDslamNtvMFSEntry ::= 
            SEQUENCE 
                {
                hwDslamNtvMFSProgramIndex 
                    Integer32,
                hwDslamNtvMFSResult   
                    Integer32
                }
                
        hwDslamNtvMFSProgramIndex OBJECT-TYPE
            SYNTAX Integer32 (1..4096)
            MAX-ACCESS read-only
            STATUS current
            DESCRIPTION
                "Indicates the program index. Its value and algorithm are the same as those of hwDslamNtvProgramIndex.  
                "
            ::= { hwDslamNtvMFSEntry 1 }
            
        hwDslamNtvMFSResult OBJECT-TYPE
            SYNTAX Integer32
            MAX-ACCESS read-only
            STATUS current
            DESCRIPTION
                "Indicates the real-time multicast traffic statistics result. 
                 Unit: kbit/s.
                "
            ::= { hwDslamNtvMFSEntry 2 }      
        
        hwDslamNtvUserActionReport OBJECT-TYPE
            SYNTAX       TruthValue
            MAX-ACCESS   read-write
            STATUS       current
            DESCRIPTION
                "Indicates the user action report switch.
                 Options:
                 1. true(1)   -indicates the user action report switch is on
                 2. false(2)  -indicates the user action report switch is off
                 Default: false(2)
                "       
           ::= { hwDslamNtv 62}
            
        hwDslamNtvCDRReportInterval   OBJECT-TYPE
            SYNTAX   Integer32 (60..43200)
            UNITS        "second"
            MAX-ACCESS   read-write
            STATUS       current
            DESCRIPTION
                "Indicates the interval of reporting the CDRs automatically. 
                 Range: 60-43200 
                 Unit: second 
                 Default: 600
                "              
            ::= { hwDslamNtv 63}
            
        hwDslamNtvCDRReportNumber   OBJECT-TYPE
            SYNTAX   Integer32 (100..200)
            MAX-ACCESS   read-write
            STATUS       current
            DESCRIPTION
                "Indicates the number of active CDR reports. 
                 Range: 100-200 
                 Default: 200
                "     
            ::= { hwDslamNtv 64}
            
        hwDslamNtvRightPrioMode   OBJECT-TYPE
            SYNTAX   INTEGER
                { 
                rightWPFI(1), 
                rightWFPI(2),
                rightPWFI(3),
                rightPFWI(4),
                rightFWPI(5),
                rightFPWI(6) 
                }
            MAX-ACCESS   read-write
            STATUS       current
            DESCRIPTION
                "Indicates the multicast user authority priority mode. 
                 Options:
                 1. rightWPFI(1) -watch-preview-forbid-idle
                 2. rightWFPI(2) -watch-preview-forbid-idle
                 3. rightPWFI(3) -preview-watch-forbid-idle
                 4. rightPFWI(4) -preview-forbid-watch-idle
                 5. rightFWPI(5) -forbid-watch-preview-idle
                 6. rightFPWI(6) -forbid-preview-watch-idle
                 Default: rightFPWI(6)
                 W = watch, P = preview, F = forbid, and I = idle.
                "     
            ::= { hwDslamNtv 65}
                 
        hwDslamNtvIgmpStatisticTable    OBJECT-TYPE
            SYNTAX          SEQUENCE OF HwDslamNtvIgmpStatisticEntry
            MAX-ACCESS      not-accessible
            STATUS          current
            DESCRIPTION
                "Indicates the various operations on IGMP packet statistics.
                 The index of this table is hwDslamNtvIgmpStatisticTypeIndex.
                "
            ::= { hwDslamNtv 66 }
        
        hwDslamNtvIgmpStatisticEntry    OBJECT-TYPE
            SYNTAX         HwDslamNtvIgmpStatisticEntry
            MAX-ACCESS     not-accessible
            STATUS         current
            DESCRIPTION
                "Indicates the various operations on IGMP packet statistics.
                 The index of this entry is hwDslamNtvIgmpStatisticTypeIndex.
                "
            INDEX   
                { 
                hwDslamNtvIgmpStatisticTypeIndex
                }
            ::= { hwDslamNtvIgmpStatisticTable  1 }
        
        HwDslamNtvIgmpStatisticEntry    ::= 
            SEQUENCE  
                {
                hwDslamNtvIgmpStatisticOperMode    
                    INTEGER, 
                hwDslamNtvIgmpStatisticTypeIndex   
                    Integer32,
                hwDslamNtvIgmpStatisticPort       
                    Integer32,
                hwDslamNtvIgmpStatisticMatchPara   
                    Integer32,
                hwDslamNtvIgmpStatisticGenQueryRcv   
                    Integer32,  
                hwDslamNtvIgmpStatisticSpecQueryRcv 
                    Integer32,
                hwDslamNtvIgmpStatisticReportV1Rcv 
                    Integer32,        
                hwDslamNtvIgmpStatisticReportV2Rcv 
                    Integer32,
                hwDslamNtvIgmpStatisticReportV3Rcv 
                    Integer32,
                hwDslamNtvIgmpStatisticErrQueryRcv 
                    Integer32,
                hwDslamNtvIgmpStatisticErrReportRcv 
                    Integer32,
                hwDslamNtvIgmpStatisticLeaveRcv    
                    Integer32,
                hwDslamNtvIgmpStatisticErrLeaveRcv 
                    Integer32,
                hwDslamNtvIgmpStatisticGenQuerySnd 
                    Integer32,
                hwDslamNtvIgmpStatisticSpecQuerySnd 
                    Integer32,
                hwDslamNtvIgmpStatisticReportV1Snd 
                    Integer32,
                hwDslamNtvIgmpStatisticReportV2Snd  
                    Integer32,
                hwDslamNtvIgmpStatisticLeaveSnd    
                    Integer32,
                hwDslamNtvIgmpStatisticSnoopingMsgSnd 
                    Integer32,
                hwDslamNtvIgmpStatisticErrV1ReportRcv
                    Integer32,                
                hwDslamNtvIgmpStatisticErrV2ReportRcv
                    Integer32,                
                hwDslamNtvIgmpStatisticErrV3ReportRcv 
                    Integer32,   
                hwDslamNtvIgmpStatisticReportV3Snd 
                    Integer32,                         
                hwDslamNtvIgmpStatisticInvalidRcv 
                    Integer32,    
                hwDslamNtvIgmpStatisticVlan       
                    Integer32,  
                hwDslamNtvIgmpActiveProgramNum     
                    Integer32,   
                hwDslamNtvIgmpActiveUserNum        
                    Integer32                   
                }
                         
        hwDslamNtvIgmpStatisticOperMode        OBJECT-TYPE
            SYNTAX   INTEGER
                 { 
                 clearStatistic(1),
                 invalid(0) 
                 }
            MAX-ACCESS   read-write
            STATUS       current
            DESCRIPTION
                "Indicates the operation mode of performance statistics. 
                 Options: 
                 1. clearStatistic(1) -indicates clearing statistics
                 2. invalid(0)        -indicates invalid operation mode 
                "
            ::= { hwDslamNtvIgmpStatisticEntry 1}
        
        hwDslamNtvIgmpStatisticTypeIndex       OBJECT-TYPE
            SYNTAX   Integer32 (1..3)
            MAX-ACCESS   read-only
            STATUS       current
            DESCRIPTION
                "Indicates the performance statistics type. Currently, only global IGMP statistic(1) is supported. 
                 Options:
                 1. global IGMP statistic(1)             -indicates the performance statistics type is global IGMP
                                                          statistic
                 2. specific port IGMP statistic(2)      -indicates the performance statistics type is specific port
                                                          IGMP statistic
                 3. specific Multicast VLAN statistic(3) -indicates the performance statistics type is specific 
                                                          Multicast VLAN statistic
                "
            ::= { hwDslamNtvIgmpStatisticEntry 2}
        
        hwDslamNtvIgmpStatisticPort           OBJECT-TYPE
            SYNTAX   Integer32 
            MAX-ACCESS   read-write
            STATUS       current
            DESCRIPTION
                "The ifIndex of IGMP statistic port.
                "
            ::= { hwDslamNtvIgmpStatisticEntry 3}
           
        hwDslamNtvIgmpStatisticMatchPara      OBJECT-TYPE
            SYNTAX   Integer32 
            MAX-ACCESS   read-write
            STATUS       current
            DESCRIPTION
                "The GemPortID of GPON port
                "
            ::= { hwDslamNtvIgmpStatisticEntry 4}
               
        hwDslamNtvIgmpStatisticGenQueryRcv    OBJECT-TYPE
            SYNTAX   Integer32 
            MAX-ACCESS   read-only
            STATUS       current
            DESCRIPTION
                "Indicates the number of received general query packets.
                "
            ::= { hwDslamNtvIgmpStatisticEntry 5}
        
        hwDslamNtvIgmpStatisticSpecQueryRcv   OBJECT-TYPE
            SYNTAX   Integer32 
            MAX-ACCESS   read-only
            STATUS       current
            DESCRIPTION
                "Indicates the number of received group-specific query packets.
                "
            ::= { hwDslamNtvIgmpStatisticEntry 6}
        
        hwDslamNtvIgmpStatisticReportV1Rcv    OBJECT-TYPE
            SYNTAX   Integer32 
            MAX-ACCESS   read-only
            STATUS       current
            DESCRIPTION
                "Indicates the number of received report packets of V1.
                "
            ::= { hwDslamNtvIgmpStatisticEntry 7}
        
        hwDslamNtvIgmpStatisticReportV2Rcv    OBJECT-TYPE
            SYNTAX   Integer32 
            MAX-ACCESS   read-only
            STATUS       current
            DESCRIPTION
                "Indicates the number of received report packets of V2.
                "
            ::= { hwDslamNtvIgmpStatisticEntry 8}
        
        hwDslamNtvIgmpStatisticReportV3Rcv    OBJECT-TYPE
            SYNTAX   Integer32 
            MAX-ACCESS   read-only
            STATUS       current
            DESCRIPTION
                "Indicates the number of received report packets of V3.
                "
            ::= { hwDslamNtvIgmpStatisticEntry 9}
        
        hwDslamNtvIgmpStatisticErrQueryRcv    OBJECT-TYPE
            SYNTAX   Integer32 
            MAX-ACCESS   read-only
            STATUS       current
            DESCRIPTION
                "Indicates the number of received errored query packets.
                "
            ::= { hwDslamNtvIgmpStatisticEntry 10}
        
        hwDslamNtvIgmpStatisticErrReportRcv   OBJECT-TYPE
            SYNTAX   Integer32 
            MAX-ACCESS   read-only
            STATUS       current
            DESCRIPTION
                "Indicates the number of received errored report packets.
                "
            ::= { hwDslamNtvIgmpStatisticEntry 11}
        
        hwDslamNtvIgmpStatisticLeaveRcv       OBJECT-TYPE
            SYNTAX   Integer32 
            MAX-ACCESS   read-only
            STATUS       current
            DESCRIPTION
                "Indicates the number of received leave packets.
                "
            ::= { hwDslamNtvIgmpStatisticEntry 12}
        
        hwDslamNtvIgmpStatisticErrLeaveRcv    OBJECT-TYPE
            SYNTAX   Integer32 
            MAX-ACCESS   read-only
            STATUS       current
            DESCRIPTION
                "Indicates the number of received errored leave packets.
                "
            ::= { hwDslamNtvIgmpStatisticEntry 13}
        
        hwDslamNtvIgmpStatisticGenQuerySnd    OBJECT-TYPE
            SYNTAX   Integer32 
            MAX-ACCESS   read-only
            STATUS       current
            DESCRIPTION
                "Indicates the number of transmitted general query packets.
                "
            ::= { hwDslamNtvIgmpStatisticEntry 14}
        
        hwDslamNtvIgmpStatisticSpecQuerySnd    OBJECT-TYPE
            SYNTAX   Integer32 
            MAX-ACCESS   read-only
            STATUS       current
            DESCRIPTION
                "Indicates the number of transmitted group-specific query packets.
                "
            ::= { hwDslamNtvIgmpStatisticEntry 15}
        
        hwDslamNtvIgmpStatisticReportV1Snd    OBJECT-TYPE
            SYNTAX   Integer32 
            MAX-ACCESS   read-only
            STATUS       current
            DESCRIPTION
                "Indicates the number of transmitted report packets of V1.
                "
            ::= { hwDslamNtvIgmpStatisticEntry 16}
        
        hwDslamNtvIgmpStatisticReportV2Snd    OBJECT-TYPE
            SYNTAX   Integer32 
            MAX-ACCESS   read-only
            STATUS       current
            DESCRIPTION
                "Indicates the number of transmitted report packets of V2.
                "
            ::= { hwDslamNtvIgmpStatisticEntry 17}
        
        hwDslamNtvIgmpStatisticLeaveSnd    OBJECT-TYPE
            SYNTAX   Integer32 
            MAX-ACCESS   read-only
            STATUS       current
            DESCRIPTION
                "Indicates the number of transmitted leave packets.
                "
            ::= { hwDslamNtvIgmpStatisticEntry 18}
        
        hwDslamNtvIgmpStatisticSnoopingMsgSnd   OBJECT-TYPE
            SYNTAX   Integer32 
            MAX-ACCESS   read-only
            STATUS       current
            DESCRIPTION
                "Indicates the number of transmitted snooping packets.
                "
            ::= { hwDslamNtvIgmpStatisticEntry 19}    
        
        hwDslamNtvIgmpStatisticErrV1ReportRcv   OBJECT-TYPE
            SYNTAX   Integer32 
            MAX-ACCESS   read-only
            STATUS       current
            DESCRIPTION
                "Indicates the number of received errored V1 packets.
                "
            ::= { hwDslamNtvIgmpStatisticEntry 20}    
        
        hwDslamNtvIgmpStatisticErrV2ReportRcv   OBJECT-TYPE
            SYNTAX   Integer32 
            MAX-ACCESS   read-only
            STATUS       current
            DESCRIPTION
                "Indicates the number of received errored V2 packets.
                "
            ::= { hwDslamNtvIgmpStatisticEntry 21}
        
        hwDslamNtvIgmpStatisticErrV3ReportRcv   OBJECT-TYPE
            SYNTAX   Integer32 
            MAX-ACCESS   read-only
            STATUS       current
            DESCRIPTION
                "Indicates the number of received errored V3 packets.
                "
            ::= { hwDslamNtvIgmpStatisticEntry 22}  
        
        hwDslamNtvIgmpStatisticReportV3Snd    OBJECT-TYPE
            SYNTAX   Integer32 
            MAX-ACCESS   read-only
            STATUS       current
            DESCRIPTION
                "Indicates the number of transmitted report packets of V3.
                "
            ::= { hwDslamNtvIgmpStatisticEntry 23}
        
        hwDslamNtvIgmpStatisticInvalidRcv    OBJECT-TYPE
            SYNTAX   Integer32 
            MAX-ACCESS   read-only
            STATUS       current
            DESCRIPTION
                "Indicates the number of received invalid IGMP packets.
                "
            ::= { hwDslamNtvIgmpStatisticEntry 24}
        
        hwDslamNtvIgmpStatisticVlan           OBJECT-TYPE
            SYNTAX   Integer32 
            MAX-ACCESS   read-write
            STATUS       current
            DESCRIPTION
                "The ID of IGMP statistic Mvlan.
                "
            ::= { hwDslamNtvIgmpStatisticEntry 25}
        
        hwDslamNtvIgmpActiveProgramNum    OBJECT-TYPE
            SYNTAX   Integer32 
            MAX-ACCESS   read-only
            STATUS       current
            DESCRIPTION
                "Indicates the number of programs in the active state in the multicast VLAN.
                "
            ::= { hwDslamNtvIgmpStatisticEntry 26}
        
        hwDslamNtvIgmpActiveUserNum    OBJECT-TYPE
            SYNTAX   Integer32 
            MAX-ACCESS   read-only
            STATUS       current
            DESCRIPTION
                "Indicates the number of users in the active state in the multicast VLAN.
                "
            ::= { hwDslamNtvIgmpStatisticEntry 27}
        
        hwDslamNtvIgmpEncap   OBJECT-TYPE
            SYNTAX INTEGER
                { 
                all(0), 
                ppp(1), 
                ip(2) 
                }
            MAX-ACCESS   read-write
            STATUS       current
            DESCRIPTION
                "Indicates the permitted IGMP packet encapsulation format. 
                 Options:
                 1. all(0)    -all encapsulation formats
                 2. ppp(1)    -IGMP over PPP encapsulation format
                 3. ip(2)     -IGMP over IP encapsulation format
                 Default: all(0)
                "
            ::= { hwDslamNtv 67 }
        
        hwDslamNtvIgmpEcho   OBJECT-TYPE
            SYNTAX   INTEGER{ true(1), false(2) }
            MAX-ACCESS   read-write
            STATUS       current
            DESCRIPTION
                "Indicates the IGMP echo switch. 
                 Options:
                 1. true(1)  -indicates the IGMP echo switch is on
                 2. false(2) -indicates the IGMP echo switch is off
                 Default: false(2)
                "
            ::= { hwDslamNtv 68 } 
        
        hwDslamNtvUpPortMFSTable OBJECT-TYPE
            SYNTAX SEQUENCE OF HwDslamNtvUpPortMFSEntry
            MAX-ACCESS not-accessible
            STATUS current
            DESCRIPTION
                "Measures the multicast traffic on a specified upstream port.
                 The index of this table is hwDslamNtvUpPortMFSIndex.
                "
            ::= { hwDslamNtv 69 }
        
        hwDslamNtvUpPortMFSEntry OBJECT-TYPE
            SYNTAX HwDslamNtvUpPortMFSEntry
            MAX-ACCESS not-accessible
            STATUS current
            DESCRIPTION
                "Measures the multicast traffic on a specified upstream port.
                 The index of this entry is hwDslamNtvUpPortMFSIndex.
                "
            INDEX { hwDslamNtvUpPortMFSIndex }
            ::= { hwDslamNtvUpPortMFSTable 1 }
        
        HwDslamNtvUpPortMFSEntry ::= 
            SEQUENCE 
                {
                hwDslamNtvUpPortMFSIndex Integer32,
                hwDslamNtvUpPortMFSResult       Integer32
                }
                  
        hwDslamNtvUpPortMFSIndex OBJECT-TYPE
            SYNTAX Integer32 (1..1024)
            MAX-ACCESS read-only
            STATUS current
            DESCRIPTION
                "Indicates the index of a multicast upstream port. Its value and usage are the same as those of hwDslamNtvVUpportTblIndex.
                "
            ::= { hwDslamNtvUpPortMFSEntry 1 }
        
        hwDslamNtvUpPortMFSResult OBJECT-TYPE
            SYNTAX Integer32
            MAX-ACCESS read-only
            STATUS current
            DESCRIPTION
                "Indicates the real-time multicast traffic statistics result. 
                 Unit: kbit/s.
                "
            ::= { hwDslamNtvUpPortMFSEntry 2 }   
        
        hwDslamNtvDefaultUpport   OBJECT-TYPE
            SYNTAX   Integer32
            MAX-ACCESS   read-write
            STATUS       current
            DESCRIPTION
                "Default upport.
                "     
            ::= { hwDslamNtv 70}
        
        hwDslamNtvCDRReport   OBJECT-TYPE
            SYNTAX INTEGER 
                { 
                fail(1), 
                all(2) 
                }
            MAX-ACCESS   read-write
            STATUS       current
            DESCRIPTION
                "Re-transmit the multicast CDR log.
                 if the value of the ACCESS clause is 'write-only', 
                 then the value of the MAX-ACCESS clause MUST be 'read-write', 
                 and the DESCRIPTION clause SHALL note that reading this object will
                 result in implementation-specific results.
                 Options:
                 1. fail(1) -indicates not to re-transmit the multicast CDR log 
                 2. all(2)  -indicates re-transmit the multicast CDR log 
                "     
            ::= { hwDslamNtv 71}
        hwDslamNtvV3QueryMaxResponseTime   OBJECT-TYPE
            SYNTAX       Integer32 (1..31744)
            UNITS        "0.1s"
            MAX-ACCESS   read-write
            STATUS       current
            DESCRIPTION
                "Indicates the maximum response time for an IGMPV3 general query. 
                 It is in the range of 1-31744 in the unit of 0.1s, that is, 0.1-3174.4s. 
                 By default, it is 10 (namely 100s). The general group query response 
                 must be shorter than the general group query interval. When a user goes 
                 offline without sending the report packet, if the system does not receive 
                 the report packet from the user within the maximum response time after the 
                 general query packet is sent, the system sends the general query packets 
                 for N-1 times based on the interval for the general query (N indicates the 
                 robustness variable). If the system does not receive the report packet within 
                 the maximum response time after the last general query is sent, it indicates 
                 that the user is offline. Aging time of a subscriber = General query interval 
                 x Robustness variable + Response time of the general query.
                 Unit: 0.1s
                "   
           ::= { hwDslamNtv 72 }        
        
        hwDslamNtvLastMemberV3QueryResponse OBJECT-TYPE
            SYNTAX Integer32 (1..31744)
            UNITS "0.1s"
            MAX-ACCESS read-write
            STATUS current
            DESCRIPTION
                "Sets/queries the maximum response time for IGMPV3 group-specific query. 
                 It is in the range of 1-31744 (in 0.1s), namely 0.1-3174.4s. By default, 
                 it is 8 (namely 0.8s). The group-specific query response must be shorter 
                 than the group-specific query interval. If the system does not receive 
                 the report packet within the maximum response time after the group-specific 
                 query packet is sent, the system sends the group-specific query packets 
                 for specified times (times of the group-specific query) based on the 
                 interval for the group-specific query. If the system does not receive 
                 the report packet within the specified time (maximum response time to 
                 the group-specific query) after the last group-specific query packet is 
                 sent, it indicates that the user is offline. User aging time = Interval 
                 for group-specific query x Times of group-specific query + Maximum response 
                 time to group-specific query.
                 Unit: 0.1s
                "
            ::= { hwDslamNtv 73 }    
            
        hwDslamNtvSnoopingProcess        OBJECT-TYPE
            SYNTAX INTEGER
                { 
                firstmatch(1),
                discard(2)
                }
            MAX-ACCESS   read-write
            STATUS       current
            DESCRIPTION
                "The process of different (S, G) matching different multicast snooping vlan in IGMPv3 Report.
                 Options:
                 1. firstmatch(1) -indicates the process of different (S, G) matching different multicast
                                   snooping vlan in IGMPv3 Report
                 2. discard(2)    -indicates the process of different (S, G) not matching different multicast
                                   snooping vlan in IGMPv3 Report
                "
            ::= { hwDslamNtv 74} 
        
        hwDslamNtvPreviewProfileTable    OBJECT-TYPE
            SYNTAX          SEQUENCE OF HwDslamNtvPreviewProfileEntry 
            MAX-ACCESS      not-accessible                     
            STATUS          current                                      
            DESCRIPTION
                "Indicates various parameters of a preview profile in the system.
                 The index of this table is hwDslamNtvPreviewProfileIndex.
                "
            ::= { hwDslamNtv 75 }
        
        hwDslamNtvPreviewProfileEntry    OBJECT-TYPE
            SYNTAX          HwDslamNtvPreviewProfileEntry
            MAX-ACCESS      not-accessible
            STATUS          current
            DESCRIPTION
                "Indicates various parameters of a preview profile in the system.
                 The index of this entry is hwDslamNtvPreviewProfileIndex.
                "
            INDEX 
                { 
                hwDslamNtvPreviewProfileIndex
                }
            ::= { hwDslamNtvPreviewProfileTable  1 }
        
        HwDslamNtvPreviewProfileEntry    ::= 
            SEQUENCE  
                {
                hwDslamNtvPreviewProfileIndex     
                    Integer32,
                hwDslamNtvPreviewRowStatus        
                    RowStatus,
                hwDslamNtvPreviewDuration         
                    Integer32,
                hwDslamNtvPreviewTimes            
                    Integer32,
                hwDslamNtvPreviewInterval         
                    Integer32,
                hwDslamNtvProgramRefCount         
                    Integer32
                }
                                        
         hwDslamNtvPreviewProfileIndex         OBJECT-TYPE
             SYNTAX          Integer32 (0..31)
             MAX-ACCESS      read-only
             STATUS          current
             DESCRIPTION
                 "Indicates the preview profile. 
                  Range: 0-31
                  Profile 0 is created by default and cannot be created or deleted.
                 "
             ::= { hwDslamNtvPreviewProfileEntry 1}   
        
        hwDslamNtvPreviewRowStatus        OBJECT-TYPE
            SYNTAX       RowStatus
            MAX-ACCESS   read-create
            STATUS       current
            DESCRIPTION
                "Row status, used to query, create, modify, and delete a multicast preview profile. 
                 It supports the active(1), createAndGo(4), and destroy(6) operations.
                 During query, the value of this leaf is always active(1).
                 During deletion, specify the value of this leaf to destroy(6).
                 During creation, specify the value of this leaf to createAndGo(4).
                 To modify the parameters of a multicast preview profile, this leaf need not be issued together.
                 Options:
                 1. active(1)      -indicates the query operation
                 2. createAndGo(4) -indicates the creating operation
                 3. destroy(6)     -indicates the deleting operation
                "
            ::= { hwDslamNtvPreviewProfileEntry 2}
        
        hwDslamNtvPreviewDuration        OBJECT-TYPE
            SYNTAX        Integer32 (10..6000 )
            UNITS         "second"
            MAX-ACCESS    read-write
            STATUS         current
            DESCRIPTION
                "Indicates the preview duration.
                 Range: 10-6000
                 Default: 120
                 Unit: second
                "
            DEFVAL {120}
            ::= { hwDslamNtvPreviewProfileEntry 3}
        
        hwDslamNtvPreviewTimes        OBJECT-TYPE
            SYNTAX      Integer32 (1..255 )
            MAX-ACCESS  read-write
            STATUS      current
            DESCRIPTION
                "Indicates the preview times. 
                 Range: 1-255
                 Default: 8
                " 
            DEFVAL {8 }
            ::= { hwDslamNtvPreviewProfileEntry 4}
        
        hwDslamNtvPreviewInterval      OBJECT-TYPE
            SYNTAX      Integer32 (0..7650)
            UNITS        "second"
            MAX-ACCESS  read-write
            STATUS       current
            DESCRIPTION
                "Indicates the preview interval. 
                 Range: 0-7650
                 Default: 120 
                 Unit: second
                "
            DEFVAL {120 }   
            ::= { hwDslamNtvPreviewProfileEntry 5}
        
        hwDslamNtvProgramRefCount        OBJECT-TYPE
            SYNTAX       Integer32
            MAX-ACCESS   read-only
            STATUS       current
            DESCRIPTION
                "Indicates the number of programs bound to the profile.
                "
            ::= { hwDslamNtvPreviewProfileEntry 6}
        
        hwDslamNtvMVLANTable OBJECT-TYPE
            SYNTAX SEQUENCE OF HwDslamNtvMVLANEntry
            MAX-ACCESS not-accessible
            STATUS current
            DESCRIPTION
                "Indicates a multicast VLAN in the system, which records the VLAN attributes.
                 The index of this table is hwDslamNtvMVLANIndex.
                "
            ::= { hwDslamNtv 76 }
        
        hwDslamNtvMVLANEntry OBJECT-TYPE
            SYNTAX HwDslamNtvMVLANEntry
            MAX-ACCESS not-accessible
            STATUS current
            DESCRIPTION
                "Indicates a multicast VLAN in the system, which records the VLAN attributes.
                 The index of this entry is hwDslamNtvMVLANIndex.
                "
            INDEX { hwDslamNtvMVLANIndex }
            ::= { hwDslamNtvMVLANTable 1 }
        
        HwDslamNtvMVLANEntry ::= 
            SEQUENCE 
                {
                hwDslamNtvMVLANIndex                    
                    Integer32,
                hwDslamNtvMVLANLogSwitch                 
                    INTEGER{ enable(1),disable(2)},
                hwDslamNtvMVLANIGMPPriority              
                    Integer32 (0..7),
                hwDslamNtvMVLANGlobalLeaveSendSwitch     
                    INTEGER{ enable(1),disable(2)},
                hwDslamNtvMVLANIgmpMode                  
                    INTEGER{igmpproxy(1),igmpsnooping(2),tvoff(3)},
                hwDslamNtvMVLANIgmpVer                  
                    INTEGER{igmpv2(1),igmpv3(2)},
                hwDslamNtvMVLANMatchMode               
                    INTEGER{ enable(1),disable(2)},
                hwDslamNtvMVLANDynStartIP                
                    IpAddress,
                hwDslamNtvMVLANDynEndIP                  
                    IpAddress,
                hwDslamNtvMVLANSnoopingReportSwitch      
                    INTEGER{ enable(1),disable(2)},
                hwDslamNtvMVLANSnoopingLeaveSwitch       
                    INTEGER{ enable(1),disable(2)},     
                hwDslamNtvMVLANUnsoliReportTime          
                    Integer32 (10..5000),
                hwDslamNtvMVLANRowstatus                
                    RowStatus,
                hwDslamNtvDefaultUplinkPort              
                    Integer32,     
                hwDslamNtvVlanID                        
                    Integer32,
                hwDslamNtvMVLANProgramMask1             
                    BITS,
                hwDslamNtvMVLANProgramMask2             
                    BITS,
                hwDslamNtvMVLANProgramMask3              
                    BITS,
                hwDslamNtvMVLANProgramMask4              
                    BITS,
                hwDslamNtvMVLANProgramMask5              
                    BITS,
                hwDslamNtvMVLANProgramMask6             
                    BITS,
                hwDslamNtvMVLANProgramMask7               
                    BITS,
                hwDslamNtvMVLANProgramMask8             
                    BITS,
                hwDslamNtvMVLANProgramMask9              
                    BITS,
                hwDslamNtvMVLANProgramMask10             
                    BITS,
                hwDslamNtvMVLANProgramMask11             
                    BITS,
                hwDslamNtvMVLANProgramMask12             
                    BITS,
                hwDslamNtvMVLANProgramMask13             
                    BITS,
                hwDslamNtvMVLANProgramMask14             
                    BITS,
                hwDslamNtvMVLANProgramMask15             
                    BITS,
                hwDslamNtvMVLANProgramMask16              
                    BITS,
                hwDslamNtvMVLANProgramMask17            
                    BITS,
                hwDslamNtvMVLANProgramMask18             
                    BITS,
                hwDslamNtvMVLANProgramMask19             
                    BITS,
                hwDslamNtvMVLANProgramMask20             
                    BITS,
                hwDslamNtvMVLANProgramMask21            
                    BITS,
                hwDslamNtvMVLANProgramMask22            
                    BITS,
                hwDslamNtvMVLANProgramMask23            
                    BITS,
                hwDslamNtvMVLANProgramMask24             
                    BITS,
                hwDslamNtvMVLANProgramMask25             
                    BITS,
                hwDslamNtvMVLANProgramMask26             
                    BITS,
                hwDslamNtvMVLANProgramMask27             
                    BITS,
                hwDslamNtvMVLANProgramMask28             
                    BITS,
                hwDslamNtvMVLANProgramMask29             
                    BITS,
                hwDslamNtvMVLANProgramMask30             
                    BITS,
                hwDslamNtvMVLANProgramMask31             
                    BITS,
                hwDslamNtvMVLANProgramMask32             
                    BITS,
                hwDslamNtvMVlANInnerVlan
                    Integer32,
                hwDslamNtvMvlanVideoMode
                    INTEGER{multicast(1),unicast(2)},
                hwDslamNtvMVLANIgmpQueryInterval
                    Integer32 (-1|30..5000),
                hwDslamNtvMVLANIgmpV2QueryMaxResponseTime
                    Integer32 (-1|1..255),
                hwDslamNtvMVLANIgmpV3QueryMaxResponseTime
                    Integer32 (-1|1..31744),
                hwDslamNtvMVLANIgmpRobustness
                    Integer32 (-1|1..10),
                hwDslamNtvMVLANIgmpLastMemberQueryInterval
                    Integer32 (-1|1..50000),
                hwDslamNtvMVLANIgmpV2LastMemberQueryResponse
                    Integer32 (-1|1..255),
                hwDslamNtvMVLANIgmpV3LastMemberQueryResponse
                    Integer32 (-1|1..31744),
                hwDslamNtvMVLANIgmpLastMemberQueryCount
                    Integer32 (-1|1..10),
                hwDslamNtvMVLANIgmpV2RouterTimerout
                    Integer32 (-1|1..5000),
                hwDslamNtvMVLANIgmpInitialUnsolicitedReportInterval
                    Integer32 (-1|1..10),
                hwDslamNtvMVLANSnoopingQueryProxy
                    INTEGER{enable(1),disable(2)},
                hwDslamNtvMVLANGroupFilterMode                  
                    INTEGER{asmOnly(1),ssmOnly(2),asmSsm(3)},
                hwDslamNtvMVLANDualPwSwitch      
                    INTEGER{ enable(1),disable(2)},   
                hwDslamNtvMVLANMldVer
                        INTEGER{mldV1(1),mldV2(2)},
                hwDslamNtvMVLANMldUnsoliReportTime
                        Integer32 (10..5000),
                hwDslamNtvMVLANMldPriority
                        Integer32 (0..7),
                hwDslamNtvMVLANMldMode
                        INTEGER{mldProxy(1),mldSnooping(2),tvOff(3)},
                hwDslamNtvMVLANMldMatchMode
                        INTEGER{enable(1),disable(2)},
                hwDslamNtvMVLANMldSnoopingReportSwitch
                        INTEGER{enable(1),disable(2)},
                hwDslamNtvMVLANMldSnoopingLeaveSwitch
                        INTEGER{enable(1),disable(2)},
                hwDslamNtvMldQueryInterval
                        Integer32 (30..5000),
                hwDslamNtvMldV1QueryMaxResponseTime
                        Integer32 (1..655),
                hwDslamNtvMldV2QueryMaxResponseTime
                        Integer32 (1..50000),
                hwDslamNtvMldRobustness
                        Integer32 (1..10),
                hwDslamNtvMVLANMldLastMemberQueryInterval
                        Integer32 (1..50000),
                hwDslamNtvMldV1LastMemberQueryResponse
                        Integer32 (1..655),
                hwDslamNtvMldV2LastMemberQueryResponse
                        Integer32 (1..50000),
                hwDslamNtvMVLANMldLastMemberQueryCount
                        Integer32 (1..10),
                hwDslamNtvMldInitialUnsolicitedReportInterval
                        Integer32 (1..10),
                hwDslamNtvMVLANIgmpDscpValue
                        Integer32 (0..63),
                hwDslamNtvMVLANMldDscpValue
                        Integer32 (0..63)                
                }
           
        hwDslamNtvMVLANIndex OBJECT-TYPE
            SYNTAX Integer32 (-1|1..256)
            MAX-ACCESS read-only
            STATUS current
            DESCRIPTION
                "Indicates the index of a multicast VLAN. 
                 You can also fill -1 and the system will automatically allocate an index. 
                "
            ::= { hwDslamNtvMVLANEntry 1 }
        
        hwDslamNtvMVLANLogSwitch OBJECT-TYPE
            SYNTAX INTEGER
                { 
                enable(1),
                disable(2)
                }
            MAX-ACCESS read-write
            STATUS current
            DESCRIPTION
                "Sets the log switch. 
                 Options:
                 1. enable(1)  -indicates the log switch is on
                 2. disable(2) -indicates the log switch is off
                 Default: enable(1)
                "
            DEFVAL { 2 }
            ::= { hwDslamNtvMVLANEntry 2 }   

        hwDslamNtvMVLANIGMPPriority OBJECT-TYPE
            SYNTAX  Integer32 (0..7)
            MAX-ACCESS read-write
            STATUS current
            DESCRIPTION
                "Sets the priority of IGMP packets based on a multicast VLAN. 
                 Range: 0-7 
                 Default: 6
                "
            DEFVAL { 6 }
            ::= { hwDslamNtvMVLANEntry 3 } 
    
        hwDslamNtvMVLANGlobalLeaveSendSwitch OBJECT-TYPE
            SYNTAX  INTEGER{ enable(1),disable(2)}
            MAX-ACCESS read-write
            STATUS current
            DESCRIPTION
                "Indicates whether to set the switch for sending global leave packets based on a multicast VLAN. 
                 Options:
                 1. enable(1)  -indicates setting the switch for sending global leave 
                                packets based on a multicast VLAN
                 2. disable(2) -indicates not setting the switch for sending global leave 
                                packets based on a multicast VLAN
                 Default: enable(1)
                "
            DEFVAL { 1 }
            ::= { hwDslamNtvMVLANEntry 4 } 

        hwDslamNtvMVLANIgmpMode OBJECT-TYPE
            SYNTAX  INTEGER 
                {
                igmpProxy(1),
                igmpSnooping(2),
                tvOff(3)
                }
            MAX-ACCESS read-write
            STATUS current
            DESCRIPTION
                "Indicates the IGMP working mode. 
                 Options:
                 1. igmpProxy(1)    -indicates the IGMP working mode is igmpProxy
                 2. igmpSnooping(2) -indicates the IGMP working mode is igmpSnooping
                 3. tvOff(3)        -indicates the IGMP working mode is tvOff
                 Default: tvOff(3)
                "
            DEFVAL { 3 }
            ::= { hwDslamNtvMVLANEntry 5 } 
                 
        hwDslamNtvMVLANIgmpVer OBJECT-TYPE
            SYNTAX  INTEGER
                { 
                igmpV2(1),
                igmpV3(2)
                }
            MAX-ACCESS read-write
            STATUS current
            DESCRIPTION
                "Indicates the IGMP version. 
                 Options:
                 1. igmpV2(1) -indicates the IGMP version is V2
                 2. igmpV3(2) -indicates the IGMP version is V3
                 Default: igmpV3(2)
                "
            DEFVAL { 2 }
            ::= { hwDslamNtvMVLANEntry 6 }     
             
        hwDslamNtvMVLANMatchMode OBJECT-TYPE
            SYNTAX  INTEGER
                { 
                enable(1),
                disable(2) 
                }
            MAX-ACCESS read-write
            STATUS current
            DESCRIPTION
                "Indicates the program matching mode. 
                 Options:
                 1. enable(1)  -indicates the program matching mode is enabled
                 2. disable(2) -indicates the program matching mode is disabled
                 Default: enable(1)
                "
            DEFVAL { 1 }
            ::= { hwDslamNtvMVLANEntry 7 } 
        
        hwDslamNtvMVLANDynStartIP OBJECT-TYPE
            SYNTAX  IpAddress
            MAX-ACCESS read-write
            STATUS current
            DESCRIPTION
                "Indicates the start IP address of the programs that can be generated dynamically.
                "
            ::= { hwDslamNtvMVLANEntry 8 } 
        
        hwDslamNtvMVLANDynEndIP OBJECT-TYPE
            SYNTAX  IpAddress
            MAX-ACCESS read-write
            STATUS current
            DESCRIPTION
                "Indicates the end IP address of the programs that can be generated dynamically.
                "
            ::= { hwDslamNtvMVLANEntry 9 } 
        
        hwDslamNtvMVLANSnoopingReportSwitch OBJECT-TYPE
            SYNTAX  INTEGER
                { 
                enable(1),
                disable(2)
                }
            MAX-ACCESS read-write
            STATUS current
            DESCRIPTION
                "Enables or disables the transmission of the report packet in the IGMP snooping mode.
                 Options:
                 1. enable(1)  -enable the transmission of the report packet in the IGMP snooping mode
                 2. disable(2) -disable the transmission of the report packet in the IGMP snooping mode
                 Default: disable(2)
                "
            DEFVAL { 2 }
            ::= { hwDslamNtvMVLANEntry 10 } 
        
        hwDslamNtvMVLANSnoopingLeaveSwitch OBJECT-TYPE
            SYNTAX  INTEGER{ enable(1),disable(2)}
            MAX-ACCESS read-write
            STATUS current
            DESCRIPTION
                "Enables or disables the transmission of the leave packet in the IGMP snooping mode.
                 Options:
                 1. enable(1)  -enable the transmission of the leave packet in the IGMP snooping mode
                 2. disable(2) -disable the transmission of the leave packet in the IGMP snooping mode
                 Default: disable(2)
                "
            DEFVAL { 2 }
            ::= { hwDslamNtvMVLANEntry 11 }            
   
        hwDslamNtvMVLANUnsoliReportTime OBJECT-TYPE
            SYNTAX  Integer32 (10..5000)
            MAX-ACCESS read-write
            STATUS current
            DESCRIPTION
                "Indicates the interval for a user to actively report packets.                   
                 Range: 10-5000 
                 Default: 10
                 Unit: second
                "
            DEFVAL { 10 }
            ::= { hwDslamNtvMVLANEntry 12 } 
           
        hwDslamNtvMVLANRowstatus        OBJECT-TYPE
            SYNTAX       RowStatus
            MAX-ACCESS   read-create
            STATUS       current
            DESCRIPTION
                "Row status, used to query, create, modify, and delete a multicast VLAN. 
                 It supports the active(1), createAndGo(4), and destroy(6) operations.
                 During query, the value of this leaf is always active(1).
                 During deletion, specify the value of this leaf to destroy(6).
                 During creation, specify the value of this leaf to createAndGo(4).
                 To modify the parameters of a multicast VLAN, this leaf need not be issued together.
                 Options:
                 1. active(1)      -indicates the query operation
                 2. createAndGo(4) -indicates the creating operation
                 3. destroy(6)     -indicates the deleting operation
                "
            ::= { hwDslamNtvMVLANEntry 13 }
        
        hwDslamNtvDefaultUplinkPort        OBJECT-TYPE
            SYNTAX       Integer32
            MAX-ACCESS   read-write
            STATUS       current
            DESCRIPTION
                "Indicates the default uplink port.
                 If the default uplink port is not configured, the returned value for hwDslamNtvDefaultUplinkPort is -1.
                "
            ::= { hwDslamNtvMVLANEntry 14 }         
        
        hwDslamNtvVlanID  OBJECT-TYPE
            SYNTAX     Integer32(1..4093)
            MAX-ACCESS   read-write
            STATUS       current
            DESCRIPTION
                "Indicates the multicast VLAN ID 
                 Range: 1-4093
                "
            ::= { hwDslamNtvMVLANEntry 15 }
        
        hwDslamNtvMVLANProgramMask1        OBJECT-TYPE
            SYNTAX   BITS
                {
                program1(0),
                program2(1),
                program3(2),
                program4(3),
                program5(4),
                program6(5),
                program7(6),
                program8(7),
                program9(8),
                program10(9),
                program11(10),
                program12(11),
                program13(12),
                program14(13),
                program15(14),
                program16(15),
                program17(16),
                program18(17),
                program19(18),
                program20(19),
                program21(20),
                program22(21),
                program23(22),
                program24(23),
                program25(24),
                program26(25),
                program27(26),
                program28(27),
                program29(28),
                program30(29),
                program31(30),
                program32(31),
                program33(32),
                program34(33),
                program35(34),
                program36(35),
                program37(36),
                program38(37),
                program39(38),
                program40(39),
                program41(40),
                program42(41),
                program43(42),
                program44(43),
                program45(44),
                program46(45),
                program47(46),
                program48(47),
                program49(48),
                program50(49),
                program51(50),
                program52(51),
                program53(52),
                program54(53),
                program55(54),
                program56(55),
                program57(56),
                program58(57),
                program59(58),
                program60(59),
                program61(60),
                program62(61),
                program63(62),
                program64(63),
                program65(64),
                program66(65),
                program67(66),
                program68(67),
                program69(68),
                program70(69),
                program71(70),
                program72(71),
                program73(72),
                program74(73),
                program75(74),
                program76(75),
                program77(76),
                program78(77),
                program79(78),
                program80(79),
                program81(80),
                program82(81),
                program83(82),
                program84(83),
                program85(84),
                program86(85),
                program87(86),
                program88(87),
                program89(88),
                program90(89),
                program91(90),
                program92(91),
                program93(92),
                program94(93),
                program95(94),
                program96(95),
                program97(96),
                program98(97),
                program99(98),
                program100(99),
                program101(100),
                program102(101),
                program103(102),
                program104(103),
                program105(104),
                program106(105),
                program107(106),
                program108(107),
                program109(108),
                program110(109),
                program111(110),
                program112(111),
                program113(112),
                program114(113),
                program115(114),
                program116(115),
                program117(116),
                program118(117),
                program119(118),
                program120(119),
                program121(120),
                program122(121),
                program123(122),
                program124(123),
                program125(124),
                program126(125),
                program127(126),
                program128(127)                       
                }
            MAX-ACCESS   read-only
            STATUS       current
            DESCRIPTION
                "Indicates the program mask of a multicast VLAN. It has 16 bytes and each bit indicates a program. 
                 It can indicate 16 x 8 = 128 multicast programs in total. It indicates programs according to the byte order. 
                 The first byte indicates multicast programs with indexes 1-8. Here, bit 7 indicates program 1, bit 0 indicates 
                 program 8, and other bits are in the same manner. The second 2 byte indicates multicast programs with indexes 9-16. 
                 Here, bit 7 indicates program 9, bit 0 indicates program 16, and other bits are in the same manner. 
                 Other bytes indicate programs in the same way.
                 Bit value 1 indicates that the multicast program corresponding to the index exits in the multicast VLAN; 
                 bit value 0 indicates that the multicast program corresponding to the index does not exit in the 
                 multicast VLAN. For example, the value of hwDslamNtvMVLANProgramMask1 80.00.80.00.00.00.00.00.00.00.00.00.00.00.00.00 
                 indicates that programs with index 1 and 17 exist in this multicast VLAN.
                 Range: 1-128
                "
            ::= { hwDslamNtvMVLANEntry 16}
        
        hwDslamNtvMVLANProgramMask2        OBJECT-TYPE
            SYNTAX   BITS
                {
                program129(0),
                program130(1),
                program131(2),
                program132(3),
                program133(4),
                program134(5),
                program135(6),
                program136(7),
                program137(8),
                program138(9),
                program139(10),
                program140(11),
                program141(12),
                program142(13),
                program143(14),
                program144(15),
                program145(16),
                program146(17),
                program147(18),
                program148(19),
                program149(20),
                program150(21),
                program151(22),
                program152(23),
                program153(24),
                program154(25),
                program155(26),
                program156(27),
                program157(28),
                program158(29),
                program159(30),
                program160(31),
                program161(32),
                program162(33),
                program163(34),
                program164(35),
                program165(36),
                program166(37),
                program167(38),
                program168(39),
                program169(40),
                program170(41),
                program171(42),
                program172(43),
                program173(44),
                program174(45),
                program175(46),
                program176(47),
                program177(48),
                program178(49),
                program179(50),
                program180(51),
                program181(52),
                program182(53),
                program183(54),
                program184(55),
                program185(56),
                program186(57),
                program187(58),
                program188(59),
                program189(60),
                program190(61),
                program191(62),
                program192(63),
                program193(64),
                program194(65),
                program195(66),
                program196(67),
                program197(68),
                program198(69),
                program199(70),
                program200(71),
                program201(72),
                program202(73),
                program203(74),
                program204(75),
                program205(76),
                program206(77),
                program207(78),
                program208(79),
                program209(80),
                program210(81),
                program211(82),
                program212(83),
                program213(84),
                program214(85),
                program215(86),
                program216(87),
                program217(88),
                program218(89),
                program219(90),
                program220(91),
                program221(92),
                program222(93),
                program223(94),
                program224(95),
                program225(96),
                program226(97),
                program227(98),
                program228(99),
                program229(100),
                program230(101),
                program231(102),
                program232(103),
                program233(104),
                program234(105),
                program235(106),
                program236(107),
                program237(108),
                program238(109),
                program239(110),
                program240(111),
                program241(112),
                program242(113),
                program243(114),
                program244(115),
                program245(116),
                program246(117),
                program247(118),
                program248(119),
                program249(120),
                program250(121),
                program251(122),
                program252(123),
                program253(124),
                program254(125),
                program255(126),
                program256(127)
                }           
            MAX-ACCESS   read-only
            STATUS       current
            DESCRIPTION
                "Indicates the program mask of a multicast VLAN. It indicates the 128 multicast programs 
                 after the preceding leaf. The bit meanings are the same as the preceding leaf.
                "
            ::= { hwDslamNtvMVLANEntry 17 }
        
        hwDslamNtvMVLANProgramMask3 OBJECT-TYPE
            SYNTAX BITS
                {
                program257(0),
                program258(1),
                program259(2),
                program260(3),
                program261(4),
                program262(5),
                program263(6),
                program264(7),
                program265(8),
                program266(9),
                program267(10),
                program268(11),
                program269(12),
                program270(13),
                program271(14),
                program272(15),
                program273(16),
                program274(17),
                program275(18),
                program276(19),
                program277(20),
                program278(21),
                program279(22),
                program280(23),
                program281(24),
                program282(25),
                program283(26),
                program284(27),
                program285(28),
                program286(29),
                program287(30),
                program288(31),
                program289(32),
                program290(33),
                program291(34),
                program292(35),
                program293(36),
                program294(37),
                program295(38),
                program296(39),
                program297(40),
                program298(41),
                program299(42),
                program300(43),
                program301(44),
                program302(45),
                program303(46),
                program304(47),
                program305(48),
                program306(49),
                program307(50),
                program308(51),
                program309(52),
                program310(53),
                program311(54),
                program312(55),
                program313(56),
                program314(57),
                program315(58),
                program316(59),
                program317(60),
                program318(61),
                program319(62),
                program320(63),
                program321(64),
                program322(65),
                program323(66),
                program324(67),
                program325(68),
                program326(69),
                program327(70),
                program328(71),
                program329(72),
                program330(73),
                program331(74),
                program332(75),
                program333(76),
                program334(77),
                program335(78),
                program336(79),
                program337(80),
                program338(81),
                program339(82),
                program340(83),
                program341(84),
                program342(85),
                program343(86),
                program344(87),
                program345(88),
                program346(89),
                program347(90),
                program348(91),
                program349(92),
                program350(93),
                program351(94),
                program352(95),
                program353(96),
                program354(97),
                program355(98),
                program356(99),
                program357(100),
                program358(101),
                program359(102),
                program360(103),
                program361(104),
                program362(105),
                program363(106),
                program364(107),
                program365(108),
                program366(109),
                program367(110),
                program368(111),
                program369(112),
                program370(113),
                program371(114),
                program372(115),
                program373(116),
                program374(117),
                program375(118),
                program376(119),
                program377(120),
                program378(121),
                program379(122),
                program380(123),
                program381(124),
                program382(125),
                program383(126),
                program384(127)
                }
            MAX-ACCESS read-only
            STATUS current
            DESCRIPTION
                "Indicates the program mask of a multicast VLAN. It indicates the 128 multicast 
                 programs after the preceding leaf. The bit meanings are the same as the preceding leaf.
                "
            ::= { hwDslamNtvMVLANEntry 18 }
                
        hwDslamNtvMVLANProgramMask4 OBJECT-TYPE
            SYNTAX BITS
                {
                program385(0),
                program386(1),
                program387(2),
                program388(3),
                program389(4),
                program390(5),
                program391(6),
                program392(7),
                program393(8),
                program394(9),
                program395(10),
                program396(11),
                program397(12),
                program398(13),
                program399(14),
                program400(15),
                program401(16),
                program402(17),
                program403(18),
                program404(19),
                program405(20),
                program406(21),
                program407(22),
                program408(23),
                program409(24),
                program410(25),
                program411(26),
                program412(27),
                program413(28),
                program414(29),
                program415(30),
                program416(31),
                program417(32),
                program418(33),
                program419(34),
                program420(35),
                program421(36),
                program422(37),
                program423(38),
                program424(39),
                program425(40),
                program426(41),
                program427(42),
                program428(43),
                program429(44),
                program430(45),
                program431(46),
                program432(47),
                program433(48),
                program434(49),
                program435(50),
                program436(51),
                program437(52),
                program438(53),
                program439(54),
                program440(55),
                program441(56),
                program442(57),
                program443(58),
                program444(59),
                program445(60),
                program446(61),
                program447(62),
                program448(63),
                program449(64),
                program450(65),
                program451(66),
                program452(67),
                program453(68),
                program454(69),
                program455(70),
                program456(71),
                program457(72),
                program458(73),
                program459(74),
                program460(75),
                program461(76),
                program462(77),
                program463(78),
                program464(79),
                program465(80),
                program466(81),
                program467(82),
                program468(83),
                program469(84),
                program470(85),
                program471(86),
                program472(87),
                program473(88),
                program474(89),
                program475(90),
                program476(91),
                program477(92),
                program478(93),
                program479(94),
                program480(95),
                program481(96),
                program482(97),
                program483(98),
                program484(99),
                program485(100),
                program486(101),
                program487(102),
                program488(103),
                program489(104),
                program490(105),
                program491(106),
                program492(107),
                program493(108),
                program494(109),
                program495(110),
                program496(111),
                program497(112),
                program498(113),
                program499(114),
                program500(115),
                program501(116),
                program502(117),
                program503(118),
                program504(119),
                program505(120),
                program506(121),
                program507(122),
                program508(123),
                program509(124),
                program510(125),
                program511(126),
                program512(127)
                }
            MAX-ACCESS read-only
            STATUS current
            DESCRIPTION
                "Indicates the program mask of a multicast VLAN. It indicates the 128 multicast 
                 programs after the preceding leaf. The bit meanings are the same as the preceding leaf.
                "
            ::= { hwDslamNtvMVLANEntry 19 }        
        
        hwDslamNtvMVLANProgramMask5 OBJECT-TYPE
            SYNTAX BITS
                {
                program513(0),
                program514(1),
                program515(2),
                program516(3),
                program517(4),
                program518(5),
                program519(6),
                program520(7),
                program521(8),
                program522(9),
                program523(10),
                program524(11),
                program525(12),
                program526(13),
                program527(14),
                program528(15),
                program529(16),
                program530(17),
                program531(18),
                program532(19),
                program533(20),
                program534(21),
                program535(22),
                program536(23),
                program537(24),
                program538(25),
                program539(26),
                program540(27),
                program541(28),
                program542(29),
                program543(30),
                program544(31),
                program545(32),
                program546(33),
                program547(34),
                program548(35),
                program549(36),
                program550(37),
                program551(38),
                program552(39),
                program553(40),
                program554(41),
                program555(42),
                program556(43),
                program557(44),
                program558(45),
                program559(46),
                program560(47),
                program561(48),
                program562(49),
                program563(50),
                program564(51),
                program565(52),
                program566(53),
                program567(54),
                program568(55),
                program569(56),
                program570(57),
                program571(58),
                program572(59),
                program573(60),
                program574(61),
                program575(62),
                program576(63),
                program577(64),
                program578(65),
                program579(66),
                program580(67),
                program581(68),
                program582(69),
                program583(70),
                program584(71),
                program585(72),
                program586(73),
                program587(74),
                program588(75),
                program589(76),
                program590(77),
                program591(78),
                program592(79),
                program593(80),
                program594(81),
                program595(82),
                program596(83),
                program597(84),
                program598(85),
                program599(86),
                program600(87),
                program601(88),
                program602(89),
                program603(90),
                program604(91),
                program605(92),
                program606(93),
                program607(94),
                program608(95),
                program609(96),
                program610(97),
                program611(98),
                program612(99),
                program613(100),
                program614(101),
                program615(102),
                program616(103),
                program617(104),
                program618(105),
                program619(106),
                program620(107),
                program621(108),
                program622(109),
                program623(110),
                program624(111),
                program625(112),
                program626(113),
                program627(114),
                program628(115),
                program629(116),
                program630(117),
                program631(118),
                program632(119),
                program633(120),
                program634(121),
                program635(122),
                program636(123),
                program637(124),
                program638(125),
                program639(126),
                program640(127)
                }
            MAX-ACCESS read-only
            STATUS current
            DESCRIPTION
                "Indicates the program mask of a multicast VLAN. It indicates the 128 multicast 
                 programs after the preceding leaf. The bit meanings are the same as the preceding leaf.
                "
            ::= { hwDslamNtvMVLANEntry 20 }
                
        hwDslamNtvMVLANProgramMask6 OBJECT-TYPE
            SYNTAX BITS
                {
                program641(0),
                program642(1),
                program643(2),
                program644(3),
                program645(4),
                program646(5),
                program647(6),
                program648(7),
                program649(8),
                program650(9),
                program651(10),
                program652(11),
                program653(12),
                program654(13),
                program655(14),
                program656(15),
                program657(16),
                program658(17),
                program659(18),
                program660(19),
                program661(20),
                program662(21),
                program663(22),
                program664(23),
                program665(24),
                program666(25),
                program667(26),
                program668(27),
                program669(28),
                program670(29),
                program671(30),
                program672(31),
                program673(32),
                program674(33),
                program675(34),
                program676(35),
                program677(36),
                program678(37),
                program679(38),
                program680(39),
                program681(40),
                program682(41),
                program683(42),
                program684(43),
                program685(44),
                program686(45),
                program687(46),
                program688(47),
                program689(48),
                program690(49),
                program691(50),
                program692(51),
                program693(52),
                program694(53),
                program695(54),
                program696(55),
                program697(56),
                program698(57),
                program699(58),
                program700(59),
                program701(60),
                program702(61),
                program703(62),
                program704(63),
                program705(64),
                program706(65),
                program707(66),
                program708(67),
                program709(68),
                program710(69),
                program711(70),
                program712(71),
                program713(72),
                program714(73),
                program715(74),
                program716(75),
                program717(76),
                program718(77),
                program719(78),
                program720(79),
                program721(80),
                program722(81),
                program723(82),
                program724(83),
                program725(84),
                program726(85),
                program727(86),
                program728(87),
                program729(88),
                program730(89),
                program731(90),
                program732(91),
                program733(92),
                program734(93),
                program735(94),
                program736(95),
                program737(96),
                program738(97),
                program739(98),
                program740(99),
                program741(100),
                program742(101),
                program743(102),
                program744(103),
                program745(104),
                program746(105),
                program747(106),
                program748(107),
                program749(108),
                program750(109),
                program751(110),
                program752(111),
                program753(112),
                program754(113),
                program755(114),
                program756(115),
                program757(116),
                program758(117),
                program759(118),
                program760(119),
                program761(120),
                program762(121),
                program763(122),
                program764(123),
                program765(124),
                program766(125),
                program767(126),
                program768(127)
                }
            MAX-ACCESS read-only
            STATUS current
            DESCRIPTION
                "Indicates the program mask of a multicast VLAN. It indicates the 128 multicast 
                 programs after the preceding leaf. The bit meanings are the same as the preceding leaf.
                "
            ::= { hwDslamNtvMVLANEntry 21 }        
        
        hwDslamNtvMVLANProgramMask7 OBJECT-TYPE
            SYNTAX BITS
                {
                program769(0),
                program770(1),
                program771(2),
                program772(3),
                program773(4),
                program774(5),
                program775(6),
                program776(7),
                program777(8),
                program778(9),
                program779(10),
                program780(11),
                program781(12),
                program782(13),
                program783(14),
                program784(15),
                program785(16),
                program786(17),
                program787(18),
                program788(19),
                program789(20),
                program790(21),
                program791(22),
                program792(23),
                program793(24),
                program794(25),
                program795(26),
                program796(27),
                program797(28),
                program798(29),
                program799(30),
                program800(31),
                program801(32),
                program802(33),
                program803(34),
                program804(35),
                program805(36),
                program806(37),
                program807(38),
                program808(39),
                program809(40),
                program810(41),
                program811(42),
                program812(43),
                program813(44),
                program814(45),
                program815(46),
                program816(47),
                program817(48),
                program818(49),
                program819(50),
                program820(51),
                program821(52),
                program822(53),
                program823(54),
                program824(55),
                program825(56),
                program826(57),
                program827(58),
                program828(59),
                program829(60),
                program830(61),
                program831(62),
                program832(63),
                program833(64),
                program834(65),
                program835(66),
                program836(67),
                program837(68),
                program838(69),
                program839(70),
                program840(71),
                program841(72),
                program842(73),
                program843(74),
                program844(75),
                program845(76),
                program846(77),
                program847(78),
                program848(79),
                program849(80),
                program850(81),
                program851(82),
                program852(83),
                program853(84),
                program854(85),
                program855(86),
                program856(87),
                program857(88),
                program858(89),
                program859(90),
                program860(91),
                program861(92),
                program862(93),
                program863(94),
                program864(95),
                program865(96),
                program866(97),
                program867(98),
                program868(99),
                program869(100),
                program870(101),
                program871(102),
                program872(103),
                program873(104),
                program874(105),
                program875(106),
                program876(107),
                program877(108),
                program878(109),
                program879(110),
                program880(111),
                program881(112),
                program882(113),
                program883(114),
                program884(115),
                program885(116),
                program886(117),
                program887(118),
                program888(119),
                program889(120),
                program890(121),
                program891(122),
                program892(123),
                program893(124),
                program894(125),
                program895(126),
                program896(127)
                }
            MAX-ACCESS read-only
            STATUS current
            DESCRIPTION
                "Indicates the program mask of a multicast VLAN. It indicates the 128 multicast 
                 programs after the preceding leaf. The bit meanings are the same as the preceding leaf
                "
            ::= { hwDslamNtvMVLANEntry 22 }        
        
        hwDslamNtvMVLANProgramMask8 OBJECT-TYPE
            SYNTAX BITS
                {
                program897(0),
                program898(1),
                program899(2),
                program900(3),
                program901(4),
                program902(5),
                program903(6),
                program904(7),
                program905(8),
                program906(9),
                program907(10),
                program908(11),
                program909(12),
                program910(13),
                program911(14),
                program912(15),
                program913(16),
                program914(17),
                program915(18),
                program916(19),
                program917(20),
                program918(21),
                program919(22),
                program920(23),
                program921(24),
                program922(25),
                program923(26),
                program924(27),
                program925(28),
                program926(29),
                program927(30),
                program928(31),
                program929(32),
                program930(33),
                program931(34),
                program932(35),
                program933(36),
                program934(37),
                program935(38),
                program936(39),
                program937(40),
                program938(41),
                program939(42),
                program940(43),
                program941(44),
                program942(45),
                program943(46),
                program944(47),
                program945(48),
                program946(49),
                program947(50),
                program948(51),
                program949(52),
                program950(53),
                program951(54),
                program952(55),
                program953(56),
                program954(57),
                program955(58),
                program956(59),
                program957(60),
                program958(61),
                program959(62),
                program960(63),
                program961(64),
                program962(65),
                program963(66),
                program964(67),
                program965(68),
                program966(69),
                program967(70),
                program968(71),
                program969(72),
                program970(73),
                program971(74),
                program972(75),
                program973(76),
                program974(77),
                program975(78),
                program976(79),
                program977(80),
                program978(81),
                program979(82),
                program980(83),
                program981(84),
                program982(85),
                program983(86),
                program984(87),
                program985(88),
                program986(89),
                program987(90),
                program988(91),
                program989(92),
                program990(93),
                program991(94),
                program992(95),
                program993(96),
                program994(97),
                program995(98),
                program996(99),
                program997(100),
                program998(101),
                program999(102),
                program1000(103),
                program1001(104),
                program1002(105),
                program1003(106),
                program1004(107),
                program1005(108),
                program1006(109),
                program1007(110),
                program1008(111),
                program1009(112),
                program1010(113),
                program1011(114),
                program1012(115),
                program1013(116),
                program1014(117),
                program1015(118),
                program1016(119),
                program1017(120),
                program1018(121),
                program1019(122),
                program1020(123),
                program1021(124),
                program1022(125),
                program1023(126),
                program1024(127)
                }
            MAX-ACCESS read-only
            STATUS current
            DESCRIPTION
                "Indicates the program mask of a multicast VLAN. It indicates the 128 multicast 
                 programs after the preceding leaf. The bit meanings are the same as the preceding leaf.
                "
            ::= { hwDslamNtvMVLANEntry 23 }

        hwDslamNtvMVLANProgramMask9 OBJECT-TYPE
            SYNTAX BITS
                {
                program1025(0),
                program1026(1),
                program1027(2),
                program1028(3),
                program1029(4),
                program1030(5),
                program1031(6),
                program1032(7),
                program1033(8),
                program1034(9),
                program1035(10),
                program1036(11),
                program1037(12),
                program1038(13),
                program1039(14),
                program1040(15),
                program1041(16),
                program1042(17),
                program1043(18),
                program1044(19),
                program1045(20),
                program1046(21),
                program1047(22),
                program1048(23),
                program1049(24),
                program1050(25),
                program1051(26),
                program1052(27),
                program1053(28),
                program1054(29),
                program1055(30),
                program1056(31),
                program1057(32),
                program1058(33),
                program1059(34),
                program1060(35),
                program1061(36),
                program1062(37),
                program1063(38),
                program1064(39),
                program1065(40),
                program1066(41),
                program1067(42),
                program1068(43),
                program1069(44),
                program1070(45),
                program1071(46),
                program1072(47),
                program1073(48),
                program1074(49),
                program1075(50),
                program1076(51),
                program1077(52),
                program1078(53),
                program1079(54),
                program1080(55),
                program1081(56),
                program1082(57),
                program1083(58),
                program1084(59),
                program1085(60),
                program1086(61),
                program1087(62),
                program1088(63),
                program1089(64),
                program1090(65),
                program1091(66),
                program1092(67),
                program1093(68),
                program1094(69),
                program1095(70),
                program1096(71),
                program1097(72),
                program1098(73),
                program1099(74),
                program1100(75),
                program1101(76),
                program1102(77),
                program1103(78),
                program1104(79),
                program1105(80),
                program1106(81),
                program1107(82),
                program1108(83),
                program1109(84),
                program1110(85),
                program1111(86),
                program1112(87),
                program1113(88),
                program1114(89),
                program1115(90),
                program1116(91),
                program1117(92),
                program1118(93),
                program1119(94),
                program1120(95),
                program1121(96),
                program1122(97),
                program1123(98),
                program1124(99),
                program1125(100),
                program1126(101),
                program1127(102),
                program1128(103),
                program1129(104),
                program1130(105),
                program1131(106),
                program1132(107),
                program1133(108),
                program1134(109),
                program1135(110),
                program1136(111),
                program1137(112),
                program1138(113),
                program1139(114),
                program1140(115),
                program1141(116),
                program1142(117),
                program1143(118),
                program1144(119),
                program1145(120),
                program1146(121),
                program1147(122),
                program1148(123),
                program1149(124),
                program1150(125),
                program1151(126),
                program1152(127)
                }
            MAX-ACCESS read-only
            STATUS current
            DESCRIPTION
                "Indicates the program mask of a multicast VLAN. It indicates the 128 multicast 
                 programs after the preceding leaf. The bit meanings are the same as the preceding leaf.
                "
            ::= { hwDslamNtvMVLANEntry 24 }            
            
        hwDslamNtvMVLANProgramMask10 OBJECT-TYPE
            SYNTAX BITS
                {
                program1153(0),
                program1154(1),
                program1155(2),
                program1156(3),
                program1157(4),
                program1158(5),
                program1159(6),
                program1160(7),
                program1161(8),
                program1162(9),
                program1163(10),
                program1164(11),
                program1165(12),
                program1166(13),
                program1167(14),
                program1168(15),
                program1169(16),
                program1170(17),
                program1171(18),
                program1172(19),
                program1173(20),
                program1174(21),
                program1175(22),
                program1176(23),
                program1177(24),
                program1178(25),
                program1179(26),
                program1180(27),
                program1181(28),
                program1182(29),
                program1183(30),
                program1184(31),
                program1185(32),
                program1186(33),
                program1187(34),
                program1188(35),
                program1189(36),
                program1190(37),
                program1191(38),
                program1192(39),
                program1193(40),
                program1194(41),
                program1195(42),
                program1196(43),
                program1197(44),
                program1198(45),
                program1199(46),
                program1200(47),
                program1201(48),
                program1202(49),
                program1203(50),
                program1204(51),
                program1205(52),
                program1206(53),
                program1207(54),
                program1208(55),
                program1209(56),
                program1210(57),
                program1211(58),
                program1212(59),
                program1213(60),
                program1214(61),
                program1215(62),
                program1216(63),
                program1217(64),
                program1218(65),
                program1219(66),
                program1220(67),
                program1221(68),
                program1222(69),
                program1223(70),
                program1224(71),
                program1225(72),
                program1226(73),
                program1227(74),
                program1228(75),
                program1229(76),
                program1230(77),
                program1231(78),
                program1232(79),
                program1233(80),
                program1234(81),
                program1235(82),
                program1236(83),
                program1237(84),
                program1238(85),
                program1239(86),
                program1240(87),
                program1241(88),
                program1242(89),
                program1243(90),
                program1244(91),
                program1245(92),
                program1246(93),
                program1247(94),
                program1248(95),
                program1249(96),
                program1250(97),
                program1251(98),
                program1252(99),
                program1253(100),
                program1254(101),
                program1255(102),
                program1256(103),
                program1257(104),
                program1258(105),
                program1259(106),
                program1260(107),
                program1261(108),
                program1262(109),
                program1263(110),
                program1264(111),
                program1265(112),
                program1266(113),
                program1267(114),
                program1268(115),
                program1269(116),
                program1270(117),
                program1271(118),
                program1272(119),
                program1273(120),
                program1274(121),
                program1275(122),
                program1276(123),
                program1277(124),
                program1278(125),
                program1279(126),
                program1280(127)
                }
            MAX-ACCESS read-only
            STATUS current
            DESCRIPTION
                "Indicates the program mask of a multicast VLAN. It indicates the 128 multicast 
                 programs after the preceding leaf. The bit meanings are the same as the preceding leaf.
                "
            ::= { hwDslamNtvMVLANEntry 25 }                        

        hwDslamNtvMVLANProgramMask11 OBJECT-TYPE
            SYNTAX BITS
                {
                program1281(0),  
                program1282(1),  
                program1283(2),  
                program1284(3),  
                program1285(4),  
                program1286(5),  
                program1287(6),  
                program1288(7),  
                program1289(8),  
                program1290(9),  
                program1291(10), 
                program1292(11), 
                program1293(12), 
                program1294(13), 
                program1295(14), 
                program1296(15), 
                program1297(16), 
                program1298(17), 
                program1299(18), 
                program1300(19), 
                program1301(20), 
                program1302(21), 
                program1303(22), 
                program1304(23), 
                program1305(24), 
                program1306(25), 
                program1307(26), 
                program1308(27), 
                program1309(28), 
                program1310(29), 
                program1311(30), 
                program1312(31), 
                program1313(32), 
                program1314(33), 
                program1315(34), 
                program1316(35), 
                program1317(36), 
                program1318(37), 
                program1319(38), 
                program1320(39), 
                program1321(40), 
                program1322(41), 
                program1323(42), 
                program1324(43), 
                program1325(44), 
                program1326(45), 
                program1327(46), 
                program1328(47), 
                program1329(48), 
                program1330(49), 
                program1331(50), 
                program1332(51), 
                program1333(52), 
                program1334(53), 
                program1335(54), 
                program1336(55), 
                program1337(56), 
                program1338(57), 
                program1339(58), 
                program1340(59), 
                program1341(60), 
                program1342(61), 
                program1343(62), 
                program1344(63), 
                program1345(64), 
                program1346(65), 
                program1347(66), 
                program1348(67), 
                program1349(68), 
                program1350(69), 
                program1351(70), 
                program1352(71), 
                program1353(72), 
                program1354(73), 
                program1355(74), 
                program1356(75), 
                program1357(76), 
                program1358(77), 
                program1359(78), 
                program1360(79), 
                program1361(80), 
                program1362(81), 
                program1363(82), 
                program1364(83), 
                program1365(84), 
                program1366(85), 
                program1367(86), 
                program1368(87), 
                program1369(88), 
                program1370(89), 
                program1371(90), 
                program1372(91), 
                program1373(92), 
                program1374(93), 
                program1375(94), 
                program1376(95), 
                program1377(96), 
                program1378(97), 
                program1379(98), 
                program1380(99), 
                program1381(100),
                program1382(101),
                program1383(102),
                program1384(103),
                program1385(104),
                program1386(105),
                program1387(106),
                program1388(107),
                program1389(108),
                program1390(109),
                program1391(110),
                program1392(111),
                program1393(112),
                program1394(113),
                program1395(114),
                program1396(115),
                program1397(116),
                program1398(117),
                program1399(118),
                program1400(119),
                program1401(120),
                program1402(121),
                program1403(122),
                program1404(123),
                program1405(124),
                program1406(125),
                program1407(126),
                program1408(127) 
                }
            MAX-ACCESS read-only
            STATUS current
            DESCRIPTION
                "Indicates the program mask of a multicast VLAN. It indicates the 128 multicast 
                 programs after the preceding leaf. The bit meanings are the same as the preceding leaf.
                "
            ::= { hwDslamNtvMVLANEntry 26 }        
            
        hwDslamNtvMVLANProgramMask12 OBJECT-TYPE
            SYNTAX BITS
                {
                program1409(0),  
                program1410(1),  
                program1411(2),  
                program1412(3),  
                program1413(4),  
                program1414(5),  
                program1415(6),  
                program1416(7),  
                program1417(8),  
                program1418(9),  
                program1419(10), 
                program1420(11), 
                program1421(12), 
                program1422(13), 
                program1423(14), 
                program1424(15), 
                program1425(16), 
                program1426(17), 
                program1427(18), 
                program1428(19), 
                program1429(20), 
                program1430(21), 
                program1431(22), 
                program1432(23), 
                program1433(24), 
                program1434(25), 
                program1435(26), 
                program1436(27), 
                program1437(28), 
                program1438(29), 
                program1439(30), 
                program1440(31), 
                program1441(32), 
                program1442(33), 
                program1443(34), 
                program1444(35), 
                program1445(36), 
                program1446(37), 
                program1447(38), 
                program1448(39), 
                program1449(40), 
                program1450(41), 
                program1451(42), 
                program1452(43), 
                program1453(44), 
                program1454(45), 
                program1455(46), 
                program1456(47), 
                program1457(48), 
                program1458(49), 
                program1459(50), 
                program1460(51), 
                program1461(52), 
                program1462(53), 
                program1463(54), 
                program1464(55), 
                program1465(56), 
                program1466(57), 
                program1467(58), 
                program1468(59), 
                program1469(60), 
                program1470(61), 
                program1471(62), 
                program1472(63), 
                program1473(64), 
                program1474(65), 
                program1475(66), 
                program1476(67), 
                program1477(68), 
                program1478(69), 
                program1479(70), 
                program1480(71), 
                program1481(72), 
                program1482(73), 
                program1483(74), 
                program1484(75), 
                program1485(76), 
                program1486(77), 
                program1487(78), 
                program1488(79), 
                program1489(80), 
                program1490(81), 
                program1491(82), 
                program1492(83), 
                program1493(84), 
                program1494(85), 
                program1495(86), 
                program1496(87), 
                program1497(88), 
                program1498(89), 
                program1499(90), 
                program1500(91), 
                program1501(92), 
                program1502(93), 
                program1503(94), 
                program1504(95), 
                program1505(96), 
                program1506(97), 
                program1507(98), 
                program1508(99), 
                program1509(100),
                program1510(101),
                program1511(102),
                program1512(103),
                program1513(104),
                program1514(105),
                program1515(106),
                program1516(107),
                program1517(108),
                program1518(109),
                program1519(110),
                program1520(111),
                program1521(112),
                program1522(113),
                program1523(114),
                program1524(115),
                program1525(116),
                program1526(117),
                program1527(118),
                program1528(119),
                program1529(120),
                program1530(121),
                program1531(122),
                program1532(123),
                program1533(124),
                program1534(125),
                program1535(126),
                program1536(127) 
                }
            MAX-ACCESS read-only
            STATUS current
            DESCRIPTION
                "Indicates the program mask of a multicast VLAN. It indicates the 128 multicast 
                 programs after the preceding leaf. The bit meanings are the same as the preceding leaf.
                "
            ::= { hwDslamNtvMVLANEntry 27 }    
            
        hwDslamNtvMVLANProgramMask13 OBJECT-TYPE
            SYNTAX BITS
                {
                program1537(0),  
                program1538(1),  
                program1539(2),  
                program1540(3),  
                program1541(4),  
                program1542(5),  
                program1543(6),  
                program1544(7),  
                program1545(8),  
                program1546(9),  
                program1547(10), 
                program1548(11), 
                program1549(12), 
                program1550(13), 
                program1551(14), 
                program1552(15), 
                program1553(16), 
                program1554(17), 
                program1555(18), 
                program1556(19), 
                program1557(20), 
                program1558(21), 
                program1559(22), 
                program1560(23), 
                program1561(24), 
                program1562(25), 
                program1563(26), 
                program1564(27), 
                program1565(28), 
                program1566(29), 
                program1567(30), 
                program1568(31), 
                program1569(32), 
                program1570(33), 
                program1571(34), 
                program1572(35), 
                program1573(36), 
                program1574(37), 
                program1575(38), 
                program1576(39), 
                program1577(40), 
                program1578(41), 
                program1579(42), 
                program1580(43), 
                program1581(44), 
                program1582(45), 
                program1583(46), 
                program1584(47), 
                program1585(48), 
                program1586(49), 
                program1587(50), 
                program1588(51), 
                program1589(52), 
                program1590(53), 
                program1591(54), 
                program1592(55), 
                program1593(56), 
                program1594(57), 
                program1595(58), 
                program1596(59), 
                program1597(60), 
                program1598(61), 
                program1599(62), 
                program1600(63), 
                program1601(64), 
                program1602(65), 
                program1603(66), 
                program1604(67), 
                program1605(68), 
                program1606(69), 
                program1607(70), 
                program1608(71), 
                program1609(72), 
                program1610(73), 
                program1611(74), 
                program1612(75), 
                program1613(76), 
                program1614(77), 
                program1615(78), 
                program1616(79), 
                program1617(80), 
                program1618(81), 
                program1619(82), 
                program1620(83), 
                program1621(84), 
                program1622(85), 
                program1623(86), 
                program1624(87), 
                program1625(88), 
                program1626(89), 
                program1627(90), 
                program1628(91), 
                program1629(92), 
                program1630(93), 
                program1631(94), 
                program1632(95), 
                program1633(96), 
                program1634(97), 
                program1635(98), 
                program1636(99), 
                program1637(100),
                program1638(101),
                program1639(102),
                program1640(103),
                program1641(104),
                program1642(105),
                program1643(106),
                program1644(107),
                program1645(108),
                program1646(109),
                program1647(110),
                program1648(111),
                program1649(112),
                program1650(113),
                program1651(114),
                program1652(115),
                program1653(116),
                program1654(117),
                program1655(118),
                program1656(119),
                program1657(120),
                program1658(121),
                program1659(122),
                program1660(123),
                program1661(124),
                program1662(125),
                program1663(126),
                program1664(127) 
                }
            MAX-ACCESS read-only
            STATUS current
            DESCRIPTION
                "Indicates the program mask of a multicast VLAN. It indicates the 128 multicast 
                 programs after the preceding leaf. The bit meanings are the same as the preceding leaf.
                "
            ::= { hwDslamNtvMVLANEntry 28 }                        
            
        hwDslamNtvMVLANProgramMask14 OBJECT-TYPE
            SYNTAX BITS
                {
                program1665(0),  
                program1666(1),  
                program1667(2),  
                program1668(3),  
                program1669(4),  
                program1670(5),  
                program1671(6),  
                program1672(7),  
                program1673(8),  
                program1674(9),  
                program1675(10), 
                program1676(11), 
                program1677(12), 
                program1678(13), 
                program1679(14), 
                program1680(15), 
                program1681(16), 
                program1682(17), 
                program1683(18), 
                program1684(19), 
                program1685(20), 
                program1686(21), 
                program1687(22), 
                program1688(23), 
                program1689(24), 
                program1690(25), 
                program1691(26), 
                program1692(27), 
                program1693(28), 
                program1694(29), 
                program1695(30), 
                program1696(31), 
                program1697(32), 
                program1698(33), 
                program1699(34), 
                program1700(35), 
                program1701(36), 
                program1702(37), 
                program1703(38), 
                program1704(39), 
                program1705(40), 
                program1706(41), 
                program1707(42), 
                program1708(43), 
                program1709(44), 
                program1710(45), 
                program1711(46), 
                program1712(47), 
                program1713(48), 
                program1714(49), 
                program1715(50), 
                program1716(51), 
                program1717(52), 
                program1718(53), 
                program1719(54), 
                program1720(55), 
                program1721(56), 
                program1722(57), 
                program1723(58), 
                program1724(59), 
                program1725(60), 
                program1726(61), 
                program1727(62), 
                program1728(63), 
                program1729(64), 
                program1730(65), 
                program1731(66), 
                program1732(67), 
                program1733(68), 
                program1734(69), 
                program1735(70), 
                program1736(71), 
                program1737(72), 
                program1738(73), 
                program1739(74), 
                program1740(75), 
                program1741(76), 
                program1742(77), 
                program1743(78), 
                program1744(79), 
                program1745(80), 
                program1746(81), 
                program1747(82), 
                program1748(83), 
                program1749(84), 
                program1750(85), 
                program1751(86), 
                program1752(87), 
                program1753(88), 
                program1754(89), 
                program1755(90), 
                program1756(91), 
                program1757(92), 
                program1758(93), 
                program1759(94), 
                program1760(95), 
                program1761(96), 
                program1762(97), 
                program1763(98), 
                program1764(99), 
                program1765(100),
                program1766(101),
                program1767(102),
                program1768(103),
                program1769(104),
                program1770(105),
                program1771(106),
                program1772(107),
                program1773(108),
                program1774(109),
                program1775(110),
                program1776(111),
                program1777(112),
                program1778(113),
                program1779(114),
                program1780(115),
                program1781(116),
                program1782(117),
                program1783(118),
                program1784(119),
                program1785(120),
                program1786(121),
                program1787(122),
                program1788(123),
                program1789(124),
                program1790(125),
                program1791(126),
                program1792(127) 
                }
            MAX-ACCESS read-only
            STATUS current
            DESCRIPTION
                "Indicates the program mask of a multicast VLAN. It indicates the 128 multicast 
                 programs after the preceding leaf. The bit meanings are the same as the preceding leaf.
                "
            ::= { hwDslamNtvMVLANEntry 29 }                        
            
        hwDslamNtvMVLANProgramMask15 OBJECT-TYPE
            SYNTAX BITS
                {
                program1793(0),  
                program1794(1),  
                program1795(2),  
                program1796(3),  
                program1797(4),  
                program1798(5),  
                program1799(6),  
                program1800(7),  
                program1801(8),  
                program1802(9),  
                program1803(10), 
                program1804(11), 
                program1805(12), 
                program1806(13), 
                program1807(14), 
                program1808(15), 
                program1809(16), 
                program1810(17), 
                program1811(18), 
                program1812(19), 
                program1813(20), 
                program1814(21), 
                program1815(22), 
                program1816(23), 
                program1817(24), 
                program1818(25), 
                program1819(26), 
                program1820(27), 
                program1821(28), 
                program1822(29), 
                program1823(30), 
                program1824(31), 
                program1825(32), 
                program1826(33), 
                program1827(34), 
                program1828(35), 
                program1829(36), 
                program1830(37), 
                program1831(38), 
                program1832(39), 
                program1833(40), 
                program1834(41), 
                program1835(42), 
                program1836(43), 
                program1837(44), 
                program1838(45), 
                program1839(46), 
                program1840(47), 
                program1841(48), 
                program1842(49), 
                program1843(50), 
                program1844(51), 
                program1845(52), 
                program1846(53), 
                program1847(54), 
                program1848(55), 
                program1849(56), 
                program1850(57), 
                program1851(58), 
                program1852(59), 
                program1853(60), 
                program1854(61), 
                program1855(62), 
                program1856(63), 
                program1857(64), 
                program1858(65), 
                program1859(66), 
                program1860(67), 
                program1861(68), 
                program1862(69), 
                program1863(70), 
                program1864(71), 
                program1865(72), 
                program1866(73), 
                program1867(74), 
                program1868(75), 
                program1869(76), 
                program1870(77), 
                program1871(78), 
                program1872(79), 
                program1873(80), 
                program1874(81), 
                program1875(82), 
                program1876(83), 
                program1877(84), 
                program1878(85), 
                program1879(86), 
                program1880(87), 
                program1881(88), 
                program1882(89), 
                program1883(90), 
                program1884(91), 
                program1885(92), 
                program1886(93), 
                program1887(94), 
                program1888(95), 
                program1889(96), 
                program1890(97), 
                program1891(98), 
                program1892(99), 
                program1893(100),
                program1894(101),
                program1895(102),
                program1896(103),
                program1897(104),
                program1898(105),
                program1899(106),
                program1900(107),
                program1901(108),
                program1902(109),
                program1903(110),
                program1904(111),
                program1905(112),
                program1906(113),
                program1907(114),
                program1908(115),
                program1909(116),
                program1910(117),
                program1911(118),
                program1912(119),
                program1913(120),
                program1914(121),
                program1915(122),
                program1916(123),
                program1917(124),
                program1918(125),
                program1919(126),
                program1920(127) 
                }
            MAX-ACCESS read-only
            STATUS current
            DESCRIPTION
                "Indicates the program mask of a multicast VLAN. It indicates the 128 multicast 
                 programs after the preceding leaf. The bit meanings are the same as the preceding leaf.
                "
            ::= { hwDslamNtvMVLANEntry 30 }                        
            
        hwDslamNtvMVLANProgramMask16 OBJECT-TYPE
            SYNTAX BITS
                {
                program1921(0),  
                program1922(1),  
                program1923(2),  
                program1924(3),  
                program1925(4),  
                program1926(5),  
                program1927(6),  
                program1928(7),  
                program1929(8),  
                program1930(9),  
                program1931(10), 
                program1932(11), 
                program1933(12), 
                program1934(13), 
                program1935(14), 
                program1936(15), 
                program1937(16), 
                program1938(17), 
                program1939(18), 
                program1940(19), 
                program1941(20), 
                program1942(21), 
                program1943(22), 
                program1944(23), 
                program1945(24), 
                program1946(25), 
                program1947(26), 
                program1948(27), 
                program1949(28), 
                program1950(29), 
                program1951(30), 
                program1952(31), 
                program1953(32), 
                program1954(33), 
                program1955(34), 
                program1956(35), 
                program1957(36), 
                program1958(37), 
                program1959(38), 
                program1960(39), 
                program1961(40), 
                program1962(41), 
                program1963(42), 
                program1964(43), 
                program1965(44), 
                program1966(45), 
                program1967(46), 
                program1968(47), 
                program1969(48), 
                program1970(49), 
                program1971(50), 
                program1972(51), 
                program1973(52), 
                program1974(53), 
                program1975(54), 
                program1976(55), 
                program1977(56), 
                program1978(57), 
                program1979(58), 
                program1980(59), 
                program1981(60), 
                program1982(61), 
                program1983(62), 
                program1984(63), 
                program1985(64), 
                program1986(65), 
                program1987(66), 
                program1988(67), 
                program1989(68), 
                program1990(69), 
                program1991(70), 
                program1992(71), 
                program1993(72), 
                program1994(73), 
                program1995(74), 
                program1996(75), 
                program1997(76), 
                program1998(77), 
                program1999(78), 
                program2000(79), 
                program2001(80), 
                program2002(81), 
                program2003(82), 
                program2004(83), 
                program2005(84), 
                program2006(85), 
                program2007(86), 
                program2008(87), 
                program2009(88), 
                program2010(89), 
                program2011(90), 
                program2012(91), 
                program2013(92), 
                program2014(93), 
                program2015(94), 
                program2016(95), 
                program2017(96), 
                program2018(97), 
                program2019(98), 
                program2020(99), 
                program2021(100),
                program2022(101),
                program2023(102),
                program2024(103),
                program2025(104),
                program2026(105),
                program2027(106),
                program2028(107),
                program2029(108),
                program2030(109),
                program2031(110),
                program2032(111),
                program2033(112),
                program2034(113),
                program2035(114),
                program2036(115),
                program2037(116),
                program2038(117),
                program2039(118),
                program2040(119),
                program2041(120),
                program2042(121),
                program2043(122),
                program2044(123),
                program2045(124),
                program2046(125),
                program2047(126),
                program2048(127) 
                }
            MAX-ACCESS read-only
            STATUS current
            DESCRIPTION
                "Indicates the program mask of a multicast VLAN. It indicates the 128 multicast 
                 programs after the preceding leaf. The bit meanings are the same as the preceding leaf
                "
            ::= { hwDslamNtvMVLANEntry 31 }                        
            
        hwDslamNtvMVLANProgramMask17 OBJECT-TYPE
            SYNTAX BITS
                {
                program2049(0),  
                program2050(1),  
                program2051(2),  
                program2052(3),  
                program2053(4),  
                program2054(5),  
                program2055(6),  
                program2056(7),  
                program2057(8),  
                program2058(9),  
                program2059(10), 
                program2060(11), 
                program2061(12), 
                program2062(13), 
                program2063(14), 
                program2064(15), 
                program2065(16), 
                program2066(17), 
                program2067(18), 
                program2068(19), 
                program2069(20), 
                program2070(21), 
                program2071(22), 
                program2072(23), 
                program2073(24), 
                program2074(25), 
                program2075(26), 
                program2076(27), 
                program2077(28), 
                program2078(29), 
                program2079(30), 
                program2080(31), 
                program2081(32), 
                program2082(33), 
                program2083(34), 
                program2084(35), 
                program2085(36), 
                program2086(37), 
                program2087(38), 
                program2088(39), 
                program2089(40), 
                program2090(41), 
                program2091(42), 
                program2092(43), 
                program2093(44), 
                program2094(45), 
                program2095(46), 
                program2096(47), 
                program2097(48), 
                program2098(49), 
                program2099(50), 
                program2100(51), 
                program2101(52), 
                program2102(53), 
                program2103(54), 
                program2104(55), 
                program2105(56), 
                program2106(57), 
                program2107(58), 
                program2108(59), 
                program2109(60), 
                program2110(61), 
                program2111(62), 
                program2112(63), 
                program2113(64), 
                program2114(65), 
                program2115(66), 
                program2116(67), 
                program2117(68), 
                program2118(69), 
                program2119(70), 
                program2120(71), 
                program2121(72), 
                program2122(73), 
                program2123(74), 
                program2124(75), 
                program2125(76), 
                program2126(77), 
                program2127(78), 
                program2128(79), 
                program2129(80), 
                program2130(81), 
                program2131(82), 
                program2132(83), 
                program2133(84), 
                program2134(85), 
                program2135(86), 
                program2136(87), 
                program2137(88), 
                program2138(89), 
                program2139(90), 
                program2140(91), 
                program2141(92), 
                program2142(93), 
                program2143(94), 
                program2144(95), 
                program2145(96), 
                program2146(97), 
                program2147(98), 
                program2148(99), 
                program2149(100),
                program2150(101),
                program2151(102),
                program2152(103),
                program2153(104),
                program2154(105),
                program2155(106),
                program2156(107),
                program2157(108),
                program2158(109),
                program2159(110),
                program2160(111),
                program2161(112),
                program2162(113),
                program2163(114),
                program2164(115),
                program2165(116),
                program2166(117),
                program2167(118),
                program2168(119),
                program2169(120),
                program2170(121),
                program2171(122),
                program2172(123),
                program2173(124),
                program2174(125),
                program2175(126),
                program2176(127) 
                }
            MAX-ACCESS read-only
            STATUS current
            DESCRIPTION
                "Indicates the program mask of a multicast VLAN. It indicates the 128 multicast 
                 programs after the preceding leaf. The bit meanings are the same as the preceding leaf.
                "
            ::= { hwDslamNtvMVLANEntry 32 }                        
            
        hwDslamNtvMVLANProgramMask18 OBJECT-TYPE
            SYNTAX BITS
                {
                program2177(0),  
                program2178(1),  
                program2179(2),  
                program2180(3),  
                program2181(4),  
                program2182(5),  
                program2183(6),  
                program2184(7),  
                program2185(8),  
                program2186(9),  
                program2187(10), 
                program2188(11), 
                program2189(12), 
                program2190(13), 
                program2191(14), 
                program2192(15), 
                program2193(16), 
                program2194(17), 
                program2195(18), 
                program2196(19), 
                program2197(20), 
                program2198(21), 
                program2199(22), 
                program2200(23), 
                program2201(24), 
                program2202(25), 
                program2203(26), 
                program2204(27), 
                program2205(28), 
                program2206(29), 
                program2207(30), 
                program2208(31), 
                program2209(32), 
                program2210(33), 
                program2211(34), 
                program2212(35), 
                program2213(36), 
                program2214(37), 
                program2215(38), 
                program2216(39), 
                program2217(40), 
                program2218(41), 
                program2219(42), 
                program2220(43), 
                program2221(44), 
                program2222(45), 
                program2223(46), 
                program2224(47), 
                program2225(48), 
                program2226(49), 
                program2227(50), 
                program2228(51), 
                program2229(52), 
                program2230(53), 
                program2231(54), 
                program2232(55), 
                program2233(56), 
                program2234(57), 
                program2235(58), 
                program2236(59), 
                program2237(60), 
                program2238(61), 
                program2239(62), 
                program2240(63), 
                program2241(64), 
                program2242(65), 
                program2243(66), 
                program2244(67), 
                program2245(68), 
                program2246(69), 
                program2247(70), 
                program2248(71), 
                program2249(72), 
                program2250(73), 
                program2251(74), 
                program2252(75), 
                program2253(76), 
                program2254(77), 
                program2255(78), 
                program2256(79), 
                program2257(80), 
                program2258(81), 
                program2259(82), 
                program2260(83), 
                program2261(84), 
                program2262(85), 
                program2263(86), 
                program2264(87), 
                program2265(88), 
                program2266(89), 
                program2267(90), 
                program2268(91), 
                program2269(92), 
                program2270(93), 
                program2271(94), 
                program2272(95), 
                program2273(96), 
                program2274(97), 
                program2275(98), 
                program2276(99), 
                program2277(100),
                program2278(101),
                program2279(102),
                program2280(103),
                program2281(104),
                program2282(105),
                program2283(106),
                program2284(107),
                program2285(108),
                program2286(109),
                program2287(110),
                program2288(111),
                program2289(112),
                program2290(113),
                program2291(114),
                program2292(115),
                program2293(116),
                program2294(117),
                program2295(118),
                program2296(119),
                program2297(120),
                program2298(121),
                program2299(122),
                program2300(123),
                program2301(124),
                program2302(125),
                program2303(126),
                program2304(127) 
                }
            MAX-ACCESS read-only
            STATUS current
            DESCRIPTION
                "Indicates the program mask of a multicast VLAN. It indicates the 128 multicast 
                 programs after the preceding leaf. The bit meanings are the same as the preceding leaf.
                "
            ::= { hwDslamNtvMVLANEntry 33 }                        
            
        hwDslamNtvMVLANProgramMask19 OBJECT-TYPE
            SYNTAX BITS
                {
                program2305(0),  
                program2306(1),  
                program2307(2),  
                program2308(3),  
                program2309(4),  
                program2310(5),  
                program2311(6),  
                program2312(7),  
                program2313(8),  
                program2314(9),  
                program2315(10), 
                program2316(11), 
                program2317(12), 
                program2318(13), 
                program2319(14), 
                program2320(15), 
                program2321(16), 
                program2322(17), 
                program2323(18), 
                program2324(19), 
                program2325(20), 
                program2326(21), 
                program2327(22), 
                program2328(23), 
                program2329(24), 
                program2330(25), 
                program2331(26), 
                program2332(27), 
                program2333(28), 
                program2334(29), 
                program2335(30), 
                program2336(31), 
                program2337(32), 
                program2338(33), 
                program2339(34), 
                program2340(35), 
                program2341(36), 
                program2342(37), 
                program2343(38), 
                program2344(39), 
                program2345(40), 
                program2346(41), 
                program2347(42), 
                program2348(43), 
                program2349(44), 
                program2350(45), 
                program2351(46), 
                program2352(47), 
                program2353(48), 
                program2354(49), 
                program2355(50), 
                program2356(51), 
                program2357(52), 
                program2358(53), 
                program2359(54), 
                program2360(55), 
                program2361(56), 
                program2362(57), 
                program2363(58), 
                program2364(59), 
                program2365(60), 
                program2366(61), 
                program2367(62), 
                program2368(63), 
                program2369(64), 
                program2370(65), 
                program2371(66), 
                program2372(67), 
                program2373(68), 
                program2374(69), 
                program2375(70), 
                program2376(71), 
                program2377(72), 
                program2378(73), 
                program2379(74), 
                program2380(75), 
                program2381(76), 
                program2382(77), 
                program2383(78), 
                program2384(79), 
                program2385(80), 
                program2386(81), 
                program2387(82), 
                program2388(83), 
                program2389(84), 
                program2390(85), 
                program2391(86), 
                program2392(87), 
                program2393(88), 
                program2394(89), 
                program2395(90), 
                program2396(91), 
                program2397(92), 
                program2398(93), 
                program2399(94), 
                program2400(95), 
                program2401(96), 
                program2402(97), 
                program2403(98), 
                program2404(99), 
                program2405(100),
                program2406(101),
                program2407(102),
                program2408(103),
                program2409(104),
                program2410(105),
                program2411(106),
                program2412(107),
                program2413(108),
                program2414(109),
                program2415(110),
                program2416(111),
                program2417(112),
                program2418(113),
                program2419(114),
                program2420(115),
                program2421(116),
                program2422(117),
                program2423(118),
                program2424(119),
                program2425(120),
                program2426(121),
                program2427(122),
                program2428(123),
                program2429(124),
                program2430(125),
                program2431(126),
                program2432(127) 
                }
            MAX-ACCESS read-only
            STATUS current
            DESCRIPTION
                "Indicates the program mask of a multicast VLAN. It indicates the 128 multicast 
                 programs after the preceding leaf. The bit meanings are the same as the preceding leaf.
                "
            ::= { hwDslamNtvMVLANEntry 34 }                        
            
        hwDslamNtvMVLANProgramMask20 OBJECT-TYPE
            SYNTAX BITS
                {
                program2433(0),  
                program2434(1),  
                program2435(2),  
                program2436(3),  
                program2437(4),  
                program2438(5),  
                program2439(6),  
                program2440(7),  
                program2441(8),  
                program2442(9),  
                program2443(10), 
                program2444(11), 
                program2445(12), 
                program2446(13), 
                program2447(14), 
                program2448(15), 
                program2449(16), 
                program2450(17), 
                program2451(18), 
                program2452(19), 
                program2453(20), 
                program2454(21), 
                program2455(22), 
                program2456(23), 
                program2457(24), 
                program2458(25), 
                program2459(26), 
                program2460(27), 
                program2461(28), 
                program2462(29), 
                program2463(30), 
                program2464(31), 
                program2465(32), 
                program2466(33), 
                program2467(34), 
                program2468(35), 
                program2469(36), 
                program2470(37), 
                program2471(38), 
                program2472(39), 
                program2473(40), 
                program2474(41), 
                program2475(42), 
                program2476(43), 
                program2477(44), 
                program2478(45), 
                program2479(46), 
                program2480(47), 
                program2481(48), 
                program2482(49), 
                program2483(50), 
                program2484(51), 
                program2485(52), 
                program2486(53), 
                program2487(54), 
                program2488(55), 
                program2489(56), 
                program2490(57), 
                program2491(58), 
                program2492(59), 
                program2493(60), 
                program2494(61), 
                program2495(62), 
                program2496(63), 
                program2497(64), 
                program2498(65), 
                program2499(66), 
                program2500(67), 
                program2501(68), 
                program2502(69), 
                program2503(70), 
                program2504(71), 
                program2505(72), 
                program2506(73), 
                program2507(74), 
                program2508(75), 
                program2509(76), 
                program2510(77), 
                program2511(78), 
                program2512(79), 
                program2513(80), 
                program2514(81), 
                program2515(82), 
                program2516(83), 
                program2517(84), 
                program2518(85), 
                program2519(86), 
                program2520(87), 
                program2521(88), 
                program2522(89), 
                program2523(90), 
                program2524(91), 
                program2525(92), 
                program2526(93), 
                program2527(94), 
                program2528(95), 
                program2529(96), 
                program2530(97), 
                program2531(98), 
                program2532(99), 
                program2533(100),
                program2534(101),
                program2535(102),
                program2536(103),
                program2537(104),
                program2538(105),
                program2539(106),
                program2540(107),
                program2541(108),
                program2542(109),
                program2543(110),
                program2544(111),
                program2545(112),
                program2546(113),
                program2547(114),
                program2548(115),
                program2549(116),
                program2550(117),
                program2551(118),
                program2552(119),
                program2553(120),
                program2554(121),
                program2555(122),
                program2556(123),
                program2557(124),
                program2558(125),
                program2559(126),
                program2560(127) 
                }
            MAX-ACCESS read-only
            STATUS current
            DESCRIPTION
                "Indicates the program mask of a multicast VLAN. It indicates the 128 multicast 
                 programs after the preceding leaf. The bit meanings are the same as the preceding leaf.
                "
            ::= { hwDslamNtvMVLANEntry 35 }                        
            
        hwDslamNtvMVLANProgramMask21 OBJECT-TYPE
            SYNTAX BITS
                {
                program2561(0),  
                program2562(1),  
                program2563(2),  
                program2564(3),  
                program2565(4),  
                program2566(5),  
                program2567(6),  
                program2568(7),  
                program2569(8),  
                program2570(9),  
                program2571(10), 
                program2572(11), 
                program2573(12), 
                program2574(13), 
                program2575(14), 
                program2576(15), 
                program2577(16), 
                program2578(17), 
                program2579(18), 
                program2580(19), 
                program2581(20), 
                program2582(21), 
                program2583(22), 
                program2584(23), 
                program2585(24), 
                program2586(25), 
                program2587(26), 
                program2588(27), 
                program2589(28), 
                program2590(29), 
                program2591(30), 
                program2592(31), 
                program2593(32), 
                program2594(33), 
                program2595(34), 
                program2596(35), 
                program2597(36), 
                program2598(37), 
                program2599(38), 
                program2600(39), 
                program2601(40), 
                program2602(41), 
                program2603(42), 
                program2604(43), 
                program2605(44), 
                program2606(45), 
                program2607(46), 
                program2608(47), 
                program2609(48), 
                program2610(49), 
                program2611(50), 
                program2612(51), 
                program2613(52), 
                program2614(53), 
                program2615(54), 
                program2616(55), 
                program2617(56), 
                program2618(57), 
                program2619(58), 
                program2620(59), 
                program2621(60), 
                program2622(61), 
                program2623(62), 
                program2624(63), 
                program2625(64), 
                program2626(65), 
                program2627(66), 
                program2628(67), 
                program2629(68), 
                program2630(69), 
                program2631(70), 
                program2632(71), 
                program2633(72), 
                program2634(73), 
                program2635(74), 
                program2636(75), 
                program2637(76), 
                program2638(77), 
                program2639(78), 
                program2640(79), 
                program2641(80), 
                program2642(81), 
                program2643(82), 
                program2644(83), 
                program2645(84), 
                program2646(85), 
                program2647(86), 
                program2648(87), 
                program2649(88), 
                program2650(89), 
                program2651(90), 
                program2652(91), 
                program2653(92), 
                program2654(93), 
                program2655(94), 
                program2656(95), 
                program2657(96), 
                program2658(97), 
                program2659(98), 
                program2660(99), 
                program2661(100),
                program2662(101),
                program2663(102),
                program2664(103),
                program2665(104),
                program2666(105),
                program2667(106),
                program2668(107),
                program2669(108),
                program2670(109),
                program2671(110),
                program2672(111),
                program2673(112),
                program2674(113),
                program2675(114),
                program2676(115),
                program2677(116),
                program2678(117),
                program2679(118),
                program2680(119),
                program2681(120),
                program2682(121),
                program2683(122),
                program2684(123),
                program2685(124),
                program2686(125),
                program2687(126),
                program2688(127) 
                }
            MAX-ACCESS read-only
            STATUS current
            DESCRIPTION
                "Indicates the program mask of a multicast VLAN. It indicates the 128 multicast 
                 programs after the preceding leaf. The bit meanings are the same as the preceding leaf.
                "
            ::= { hwDslamNtvMVLANEntry 36 }                        
            
        hwDslamNtvMVLANProgramMask22 OBJECT-TYPE
            SYNTAX BITS
                {
                program2689(0),   
                program2690(1),   
                program2691(2),   
                program2692(3),   
                program2693(4),   
                program2694(5),   
                program2695(6),   
                program2696(7),   
                program2697(8),   
                program2698(9),   
                program2699(10),  
                program2700(11),  
                program2701(12),  
                program2702(13),  
                program2703(14),  
                program2704(15),  
                program2705(16),  
                program2706(17),  
                program2707(18),  
                program2708(19),  
                program2709(20),  
                program2710(21),  
                program2711(22),  
                program2712(23),  
                program2713(24),  
                program2714(25),  
                program2715(26),  
                program2716(27),  
                program2717(28),  
                program2718(29),  
                program2719(30),  
                program2720(31),  
                program2721(32),  
                program2722(33),  
                program2723(34),  
                program2724(35),  
                program2725(36),  
                program2726(37),  
                program2727(38),  
                program2728(39),  
                program2729(40),  
                program2730(41),  
                program2731(42),  
                program2732(43),  
                program2733(44),  
                program2734(45),  
                program2735(46),  
                program2736(47),  
                program2737(48),  
                program2738(49),  
                program2739(50),  
                program2740(51),  
                program2741(52),  
                program2742(53),  
                program2743(54),  
                program2744(55),  
                program2745(56),  
                program2746(57),  
                program2747(58),  
                program2748(59),  
                program2749(60),  
                program2750(61),  
                program2751(62),  
                program2752(63),  
                program2753(64),  
                program2754(65),  
                program2755(66),  
                program2756(67),  
                program2757(68),  
                program2758(69),  
                program2759(70),  
                program2760(71),  
                program2761(72),  
                program2762(73),  
                program2763(74),  
                program2764(75),  
                program2765(76),  
                program2766(77),  
                program2767(78),  
                program2768(79),  
                program2769(80),  
                program2770(81),  
                program2771(82),  
                program2772(83),  
                program2773(84),  
                program2774(85),  
                program2775(86),  
                program2776(87),  
                program2777(88),  
                program2778(89),  
                program2779(90),  
                program2780(91),  
                program2781(92),  
                program2782(93),  
                program2783(94),  
                program2784(95),  
                program2785(96),  
                program2786(97),  
                program2787(98),  
                program2788(99),  
                program2789(100), 
                program2790(101), 
                program2791(102), 
                program2792(103), 
                program2793(104), 
                program2794(105), 
                program2795(106), 
                program2796(107), 
                program2797(108), 
                program2798(109), 
                program2799(110), 
                program2800(111), 
                program2801(112), 
                program2802(113), 
                program2803(114), 
                program2804(115), 
                program2805(116), 
                program2806(117), 
                program2807(118), 
                program2808(119), 
                program2809(120), 
                program2810(121), 
                program2811(122), 
                program2812(123), 
                program2813(124), 
                program2814(125), 
                program2815(126), 
                program2816(127)  
                }
            MAX-ACCESS read-only
            STATUS current
            DESCRIPTION
                "Indicates the program mask of a multicast VLAN. It indicates the 128 multicast 
                 programs after the preceding leaf. The bit meanings are the same as the preceding leaf.
                "
            ::= { hwDslamNtvMVLANEntry 37 }                        
            
        hwDslamNtvMVLANProgramMask23 OBJECT-TYPE
            SYNTAX BITS
                {
                program2817(0),  
                program2818(1),  
                program2819(2),  
                program2820(3),  
                program2821(4),  
                program2822(5),  
                program2823(6),  
                program2824(7),  
                program2825(8),  
                program2826(9),  
                program2827(10), 
                program2828(11), 
                program2829(12), 
                program2830(13), 
                program2831(14), 
                program2832(15), 
                program2833(16), 
                program2834(17), 
                program2835(18), 
                program2836(19), 
                program2837(20), 
                program2838(21), 
                program2839(22), 
                program2840(23), 
                program2841(24), 
                program2842(25), 
                program2843(26), 
                program2844(27), 
                program2845(28), 
                program2846(29), 
                program2847(30), 
                program2848(31), 
                program2849(32), 
                program2850(33), 
                program2851(34), 
                program2852(35), 
                program2853(36), 
                program2854(37), 
                program2855(38), 
                program2856(39), 
                program2857(40), 
                program2858(41), 
                program2859(42), 
                program2860(43), 
                program2861(44), 
                program2862(45), 
                program2863(46), 
                program2864(47), 
                program2865(48), 
                program2866(49), 
                program2867(50), 
                program2868(51), 
                program2869(52), 
                program2870(53), 
                program2871(54), 
                program2872(55), 
                program2873(56), 
                program2874(57), 
                program2875(58), 
                program2876(59), 
                program2877(60), 
                program2878(61), 
                program2879(62), 
                program2880(63), 
                program2881(64), 
                program2882(65), 
                program2883(66), 
                program2884(67), 
                program2885(68), 
                program2886(69), 
                program2887(70), 
                program2888(71), 
                program2889(72), 
                program2890(73), 
                program2891(74), 
                program2892(75), 
                program2893(76), 
                program2894(77), 
                program2895(78), 
                program2896(79), 
                program2897(80), 
                program2898(81), 
                program2899(82), 
                program2900(83), 
                program2901(84), 
                program2902(85), 
                program2903(86), 
                program2904(87), 
                program2905(88), 
                program2906(89), 
                program2907(90), 
                program2908(91), 
                program2909(92), 
                program2910(93), 
                program2911(94), 
                program2912(95), 
                program2913(96), 
                program2914(97), 
                program2915(98), 
                program2916(99), 
                program2917(100),
                program2918(101),
                program2919(102),
                program2920(103),
                program2921(104),
                program2922(105),
                program2923(106),
                program2924(107),
                program2925(108),
                program2926(109),
                program2927(110),
                program2928(111),
                program2929(112),
                program2930(113),
                program2931(114),
                program2932(115),
                program2933(116),
                program2934(117),
                program2935(118),
                program2936(119),
                program2937(120),
                program2938(121),
                program2939(122),
                program2940(123),
                program2941(124),
                program2942(125),
                program2943(126),
                program2944(127) 
                }
            MAX-ACCESS read-only
            STATUS current
            DESCRIPTION
                "Indicates the program mask of a multicast VLAN. It indicates the 128 multicast 
                 programs after the preceding leaf. The bit meanings are the same as the preceding leaf.
                "
            ::= { hwDslamNtvMVLANEntry 38 }                        
            
        hwDslamNtvMVLANProgramMask24 OBJECT-TYPE
            SYNTAX BITS
                {
                program2945(0),  
                program2946(1),  
                program2947(2),  
                program2948(3),  
                program2949(4),  
                program2950(5),  
                program2951(6),  
                program2952(7),  
                program2953(8),  
                program2954(9),  
                program2955(10), 
                program2956(11), 
                program2957(12), 
                program2958(13), 
                program2959(14), 
                program2960(15), 
                program2961(16), 
                program2962(17), 
                program2963(18), 
                program2964(19), 
                program2965(20), 
                program2966(21), 
                program2967(22), 
                program2968(23), 
                program2969(24), 
                program2970(25), 
                program2971(26), 
                program2972(27), 
                program2973(28), 
                program2974(29), 
                program2975(30), 
                program2976(31), 
                program2977(32), 
                program2978(33), 
                program2979(34), 
                program2980(35), 
                program2981(36), 
                program2982(37), 
                program2983(38), 
                program2984(39), 
                program2985(40), 
                program2986(41), 
                program2987(42), 
                program2988(43), 
                program2989(44), 
                program2990(45), 
                program2991(46), 
                program2992(47), 
                program2993(48), 
                program2994(49), 
                program2995(50), 
                program2996(51), 
                program2997(52), 
                program2998(53), 
                program2999(54), 
                program3000(55), 
                program3001(56), 
                program3002(57), 
                program3003(58), 
                program3004(59), 
                program3005(60), 
                program3006(61), 
                program3007(62), 
                program3008(63), 
                program3009(64), 
                program3010(65), 
                program3011(66), 
                program3012(67), 
                program3013(68), 
                program3014(69), 
                program3015(70), 
                program3016(71), 
                program3017(72), 
                program3018(73), 
                program3019(74), 
                program3020(75), 
                program3021(76), 
                program3022(77), 
                program3023(78), 
                program3024(79), 
                program3025(80), 
                program3026(81), 
                program3027(82), 
                program3028(83), 
                program3029(84), 
                program3030(85), 
                program3031(86), 
                program3032(87), 
                program3033(88), 
                program3034(89), 
                program3035(90), 
                program3036(91), 
                program3037(92), 
                program3038(93), 
                program3039(94), 
                program3040(95), 
                program3041(96), 
                program3042(97), 
                program3043(98), 
                program3044(99), 
                program3045(100),
                program3046(101),
                program3047(102),
                program3048(103),
                program3049(104),
                program3050(105),
                program3051(106),
                program3052(107),
                program3053(108),
                program3054(109),
                program3055(110),
                program3056(111),
                program3057(112),
                program3058(113),
                program3059(114),
                program3060(115),
                program3061(116),
                program3062(117),
                program3063(118),
                program3064(119),
                program3065(120),
                program3066(121),
                program3067(122),
                program3068(123),
                program3069(124),
                program3070(125),
                program3071(126),
                program3072(127) 
                }
            MAX-ACCESS read-only
            STATUS current
            DESCRIPTION
                "Indicates the program mask of a multicast VLAN. It indicates the 128 multicast 
                 programs after the preceding leaf. The bit meanings are the same as the preceding leaf.
                "
            ::= { hwDslamNtvMVLANEntry 39 }                        
            
        hwDslamNtvMVLANProgramMask25 OBJECT-TYPE
            SYNTAX BITS
                {
                program3073(0),  
                program3074(1),  
                program3075(2),  
                program3076(3),  
                program3077(4),  
                program3078(5),  
                program3079(6),  
                program3080(7),  
                program3081(8),  
                program3082(9),  
                program3083(10), 
                program3084(11), 
                program3085(12), 
                program3086(13), 
                program3087(14), 
                program3088(15), 
                program3089(16), 
                program3090(17), 
                program3091(18), 
                program3092(19), 
                program3093(20), 
                program3094(21), 
                program3095(22), 
                program3096(23), 
                program3097(24), 
                program3098(25), 
                program3099(26), 
                program3100(27), 
                program3101(28), 
                program3102(29), 
                program3103(30), 
                program3104(31), 
                program3105(32), 
                program3106(33), 
                program3107(34), 
                program3108(35), 
                program3109(36), 
                program3110(37), 
                program3111(38), 
                program3112(39), 
                program3113(40), 
                program3114(41), 
                program3115(42), 
                program3116(43), 
                program3117(44), 
                program3118(45), 
                program3119(46), 
                program3120(47), 
                program3121(48), 
                program3122(49), 
                program3123(50), 
                program3124(51), 
                program3125(52), 
                program3126(53), 
                program3127(54), 
                program3128(55), 
                program3129(56), 
                program3130(57), 
                program3131(58), 
                program3132(59), 
                program3133(60), 
                program3134(61), 
                program3135(62), 
                program3136(63), 
                program3137(64), 
                program3138(65), 
                program3139(66), 
                program3140(67), 
                program3141(68), 
                program3142(69), 
                program3143(70), 
                program3144(71), 
                program3145(72), 
                program3146(73), 
                program3147(74), 
                program3148(75), 
                program3149(76), 
                program3150(77), 
                program3151(78), 
                program3152(79), 
                program3153(80), 
                program3154(81), 
                program3155(82), 
                program3156(83), 
                program3157(84), 
                program3158(85), 
                program3159(86), 
                program3160(87), 
                program3161(88), 
                program3162(89), 
                program3163(90), 
                program3164(91), 
                program3165(92), 
                program3166(93), 
                program3167(94), 
                program3168(95), 
                program3169(96), 
                program3170(97), 
                program3171(98), 
                program3172(99), 
                program3173(100),
                program3174(101),
                program3175(102),
                program3176(103),
                program3177(104),
                program3178(105),
                program3179(106),
                program3180(107),
                program3181(108),
                program3182(109),
                program3183(110),
                program3184(111),
                program3185(112),
                program3186(113),
                program3187(114),
                program3188(115),
                program3189(116),
                program3190(117),
                program3191(118),
                program3192(119),
                program3193(120),
                program3194(121),
                program3195(122),
                program3196(123),
                program3197(124),
                program3198(125),
                program3199(126),
                program3200(127) 
                }
            MAX-ACCESS read-only
            STATUS current
            DESCRIPTION
                "Indicates the program mask of a multicast VLAN. It indicates the 128 multicast 
                 programs after the preceding leaf. The bit meanings are the same as the preceding leaf.
                "
            ::= { hwDslamNtvMVLANEntry 40 }                        
            
        hwDslamNtvMVLANProgramMask26 OBJECT-TYPE
            SYNTAX BITS
                {
                program3201(0),  
                program3202(1),  
                program3203(2),  
                program3204(3),  
                program3205(4),  
                program3206(5),  
                program3207(6),  
                program3208(7),  
                program3209(8),  
                program3210(9),  
                program3211(10), 
                program3212(11), 
                program3213(12), 
                program3214(13), 
                program3215(14), 
                program3216(15), 
                program3217(16), 
                program3218(17), 
                program3219(18), 
                program3220(19), 
                program3221(20), 
                program3222(21), 
                program3223(22), 
                program3224(23), 
                program3225(24), 
                program3226(25), 
                program3227(26), 
                program3228(27), 
                program3229(28), 
                program3230(29), 
                program3231(30), 
                program3232(31), 
                program3233(32), 
                program3234(33), 
                program3235(34), 
                program3236(35), 
                program3237(36), 
                program3238(37), 
                program3239(38), 
                program3240(39), 
                program3241(40), 
                program3242(41), 
                program3243(42), 
                program3244(43), 
                program3245(44), 
                program3246(45), 
                program3247(46), 
                program3248(47), 
                program3249(48), 
                program3250(49), 
                program3251(50), 
                program3252(51), 
                program3253(52), 
                program3254(53), 
                program3255(54), 
                program3256(55), 
                program3257(56), 
                program3258(57), 
                program3259(58), 
                program3260(59), 
                program3261(60), 
                program3262(61), 
                program3263(62), 
                program3264(63), 
                program3265(64), 
                program3266(65), 
                program3267(66), 
                program3268(67), 
                program3269(68), 
                program3270(69), 
                program3271(70), 
                program3272(71), 
                program3273(72), 
                program3274(73), 
                program3275(74), 
                program3276(75), 
                program3277(76), 
                program3278(77), 
                program3279(78), 
                program3280(79), 
                program3281(80), 
                program3282(81), 
                program3283(82), 
                program3284(83), 
                program3285(84), 
                program3286(85), 
                program3287(86), 
                program3288(87), 
                program3289(88), 
                program3290(89), 
                program3291(90), 
                program3292(91), 
                program3293(92), 
                program3294(93), 
                program3295(94), 
                program3296(95), 
                program3297(96), 
                program3298(97), 
                program3299(98), 
                program3300(99), 
                program3301(100),
                program3302(101),
                program3303(102),
                program3304(103),
                program3305(104),
                program3306(105),
                program3307(106),
                program3308(107),
                program3309(108),
                program3310(109),
                program3311(110),
                program3312(111),
                program3313(112),
                program3314(113),
                program3315(114),
                program3316(115),
                program3317(116),
                program3318(117),
                program3319(118),
                program3320(119),
                program3321(120),
                program3322(121),
                program3323(122),
                program3324(123),
                program3325(124),
                program3326(125),
                program3327(126),
                program3328(127) 
                }
            MAX-ACCESS read-only
            STATUS current
            DESCRIPTION
                "Indicates the program mask of a multicast VLAN. It indicates the 128 multicast 
                 programs after the preceding leaf. The bit meanings are the same as the preceding leaf.
                "
            ::= { hwDslamNtvMVLANEntry 41 }                        
            
        hwDslamNtvMVLANProgramMask27 OBJECT-TYPE
            SYNTAX BITS
                {
                program3329(0),  
                program3330(1),  
                program3331(2),  
                program3332(3),  
                program3333(4),  
                program3334(5),  
                program3335(6),  
                program3336(7),  
                program3337(8),  
                program3338(9),  
                program3339(10), 
                program3340(11), 
                program3341(12), 
                program3342(13), 
                program3343(14), 
                program3344(15), 
                program3345(16), 
                program3346(17), 
                program3347(18), 
                program3348(19), 
                program3349(20), 
                program3350(21), 
                program3351(22), 
                program3352(23), 
                program3353(24), 
                program3354(25), 
                program3355(26), 
                program3356(27), 
                program3357(28), 
                program3358(29), 
                program3359(30), 
                program3360(31), 
                program3361(32), 
                program3362(33), 
                program3363(34), 
                program3364(35), 
                program3365(36), 
                program3366(37), 
                program3367(38), 
                program3368(39), 
                program3369(40), 
                program3370(41), 
                program3371(42), 
                program3372(43), 
                program3373(44), 
                program3374(45), 
                program3375(46), 
                program3376(47), 
                program3377(48), 
                program3378(49), 
                program3379(50), 
                program3380(51), 
                program3381(52), 
                program3382(53), 
                program3383(54), 
                program3384(55), 
                program3385(56), 
                program3386(57), 
                program3387(58), 
                program3388(59), 
                program3389(60), 
                program3390(61), 
                program3391(62), 
                program3392(63), 
                program3393(64), 
                program3394(65), 
                program3395(66), 
                program3396(67), 
                program3397(68), 
                program3398(69), 
                program3399(70), 
                program3400(71), 
                program3401(72), 
                program3402(73), 
                program3403(74), 
                program3404(75), 
                program3405(76), 
                program3406(77), 
                program3407(78), 
                program3408(79), 
                program3409(80), 
                program3410(81), 
                program3411(82), 
                program3412(83), 
                program3413(84), 
                program3414(85), 
                program3415(86), 
                program3416(87), 
                program3417(88), 
                program3418(89), 
                program3419(90), 
                program3420(91), 
                program3421(92), 
                program3422(93), 
                program3423(94), 
                program3424(95), 
                program3425(96), 
                program3426(97), 
                program3427(98), 
                program3428(99), 
                program3429(100),
                program3430(101),
                program3431(102),
                program3432(103),
                program3433(104),
                program3434(105),
                program3435(106),
                program3436(107),
                program3437(108),
                program3438(109),
                program3439(110),
                program3440(111),
                program3441(112),
                program3442(113),
                program3443(114),
                program3444(115),
                program3445(116),
                program3446(117),
                program3447(118),
                program3448(119),
                program3449(120),
                program3450(121),
                program3451(122),
                program3452(123),
                program3453(124),
                program3454(125),
                program3455(126),
                program3456(127) 
                }
            MAX-ACCESS read-only
            STATUS current
            DESCRIPTION
                "Indicates the program mask of a multicast VLAN. It indicates the 128 multicast 
                 programs after the preceding leaf. The bit meanings are the same as the preceding leaf.
                "
            ::= { hwDslamNtvMVLANEntry 42 }                        
            
        hwDslamNtvMVLANProgramMask28 OBJECT-TYPE
            SYNTAX BITS
                {
                program3457(0),  
                program3458(1),  
                program3459(2),  
                program3460(3),  
                program3461(4),  
                program3462(5),  
                program3463(6),  
                program3464(7),  
                program3465(8),  
                program3466(9),  
                program3467(10), 
                program3468(11), 
                program3469(12), 
                program3470(13), 
                program3471(14), 
                program3472(15), 
                program3473(16), 
                program3474(17), 
                program3475(18), 
                program3476(19), 
                program3477(20), 
                program3478(21), 
                program3479(22), 
                program3480(23), 
                program3481(24), 
                program3482(25), 
                program3483(26), 
                program3484(27), 
                program3485(28), 
                program3486(29), 
                program3487(30), 
                program3488(31), 
                program3489(32), 
                program3490(33), 
                program3491(34), 
                program3492(35), 
                program3493(36), 
                program3494(37), 
                program3495(38), 
                program3496(39), 
                program3497(40), 
                program3498(41), 
                program3499(42), 
                program3500(43), 
                program3501(44), 
                program3502(45), 
                program3503(46), 
                program3504(47), 
                program3505(48), 
                program3506(49), 
                program3507(50), 
                program3508(51), 
                program3509(52), 
                program3510(53), 
                program3511(54), 
                program3512(55), 
                program3513(56), 
                program3514(57), 
                program3515(58), 
                program3516(59), 
                program3517(60), 
                program3518(61), 
                program3519(62), 
                program3520(63), 
                program3521(64), 
                program3522(65), 
                program3523(66), 
                program3524(67), 
                program3525(68), 
                program3526(69), 
                program3527(70), 
                program3528(71), 
                program3529(72), 
                program3530(73), 
                program3531(74), 
                program3532(75), 
                program3533(76), 
                program3534(77), 
                program3535(78), 
                program3536(79), 
                program3537(80), 
                program3538(81), 
                program3539(82), 
                program3540(83), 
                program3541(84), 
                program3542(85), 
                program3543(86), 
                program3544(87), 
                program3545(88), 
                program3546(89), 
                program3547(90), 
                program3548(91), 
                program3549(92), 
                program3550(93), 
                program3551(94), 
                program3552(95), 
                program3553(96), 
                program3554(97), 
                program3555(98), 
                program3556(99), 
                program3557(100),
                program3558(101),
                program3559(102),
                program3560(103),
                program3561(104),
                program3562(105),
                program3563(106),
                program3564(107),
                program3565(108),
                program3566(109),
                program3567(110),
                program3568(111),
                program3569(112),
                program3570(113),
                program3571(114),
                program3572(115),
                program3573(116),
                program3574(117),
                program3575(118),
                program3576(119),
                program3577(120),
                program3578(121),
                program3579(122),
                program3580(123),
                program3581(124),
                program3582(125),
                program3583(126),
                program3584(127) 
                }
            MAX-ACCESS read-only
            STATUS current
            DESCRIPTION
                "Indicates the program mask of a multicast VLAN. It indicates the 128 multicast 
                 programs after the preceding leaf. The bit meanings are the same as the preceding leaf.
                "
            ::= { hwDslamNtvMVLANEntry 43 }                        
            
        hwDslamNtvMVLANProgramMask29 OBJECT-TYPE
            SYNTAX BITS
                {
                program3585(0),  
                program3586(1),  
                program3587(2),  
                program3588(3),  
                program3589(4),  
                program3590(5),  
                program3591(6),  
                program3592(7),  
                program3593(8),  
                program3594(9),  
                program3595(10), 
                program3596(11), 
                program3597(12), 
                program3598(13), 
                program3599(14), 
                program3600(15), 
                program3601(16), 
                program3602(17), 
                program3603(18), 
                program3604(19), 
                program3605(20), 
                program3606(21), 
                program3607(22), 
                program3608(23), 
                program3609(24), 
                program3610(25), 
                program3611(26), 
                program3612(27), 
                program3613(28), 
                program3614(29), 
                program3615(30), 
                program3616(31), 
                program3617(32), 
                program3618(33), 
                program3619(34), 
                program3620(35), 
                program3621(36), 
                program3622(37), 
                program3623(38), 
                program3624(39), 
                program3625(40), 
                program3626(41), 
                program3627(42), 
                program3628(43), 
                program3629(44), 
                program3630(45), 
                program3631(46), 
                program3632(47), 
                program3633(48), 
                program3634(49), 
                program3635(50), 
                program3636(51), 
                program3637(52), 
                program3638(53), 
                program3639(54), 
                program3640(55), 
                program3641(56), 
                program3642(57), 
                program3643(58), 
                program3644(59), 
                program3645(60), 
                program3646(61), 
                program3647(62), 
                program3648(63), 
                program3649(64), 
                program3650(65), 
                program3651(66), 
                program3652(67), 
                program3653(68), 
                program3654(69), 
                program3655(70), 
                program3656(71), 
                program3657(72), 
                program3658(73), 
                program3659(74), 
                program3660(75), 
                program3661(76), 
                program3662(77), 
                program3663(78), 
                program3664(79), 
                program3665(80), 
                program3666(81), 
                program3667(82), 
                program3668(83), 
                program3669(84), 
                program3670(85), 
                program3671(86), 
                program3672(87), 
                program3673(88), 
                program3674(89), 
                program3675(90), 
                program3676(91), 
                program3677(92), 
                program3678(93), 
                program3679(94), 
                program3680(95), 
                program3681(96), 
                program3682(97), 
                program3683(98), 
                program3684(99), 
                program3685(100),
                program3686(101),
                program3687(102),
                program3688(103),
                program3689(104),
                program3690(105),
                program3691(106),
                program3692(107),
                program3693(108),
                program3694(109),
                program3695(110),
                program3696(111),
                program3697(112),
                program3698(113),
                program3699(114),
                program3700(115),
                program3701(116),
                program3702(117),
                program3703(118),
                program3704(119),
                program3705(120),
                program3706(121),
                program3707(122),
                program3708(123),
                program3709(124),
                program3710(125),
                program3711(126),
                program3712(127) 
                }
            MAX-ACCESS read-only
            STATUS current
            DESCRIPTION
                "Indicates the program mask of a multicast VLAN. It indicates the 128 multicast 
                 programs after the preceding leaf. The bit meanings are the same as the preceding leaf.
                "
            ::= { hwDslamNtvMVLANEntry 44 }                        
            
        hwDslamNtvMVLANProgramMask30 OBJECT-TYPE
            SYNTAX BITS
                {
                program3713(0),  
                program3714(1),  
                program3715(2),  
                program3716(3),  
                program3717(4),  
                program3718(5),  
                program3719(6),  
                program3720(7),  
                program3721(8),  
                program3722(9),  
                program3723(10), 
                program3724(11), 
                program3725(12), 
                program3726(13), 
                program3727(14), 
                program3728(15), 
                program3729(16), 
                program3730(17), 
                program3731(18), 
                program3732(19), 
                program3733(20), 
                program3734(21), 
                program3735(22), 
                program3736(23), 
                program3737(24), 
                program3738(25), 
                program3739(26), 
                program3740(27), 
                program3741(28), 
                program3742(29), 
                program3743(30), 
                program3744(31), 
                program3745(32), 
                program3746(33), 
                program3747(34), 
                program3748(35), 
                program3749(36), 
                program3750(37), 
                program3751(38), 
                program3752(39), 
                program3753(40), 
                program3754(41), 
                program3755(42), 
                program3756(43), 
                program3757(44), 
                program3758(45), 
                program3759(46), 
                program3760(47), 
                program3761(48), 
                program3762(49), 
                program3763(50), 
                program3764(51), 
                program3765(52), 
                program3766(53), 
                program3767(54), 
                program3768(55), 
                program3769(56), 
                program3770(57), 
                program3771(58), 
                program3772(59), 
                program3773(60), 
                program3774(61), 
                program3775(62), 
                program3776(63), 
                program3777(64), 
                program3778(65), 
                program3779(66), 
                program3780(67), 
                program3781(68), 
                program3782(69), 
                program3783(70), 
                program3784(71), 
                program3785(72), 
                program3786(73), 
                program3787(74), 
                program3788(75), 
                program3789(76), 
                program3790(77), 
                program3791(78), 
                program3792(79), 
                program3793(80), 
                program3794(81), 
                program3795(82), 
                program3796(83), 
                program3797(84), 
                program3798(85), 
                program3799(86), 
                program3800(87), 
                program3801(88), 
                program3802(89), 
                program3803(90), 
                program3804(91), 
                program3805(92), 
                program3806(93), 
                program3807(94), 
                program3808(95), 
                program3809(96), 
                program3810(97), 
                program3811(98), 
                program3812(99), 
                program3813(100),
                program3814(101),
                program3815(102),
                program3816(103),
                program3817(104),
                program3818(105),
                program3819(106),
                program3820(107),
                program3821(108),
                program3822(109),
                program3823(110),
                program3824(111),
                program3825(112),
                program3826(113),
                program3827(114),
                program3828(115),
                program3829(116),
                program3830(117),
                program3831(118),
                program3832(119),
                program3833(120),
                program3834(121),
                program3835(122),
                program3836(123),
                program3837(124),
                program3838(125),
                program3839(126),
                program3840(127) 
                }
            MAX-ACCESS read-only
            STATUS current
            DESCRIPTION
                "Indicates the program mask of a multicast VLAN. It indicates the 128 multicast 
                 programs after the preceding leaf. The bit meanings are the same as the preceding leaf.
                "
            ::= { hwDslamNtvMVLANEntry 45 }                        
            
        hwDslamNtvMVLANProgramMask31 OBJECT-TYPE
            SYNTAX BITS
                {
                program3841(0),  
                program3842(1),  
                program3843(2),  
                program3844(3),  
                program3845(4),  
                program3846(5),  
                program3847(6),  
                program3848(7),  
                program3849(8),  
                program3850(9),  
                program3851(10), 
                program3852(11), 
                program3853(12), 
                program3854(13), 
                program3855(14), 
                program3856(15), 
                program3857(16), 
                program3858(17), 
                program3859(18), 
                program3860(19), 
                program3861(20), 
                program3862(21), 
                program3863(22), 
                program3864(23), 
                program3865(24), 
                program3866(25), 
                program3867(26), 
                program3868(27), 
                program3869(28), 
                program3870(29), 
                program3871(30), 
                program3872(31), 
                program3873(32), 
                program3874(33), 
                program3875(34), 
                program3876(35), 
                program3877(36), 
                program3878(37), 
                program3879(38), 
                program3880(39), 
                program3881(40), 
                program3882(41), 
                program3883(42), 
                program3884(43), 
                program3885(44), 
                program3886(45), 
                program3887(46), 
                program3888(47), 
                program3889(48), 
                program3890(49), 
                program3891(50), 
                program3892(51), 
                program3893(52), 
                program3894(53), 
                program3895(54), 
                program3896(55), 
                program3897(56), 
                program3898(57), 
                program3899(58), 
                program3900(59), 
                program3901(60), 
                program3902(61), 
                program3903(62), 
                program3904(63), 
                program3905(64), 
                program3906(65), 
                program3907(66), 
                program3908(67), 
                program3909(68), 
                program3910(69), 
                program3911(70), 
                program3912(71), 
                program3913(72), 
                program3914(73), 
                program3915(74), 
                program3916(75), 
                program3917(76), 
                program3918(77), 
                program3919(78), 
                program3920(79), 
                program3921(80), 
                program3922(81), 
                program3923(82), 
                program3924(83), 
                program3925(84), 
                program3926(85), 
                program3927(86), 
                program3928(87), 
                program3929(88), 
                program3930(89), 
                program3931(90), 
                program3932(91), 
                program3933(92), 
                program3934(93), 
                program3935(94), 
                program3936(95), 
                program3937(96), 
                program3938(97), 
                program3939(98), 
                program3940(99), 
                program3941(100),
                program3942(101),
                program3943(102),
                program3944(103),
                program3945(104),
                program3946(105),
                program3947(106),
                program3948(107),
                program3949(108),
                program3950(109),
                program3951(110),
                program3952(111),
                program3953(112),
                program3954(113),
                program3955(114),
                program3956(115),
                program3957(116),
                program3958(117),
                program3959(118),
                program3960(119),
                program3961(120),
                program3962(121),
                program3963(122),
                program3964(123),
                program3965(124),
                program3966(125),
                program3967(126),
                program3968(127)
                }
            MAX-ACCESS read-only
            STATUS current
            DESCRIPTION
                "Indicates the program mask of a multicast VLAN. It indicates the 128 multicast 
                 programs after the preceding leaf. The bit meanings are the same as the preceding leaf.
                "
            ::= { hwDslamNtvMVLANEntry 46 }                        
            
        hwDslamNtvMVLANProgramMask32 OBJECT-TYPE
            SYNTAX BITS
                {
                program3969(0),  
                program3970(1),  
                program3971(2),  
                program3972(3),  
                program3973(4),  
                program3974(5),  
                program3975(6),  
                program3976(7),  
                program3977(8),  
                program3978(9),  
                program3979(10), 
                program3980(11), 
                program3981(12), 
                program3982(13), 
                program3983(14), 
                program3984(15), 
                program3985(16), 
                program3986(17), 
                program3987(18), 
                program3988(19), 
                program3989(20), 
                program3990(21), 
                program3991(22), 
                program3992(23), 
                program3993(24), 
                program3994(25), 
                program3995(26), 
                program3996(27), 
                program3997(28), 
                program3998(29), 
                program3999(30), 
                program4000(31),
                program4001(32), 
                program4002(33), 
                program4003(34), 
                program4004(35), 
                program4005(36), 
                program4006(37), 
                program4007(38), 
                program4008(39), 
                program4009(40), 
                program4010(41), 
                program4011(42), 
                program4012(43), 
                program4013(44), 
                program4014(45), 
                program4015(46), 
                program4016(47), 
                program4017(48), 
                program4018(49), 
                program4019(50), 
                program4020(51), 
                program4021(52), 
                program4022(53), 
                program4023(54), 
                program4024(55), 
                program4025(56), 
                program4026(57), 
                program4027(58), 
                program4028(59), 
                program4029(60), 
                program4030(61), 
                program4031(62), 
                program4032(63), 
                program4033(64), 
                program4034(65), 
                program4035(66), 
                program4036(67), 
                program4037(68), 
                program4038(69), 
                program4039(70), 
                program4040(71), 
                program4041(72), 
                program4042(73), 
                program4043(74), 
                program4044(75), 
                program4045(76), 
                program4046(77), 
                program4047(78), 
                program4048(79), 
                program4049(80), 
                program4050(81), 
                program4051(82), 
                program4052(83), 
                program4053(84), 
                program4054(85), 
                program4055(86), 
                program4056(87), 
                program4057(88), 
                program4058(89), 
                program4059(90), 
                program4060(91), 
                program4061(92), 
                program4062(93), 
                program4063(94), 
                program4064(95), 
                program4065(96), 
                program4066(97), 
                program4067(98), 
                program4068(99), 
                program4069(100),
                program4070(101),
                program4071(102),
                program4072(103),
                program4073(104),
                program4074(105),
                program4075(106),
                program4076(107),
                program4077(108),
                program4078(109),
                program4079(110),
                program4080(111),
                program4081(112),
                program4082(113),
                program4083(114),
                program4084(115),
                program4085(116),
                program4086(117),
                program4087(118),
                program4088(119),
                program4089(120),
                program4090(121),
                program4091(122),
                program4092(123),
                program4093(124),
                program4094(125),
                program4095(126),
                program4096(127)                  
                }
            MAX-ACCESS read-only
            STATUS current
            DESCRIPTION
                "Indicates the program mask of a multicast VLAN. It indicates the 128 multicast 
                 programs after the preceding leaf. The bit meanings are the same as the preceding leaf.
                "
            ::= { hwDslamNtvMVLANEntry 47 }                                                                                                                                                                                                                                                                                                                            

        hwDslamNtvMVlANInnerVlan  OBJECT-TYPE
            SYNTAX     Integer32(1..4095)
            MAX-ACCESS   read-write
            STATUS       current
            DESCRIPTION
                "Indicates the inner VLAN of a multicast VLAN. 
                 Range: 1-4095 
                 Default: 1
                "
            ::= { hwDslamNtvMVLANEntry 48 }
      
        hwDslamNtvMvlanVideoMode OBJECT-TYPE
            SYNTAX INTEGER{ multicast(1),unicast(2)}
            MAX-ACCESS read-write
            STATUS current
            DESCRIPTION
                "Indicates the duplication mode of a multicast VLAN. 
                 Options:
                 1. multicast(1) -indicates the duplication mode is multicast.
                 2. unicast(2)   -indicates the duplication mode is unicast.
                 Default: multicast(1)
                "
            DEFVAL { 1 }
            ::= { hwDslamNtvMVLANEntry 49 }

        hwDslamNtvMVLANIgmpQueryInterval OBJECT-TYPE
            SYNTAX Integer32 (-1|30..5000)
            MAX-ACCESS read-write
            STATUS current
            DESCRIPTION
                "Indicates the general query interval of query message in multicast VLAN.
                 When the value is -1, the query interval will be the global configuration.
                 If the MVLAN general query interval is not configured, the returned value 
                 for hwDslamNtvMVLANIgmpQueryInterval is -1.
                "
            DEFVAL { -1 }
            ::= { hwDslamNtvMVLANEntry 50 }

        hwDslamNtvMVLANIgmpV2QueryMaxResponseTime OBJECT-TYPE
            SYNTAX       Integer32 (-1|1..255)
            MAX-ACCESS   read-write
            STATUS       current
            DESCRIPTION
                "Indicates the maximum response time for general query message in multicast VLAN,
                 whose version is IGMP v2.
                 When the value is -1, the max response time will be the global configuration.
                "
            DEFVAL { -1 }
            ::= { hwDslamNtvMVLANEntry 51 }

        hwDslamNtvMVLANIgmpV3QueryMaxResponseTime OBJECT-TYPE
            SYNTAX       Integer32 (-1|1..31744)
            MAX-ACCESS   read-write
            STATUS       current
            DESCRIPTION
                "Indicates the maximum response time for general query message in multicast VLAN,
                 whose version is IGMP v3.
                 When the value is -1, the max response time will be the global configuration.
                "
            DEFVAL { -1 }
            ::= { hwDslamNtvMVLANEntry 52 }

        hwDslamNtvMVLANIgmpRobustness OBJECT-TYPE
            SYNTAX       Integer32 (-1|1..10)
            MAX-ACCESS   read-write
            STATUS       current
            DESCRIPTION
                "Indicates the robustness for query message in multicast VLAN.
                 When the value is -1, the robustness will be the global configuration.
                "
            DEFVAL { -1 }
            ::= { hwDslamNtvMVLANEntry 53 }

        hwDslamNtvMVLANIgmpLastMemberQueryInterval OBJECT-TYPE
            SYNTAX       Integer32 (-1|1..50000)
            MAX-ACCESS   read-write
            STATUS       current
            DESCRIPTION
                "Indicates the special query interval of query message in multicast VLAN.
                 When the value is -1, the query interval will be the global configuration.
                "
            DEFVAL { -1 }
            ::= { hwDslamNtvMVLANEntry 54 }

        hwDslamNtvMVLANIgmpV2LastMemberQueryResponse OBJECT-TYPE
            SYNTAX       Integer32 (-1|1..255)
            MAX-ACCESS   read-write
            STATUS       current
            DESCRIPTION
                "Indicates the maximum response time for special query message in multicast VLAN,
                 whose version is IGMP v2.
                 When the value is -1, the max response time will be the global configuration.
                "
            DEFVAL { -1 }
            ::= { hwDslamNtvMVLANEntry 55 }

        hwDslamNtvMVLANIgmpV3LastMemberQueryResponse OBJECT-TYPE
            SYNTAX       Integer32 (-1|1..31744)
            MAX-ACCESS   read-write
            STATUS       current
            DESCRIPTION
                "Indicates the maximum response time for special query message in multicast VLAN,
                 whose version is IGMP v3.
                 When the value is -1, the max response time will be the global configuration.
                "
            DEFVAL { -1 }
            ::= { hwDslamNtvMVLANEntry 56 }

        hwDslamNtvMVLANIgmpLastMemberQueryCount OBJECT-TYPE
            SYNTAX       Integer32 (-1|1..10)
            MAX-ACCESS   read-write
            STATUS       current
            DESCRIPTION
                "Indicates the special query times of query message in multicast VLAN.
                 When the value is -1, the query times will be the global configuration.
                "
            DEFVAL { -1 }
            ::= { hwDslamNtvMVLANEntry 57 }

        hwDslamNtvMVLANIgmpV2RouterTimerout OBJECT-TYPE
            SYNTAX       Integer32 (-1|1..5000)
            MAX-ACCESS   read-write
            STATUS       current
            DESCRIPTION
                "Indicates the max timeout for igmp version 2.
                 When the value is -1, the max timeout will be the global configuration.
                "
            DEFVAL { -1 }
            ::= { hwDslamNtvMVLANEntry 58 }

        hwDslamNtvMVLANIgmpInitialUnsolicitedReportInterval OBJECT-TYPE
            SYNTAX       Integer32 (-1|1..10)
            MAX-ACCESS   read-write
            STATUS       current
            DESCRIPTION
                "Indicates the initial unsolicited report interval of user.
                 When the value is -1, the report interval will be the global configuration.
                "
            DEFVAL { -1 }
            ::= { hwDslamNtvMVLANEntry 59 }
            
        hwDslamNtvMVLANSnoopingQueryProxy OBJECT-TYPE
            SYNTAX  INTEGER{enable(1),disable(2)}
            MAX-ACCESS read-write
            STATUS current
            DESCRIPTION
                "Enables or disables the transmission of the query packet in the IGMP snooping mode.
                 Options:
                 1. enable(1)  -enable the transmission of the query packet in the IGMP snooping mode.
                 2. disable(2) -disable the transmission of the query packet in the IGMP snooping mode.
                 Default: enable(1)
                "
            DEFVAL { 1 }
            ::= { hwDslamNtvMVLANEntry 60 }
            
        hwDslamNtvMVLANGroupFilterMode OBJECT-TYPE
            SYNTAX  INTEGER 
                {
                asmOnly(1),
                ssmOnly(2),
                asmSsm(3)
                }
            MAX-ACCESS read-write
            STATUS current
            DESCRIPTION
                "Indicates the IGMP group filter mode. 
                 Options:
                 1. asmOnly(1) -indicates that the group filter mode is asm-only.
                 2. ssmOnly(2) -indicates that the group filter mode is ssm-only.
                 3. asmSsm(3)  -indicates that the group filter mode is asm-ssm.
                 Default: asmSsm(3)
                "
            DEFVAL { 3 }
            ::= { hwDslamNtvMVLANEntry 61 } 
            
        hwDslamNtvMVLANDualPwSwitch OBJECT-TYPE
            SYNTAX  INTEGER
                { 
                enable(1),
                disable(2)
                }
            MAX-ACCESS read-write
            STATUS current
            DESCRIPTION
                "Enables or disables the dual-pw switch in multicast-vlan.
                 Options:
                 1. enable(1)  -enable the dual-pw switch in multicast-vlan.
                 2. disable(2) -disable the dual-pw switch in multicast-vlan.
                 Default: disable(2)
                "
            DEFVAL { 2 }
            ::= { hwDslamNtvMVLANEntry 62 } 

        hwDslamNtvMVLANMldVer OBJECT-TYPE
            SYNTAX INTEGER
                { 
                mldV1(1),
                mldV2(2)
                }
            MAX-ACCESS read-write
            STATUS current
            DESCRIPTION
                "Indicates the MLD version. 
                 Options:
                 1. mldV1(1) -indicates the MLD version is V1
                 2. mldV2(2) -indicates the MLD version is V2
                 Default: mldV2(2)
                "
            DEFVAL { 2 }
            ::= { hwDslamNtvMVLANEntry 63 }

        hwDslamNtvMVLANMldUnsoliReportTime OBJECT-TYPE
            SYNTAX Integer32 (10..5000)
            UNITS "second"
            MAX-ACCESS read-write
            STATUS current
            DESCRIPTION
                "Indicates the interval for a user to actively report MLD packets.                   
                 Range: 10-5000 
                 Default: 10
                 Unit: second
                "
            DEFVAL { 10 }
            ::= { hwDslamNtvMVLANEntry 64 }

        hwDslamNtvMVLANMldPriority OBJECT-TYPE
            SYNTAX Integer32 (0..7)
            MAX-ACCESS read-write
            STATUS current
            DESCRIPTION
                "Sets the priority of MLD packets based on a multicast VLAN. 
                 Range: 0-7 
                 Default: 6
                "
            DEFVAL { 6 }
            ::= { hwDslamNtvMVLANEntry 65 }

        hwDslamNtvMVLANMldMode OBJECT-TYPE
            SYNTAX INTEGER
                {
                mldProxy(1),
                mldSnooping(2),
                tvOff(3)
                }
            MAX-ACCESS read-write
            STATUS current
            DESCRIPTION
                "Indicates the MLD working mode. 
                 Options:
                 1. mldProxy(1)    -indicates the MLD working mode is mldProxy
                 2. mldSnooping(2) -indicates the MLD working mode is mldSnooping
                 3. tvOff(3)       -indicates the MLD working mode is tvOff
                 Default: tvOff(3)
                "
            DEFVAL { 3 }
            ::= { hwDslamNtvMVLANEntry 66 }

        hwDslamNtvMVLANMldMatchMode OBJECT-TYPE
            SYNTAX INTEGER
                {
                enable(1),
                disable(2)
                }
            MAX-ACCESS read-write
            STATUS current
            DESCRIPTION
                "Indicates the program matching mode. 
                 Options:
                 1. enable(1)  -indicates the program matching mode is enabled
                 2. disable(2) -indicates the program matching mode is disabled
                 Default: enable(1)
                "
            DEFVAL { 1 }
            ::= { hwDslamNtvMVLANEntry 67 }

        hwDslamNtvMVLANMldSnoopingReportSwitch OBJECT-TYPE
            SYNTAX INTEGER
                {
                enable(1),
                disable(2)
                }
            MAX-ACCESS read-write
            STATUS current
            DESCRIPTION
                "Enables or disables the transmission of the report packet in the MLD snooping mode.
                 Options:
                 1. enable(1)  -enable the transmission of the report packet in the MLD snooping mode
                 2. disable(2) -disable the transmission of the report packet in the MLD snooping mode
                 Default: disable(2)
                "
            DEFVAL { 2 }
            ::= { hwDslamNtvMVLANEntry 68 }

        hwDslamNtvMVLANMldSnoopingLeaveSwitch OBJECT-TYPE
            SYNTAX INTEGER
                {
                enable(1),
                disable(2)
                }
            MAX-ACCESS read-write
            STATUS current
            DESCRIPTION
                "Enables or disables the transmission of the leave packet in the MLD snooping mode.
                 Options:
                 1. enable(1)  -enable the transmission of the leave packet in the MLD snooping mode
                 2. disable(2) -disable the transmission of the leave packet in the MLD snooping mode
                 Default: disable(2)
                "
            DEFVAL { 2 }
            ::= { hwDslamNtvMVLANEntry 69 }

        hwDslamNtvMldQueryInterval OBJECT-TYPE
            SYNTAX Integer32 (30..5000)
            UNITS "second"
            MAX-ACCESS read-write
            STATUS current
            DESCRIPTION
                "Indicates the MLD general query interval.
                 Range: 30-5000 
                 Default: 125
                 Unit: second
                "
            DEFVAL { 125 }
            ::= { hwDslamNtvMVLANEntry 70 }

        hwDslamNtvMldV1QueryMaxResponseTime OBJECT-TYPE
            SYNTAX Integer32 (1..655)
            UNITS "0.1s"
            MAX-ACCESS read-write
            STATUS current
            DESCRIPTION
                "Indicates the maximum response time for general query message in MLD v1.
                 Range: 1-655
                 Default: 100
                 Unit: 0.1s
                "
            DEFVAL { 100 }
            ::= { hwDslamNtvMVLANEntry 71 }

        hwDslamNtvMldV2QueryMaxResponseTime OBJECT-TYPE
            SYNTAX Integer32 (1..50000)
            UNITS "0.1s"
            MAX-ACCESS read-write
            STATUS current
            DESCRIPTION
                "Indicates the maximum response time for general query message in MLD v2.
                 Range: 1-50000
                 Default: 100
                 Unit: 0.1s
                "
            DEFVAL { 100 }
            ::= { hwDslamNtvMVLANEntry 72 }

        hwDslamNtvMldRobustness OBJECT-TYPE
            SYNTAX Integer32 (1..10)
            MAX-ACCESS read-write
            STATUS current
            DESCRIPTION
                "Indicates the MLD robustness variable.
                 Range: 1-10
                 Default: 2
                "
            DEFVAL { 2 }
            ::= { hwDslamNtvMVLANEntry 73 }

        hwDslamNtvMVLANMldLastMemberQueryInterval OBJECT-TYPE
            SYNTAX Integer32 (1..50000)
            UNITS "0.1s"
            MAX-ACCESS read-write
            STATUS current
            DESCRIPTION
                "Indicates the MLD special query interval.
                 Range: 1-50000
                 Default: 10
                 Unit: 0.1s
                "
            DEFVAL { 10 }
            ::= { hwDslamNtvMVLANEntry 74 }

        hwDslamNtvMldV1LastMemberQueryResponse OBJECT-TYPE
            SYNTAX Integer32 (1..655)
            UNITS "0.1s"
            MAX-ACCESS read-write
            STATUS current
            DESCRIPTION
                "Indicates the maximum response time for special query message in MLD v1.
                 Range: 1-655
                 Default: 8
                 Unit: 0.1s
                "
            DEFVAL { 8 }
            ::= { hwDslamNtvMVLANEntry 75 }

        hwDslamNtvMldV2LastMemberQueryResponse OBJECT-TYPE
            SYNTAX Integer32 (1..50000)
            UNITS "0.1s"
            MAX-ACCESS read-write
            STATUS current
            DESCRIPTION
                "Indicates the maximum response time for special query message in MLD v2.
                 Range: 1-50000
                 Default: 8
                 Unit: 0.1s
                "
            DEFVAL { 8 }
            ::= { hwDslamNtvMVLANEntry 76 }

        hwDslamNtvMVLANMldLastMemberQueryCount OBJECT-TYPE
            SYNTAX Integer32 (1..10)
            MAX-ACCESS read-write
            STATUS current
            DESCRIPTION
                "Indicates the MLD group-specific query times.
                 Range: 1-10
                 Default: 2
                "
            DEFVAL { 2 }
            ::= { hwDslamNtvMVLANEntry 77 }

        hwDslamNtvMldInitialUnsolicitedReportInterval OBJECT-TYPE
            SYNTAX Integer32 (1..10)
            UNITS "second"
            MAX-ACCESS read-write
            STATUS current
            DESCRIPTION
                "Indicates the initial unsolicited report interval of MLD.
                 Range: 1-10
                 Default: 1
                 Unit: second
                "
            DEFVAL { 1 }
            ::= { hwDslamNtvMVLANEntry 78 }  
            
        hwDslamNtvMVLANIgmpDscpValue OBJECT-TYPE
            SYNTAX Integer32 (0..63)
            MAX-ACCESS read-write
            STATUS current
            DESCRIPTION
                "Indicates the DSCP value for IGMP package.
                 Range: 0-63
                 Default: 0
                "
            DEFVAL { 0 }
            ::= { hwDslamNtvMVLANEntry 79 }  
            
        hwDslamNtvMVLANMldDscpValue OBJECT-TYPE
            SYNTAX Integer32 (0..63)
            MAX-ACCESS read-write
            STATUS current
            DESCRIPTION
                "Indicates the DSCP value for MLD package.
                 Range: 0-63
                 Default: 0
                "
            DEFVAL { 0 }
            ::= { hwDslamNtvMVLANEntry 80 }

        hwDslamNtvFlowBasedMulticastPolicyTable OBJECT-TYPE
            SYNTAX SEQUENCE OF HwDslamNtvFlowBasedMulticastPolicyEntry
            MAX-ACCESS not-accessible
            STATUS current
            DESCRIPTION
                "Indicates the flow-based suppression policy of unknown multicast streams and processing mode of IGMP packets.
                 The index of this table is hwDslamNtvFlowID.
                "
            ::= { hwDslamNtv 77 }
   
        hwDslamNtvFlowBasedMulticastPolicyEntry OBJECT-TYPE
            SYNTAX HwDslamNtvFlowBasedMulticastPolicyEntry
            MAX-ACCESS not-accessible
            STATUS current
            DESCRIPTION
                   "Indicates the flow-based suppression policy of unknown multicast streams and processing mode of IGMP packets.
                    The index of this entry is hwDslamNtvFlowID.
                   "
            INDEX 
                { 
                hwDslamNtvFlowID
                }
            ::= { hwDslamNtvFlowBasedMulticastPolicyTable 1 }
   
        HwDslamNtvFlowBasedMulticastPolicyEntry ::= 
            SEQUENCE 
                {
                hwDslamNtvFlowID
                    Integer32,
                hwDslamNtvUnknownMulticastTrafficPolicy
                    INTEGER{ transparent(2),discard(3)},
                hwDslamNtvIgmpPacketPolicy 
                    INTEGER{ normal(1),transparent(2),discard(3)}
                }
         
        hwDslamNtvFlowID OBJECT-TYPE
            SYNTAX  Integer32 
            MAX-ACCESS read-write
            STATUS current
            DESCRIPTION
                "Indicates the service flow ID. Its value and algorithm are the same as those of hwExtSrvFlowIndex.
                "
            ::= { hwDslamNtvFlowBasedMulticastPolicyEntry 1 } 
        
        hwDslamNtvUnknownMulticastTrafficPolicy OBJECT-TYPE
            SYNTAX  INTEGER
                { 
                transparent(2),
                discard(3) 
                }
            MAX-ACCESS read-write
            STATUS current
            DESCRIPTION
                "Indicates the suppression policy of unknown multicast streams. 
                 Options:
                 1. transparent(2) -indicates the suppression policy of unknown multicast stream is transparent
                 2. discard(3)     -indicates the suppression policy of unknown multicast stream is discard
                 For the switching-oriented service flow, it is discard(3) by default.
                 For the connection-oriented service flow, it is transparent(2) and does not support the set operation.
                 Default: discard(3)
                "
            DEFVAL { 3 }
            ::= { hwDslamNtvFlowBasedMulticastPolicyEntry 2 } 
   
        hwDslamNtvIgmpPacketPolicy OBJECT-TYPE
            SYNTAX  INTEGER
                { 
                normal(1),
                transparent(2),
                discard(3) 
                }
            MAX-ACCESS read-write
            STATUS current
            DESCRIPTION
                "Indicates the processing mode of IGMP packets. 
                 Options:
                 1. normal(1)      -indicates the processing mode of IGMP packets is normal
                 2. transparent(2) -indicates the processing mode of IGMP packets is transparent
                 3. discard(3)     -indicates the processing mode of IGMP packets is discard
                 Default: normal(1) 
                "
            DEFVAL { 1 }
            ::= { hwDslamNtvFlowBasedMulticastPolicyEntry 3 } 

        hwDslamNtvV2RouterTimerout   OBJECT-TYPE
            SYNTAX       Integer32(1..5000)
            UNITS        "seconds"
            MAX-ACCESS   read-write
            STATUS       current
            DESCRIPTION
                "Sets/Queries the timeout time of router V2. 
                 Range: 1-5000
                 Unit: second
                 Default: 400
                "       
            ::= { hwDslamNtv 78 }
          
        hwDslamNtvMVlanMemberStatusTable OBJECT-TYPE
             SYNTAX SEQUENCE OF HwDslamNtvMVlanMemberStatusEntry
             MAX-ACCESS not-accessible
             STATUS current
             DESCRIPTION
                 "Indicates the member relationship between the multicast VLAN and the multicast user.
                  The indexes of this table are hwDslamNtvMVLANIndex and hwDslamNtvUserIndex. 
                 "
             ::= { hwDslamNtv 80 }
        
        hwDslamNtvMVlanMemberStatusEntry OBJECT-TYPE
            SYNTAX HwDslamNtvMVlanMemberStatusEntry
            MAX-ACCESS not-accessible
            STATUS current
            DESCRIPTION
                "Indicates the member relationship between the multicast VLAN and the multicast user.
                 The indexes of this entry are hwDslamNtvMVLANIndex and hwDslamNtvUserIndex.
                "
            INDEX 
                { 
                hwDslamNtvMVLANIndex,
                hwDslamNtvUserIndex
                }
            ::= { hwDslamNtvMVlanMemberStatusTable 1 }
        
        HwDslamNtvMVlanMemberStatusEntry ::= 
            SEQUENCE 
                {
                hwDslamNtvMVlanMemberStatus 
                    INTEGER{ enable(1),disable(2) }
                }
         
        hwDslamNtvMVlanMemberStatus OBJECT-TYPE
            SYNTAX  INTEGER{ enable(1),disable(2) }
            MAX-ACCESS read-write
            STATUS current
            DESCRIPTION
                "Indicates the member relationship between the multicast VLAN and the multicast user. Options:
                 1. enable(1)  -indicates that the user is a member of the multicast VLAN.
                 2. disable(2) -indicates that the user is not a member of the multicast VLAN.
                "
            ::= { hwDslamNtvMVlanMemberStatusEntry 1 } 
        
        hwDslamNtvRouterInterAgingTime   OBJECT-TYPE
            SYNTAX   Integer32 (30..5000)
            MAX-ACCESS   read-write
            STATUS       current
            DESCRIPTION
                "The aging time of router interface.
                 Default: 260s
                "           
            ::= { hwDslamNtv 81 } 
        
        hwDslamNtvAllowToBeRouterInterTable    OBJECT-TYPE
            SYNTAX          SEQUENCE OF HwDslamNtvAllowToBeRouterInterEntry
            MAX-ACCESS      not-accessible
            STATUS          current
            DESCRIPTION
                "Port table which allows to be router interface.
                 The index of this table is hwDslamNtvAllowToBeRouterInterIndex.
                "
            ::= { hwDslamNtv 82 }
        
        hwDslamNtvAllowToBeRouterInterEntry    OBJECT-TYPE
            SYNTAX          HwDslamNtvAllowToBeRouterInterEntry
            MAX-ACCESS      not-accessible
            STATUS          current
            DESCRIPTION
                "Port table which allows to be router interface.
                 The index of this entry is hwDslamNtvAllowToBeRouterInterIndex.
                "
            INDEX 
                { 
                hwDslamNtvAllowToBeRouterInterIndex
                }
            ::= { hwDslamNtvAllowToBeRouterInterTable  1 }
        
        HwDslamNtvAllowToBeRouterInterEntry ::= 
            SEQUENCE  
                {
                hwDslamNtvAllowToBeRouterInterIndex       
                    Integer32,
                hwDslamNtvAllowToBeRouterInterRowStatus   
                    RowStatus, 
                hwDslamNtvAllowToBeRouterInterFSP        
                    Integer32
                }
                                        
        hwDslamNtvAllowToBeRouterInterIndex        OBJECT-TYPE
            SYNTAX       Integer32(0..128)
            MAX-ACCESS   read-only
            STATUS       current
            DESCRIPTION
                "Port index which allows to be router interface.
                "
            ::= { hwDslamNtvAllowToBeRouterInterEntry 1}   
        
        hwDslamNtvAllowToBeRouterInterRowStatus     OBJECT-TYPE
            SYNTAX       RowStatus
            MAX-ACCESS   read-create
            STATUS       current
            DESCRIPTION
                "Row status.
                 Add or delete a table item.
                 Options:
                 1. active(1)      -indicates the query operation
                 2. createAndGo(4) -indicates the adding operation
                 3. destroy(6)     -indicates the deleting operation
                "
            ::= { hwDslamNtvAllowToBeRouterInterEntry 2}   
        
        hwDslamNtvAllowToBeRouterInterFSP   OBJECT-TYPE
            SYNTAX       Integer32
            MAX-ACCESS   read-create
            STATUS       current
            DESCRIPTION
                "Combination of 'frame/slot/port' which allow to be router interface.
                 Using 32 bits to express 'frame/slot/port'. The frame and slot both occupied 8 bits, 
                 and the port occupied 16 bits. For example, 0/3/7 can be expressed as 0x00 03 0007.
                "
            ::= { hwDslamNtvAllowToBeRouterInterEntry 3}   
          
        hwDslamNtvRouterInterTable    OBJECT-TYPE
            SYNTAX          SEQUENCE OF HwDslamNtvRouterInterEntry
            MAX-ACCESS      not-accessible
            STATUS          current
            DESCRIPTION
                "The table included the router interface learned currently.
                 The index of this table is hwDslamNtvRouterInterIndex.
                "
            ::=  { hwDslamNtv 83 }
            
        hwDslamNtvRouterInterEntry    OBJECT-TYPE
            SYNTAX          HwDslamNtvRouterInterEntry
            MAX-ACCESS      not-accessible
            STATUS          current
            DESCRIPTION
                "The table included the router interface learned currently.
                 The index of this entry is hwDslamNtvRouterInterIndex.
                "
            INDEX 
                { 
                hwDslamNtvRouterInterIndex
                }
            ::= { hwDslamNtvRouterInterTable  1 }
        
        HwDslamNtvRouterInterEntry    ::= 
            SEQUENCE   
                {
                hwDslamNtvRouterInterIndex    
                    Integer32,
                hwDslamNtvRouterInterFSP      
                    Integer32, 
                hwDslamNtvRouterInterVlan     
                    Integer32,
                hwDslamNtvRouterInterTimeout  
                    Integer32,
                hwDslamNtvRouterVersion      
                    Integer32
                }
                                        
        hwDslamNtvRouterInterIndex        OBJECT-TYPE
            SYNTAX       Integer32
            MAX-ACCESS   read-only
            STATUS       current
            DESCRIPTION
                "Router interface index. 256 is the max value of the index.
                "
            ::= { hwDslamNtvRouterInterEntry 1}   
        
        hwDslamNtvRouterInterFSP   OBJECT-TYPE
            SYNTAX       Integer32
            MAX-ACCESS   read-only
            STATUS       current
            DESCRIPTION          
                "Combination of 'frame/slot/port', which is the router interface learned.      
                 Using 32 bits to express 'frame/slot/port'. The frame and slot both occupied 8 bits, 
                 and the port occupied 16 bits. For example, 0/3/7 can be expressed as 0x00030007 .
                "    
            ::= { hwDslamNtvRouterInterEntry 2 }
        
        hwDslamNtvRouterInterVlan   OBJECT-TYPE
            SYNTAX       Integer32
            MAX-ACCESS   read-only
            STATUS       current
            DESCRIPTION
                "Vlan of the router interface
                "
            ::= { hwDslamNtvRouterInterEntry 3 }
        
        hwDslamNtvRouterInterTimeout   OBJECT-TYPE
            SYNTAX       Integer32
            MAX-ACCESS   read-only
            STATUS       current
            DESCRIPTION
                "The remain time of the router interface before deleted.
                 After the system learned router interface, the router interface's aging timer is running.
                 When it is timeout two times, the router interface will be deleted.
                "
            ::= { hwDslamNtvRouterInterEntry 4 }
        
        hwDslamNtvRouterVersion  OBJECT-TYPE
            SYNTAX       Integer32 
            MAX-ACCESS   read-only
            STATUS       current
            DESCRIPTION
                "The IGMP Version of  multicast router.
                 It is include V1/V2/V3 version.
                "
            ::= { hwDslamNtvRouterInterEntry 5 }    
        
        hwDslamNtvVUpportTable    OBJECT-TYPE
            SYNTAX          SEQUENCE OF HwDslamNtvVUpportEntry
            MAX-ACCESS      not-accessible
            STATUS          current
            DESCRIPTION
                "Indicates the feature parameters of an upstream service port.
                 The index of this table is hwDslamNtvVUpportTblIndex.
                "
            ::= { hwDslamNtv 84 }
        
        hwDslamNtvVUpportEntry    OBJECT-TYPE
             SYNTAX          HwDslamNtvVUpportEntry
             MAX-ACCESS      not-accessible
             STATUS          current
             DESCRIPTION
                 "Indicates the feature parameters of an upstream service port.
                  The index of this entry is hwDslamNtvVUpportTblIndex.
                 "
             INDEX 
                 { 
                 hwDslamNtvVUpportTblIndex
                 }
             ::= { hwDslamNtvVUpportTable  1 }
        
        HwDslamNtvVUpportEntry    ::= 
            SEQUENCE  
                {
                hwDslamNtvVUpportTblIndex      
                    Integer32,
                hwDslamNtvVUpportTblRowStatus  
                    RowStatus, 
                hwDslamNtvVUpportTblInter      
                    Integer32, 
                hwDslamNtvVUpportTblVlan       
                    Integer32,
                hwDslamNtvVUpportTblRouterVersion
                    INTEGER,
                hwDslamNtvVUpportTblMldRouterVersion
                    INTEGER
                }
                                        
        hwDslamNtvVUpportTblIndex        OBJECT-TYPE
            SYNTAX       Integer32(-1|1..1024)
            MAX-ACCESS   read-create
            STATUS       current
            DESCRIPTION
                "Indicates the index of a multicast virtual upstream port.
                 Range: 1-1024
                 You can fill -1 and the system will automatically allocate an index.
                "
            ::= { hwDslamNtvVUpportEntry 1}   
        
        hwDslamNtvVUpportTblRowStatus        OBJECT-TYPE
            SYNTAX       RowStatus
            MAX-ACCESS   read-create
            STATUS       current
            DESCRIPTION
                "Row status, used to query, create, modify, and delete a multicast upstream port. 
                 It supports the active(1), createAndGo(4), and destroy(6) operations.
                 During query, the value of this leaf is always active(1).
                 During deletion, specify the value of this leaf to destroy(6).
                 During creation, specify the value of this leaf to createAndGo(4).
                 Options:
                 1. active(1)      -indicates the query operation
                 2. createAndGo(4) -indicates the creating operation
                 3. destroy(6)     -indicates the deleting operation
                "
            ::= { hwDslamNtvVUpportEntry 2}   
        
        hwDslamNtvVUpportTblInter   OBJECT-TYPE
            SYNTAX       Integer32
            MAX-ACCESS   read-create
            STATUS       current
            DESCRIPTION
                "Indicates the upstream port, a combination of shelf ID, slot ID, and port ID. 
                 8 bits for the shelf ID, 8 bits for the slot ID, and 16 bits for the port ID, 
                 forming an integer of 32 bits. The most significant 8 bits indicate the shelf ID, 
                 the next 8 bits indicate the slot ID, and the last 16 bits indicate the port ID.
                "
            ::= { hwDslamNtvVUpportEntry 3 }
        
        hwDslamNtvVUpportTblVlan   OBJECT-TYPE
            SYNTAX       Integer32(1..4093)
            MAX-ACCESS   read-create
            STATUS       current
            DESCRIPTION
                "Indicates the VLAN ID of an upstream port. 
                 Range: 1-4093
                "
            ::= { hwDslamNtvVUpportEntry 4 }
        
        hwDslamNtvVUpportTblRouterVersion  OBJECT-TYPE
            SYNTAX  INTEGER
                {
                igmpV2(2),
                igmpV3(3)
                }
            MAX-ACCESS   read-only
            STATUS       current
            DESCRIPTION
                "Indicates the version of the multicast router connected to the upstream port. 
                 Options:
                 1. igmpV2(2) -indicates the IGMP version is V2 
                 2. igmpV3(3) -indicates the IGMP version is V3 
                "
            ::= { hwDslamNtvVUpportEntry 5}
        
        hwDslamNtvVUpportTblMldRouterVersion OBJECT-TYPE
            SYNTAX  INTEGER
                {
                mldV1(1),
                mldV2(2)
                }
            MAX-ACCESS read-only
            STATUS current
            DESCRIPTION
                "Indicates the MLD version of the multicast router connected to the upstream port. 
                 Options:
                 1. mldV1(1) -indicates the MLD version is V1 
                 2. mldV2(2) -indicates the MLD version is V2 
                "
            ::= { hwDslamNtvVUpportEntry 6 }

        hwDslamNtvUserQueryTable    OBJECT-TYPE
            SYNTAX          SEQUENCE OF HwDslamNtvUserQueryEntry
            MAX-ACCESS      not-accessible
            STATUS          current
            DESCRIPTION
                "Queries the index of a multicast user according to the stream parameters of the multicast user.
                 The indexes of this table are hwDslamNtvUserQueryIfIndex, hwDslamNtvUserQueryVpi, hwDslamNtvUserQueryVci,
                 hwDslamNtvUserQueryFlowType, hwDslamNtvUserQueryFlowPara, hwDslamNtvUserQueryMatchPara1 and 
                 hwDslamNtvUserQueryMatchPara2.
                "
            ::= { hwDslamNtv 85 }
        
        hwDslamNtvUserQueryEntry    OBJECT-TYPE
            SYNTAX          HwDslamNtvUserQueryEntry
            MAX-ACCESS      not-accessible
            STATUS          current
            DESCRIPTION
                "Queries the index of a multicast user according to the stream parameters of the multicast user.
                 The indexes of this entry are hwDslamNtvUserQueryIfIndex, hwDslamNtvUserQueryVpi, hwDslamNtvUserQueryVci,
                 hwDslamNtvUserQueryFlowType, hwDslamNtvUserQueryFlowPara, hwDslamNtvUserQueryMatchPara1 and 
                 hwDslamNtvUserQueryMatchPara2.
                "
            INDEX { 
                  hwDslamNtvUserQueryIfIndex,
                  hwDslamNtvUserQueryVpi,
                  hwDslamNtvUserQueryVci,
                  hwDslamNtvUserQueryFlowType,
                  hwDslamNtvUserQueryFlowPara,
                  hwDslamNtvUserQueryMatchPara1,
                  hwDslamNtvUserQueryMatchPara2                 
                 }
            ::= { hwDslamNtvUserQueryTable  1 }
        
        HwDslamNtvUserQueryEntry    ::= 
            SEQUENCE  
                {
                hwDslamNtvUserQueryIfIndex   
                    Integer32,
                hwDslamNtvUserQueryVpi      
                    Integer32,
                hwDslamNtvUserQueryVci      
                    Integer32, 
                hwDslamNtvUserQueryFlowType  
                    INTEGER, 
                hwDslamNtvUserQueryFlowPara 
                    Integer32,
                hwDslamNtvUserQueryMatchPara1
                    Integer32,
                hwDslamNtvUserQueryMatchPara2
                    Integer32,
                hwDslamNtvUserQueryIndex    
                    Integer32
              }
                                        
        hwDslamNtvUserQueryIfIndex OBJECT-TYPE
            SYNTAX Integer32
            MAX-ACCESS not-accessible
            STATUS current
            DESCRIPTION
                "Indicates the port index, corresponding to the shelf ID and slot ID of the port. 
                 Its value and algorithm are the same as those of ifIndex.
                "
            ::= { hwDslamNtvUserQueryEntry 1 }        
        
        hwDslamNtvUserQueryVpi OBJECT-TYPE
            SYNTAX Integer32
            MAX-ACCESS not-accessible
            STATUS current
            DESCRIPTION
                "Indicates the VPI of the PVC carrying IGMP packets. This leaf and the VCI leaf 
                 together identify an xDSL user. The value range is determined by the xDSL line 
                 specifications.
                "
            ::= { hwDslamNtvUserQueryEntry 2 }
        
        hwDslamNtvUserQueryVci OBJECT-TYPE
            SYNTAX Integer32
            MAX-ACCESS not-accessible
            STATUS current
            DESCRIPTION
                "Indicates the VCI of the PVC carrying IGMP packets. This leaf and the VPI leaf 
                 together identify an xDSL user. The value range is determined by the xDSL line 
                 specifications.
                "
            ::= { hwDslamNtvUserQueryEntry 3 }
        
        hwDslamNtvUserQueryFlowType OBJECT-TYPE
            SYNTAX INTEGER
                {
                byUserVlan(1),
                byEncap(2),
                by8021p(3),
                byVlanEtherType(4),
                singleFlow(-1)
                }
            MAX-ACCESS not-accessible
            STATUS current
            DESCRIPTION
                "Indicates the multi-service flow type. 
                 Options:
                 1. byUserVlan(1)      -indicates the multi-service flow type is byUserVlan
                 2. byEncap(2)         -indicates the multi-service flow type is byEncap
                 3. by8021p(3)         -indicates the multi-service flow type is by8021p
                 4. byVlanEtherType(4) -indicates the multi-service flow type is byVlanEtherType
                 5. singleFlow(-1)     -indicates the multi-service flow type is singleFlow
                "
            ::= { hwDslamNtvUserQueryEntry 4 }
        
        hwDslamNtvUserQueryFlowPara OBJECT-TYPE
            SYNTAX Integer32
            MAX-ACCESS not-accessible
            STATUS current
            DESCRIPTION
                "Specifies the parameter value of the flow type. 
                 The parameter value varies with the flow type. In detail:
                 (1) singleFlow(-1). Fill -1 for a single service flow.
                 (2) byUserVlan(1). Range: 1-4095. For an untagged flow, the value is 0xFFFF.
                 (3) byEncap(2). Options: ipoe(1) and pppoe(2).
                 (4) by8021p. Range 0-7.
                 (5) by-vlan-ethertype. The flow parameter is a combination of the EtherType and the user VLAN. 
                     The EtherType can be IPoE, PPPoE, and the user VLAN is in the range of 1-4095, 0 (priority-tagged), 
                     and untagged.
                "
            ::= { hwDslamNtvUserQueryEntry 5 }        
                 
        hwDslamNtvUserQueryMatchPara1 OBJECT-TYPE
            SYNTAX Integer32
            MAX-ACCESS not-accessible
            STATUS current
            DESCRIPTION
                "Indicates gemportid in the GPON distributed mode. 
                 The range is determined by the line specifications.
                 Indicates ontid in the GPON profile mode and the EPON mode. 
                 The range is determined by the line specifications.
                 VDSL port type, indicating PTM/ATM mode. 
                 Options:
                 1. PTM(1) -indicates gemportid in the GPON distributed mode is PTM
                 2. ATM(2) -indicates gemportid in the GPON distributed mode is ATM            
                "
            ::= { hwDslamNtvUserQueryEntry 6 }
                
        hwDslamNtvUserQueryMatchPara2 OBJECT-TYPE
            SYNTAX Integer32
            MAX-ACCESS not-accessible
            STATUS current
            DESCRIPTION
                "Indicates gemindex of a GPON user in the GPON profile mode. This leaf is 
                 currently not used for users in the GPON non-profile mode or other modes.
                "
            ::= { hwDslamNtvUserQueryEntry 7 }            
                
        hwDslamNtvUserQueryIndex OBJECT-TYPE
            SYNTAX Integer32
            MAX-ACCESS read-only
            STATUS current
            DESCRIPTION
                "Indicates the index of a multicast user. Its value and usage are the same 
                 as those of hwDslamNtvUserIndex.
                "
            ::= { hwDslamNtvUserQueryEntry 8 }    
        
        hwDslamNtvUpstreamMode   OBJECT-TYPE
            SYNTAX  INTEGER 
                { 
                igmp(1),
                pimSsm(2) 
                }
            MAX-ACCESS   read-write
            STATUS       current
            DESCRIPTION
                "Sets/Queries the interaction mode of the upstream port. 
                 Options:
                 1. igmp(1)   -indicates the interaction mode of the upstream port is igmp
                 2. pimSsm(2) -indicates the interaction mode of the upstream port is pimSsm
                 Default: igmp(1)
                "
            ::= { hwDslamNtv 86 }
        
        hwDslamNtvUserExtendedAttributesTable OBJECT-TYPE
            SYNTAX SEQUENCE OF HwDslamNtvUserExtendedAttributesEntry
            MAX-ACCESS not-accessible
            STATUS current
            DESCRIPTION
                "Indicates the maximum count for a user to watch programs at various grades.
                 The index of this table is hwDslamNtvUserInnerIndex.
                "
            ::= { hwDslamNtv 87 }
        
        hwDslamNtvUserExtendedAttributesEntry OBJECT-TYPE
            SYNTAX HwDslamNtvUserExtendedAttributesEntry
            MAX-ACCESS not-accessible
            STATUS current
            DESCRIPTION
                "Indicates the maximum count for a user to watch programs at various grades.
                 The index of this entry is hwDslamNtvUserInnerIndex.
                "
            INDEX 
                { 
                hwDslamNtvUserInnerIndex
                }
            ::= { hwDslamNtvUserExtendedAttributesTable 1 }
        
        HwDslamNtvUserExtendedAttributesEntry ::= 
            SEQUENCE 
                {
                hwDslamNtvUserInnerIndex
                    Integer32,
                hwDslamNtvUserHdtvWatchLimit 
                    Integer32,
                hwDslamNtvUserSdtvWatchLimit
                    Integer32,  
                hwDslamNtvUserStreamingVideoWatchLimit
                    Integer32
               }
            
        hwDslamNtvUserInnerIndex OBJECT-TYPE
            SYNTAX Integer32
            MAX-ACCESS read-only
            STATUS current
            DESCRIPTION
                "Indicates the user index.
                "
            ::= { hwDslamNtvUserExtendedAttributesEntry 1 }    
                
        hwDslamNtvUserHdtvWatchLimit  OBJECT-TYPE
            SYNTAX Integer32 (0..32|255)
            MAX-ACCESS read-write
            STATUS current
            DESCRIPTION
                "Indicates the watch limit on the HDTV program.
                 Range: 0-32, 255
                 Default: 255 (the number of watched programs is not limited).
                "
            ::= { hwDslamNtvUserExtendedAttributesEntry 2 } 
                
        hwDslamNtvUserSdtvWatchLimit  OBJECT-TYPE
            SYNTAX       Integer32 (0..32|255)
            MAX-ACCESS read-write
            STATUS current
            DESCRIPTION
                "Indicates the watch limit on the SDTV program.
                 Range: 0-32, 255
                 Default: 255 (the number of watched programs is not limited).
                "
            ::= { hwDslamNtvUserExtendedAttributesEntry 3 } 
                
        hwDslamNtvUserStreamingVideoWatchLimit  OBJECT-TYPE
            SYNTAX       Integer32 (0..32|255)
            MAX-ACCESS read-write
            STATUS current
            DESCRIPTION
                "Indicates the watch limit on the streaming-video program.
                 Range: 0-32, 255
                 Default: 255 (the number of watched programs is not limited).
                "
            ::= { hwDslamNtvUserExtendedAttributesEntry 4 }                         
                
        hwDslamNtvVersionForceSwitch   OBJECT-TYPE
            SYNTAX      TruthValue
            MAX-ACCESS  read-write
            STATUS      current
            DESCRIPTION
                "Force switch upplink-port version to IGMP V2.
                 TRUE(enable) means that upport-port version is force to V2,
                 FALSE(disable) means that upport-port version is auto-selected.
                 The default value is 'enable'.
                 Options:
                 1. true(1)  -indicates the upport-port version is force to V2
                 2. false(2) -indicates the upport-port version is auto-selected
                "
            ::= { hwDslamNtv 88 }            
                
        hwDslamNtvBandwidthCACTable OBJECT-TYPE
            SYNTAX SEQUENCE OF HwDslamNtvBandwidthCACEntry
            MAX-ACCESS not-accessible
            STATUS current
            DESCRIPTION
                "Sets the port bandwidth; queries the allocated and used bandwidth of a port.
                 The index of this table is hwDslamNtvBandwidthCACifIndex.
                "
            ::= { hwDslamNtv 89 }
        
        hwDslamNtvBandwidthCACEntry OBJECT-TYPE
            SYNTAX HwDslamNtvBandwidthCACEntry
            MAX-ACCESS not-accessible
            STATUS current
            DESCRIPTION
                "Sets the port bandwidth; queries the allocated and used bandwidth of a port.
                 The index of this entry is hwDslamNtvBandwidthCACifIndex.
                "
            INDEX 
                { 
                hwDslamNtvBandwidthCACifIndex
                }
            ::= { hwDslamNtvBandwidthCACTable 1 }
        
        HwDslamNtvBandwidthCACEntry ::= 
             SEQUENCE 
                 {
                 hwDslamNtvBandwidthCACifIndex 
                     Integer32,
                 hwDslamNtvAssignBandwidth 
                     Integer32,
                 hwDslamNtvUsedBandwidth 
                     Integer32,
                 hwDslamNtvAncpVideoBandwidth 
                     Integer32,
                 hwDslamNtvAncpMcastBandwidth 
                     Integer32  
                 }       
                
        hwDslamNtvBandwidthCACifIndex OBJECT-TYPE
            SYNTAX Integer32
            MAX-ACCESS read-only
            STATUS current
            DESCRIPTION
                "Indicates the port index, corresponding to the shelf ID and slot ID of the port. 
                 The value and algorithm of this index are the same as those of the ifIndex.
                "
            ::= { hwDslamNtvBandwidthCACEntry 1 }
                
        hwDslamNtvAssignBandwidth  OBJECT-TYPE
            SYNTAX Integer32
            MAX-ACCESS read-write
            STATUS current
            DESCRIPTION
                "Indicates the allocable port bandwidth. 
                 If the bandwidth is not limited, the returned value for hwDslamNtvAssignBandwidth is -1.
                 Range: 0-2147483647, -1
                 Default: 716800
                 Unit: kbit/s
                "
            ::= { hwDslamNtvBandwidthCACEntry 2 } 
                
        hwDslamNtvUsedBandwidth  OBJECT-TYPE
            SYNTAX Integer32
            MAX-ACCESS read-only
            STATUS current
            DESCRIPTION
                "Indicates the used bandwidth of the port.
                "
            ::= { hwDslamNtvBandwidthCACEntry 3 } 
                
        hwDslamNtvAncpVideoBandwidth  OBJECT-TYPE
            SYNTAX Integer32
            MAX-ACCESS read-only
            STATUS current
            DESCRIPTION
                "Indicates the total ANCP video bandwidth. When ANCP CAC is disabled, 
                 the returned value for hwDslamNtvAncpVideoBandwidth is -1.
                 Unit: kbit/s.
                "
            ::= { hwDslamNtvBandwidthCACEntry 4 }
        
        hwDslamNtvAncpMcastBandwidth  OBJECT-TYPE
            SYNTAX Integer32
            MAX-ACCESS read-only
            STATUS current
            DESCRIPTION
                "Indicates the ANCP multicast video bandwidth. When ANCP CAC is disabled, 
                 the returned value for hwDslamNtvAncpMcastBandwidth is -1.
                 Unit: kbit/s.
                "
            ::= { hwDslamNtvBandwidthCACEntry 5 }
        
        hwDslamNtvMVlanIgmpStatTable    OBJECT-TYPE
            SYNTAX          SEQUENCE OF HwDslamNtvMVlanIgmpStatEntry
            MAX-ACCESS      not-accessible
            STATUS          current
            DESCRIPTION
                "Indicates the statistics of IGMP packets transmitted and received in a multicast VLAN.
                 The index of this table is hwDslamNtvMVlanIgmpStatMVlanIndex.
                "
            ::= { hwDslamNtv 90 }
        
        hwDslamNtvMVlanIgmpStatEntry    OBJECT-TYPE
            SYNTAX         HwDslamNtvMVlanIgmpStatEntry
            MAX-ACCESS     not-accessible
            STATUS         current
            DESCRIPTION
                "Indicates the statistics of IGMP packets transmitted and received in a multicast VLAN.
                 The index of this entry is hwDslamNtvMVlanIgmpStatMVlanIndex.
                "
            INDEX   
                { 
                hwDslamNtvMVlanIgmpStatMVlanIndex
                }
            ::= { hwDslamNtvMVlanIgmpStatTable  1 }
        
        HwDslamNtvMVlanIgmpStatEntry    ::= 
            SEQUENCE  
                {
                hwDslamNtvMVlanIgmpStatMVlanIndex  
                    Integer32,
                hwDslamNtvMVlanIgmpStatOperMode    
                    INTEGER,
                hwDslamNtvMVlanIgmpStatGenQueryRcv 
                    Integer32,  
                hwDslamNtvMVlanIgmpStatSpecQueryRcv 
                    Integer32,       
                hwDslamNtvMVlanIgmpStatReportV2Rcv 
                    Integer32,
                hwDslamNtvMVlanIgmpStatErrV2ReportRcv
                    Integer32,  
                hwDslamNtvMVlanIgmpStatReportV3Rcv 
                    Integer32,
                hwDslamNtvMVlanIgmpStatErrV3ReportRcv
                    Integer32,   
                hwDslamNtvMVlanIgmpStatLeaveRcv    
                    Integer32,
                hwDslamNtvMVlanIgmpStatGenQuerySnd 
                    Integer32,
                hwDslamNtvMVlanIgmpStatSpecQuerySnd
                    Integer32,
                hwDslamNtvMVlanIgmpStatReportV2Snd 
                    Integer32,
                hwDslamNtvMVlanIgmpStatReportV3Snd 
                    Integer32,  
                hwDslamNtvMVlanIgmpStatLeaveSnd    
                    Integer32, 
                hwDslamNtvMVlanIgmpActiveProgramNum 
                    Integer32,   
                hwDslamNtvMVlanIgmpActiveUserNum   
                    Integer32,   
                hwDslamNtvMVlanIgmpStatInvalidRcv
                    Integer32,
                hwDslamNtvMVlanIgmpStatJoinProgRcvUser
                    Integer32,
                hwDslamNtvMVlanIgmpStatLeaveProgRcvUser
                    Integer32,
                hwDslamNtvMVlanIgmpStatGenQuerySndUser
                    Integer32,
                hwDslamNtvMVlanIgmpStatSpecQuerySndUser
                    Integer32,
                hwDslamNtvMVlanIgmpStatInvalidRcvUser
                    Integer32,
                hwDslamNtvMVlanIgmpStatV2JoinRcvdFromUser
                    Counter32,
                hwDslamNtvMVlanIgmpStatV3JoinRcvdFromUser
                    Counter32,
                hwDslamNtvMVlanIgmpStatLeaveSentToNetwork
                    Counter32,
                hwDslamNtvMVlanIgmpStatV3JoinSentToNetwork
                    Counter32          
               }
               
        hwDslamNtvMVlanIgmpStatMVlanIndex       OBJECT-TYPE
            SYNTAX Integer32 (1..256)
            MAX-ACCESS read-only
            STATUS current
            DESCRIPTION
                "Indicates the multicast VLAN index. Its value and algorithm are the same as those of hwDslamNtvMVLANIndex.
                "
            ::= { hwDslamNtvMVlanIgmpStatEntry 1 }
                       
        hwDslamNtvMVlanIgmpStatOperMode        OBJECT-TYPE
            SYNTAX   INTEGER
            { 
            clearStatistic(1),
            invalid(-1) 
            }
            MAX-ACCESS   read-write
            STATUS       current
            DESCRIPTION
                "Indicates the operation mode. The set operation can clear statistics of IGMP packets. 
                 Options: 
                 1. clearStatistic(1) -indicates clearing statistics of multicast VLAN packets
                 2. invalid(-1)       -indicates invalid
                "
            ::= { hwDslamNtvMVlanIgmpStatEntry 2}
          
        hwDslamNtvMVlanIgmpStatGenQueryRcv    OBJECT-TYPE
            SYNTAX   Integer32 
            MAX-ACCESS   read-only
            STATUS       current
            DESCRIPTION
                "Indicates the number of general query packets received in a multicast VLAN.
                "
            ::= { hwDslamNtvMVlanIgmpStatEntry 3}
        
        hwDslamNtvMVlanIgmpStatSpecQueryRcv   OBJECT-TYPE
            SYNTAX   Integer32 
            MAX-ACCESS   read-only
            STATUS       current
            DESCRIPTION
                "Indicates the number of specific query packets received in a multicast VLAN.
                "
            ::= { hwDslamNtvMVlanIgmpStatEntry 4}
        
        hwDslamNtvMVlanIgmpStatReportV2Rcv    OBJECT-TYPE
            SYNTAX   Integer32 
            MAX-ACCESS   read-only
            STATUS       current
            DESCRIPTION
                "Indicates the number of V2 report packets received in a multicast VLAN.
                "
            ::= { hwDslamNtvMVlanIgmpStatEntry 5}
        
        hwDslamNtvMVlanIgmpStatErrV2ReportRcv    OBJECT-TYPE
            SYNTAX   Integer32 
            MAX-ACCESS   read-only
            STATUS       current
            DESCRIPTION
                "Indicates the number of errored V2 report packets received in a multicast VLAN.
                "
            ::= { hwDslamNtvMVlanIgmpStatEntry 6}
        
        hwDslamNtvMVlanIgmpStatReportV3Rcv    OBJECT-TYPE
            SYNTAX   Integer32 
            MAX-ACCESS   read-only
            STATUS       current
            DESCRIPTION
                "Indicates the number of V3 report packets received in a multicast VLAN.
                "
            ::= { hwDslamNtvMVlanIgmpStatEntry 7}
        
        hwDslamNtvMVlanIgmpStatErrV3ReportRcv    OBJECT-TYPE
            SYNTAX   Integer32 
            MAX-ACCESS   read-only
            STATUS       current
            DESCRIPTION
                "Indicates the number of errored V3 report packets received in a multicast VLAN.
                "
            ::= { hwDslamNtvMVlanIgmpStatEntry 8}
        
        hwDslamNtvMVlanIgmpStatLeaveRcv    OBJECT-TYPE
            SYNTAX   Integer32 
            MAX-ACCESS   read-only
            STATUS       current
            DESCRIPTION
                "Indicates the number of leave packets received in a multicast VLAN.
                "
            ::= { hwDslamNtvMVlanIgmpStatEntry 9}
            
        hwDslamNtvMVlanIgmpStatGenQuerySnd    OBJECT-TYPE
            SYNTAX   Integer32 
            MAX-ACCESS   read-only
            STATUS       current
            DESCRIPTION
                "Indicates the number of general query packets transmitted by a multicast VLAN.
                "
            ::= { hwDslamNtvMVlanIgmpStatEntry 10}    
                
        hwDslamNtvMVlanIgmpStatSpecQuerySnd    OBJECT-TYPE
            SYNTAX   Integer32 
            MAX-ACCESS   read-only
            STATUS       current
            DESCRIPTION
                "Indicates the number of specific query packets transmitted by a multicast VLAN.
                "
            ::= { hwDslamNtvMVlanIgmpStatEntry 11}
                
        hwDslamNtvMVlanIgmpStatReportV2Snd    OBJECT-TYPE
            SYNTAX   Integer32 
            MAX-ACCESS   read-only
            STATUS       current
            DESCRIPTION
                "Indicates the number of V2 report packets transmitted by a multicast VLAN.
                "
            ::= { hwDslamNtvMVlanIgmpStatEntry 12}
                
        hwDslamNtvMVlanIgmpStatReportV3Snd    OBJECT-TYPE
            SYNTAX   Integer32 
            MAX-ACCESS   read-only
            STATUS       current
            DESCRIPTION
                "Indicates the number of V3 report packets transmitted by a multicast VLAN.
                "
            ::= { hwDslamNtvMVlanIgmpStatEntry 13}
        
        hwDslamNtvMVlanIgmpStatLeaveSnd    OBJECT-TYPE
            SYNTAX   Integer32 
            MAX-ACCESS   read-only
            STATUS       current
            DESCRIPTION
                "Indicates the number of leave packets transmitted by a multicast VLAN.
                "
            ::= { hwDslamNtvMVlanIgmpStatEntry 14}
        
        hwDslamNtvMVlanIgmpActiveProgramNum    OBJECT-TYPE
            SYNTAX   Integer32 
            MAX-ACCESS   read-only
            STATUS       current
            DESCRIPTION
                "Indicates the number of online programs in a multicast VLAN.
                "
            ::= { hwDslamNtvMVlanIgmpStatEntry 15}
        
        hwDslamNtvMVlanIgmpActiveUserNum    OBJECT-TYPE
            SYNTAX   Integer32 
            MAX-ACCESS   read-only
            STATUS       current
            DESCRIPTION
                "Indicates the number of online users in a multicast VLAN.
                "
            ::= { hwDslamNtvMVlanIgmpStatEntry 16}
        
        hwDslamNtvMVlanIgmpStatInvalidRcv    OBJECT-TYPE
            SYNTAX   Integer32 
            MAX-ACCESS   read-only
            STATUS       current
            DESCRIPTION
                "Indicates the number of invalid packets received in a multicast VLAN.
                "
            ::= { hwDslamNtvMVlanIgmpStatEntry 17}
            
        hwDslamNtvMVlanIgmpStatJoinProgRcvUser    OBJECT-TYPE
            SYNTAX   Integer32 
            MAX-ACCESS   read-only
            STATUS       current
            DESCRIPTION
                "Indicates the number of join programs from MVLAN users based on MVLAN.
                "
            ::= { hwDslamNtvMVlanIgmpStatEntry 18 }
            
        hwDslamNtvMVlanIgmpStatLeaveProgRcvUser    OBJECT-TYPE
            SYNTAX   Integer32 
            MAX-ACCESS   read-only
            STATUS       current
            DESCRIPTION
                "Indicates the number of leaving programs from MVLAN users based on MVLAN.
                "
            ::= { hwDslamNtvMVlanIgmpStatEntry 19 }
            
        hwDslamNtvMVlanIgmpStatGenQuerySndUser    OBJECT-TYPE
            SYNTAX   Integer32 
            MAX-ACCESS   read-only
            STATUS       current
            DESCRIPTION
                "Indicates the number of general query packets transmitted by an MVLAN to MVLAN users.
                "
            ::= { hwDslamNtvMVlanIgmpStatEntry 20 }
            
        hwDslamNtvMVlanIgmpStatSpecQuerySndUser    OBJECT-TYPE
            SYNTAX   Integer32 
            MAX-ACCESS   read-only
            STATUS       current
            DESCRIPTION
                "Indicates the number of specific query packets transmitted by an MVLAN to MVLAN users.
                "
            ::= { hwDslamNtvMVlanIgmpStatEntry 21 }
            
        hwDslamNtvMVlanIgmpStatInvalidRcvUser    OBJECT-TYPE
            SYNTAX   Integer32 
            MAX-ACCESS   read-only
            STATUS       current
            DESCRIPTION
                "Indicates the number of invalid packets received in an MVLAN from MVLAN users.
                "
            ::= { hwDslamNtvMVlanIgmpStatEntry 22 }
            
        hwDslamNtvMVlanIgmpStatV2JoinRcvdFromUser    OBJECT-TYPE   
            SYNTAX   Counter32 
            MAX-ACCESS   read-only
            STATUS       current
            DESCRIPTION
                "Indicates the number of V2 join programs received from users in a multicast VLAN.
                "
            ::= { hwDslamNtvMVlanIgmpStatEntry 23 }     
           
        hwDslamNtvMVlanIgmpStatV3JoinRcvdFromUser    OBJECT-TYPE   
            SYNTAX   Counter32 
            MAX-ACCESS   read-only
            STATUS       current
            DESCRIPTION
                "Indicates the number of V3 join programs receiverd from users in a multicast VLAN.
                "
            ::= { hwDslamNtvMVlanIgmpStatEntry 24 } 
  
        hwDslamNtvMVlanIgmpStatLeaveSentToNetwork    OBJECT-TYPE   
            SYNTAX   Counter32 
            MAX-ACCESS   read-only
            STATUS       current
            DESCRIPTION
                "Indicates the number of sent leaving programs to network in a multicast VLAN.
                "
            ::= { hwDslamNtvMVlanIgmpStatEntry 25 }

        hwDslamNtvMVlanIgmpStatV3JoinSentToNetwork   OBJECT-TYPE
            SYNTAX   Counter32 
            MAX-ACCESS   read-only
            STATUS       current
            DESCRIPTION
                "Indicates the number of sent V3 join programs to network in a multicast VLAN.
                "
            ::= { hwDslamNtvMVlanIgmpStatEntry 26 }
    
        hwDslamNtvUserIgmpStatTable    OBJECT-TYPE
            SYNTAX          SEQUENCE OF HwDslamNtvUserIgmpStatEntry
            MAX-ACCESS      not-accessible
            STATUS          current
            DESCRIPTION
                "Indicates the statistics of IGMP packets transmitted and received by a multicast user.
                 The index of this table is hwDslamNtvUserIgmpStatUserIndex.
                "
            ::= { hwDslamNtv 91 }
        
        hwDslamNtvUserIgmpStatEntry    OBJECT-TYPE
            SYNTAX         HwDslamNtvUserIgmpStatEntry
            MAX-ACCESS     not-accessible
            STATUS         current
            DESCRIPTION
                "Indicates the statistics of IGMP packets transmitted and received by a multicast user.
                 The index of this entry is hwDslamNtvUserIgmpStatUserIndex.
                "
            INDEX   { 
                      hwDslamNtvUserIgmpStatUserIndex
                    }
            ::= { hwDslamNtvUserIgmpStatTable  1 }
        
        HwDslamNtvUserIgmpStatEntry    ::= 
            SEQUENCE  
                {
                hwDslamNtvUserIgmpStatUserIndex  
                    Integer32,
                hwDslamNtvUserIgmpStatOperMode    
                    INTEGER, 
                hwDslamNtvUserIgmpStatReportV1Rcv 
                    Integer32, 
                hwDslamNtvUserIgmpStatErrV1ReportRcv
                    Integer32,    
                hwDslamNtvUserIgmpStatReportV2Rcv 
                    Integer32,
                hwDslamNtvUserIgmpStatErrV2ReportRcv
                    Integer32, 
                hwDslamNtvUserIgmpStatReportV3Rcv
                    Integer32,
                hwDslamNtvUserIgmpStatErrV3ReportRcv
                    Integer32,   
                hwDslamNtvUserIgmpStatV2LeaveRcv 
                    Integer32,
                hwDslamNtvUserIgmpStatGenQuerySnd 
                    Integer32,
                hwDslamNtvUserIgmpStatSpecQuerySnd 
                    Integer32,  
                hwDslamNtvUserIgmpStatInvalidRcv  
                    Integer32,
                hwDslamNtvUserIgmpStatSuccJoinProgRcv
                    Integer32,
                hwDslamNtvUserIgmpStatErrJoinProgRcv
                    Integer32,
                hwDslamNtvUserIgmpStatLeaveProgRcv
                    Integer32
               }
               
        hwDslamNtvUserIgmpStatUserIndex       OBJECT-TYPE
            SYNTAX Integer32 (0..16383)
            MAX-ACCESS read-only
            STATUS current
            DESCRIPTION
                "Indicates the index of a multicast user. Its value and algorithm are the same as those of hwDslamNtvUserIndex.
                "
            ::= { hwDslamNtvUserIgmpStatEntry 1 }
                       
        hwDslamNtvUserIgmpStatOperMode        OBJECT-TYPE
            SYNTAX   INTEGER
                 { 
                 clearStatistic(1),
                 invalid(-1)
                 }
            MAX-ACCESS   read-write
            STATUS       current
            DESCRIPTION
                "Indicates the operation mode. The set operation can clear statistics of user IGMP packets. 
                 Options:
                 1. clearStatistic(1) -indicates clearing statistics of user packets
                 2. invalid(-1)      -indicates invalid operation mode
                "
            ::= { hwDslamNtvUserIgmpStatEntry 2}
        
        hwDslamNtvUserIgmpStatReportV1Rcv    OBJECT-TYPE
            SYNTAX   Integer32 
            MAX-ACCESS   read-only
            STATUS       current
            DESCRIPTION
                "Indicates the number of V1 report packets received by the multicast user.
                "
            ::= { hwDslamNtvUserIgmpStatEntry 3} 
        
        hwDslamNtvUserIgmpStatErrV1ReportRcv    OBJECT-TYPE
            SYNTAX   Integer32 
            MAX-ACCESS   read-only
            STATUS       current
            DESCRIPTION
                "Indicates the number of V1 report error packets received by the multicast user.
                "
            ::= { hwDslamNtvUserIgmpStatEntry 4} 
        
        hwDslamNtvUserIgmpStatReportV2Rcv    OBJECT-TYPE
            SYNTAX   Integer32 
            MAX-ACCESS   read-only
            STATUS       current
            DESCRIPTION
                "Indicates the number of V2 report packets received by the multicast user.
                "
            ::= { hwDslamNtvUserIgmpStatEntry 5} 
        
        hwDslamNtvUserIgmpStatErrV2ReportRcv    OBJECT-TYPE
            SYNTAX   Integer32 
            MAX-ACCESS   read-only
            STATUS       current
            DESCRIPTION
                "Indicates the number of errored V2 report packets received by the multicast user.
                "
            ::= { hwDslamNtvUserIgmpStatEntry 6} 
        
        hwDslamNtvUserIgmpStatReportV3Rcv    OBJECT-TYPE
            SYNTAX   Integer32 
            MAX-ACCESS   read-only
            STATUS       current
            DESCRIPTION
                "Indicates the number of V3 report packets received by the multicast user.
                "
            ::= { hwDslamNtvUserIgmpStatEntry 7} 
        
        hwDslamNtvUserIgmpStatErrV3ReportRcv    OBJECT-TYPE
            SYNTAX   Integer32 
            MAX-ACCESS   read-only
            STATUS       current
            DESCRIPTION
                "Indicates the number of errored V3 report packets received by the multicast user.
                "
            ::= { hwDslamNtvUserIgmpStatEntry 8} 
            
        hwDslamNtvUserIgmpStatV2LeaveRcv    OBJECT-TYPE
            SYNTAX   Integer32 
            MAX-ACCESS   read-only
            STATUS       current
            DESCRIPTION
                "Indicates the number of leave packets received by the multicast user.
                "
            ::= { hwDslamNtvUserIgmpStatEntry 9} 
         
        hwDslamNtvUserIgmpStatGenQuerySnd    OBJECT-TYPE
            SYNTAX   Integer32 
            MAX-ACCESS   read-only
            STATUS       current
            DESCRIPTION
                "Indicates the number of general query packets transmitted by the multicast user.
                "
            ::= { hwDslamNtvUserIgmpStatEntry 10} 
        
        hwDslamNtvUserIgmpStatSpecQuerySnd    OBJECT-TYPE
            SYNTAX   Integer32 
            MAX-ACCESS   read-only
            STATUS       current
            DESCRIPTION
                "Indicates the number of group-specific query packets transmitted by the multicast user.
                "
            ::= { hwDslamNtvUserIgmpStatEntry 11} 
        
        hwDslamNtvUserIgmpStatInvalidRcv    OBJECT-TYPE
            SYNTAX   Integer32 
            MAX-ACCESS   read-only
            STATUS       current
            DESCRIPTION
                "Indicates the number of invalid packets received by the multicast user.
                "
            ::= { hwDslamNtvUserIgmpStatEntry 12 }
            
        hwDslamNtvUserIgmpStatSuccJoinProgRcv    OBJECT-TYPE
            SYNTAX   Integer32 
            MAX-ACCESS   read-only
            STATUS       current
            DESCRIPTION
                "Indicates the number of successful join programs based on multicast user.
                "
            ::= { hwDslamNtvUserIgmpStatEntry 13 }
            
        hwDslamNtvUserIgmpStatErrJoinProgRcv    OBJECT-TYPE
            SYNTAX   Integer32 
            MAX-ACCESS   read-only
            STATUS       current
            DESCRIPTION
                "Indicates the number of unsuccessful join programs based on multicast user.
                "
            ::= { hwDslamNtvUserIgmpStatEntry 14 }
            
        hwDslamNtvUserIgmpStatLeaveProgRcv    OBJECT-TYPE
            SYNTAX   Integer32 
            MAX-ACCESS   read-only
            STATUS       current
            DESCRIPTION
                "Indicates the number of leaving programs based on multicast user.
                "
            ::= { hwDslamNtvUserIgmpStatEntry 15 }
        
        hwDslamNtvIncrementalModifyRightProfileTable    OBJECT-TYPE
            SYNTAX          SEQUENCE OF HwDslamNtvIncrementalModifyRightProfileEntry
            MAX-ACCESS      not-accessible
            STATUS          current
            DESCRIPTION
                "Modifies the authority to programs in an authority profile incrementally or in batches; 
                 queries the authority to programs in an authority profile.
                 The index of this table is hwDslamNtvRightProfileIndex.
                "
            ::= { hwDslamNtv 92 }
        
        hwDslamNtvIncrementalModifyRightProfileEntry    OBJECT-TYPE
            SYNTAX          HwDslamNtvIncrementalModifyRightProfileEntry
            MAX-ACCESS      not-accessible
            STATUS          current
            DESCRIPTION
                "Modifies the authority to programs in an authority profile incrementally or in batches; 
                 queries the authority to programs in an authority profile.
                 The index of this entry is hwDslamNtvRightProfileIndex.
                "
            INDEX 
                { 
                hwDslamNtvRightProfileIndex
                }
            ::= { hwDslamNtvIncrementalModifyRightProfileTable  1 }
        
        HwDslamNtvIncrementalModifyRightProfileEntry    ::= 
            SEQUENCE  
                {
                hwDslamNtvIncrementalModifyRightProfileMask      
                    OCTET STRING
                }
        
        hwDslamNtvIncrementalModifyRightProfileMask      OBJECT-TYPE
            SYNTAX       OCTET STRING (SIZE (0..8192))
            MAX-ACCESS   read-write
            STATUS       current
            DESCRIPTION
                "Indicates the program authority mask of an authority profile. 
                 Range: 0-8192 
                 hwDslamNtvIncrementalModifyRightProfileMask is the program authority mask of 
                 an authority profile. To modify a certain number of programs, issue the 
                 corresponding number of authority masks. Up to 4096 program masks can be issued. 
                 Each program mast occupies two bytes. The meaning of byes is shown as follows. 
                 The byte contents comply with the network byte sequence. Right(15,14): 00=idle, 
                 01=watch, 10=preview, and 11=forbidden. The reserve field is 0. The range of 
                 program index is 1-4096. If the issued masks contain repeated program authority (valid), 
                 the last program authority takes effect.
                "
            ::= { hwDslamNtvIncrementalModifyRightProfileEntry 1} 
        
        
        hwDslamNtvIgmpVersion OBJECT-TYPE
            SYNTAX  INTEGER
                { 
                igmpV2(1),
                igmpV3(2)
                }
            MAX-ACCESS read-write
            STATUS current
            DESCRIPTION
                "Indicates the IGMP version. 
                 Options:
                 1. igmpV2(1) -indicates the IGMP version is V2
                 2. igmpV3(2) -indicates the IGMP version is V3
                 Default: igmpV2(1)
                " 
            ::= { hwDslamNtv 93 }
        
        hwDslamNtvIgmpPriority OBJECT-TYPE
            SYNTAX  Integer32 (0..7)
            MAX-ACCESS read-write
            STATUS current
            DESCRIPTION
                "Indicates the IGMP priority. 
                 Range: 0-7 
                 Default: 0
                "    
            ::= { hwDslamNtv 94 } 
        
        hwDslamNtvCdrSwitch  OBJECT-TYPE
            SYNTAX      TruthValue
            MAX-ACCESS  read-write
            STATUS      current
            DESCRIPTION
                "Indicates the CDR global switch. 
                 Options:
                 1. true(1)  -indicates the CDR global switch is on
                 2. false(2) -indicates the CDR global switch is off
                 Default: false(2)
                "
            ::= { hwDslamNtv 95 }
        
        hwDslamNtvInitialUnsolicitedReportInterval  OBJECT-TYPE
            SYNTAX       Integer32(1..10)
            MAX-ACCESS   read-write
            STATUS       current
            DESCRIPTION
                "Indicates the interval for actively reporting initial IGMP join packets.                  
                 Range: 1-10 
                 Default: 1
                 Unit: second
                "      
            ::= { hwDslamNtv 96 }
        
        hwDslamNtvQueryMode OBJECT-TYPE
            SYNTAX   INTEGER
                {
                with-cvlan(1),
                with-mvlan(2)
                }
            MAX-ACCESS   read-write
            STATUS       current
            DESCRIPTION
                "The mode to send query package to EPON user.                 
                 Options:
                 1. with-cvlan(1) -indicates the mode to send query package to EPON user is with-cvlan
                 2. with-mvlan(2) -indicates the mode to send query package to EPON user is with-mvlan
                 Default: 1
                "       
            ::= { hwDslamNtv 97}        
        
        hwDslamNtvIgmpUpstreamVlanMode OBJECT-TYPE
            SYNTAX   INTEGER
                {
                mvlan(1),
                svlan(2),
                vlan(3)
                }
            MAX-ACCESS   read-write
            STATUS       current
            DESCRIPTION
                "Indicates the VLAN mode carried in an IGMP upstream packet. Options:
                 1. mvlan(1) -indicates the VLAN mode that carried in an IGMP upstream packet is mvlan
                 2. svlan(2) -indicates the VLAN mode that carried in an IGMP upstream packet is svlan
                 3. vlan(3)  -indicates the VLAN mode that carried in an IGMP upstream packet is vlan
                 Default: mvlan(1)
                 If hwDslamNtvIgmpUpstreamVlanMode is set to vlan(3), 
                 it must be issued with global leaf hwDslamNtvIgmpUpstreamVlanPara.
                "
            ::= { hwDslamNtv 98}        
        
        hwDslamNtvIgmpUpstreamVlanPara OBJECT-TYPE
            SYNTAX   Integer32
            MAX-ACCESS   read-write
            STATUS       current
            DESCRIPTION
                "Indicates the VLAN mode parameter VLAN ID carried in an IGMP upstream packet. 
                 Range: 1-4093 
                 This leaf is issued only when hwDslamNtvIgmpUpstreamVlanMode is set to vlan(3). 
                 When hwDslamNtvIgmpUpstreamVlanMode is set to mvlan (1) or svlan(2), this leaf 
                 need not be issued together. If this leaf is also issued, its value is omitted. 
                 In the get operation, -1 is returned.
                "
            ::= { hwDslamNtv 99}   
            
        hwDslamNtvEnvironmentModeSwitch OBJECT-TYPE
            SYNTAX   INTEGER
                {
                non-mvlan-mode(1),
                mvlan-mode(2)
                }
            MAX-ACCESS   read-write
            STATUS       current
            DESCRIPTION
                "The switch is offered to select a BTV environment between R3&R5. 
                 'R3' indicate BTV running under non-mvlan-mode mode,
                 Otherwise the BTV running under mvlan-mode mode.                 
                 Options:
                 1. non-mvlan-mode(1) -indicates BTV running under non-mvlan-mode mode
                 2. mvlan-mode(2)     -indicates BTV running under mvlan-mode mode
                 Default: 1
                "      
            ::= { hwDslamNtv 100}      
        
        hwDslamNtvIgmpGlobalLeaveSendSwitch OBJECT-TYPE
            SYNTAX   INTEGER
                {
                enable(1),
                disable(2)
                }
            MAX-ACCESS   read-write
            STATUS       current
            DESCRIPTION
                "The switch of Global-Leave sending.                 
                 Options:
                 1. enable(1)  -indicates the switch of Global-leave sending is enabled
                 2. disable(2) -indicates the switch of Global-leave sending is disabled
                 Default: 1
                "                         
            ::= { hwDslamNtv 101}
        
        hwDslamNtvForwardMode OBJECT-TYPE
            SYNTAX   INTEGER
                {
                mvlan(1),
                globalIp(2)
                }
            MAX-ACCESS   read-write
            STATUS       current
            DESCRIPTION
                "Indicates the forwarding control mode. 
                 Options:
                 1. mvlan(1)    -indicates the forwarding control mode is mvlan
                 2. globalIp(2) -indicates the forwarding control mode is globalIp
                 Default: mvlan(1)
                "
            ::= { hwDslamNtv 102}
        
        hwDslamNtvSendQueryToOfflineUserSwitch  OBJECT-TYPE
            SYNTAX      TruthValue
            MAX-ACCESS  read-write
            STATUS      current
            DESCRIPTION
                "Indicates the switch of sending query packets to an offline user. 
                 Options:
                 1. true(1)  -indicates sending query packets to an offline user
                 2. false(2) -indicates not sending query packets to an offline user
                 Default: false(2)
                "
            ::= { hwDslamNtv 103 }
        
        hwDslamNtvUserStaticJoinTable    OBJECT-TYPE
            SYNTAX          SEQUENCE OF HwDslamNtvUserStaticJoinEntry
            MAX-ACCESS      not-accessible
            STATUS          current
            DESCRIPTION
                "Indicates all parameters of BTV emulation.
                 The index of this table is hwDslamNtvUserStaticJoinIndex.
                "
            ::= { hwDslamNtv 104 }
        
        hwDslamNtvUserStaticJoinEntry    OBJECT-TYPE
            SYNTAX          HwDslamNtvUserStaticJoinEntry
            MAX-ACCESS      not-accessible
            STATUS          current
            DESCRIPTION
                "Indicates all parameters of BTV emulation.
                 The index of this entry is hwDslamNtvUserStaticJoinIndex.
                "
            INDEX 
                { 
                 hwDslamNtvUserStaticJoinIndex
                }
            ::= { hwDslamNtvUserStaticJoinTable  1 }
        
        HwDslamNtvUserStaticJoinEntry    ::= 
            SEQUENCE  
                {      
                hwDslamNtvUserStaticJoinRowStatus  
                    RowStatus, 
                hwDslamNtvUserStaticJoinIndex     
                    Integer32,  
                hwDslamNtvUserStaticJoinUserIndex  
                    Integer32, 
                hwDslamNtvUserStaticJoinIPAddr    
                    IpAddress,
                hwDslamNtvUserStaticJoinVlan      
                    Integer32,  
                hwDslamNtvUserStaticJoinRate      
                    Integer32, 
                hwDslamNtvUserStaticJoinResult    
                    INTEGER
                }
              
        hwDslamNtvUserStaticJoinRowStatus      OBJECT-TYPE
            SYNTAX   RowStatus
            MAX-ACCESS   read-write
            STATUS       current
            DESCRIPTION
                "Row status, used to query, create, modify, and delete a multicast emulation user. 
                 It supports the active(1), createAndGo(4), and destroy(6) operations.
                 During query, the value of this leaf is always active(1).
                 During deletion, specify the value of this leaf to destroy(6).
                 During creation, specify the value of this leaf to createAndGo(4).
                 Options:
                 1. active(1)      -indicates the query operation
                 2. createAndGo(4) -indicates the creating operation
                 3. destroy(6)     -indicates the deleting operation
                "
            ::= { hwDslamNtvUserStaticJoinEntry 1}    
         
        hwDslamNtvUserStaticJoinIndex      OBJECT-TYPE
            SYNTAX   Integer32 
            MAX-ACCESS   not-accessible
            STATUS       current
            DESCRIPTION
                "Indicates the BTV emulation index. Currently, only one emulation user is supported. 
                 Always fill 1 for the index. You can also fill -1 and the system will automatically 
                 allocate an index.
                "
            ::= { hwDslamNtvUserStaticJoinEntry 2}      
        
        hwDslamNtvUserStaticJoinUserIndex      OBJECT-TYPE
            SYNTAX   Integer32
            MAX-ACCESS   read-write
            STATUS       current
            DESCRIPTION
                "Indicates the index of a multicast user, corresponding to hwDslamNtvUserIndex
                "
            ::= { hwDslamNtvUserStaticJoinEntry 3}  
        
        hwDslamNtvUserStaticJoinIPAddr      OBJECT-TYPE
            SYNTAX   IpAddress 
            MAX-ACCESS   read-write
            STATUS       current
            DESCRIPTION
                "Indicates the IP address of an emulation program. It is the IP address of the multicast program.
                "
            ::= { hwDslamNtvUserStaticJoinEntry 4}   
        
        hwDslamNtvUserStaticJoinVlan      OBJECT-TYPE
            SYNTAX   Integer32(1..4095)
            MAX-ACCESS   read-write
            STATUS       current
            DESCRIPTION
                "Indicates the emulation program VLAN. 
                 Range: 1-4095
                "
            ::= { hwDslamNtvUserStaticJoinEntry 5}  
        
        hwDslamNtvUserStaticJoinRate      OBJECT-TYPE
            SYNTAX   Integer32
            MAX-ACCESS   read-only
            STATUS       current
            DESCRIPTION
                "Indicates the emulation program traffic.
                 Unit: kbit/s. 
                "
            ::= { hwDslamNtvUserStaticJoinEntry 6}
        
        hwDslamNtvUserStaticJoinResult      OBJECT-TYPE
            SYNTAX  INTEGER
                {             
                inProgress(1),
                success(2),
                onlineWithoutTraffic(3),
                unknownError(4),
                systemBusy(5),
                noResources(6),
                userBlocked(7),
                cacFail(8),
                authFail(9),
                previewFull(10),
                channelFull(11),
                gradedChannelFull(12)
                }         
            MAX-ACCESS   read-only
            STATUS       current
            DESCRIPTION
                "Indicates the emulation result. Options:
                 1. inProgress(1)           -started, but the final result is not obtained.
                 2. success(2)              -demand a program successfully and receive the traffic
                 3. onlineWithoutTraffic(3) -the user demands a program normally but does not receive the traffic
                 4. unknownError(4)         -demand failure caused by an exception
                 5. systemBusy(5)           -the system is busy
                 6. noResources(6)          -a lack of memory resources
                 7. userBlocked(7)          -the user is blocked
                 8. cacFail(8)              -user CAC check fails
                 9. authFail(9)             -user authentication fails
                 10. previewFull(10)        -the maximum preview count is reached
                 11. channelFull(11)        -the maximum number of channels is reached
                 12. gradedChannelFull(12)  -the number of channels at this grade reaches the maximum
                "   
            ::= { hwDslamNtvUserStaticJoinEntry 7}  
                 
        hwDslamNtvMcastVlanTagMode  OBJECT-TYPE
            SYNTAX   INTEGER
                {
                single(1),
                dual(2),
                singleTranslate(3)
                }
            MAX-ACCESS   read-write
            STATUS       current
            DESCRIPTION
                "Indicates the multicast VLAN tag mode. 
                 Options:
                 1. single(1) -indicates the multicast VLAN tag mode is single and tag transform is transparent.
                 2. dual(2)   -indicates the multicast VLAN tag mode is dual and tag transform is remove.  
                 3. singleTranslate(3) -indicates the multicast VLAN tag mode is single and tag transform is translate.
                 Default: single(1)
                "      
            ::= { hwDslamNtv 105 }    
        hwDslamNtvUserFlowTable OBJECT-TYPE
            SYNTAX SEQUENCE OF HwDslamNtvUserFlowEntry
            MAX-ACCESS not-accessible
            STATUS current
            DESCRIPTION
                "Queries the index of a corresponding multicast user according to the stream ID.
                 The index of this table is hwDslamNtvUserFlowIndex.
                "
            ::= { hwDslamNtv 106 }
               
        -- 1.3.6.1.4.1.2011.6.28.106.1
        hwDslamNtvUserFlowEntry OBJECT-TYPE
            SYNTAX HwDslamNtvUserFlowEntry
            MAX-ACCESS not-accessible
            STATUS current
            DESCRIPTION
                "Queries the index of a corresponding multicast user according to the stream ID.
                 The index of this entry is hwDslamNtvUserFlowIndex.
                "
            INDEX { hwDslamNtvUserFlowIndex }
            ::= { hwDslamNtvUserFlowTable 1 }        
        
        HwDslamNtvUserFlowEntry ::=
            SEQUENCE 
                { 
                hwDslamNtvUserFlowIndex
                    Integer32,
                hwDslamNtvUserFlowUserIndex
                    Integer32
                }
        
        -- 1.3.6.1.4.1.2011.6.28.106.1.1
        hwDslamNtvUserFlowIndex OBJECT-TYPE
            SYNTAX Integer32
            MAX-ACCESS read-only
            STATUS current
            DESCRIPTION
                "Indicates the flow ID of a multicast user. 
                "
            ::= { hwDslamNtvUserFlowEntry 1 }
        
        
        -- 1.3.6.1.4.1.2011.6.28.106.1.2
        hwDslamNtvUserFlowUserIndex OBJECT-TYPE
            SYNTAX Integer32
            MAX-ACCESS read-only
            STATUS current
            DESCRIPTION
                "Indicates the index of a multicast user, corresponding to hwDslamNtvUserIndex.
                "
            ::= { hwDslamNtvUserFlowEntry 2 }
             
        hwDslamNtvTrapsVbOids   OBJECT IDENTIFIER ::= { hwDslamNtv 107 }   
        
                 
        hwDslamNtvMvlanMemberStateOperType OBJECT-TYPE
            SYNTAX INTEGER
                {
                add(1),
                delete(2),
                block(3),
                unblock(4),
                modify(5),
                bonding(6),
                unbonding(7)
                }                                     
            MAX-ACCESS  accessible-for-notify
            STATUS      current
            DESCRIPTION
                 "It indicates OperType. 
                  Options:
                  1. add(1)       -indicates the OperType is add
                  2. delete(2)    -indicates the OperType is delete
                  3. block(3)     -indicates the OperType is block
                  4. unblock(4)   -indicates the OperType is unblock
                  5. modify(5)    -indicates the OperType is modify
                  6. bonding(6)   -indicates the OperType is bonding
                  7. unbonding(7) -indicates the OperType is unbonding
                 "
            ::= { hwDslamNtvTrapsVbOids 1}    

        hwDslamNtvFlowMulticastPolicyOperType OBJECT-TYPE
            SYNTAX INTEGER
                {
                modify(1)                
                }                                     
            MAX-ACCESS  accessible-for-notify
            STATUS      current
            DESCRIPTION
                 "It indicates the opertype of unknown multicastpolicy and IGMP packet policy change. 
                  Options:
                  1. modify(1) -indicates the opertype of unknown multicastpolicy and IGMP packet policy change
                 "
            ::= { hwDslamNtvTrapsVbOids 2}
            
        hwDslamNtvUserStaticJoinRequestID OBJECT-TYPE
            SYNTAX Integer32                                    
            MAX-ACCESS  accessible-for-notify
            STATUS      current
            DESCRIPTION
                 "It indicates the request ID of the NTV user static join trap.
                 "
            ::= { hwDslamNtvTrapsVbOids 3}
                      
            
        hwDslamNtvUserChangeType OBJECT-TYPE
            SYNTAX INTEGER
                {
                addUser(1),
                deleteUser(2),
                blockUser(3),
                unBlockUser(4),                  
                modifyUser(5),
                bindProfileToUser(6),
                unBindProfileToUser(7)
                }                                        
            MAX-ACCESS  accessible-for-notify
            STATUS      current
            DESCRIPTION
                 "It indicates the NTV user change type.
                  Options:
                  1. addUser(1)             -indicates the NTV user change type is addUser
                  2. deleteUser(2)          -indicates the NTV user change type is deleteUser
                  3. blockUser(3)           -indicates the NTV user change type is blockUser
                  4. unBlockUser(4)         -indicates the NTV user change type is unBlockUser
                  5. modifyUser(5)          -indicates the NTV user change type is modifyUser
                  6. bindProfileToUser(6)   -indicates the NTV user change type is bindProfileToUser
                  7. unBindProfileToUser(7) -indicates the NTV user change type is unBindProfileToUser
                 "
            ::= { hwDslamNtvTrapsVbOids 4}
            
        hwDslamNtvUserProfileBitMap OBJECT-TYPE
            SYNTAX OCTET STRING                                  
            MAX-ACCESS  accessible-for-notify
            STATUS      current
            DESCRIPTION
                 "The bit map indicates the relationship between user and user profile index.
                 "
            ::= { hwDslamNtvTrapsVbOids 5}
                            
        hwDslamNtvTraps OBJECT IDENTIFIER ::= { hwDslamNtv 108 } 
             
        hwDslamNtvCommonTraps OBJECT IDENTIFIER ::= { hwDslamNtvTraps 1 }  
        
        hwDslamNtvCommonTrapsPrefix OBJECT IDENTIFIER ::= { hwDslamNtvCommonTraps 0 } 
                   
        hwDslamNtvMVLANMemberStateChangeTrap NOTIFICATION-TYPE
            OBJECTS 
                {
                hwConfigChangeIP,
                hwDslamNtvMvlanMemberStateOperType,
                hwDslamNtvMVLANIndex,
                hwDslamNtvUserIndex 
                }
            STATUS current
            DESCRIPTION
                "The trap is generated when the relation of mvlan members and users changes.
                "  
            ::= { hwDslamNtvCommonTraps 0 1 }              

        hwDslamNtvFlowMulticastPolicyChangeTrap NOTIFICATION-TYPE
            OBJECTS 
                {
                hwConfigChangeIP,
                hwDslamNtvFlowMulticastPolicyOperType,
                hwDslamNtvFlowID,
                hwDslamNtvUnknownMulticastTrafficPolicy,
                hwDslamNtvIgmpPacketPolicy 
                }
            STATUS current
            DESCRIPTION
                "The trap is generated when the policy of unknown multicast based flow and IGMP packet changes.
                "  
            ::= { hwDslamNtvCommonTraps 0 2 }
            
        hwDslamNtvSmltStaticJoinTrap NOTIFICATION-TYPE
            OBJECTS 
                {
                hwDslamNtvUserStaticJoinIndex,
                hwDslamNtvUserStaticJoinUserIndex,
                hwDslamNtvUserStaticJoinIPAddr,                
                hwDslamNtvUserStaticJoinRequestID,
                hwDslamNtvUserStaticJoinVlan,
                hwDslamNtvUserStaticJoinRate,
                hwDslamNtvUserStaticJoinResult
                }
            STATUS current
            DESCRIPTION
                "The trap is generated when the user static join BTV simulation.
                "  
            ::= { hwDslamNtvCommonTraps 0 3 }   
            
            
        hwDslamNtvUserChangeTrap NOTIFICATION-TYPE
            OBJECTS 
                {
                hwConfigChangeIP,
                hwDslamNtvUserChangeType,
                hwDslamNtvUserAuthority,                
                hwDslamNtvUserOperStatus,
                hwDslamNtvUserAdminStatus,
                hwDslamNtvUserMaxChannel,
                hwDslamNtvUserEnableLog,
                hwDslamNtvUserVpi,
                hwDslamNtvUserVci,
                hwDslamNtvUserFlowType,
                hwDslamNtvUserFlowPara,
                hwDslamNtvUserUsedBandwidth,
                hwDslamNtvUserUsdBwthPcntToPortRate,
                hwDslamNtvUserIfIndex,
                hwDslamNtvUserIndex,
                hwDslamNtvUserMatchPara,
                hwDslamNtvUserMaxBandWidth,
                hwDslamNtvUserVideoVpi,
                hwDslamNtvUserVideoVci,
                hwDslamNtvUserVideoFlowType,
                hwDslamNtvUserVideoFlowPara,
                hwDslamNtvUserQuickLeaveMode,
                hwDslamNtvReceiveGlobalLeave,
                hwDslamNtvUserFlowMode,
                hwDslamNtvUserProfileBitMap,
                hwDslamNtvUserFlowID,
                hwDslamNtvUserVideoFlowID,
                hwDslamNtvUserMatchPara2, 
                hwDslamNtvUserIgmpVersion,
                hwDslamNtvUserMldQueryVersion
                }
            STATUS current
            DESCRIPTION
                "The trap is generated when the NTV user configuration changes.
                "  
            ::= { hwDslamNtvCommonTraps 0 4 }     
            
        hwDslamNtvIgmpAcceleratorMode OBJECT-TYPE
            SYNTAX   INTEGER
                {
                off(1),
                svlan(2),
                vlan(3)
                }
            MAX-ACCESS   read-write
            STATUS       current
            DESCRIPTION
                "The mode of multicast quickjoin. Options:
                 1. off(1)   -disables the IGMP accelerator in the system.
                 2. svlan(2) -enables the IGMP accelerator in all service VLANs (SVLANs) in the system.
                 3. vlan(3)  -enables the IGMP accelerator in a specified VLAN
                 Default: off(1). 
                 If hwDslamNtvIgmpAcceleratorMode is set to vlan(3), 
                 it must be issued with global leaf hwDslamNtvIgmpAcceleratorVlanPara.
                "
            ::= { hwDslamNtv 109}        
        
        hwDslamNtvIgmpAcceleratorVlanPara OBJECT-TYPE
            SYNTAX   Integer32 (-1|1..4093)
            MAX-ACCESS   read-write
            STATUS       current
            DESCRIPTION
                "The specified vlan value when hwDslamNtvIgmpAcceleratorMode is set to vlan(3). 
                 Range: 1-4093,-1 
                 This leaf is issued only when hwDslamNtvIgmpAcceleratorMode is set to vlan(3). 
                 When hwDslamNtvIgmpAcceleratorMode is set to off(1) or svlan(2), this leaf 
                 need not be issued together. If this leaf is also issued, its value is omitted. 
                 In the get operation, -1 is returned.
                "
            ::= { hwDslamNtv 110}      

        hwDslamNtvMVLANIPAddrRangeTable OBJECT-TYPE
            SYNTAX SEQUENCE OF HwDslamNtvMVLANIPAddrRangeEntry
            MAX-ACCESS not-accessible
            STATUS current
            DESCRIPTION
                "Indicates the range of IP address table.
                 The indexes of this table are hwDslamNtvVlanID and hwDslamNtvMVLANIPAddrRangeIndex.
                "
            ::= { hwDslamNtv 111 }
               
        -- 1.3.6.1.4.1.2011.6.28.111.1
        hwDslamNtvMVLANIPAddrRangeEntry OBJECT-TYPE
            SYNTAX HwDslamNtvMVLANIPAddrRangeEntry
            MAX-ACCESS not-accessible
            STATUS current
            DESCRIPTION
                "Indicates the range of IP address table.
                 The indexes of this entry are hwDslamNtvVlanID and hwDslamNtvMVLANIPAddrRangeIndex.
                "
            INDEX { 
                  hwDslamNtvVlanID,
                  hwDslamNtvMVLANIPAddrRangeIndex
                  }
            ::= { hwDslamNtvMVLANIPAddrRangeTable 1 }        
        
        HwDslamNtvMVLANIPAddrRangeEntry ::=
            SEQUENCE 
                { 
                hwDslamNtvMVLANIPAddrRangeIndex
                    Integer32,
                hwDslamNtvMVLANIPAddrRangeRowStatus
                    RowStatus,    
                hwDslamNtvMVLANIPAddrRangeDynStartIP                
                    IpAddress,
                hwDslamNtvMVLANIPAddrRangeDynEndIP                  
                    IpAddress
                }
        
        -- 1.3.6.1.4.1.2011.6.28.111.1.1
        hwDslamNtvMVLANIPAddrRangeIndex OBJECT-TYPE
            SYNTAX Integer32 (-1|1..16)
            MAX-ACCESS read-only
            STATUS current
            DESCRIPTION
                "Indicates the index of IP address range.
                 Range: 1-16,-1 
                 You can also fill -1 and the system will automatically allocate an index.
                "
            ::= { hwDslamNtvMVLANIPAddrRangeEntry 1 }
        
        
        -- 1.3.6.1.4.1.2011.6.28.111.1.2
        hwDslamNtvMVLANIPAddrRangeRowStatus      OBJECT-TYPE
            SYNTAX       RowStatus
            MAX-ACCESS   read-create
            STATUS       current
            DESCRIPTION
                "Row status, used to query, create, and delete an IP address range. 
                 It supports the active(1), createAndGo(4), and destroy(6) operations.
                 During query, the value of this leaf is always active(1).
                 During deletion, specify the value of this leaf to destroy(6).
                 During creation, specify the value of this leaf to createAndGo(4).
                "
            ::= { hwDslamNtvMVLANIPAddrRangeEntry 2}
            
        hwDslamNtvMVLANIPAddrRangeDynStartIP OBJECT-TYPE
            SYNTAX  IpAddress
            MAX-ACCESS read-write
            STATUS current
            DESCRIPTION
                "Indicates the start IP address of the programs that can be generated dynamically.
                "
            ::= { hwDslamNtvMVLANIPAddrRangeEntry 3 } 
            
        hwDslamNtvMVLANIPAddrRangeDynEndIP OBJECT-TYPE
            SYNTAX  IpAddress
            MAX-ACCESS read-write
            STATUS current
            DESCRIPTION
                "Indicates the end IP address of the programs that can be generated dynamically.
                "
            ::= { hwDslamNtvMVLANIPAddrRangeEntry 4 }       

            
        hwDslamNtvIgmpUserStatCurrTable OBJECT-TYPE
            SYNTAX SEQUENCE OF HwDslamNtvIgmpUserStatCurrEntry
            MAX-ACCESS not-accessible
            STATUS current
            DESCRIPTION
                "Queries the igmp current 15 minutes statistic.
                 The index of this table is hwDslamNtvUserIndex.
                "
            ::= { hwDslamNtv 112 }
               
        -- 1.3.6.1.4.1.2011.6.28.112.1
        hwDslamNtvIgmpUserStatCurrEntry OBJECT-TYPE
            SYNTAX HwDslamNtvIgmpUserStatCurrEntry
            MAX-ACCESS not-accessible
            STATUS current
            DESCRIPTION
                "Queries the igmp current 15 minutes statistic.
                 The index of this entry is hwDslamNtvUserIndex.
                "
            INDEX { hwDslamNtvUserIndex }
            ::= { hwDslamNtvIgmpUserStatCurrTable 1 }        
        
        HwDslamNtvIgmpUserStatCurrEntry ::=
            SEQUENCE 
                { 
                hwDslamNtvIgmpUserCurr15MinJoinSuccessNum
                    Counter32,
                hwDslamNtvIgmpUserCurr15MinJoinFailNum
                    Counter32,
                hwDslamNtvIgmpUserCurr15MinLeaveSuccessNum
                    Counter32,
                hwDslamNtvIgmpUserCurr15MinLeaveFailNum
                    Counter32,
                hwDslamNtvIgmpUserCurr15MinInvalidPackNum
                    Counter32
                }
        
        -- 1.3.6.1.4.1.2011.6.28.112.1.1
        hwDslamNtvIgmpUserCurr15MinJoinSuccessNum OBJECT-TYPE
            SYNTAX Counter32
            MAX-ACCESS read-only
            STATUS current
            DESCRIPTION
                "Indicates the success join number in current 15 minutes. 
                "
            ::= { hwDslamNtvIgmpUserStatCurrEntry 1 }
            
        -- 1.3.6.1.4.1.2011.6.28.112.1.2
        hwDslamNtvIgmpUserCurr15MinJoinFailNum OBJECT-TYPE
            SYNTAX Counter32
            MAX-ACCESS read-only
            STATUS current
            DESCRIPTION
                "Indicates the fail join number in current 15 minutes. 
                "
            ::= { hwDslamNtvIgmpUserStatCurrEntry 2 }
            
        -- 1.3.6.1.4.1.2011.6.28.112.1.3
        hwDslamNtvIgmpUserCurr15MinLeaveSuccessNum OBJECT-TYPE
            SYNTAX Counter32
            MAX-ACCESS read-only
            STATUS current
            DESCRIPTION
                "Indicates the success leave number in current 15 minutes. 
                "
            ::= { hwDslamNtvIgmpUserStatCurrEntry 3 }
            
        -- 1.3.6.1.4.1.2011.6.28.112.1.4
        hwDslamNtvIgmpUserCurr15MinLeaveFailNum OBJECT-TYPE
            SYNTAX Counter32
            MAX-ACCESS read-only
            STATUS current
            DESCRIPTION
                "Indicates the fail leave number in current 15 minutes. 
                "
            ::= { hwDslamNtvIgmpUserStatCurrEntry 4 }                       
            
        -- 1.3.6.1.4.1.2011.6.28.112.1.5
        hwDslamNtvIgmpUserCurr15MinInvalidPackNum OBJECT-TYPE
            SYNTAX Counter32
            MAX-ACCESS read-only
            STATUS current
            DESCRIPTION
                "Indicates the invalid igmp packet number in current 15 minutes. 
                "
            ::= { hwDslamNtvIgmpUserStatCurrEntry 5 }
            
            
         hwDslamNtvIgmpUserStatHistTable OBJECT-TYPE
            SYNTAX SEQUENCE OF HwDslamNtvIgmpUserStatHistEntry
            MAX-ACCESS not-accessible
            STATUS current
            DESCRIPTION
                "Queries the igmp history 15 minutes statistic.
                 The index of this table is hwDslamNtvUserIndex.
                "
            ::= { hwDslamNtv 113 }
               
        -- 1.3.6.1.4.1.2011.6.28.113.1
        hwDslamNtvIgmpUserStatHistEntry OBJECT-TYPE
            SYNTAX HwDslamNtvIgmpUserStatHistEntry
            MAX-ACCESS not-accessible
            STATUS current
            DESCRIPTION
                "Queries the igmp history 15 minutes statistic.
                 The index of this entry is hwDslamNtvUserIndex.
                "
            INDEX { hwDslamNtvUserIndex }
            ::= { hwDslamNtvIgmpUserStatHistTable 1 }        
        
        HwDslamNtvIgmpUserStatHistEntry ::=
            SEQUENCE 
                { 
                hwDslamNtvIgmpUserHist15MinJoinSuccessNum
                    Counter32,
                hwDslamNtvIgmpUserHist15MinJoinFailNum
                    Counter32,
                hwDslamNtvIgmpUserHist15MinLeaveSuccessNum
                    Counter32,
                hwDslamNtvIgmpUserHist15MinLeaveFailNum
                    Counter32,
                hwDslamNtvIgmpUserHist15MinInvalidPackNum
                    Counter32
                }
        
        -- 1.3.6.1.4.1.2011.6.28.113.1.1
        hwDslamNtvIgmpUserHist15MinJoinSuccessNum OBJECT-TYPE
            SYNTAX Counter32
            MAX-ACCESS read-only
            STATUS current
            DESCRIPTION
                "Indicates the success join number in history 15 minutes. 
                "
            ::= { hwDslamNtvIgmpUserStatHistEntry 1 }
            
        -- 1.3.6.1.4.1.2011.6.28.113.1.2
        hwDslamNtvIgmpUserHist15MinJoinFailNum OBJECT-TYPE
            SYNTAX Counter32
            MAX-ACCESS read-only
            STATUS current
            DESCRIPTION
                "Indicates the fail join number in history 15 minutes. 
                "
            ::= { hwDslamNtvIgmpUserStatHistEntry 2 }
            
        -- 1.3.6.1.4.1.2011.6.28.113.1.3
        hwDslamNtvIgmpUserHist15MinLeaveSuccessNum OBJECT-TYPE
            SYNTAX Counter32
            MAX-ACCESS read-only
            STATUS current
            DESCRIPTION
                "Indicates the success leave number in history 15 minutes. 
                "
            ::= { hwDslamNtvIgmpUserStatHistEntry 3 }
            
        -- 1.3.6.1.4.1.2011.6.28.113.1.4
        hwDslamNtvIgmpUserHist15MinLeaveFailNum OBJECT-TYPE
            SYNTAX Counter32
            MAX-ACCESS read-only
            STATUS current
            DESCRIPTION
                "Indicates the fail leave number in history 15 minutes. 
                "
            ::= { hwDslamNtvIgmpUserStatHistEntry 4 }

        -- 1.3.6.1.4.1.2011.6.28.113.1.5
        hwDslamNtvIgmpUserHist15MinInvalidPackNum OBJECT-TYPE
            SYNTAX Counter32
            MAX-ACCESS read-only
            STATUS current
            DESCRIPTION
                "Indicates the invalid igmp packet number in current 15 minutes. 
                "
            ::= { hwDslamNtvIgmpUserStatHistEntry 5 }
            

        hwDslamNtvSourceIpAndGroupIpMode OBJECT-TYPE
            SYNTAX      INTEGER
                {
                enable(1),
                disable(2)
                }
            MAX-ACCESS  read-write
            STATUS      current
            DESCRIPTION
                "Indicates the Source IP and Group IP forward mode. 
                 Options:
                 1. enable(1)  -indicates the Source IP and Group IP forward mode is enable
                 2. disable(2) -indicates the Source IP and Group IP forward mode is disable
                 Default: disable(2)
                "
            ::= { hwDslamNtv 114 }

        -- 1.3.6.1.4.1.2011.6.28.115
        hwDslamNtvMldStatisticTable    OBJECT-TYPE
            SYNTAX          SEQUENCE OF HwDslamNtvMldStatisticEntry
            MAX-ACCESS      not-accessible
            STATUS          current
            DESCRIPTION
                "Indicates the various operations on MLD packet statistics.
                 The index of this table is hwDslamNtvMldStatisticTypeIndex.
                "
            ::= { hwDslamNtv 115 }
            
        -- 1.3.6.1.4.1.2011.6.28.115.1
        hwDslamNtvMldStatisticEntry    OBJECT-TYPE
            SYNTAX         HwDslamNtvMldStatisticEntry
            MAX-ACCESS     not-accessible
            STATUS         current
            DESCRIPTION
                "Indicates the various operations on MLD packet statistics.
                 The index of this entry is hwDslamNtvMldStatisticTypeIndex.
                "
            INDEX
                { 
                hwDslamNtvMldStatisticTypeIndex
                }
            ::= { hwDslamNtvMldStatisticTable  1 }
        
        HwDslamNtvMldStatisticEntry    ::=
            SEQUENCE  
                {
                hwDslamNtvMldStatisticTypeIndex
                    Unsigned32,
                hwDslamNtvMldStatisticOperMode
                    INTEGER,
                hwDslamNtvMldStatisticQueryV1Rcv
                    Unsigned32,
                hwDslamNtvMldStatisticQueryV2Rcv
                    Unsigned32,
                hwDslamNtvMldStatisticReportV1Rcv
                    Unsigned32,
                hwDslamNtvMldStatisticReportV2Rcv
                    Unsigned32,
                hwDslamNtvMldStatisticDoneV1Rcv
                    Unsigned32,
                hwDslamNtvMldStatisticInvalidRcv
                    Unsigned32,
                hwDslamNtvMldStatisticQueryV1Snd
                    Unsigned32,
                hwDslamNtvMldStatisticQueryV2Snd
                    Unsigned32,
                hwDslamNtvMldStatisticReportV1Snd
                    Unsigned32,
                hwDslamNtvMldStatisticReportV2Snd
                    Unsigned32,
                hwDslamNtvMldStatisticDoneV1Snd
                    Unsigned32
                }

        -- 1.3.6.1.4.1.2011.6.28.115.1.1
        hwDslamNtvMldStatisticTypeIndex       OBJECT-TYPE
            SYNTAX       Unsigned32 (1)
            MAX-ACCESS   read-only
            STATUS       current
            DESCRIPTION
                "Indicates the performance statistics type.
                 Options:
                 1. global MLD statistic(1) -indicates that the performance statistics type is global MLD statistic
                "
            ::= { hwDslamNtvMldStatisticEntry 1}

        -- 1.3.6.1.4.1.2011.6.28.115.1.2
        hwDslamNtvMldStatisticOperMode        OBJECT-TYPE
            SYNTAX   INTEGER
                 {
                 clearStatistic(1),
                 invalid(-1)
                 }
            MAX-ACCESS   read-write
            STATUS       current
            DESCRIPTION
                "Indicates the operation mode of performance statistics.
                 Options:
                 1. clearStatistic(1) -means to clear statistics
                 2. invalid(-1)       -indicates invalid operation mode
                "
            ::= { hwDslamNtvMldStatisticEntry 2}

        -- 1.3.6.1.4.1.2011.6.28.115.1.3
        hwDslamNtvMldStatisticQueryV1Rcv    OBJECT-TYPE
            SYNTAX       Unsigned32
            MAX-ACCESS   read-only
            STATUS       current
            DESCRIPTION
                "Indicates the number of received query packets of V1 from network.
                "
            ::= { hwDslamNtvMldStatisticEntry 3}

        -- 1.3.6.1.4.1.2011.6.28.115.1.4
        hwDslamNtvMldStatisticQueryV2Rcv   OBJECT-TYPE
            SYNTAX       Unsigned32 
            MAX-ACCESS   read-only
            STATUS       current
            DESCRIPTION
                "Indicates the number of received query packets of V2 from network.
                "
            ::= { hwDslamNtvMldStatisticEntry 4}

        -- 1.3.6.1.4.1.2011.6.28.115.1.5
        hwDslamNtvMldStatisticReportV1Rcv    OBJECT-TYPE
            SYNTAX       Unsigned32 
            MAX-ACCESS   read-only
            STATUS       current
            DESCRIPTION
                "Indicates the number of received report packets of V1 from users and cascades.
                "
            ::= { hwDslamNtvMldStatisticEntry 5}

        -- 1.3.6.1.4.1.2011.6.28.115.1.6
        hwDslamNtvMldStatisticReportV2Rcv    OBJECT-TYPE
            SYNTAX       Unsigned32 
            MAX-ACCESS   read-only
            STATUS       current
            DESCRIPTION
                "Indicates the number of received report packets of V2 from users and cascades.
                "
            ::= { hwDslamNtvMldStatisticEntry 6}

        -- 1.3.6.1.4.1.2011.6.28.115.1.7
        hwDslamNtvMldStatisticDoneV1Rcv    OBJECT-TYPE
            SYNTAX       Unsigned32 
            MAX-ACCESS   read-only
            STATUS       current
            DESCRIPTION
                "Indicates the number of received done packets of V1 from users and cascades.
                "
            ::= { hwDslamNtvMldStatisticEntry 7}

        -- 1.3.6.1.4.1.2011.6.28.115.1.8
        hwDslamNtvMldStatisticInvalidRcv    OBJECT-TYPE
            SYNTAX       Unsigned32 
            MAX-ACCESS   read-only
            STATUS       current
            DESCRIPTION
                "Indicates the number of received invalid report packets.
                "
            ::= { hwDslamNtvMldStatisticEntry 8}

        -- 1.3.6.1.4.1.2011.6.28.115.1.9
        hwDslamNtvMldStatisticQueryV1Snd    OBJECT-TYPE
            SYNTAX       Unsigned32
            MAX-ACCESS   read-only
            STATUS       current
            DESCRIPTION
                "Indicates the number of sent query packets of V1 to users and cascades.
                "
            ::= { hwDslamNtvMldStatisticEntry 9}

        -- 1.3.6.1.4.1.2011.6.28.115.1.10
        hwDslamNtvMldStatisticQueryV2Snd       OBJECT-TYPE
            SYNTAX       Unsigned32 
            MAX-ACCESS   read-only
            STATUS       current
            DESCRIPTION
                "Indicates the number of sent query packets of V2 to users and cascades.
                "
            ::= { hwDslamNtvMldStatisticEntry 10}

        -- 1.3.6.1.4.1.2011.6.28.115.1.11
        hwDslamNtvMldStatisticReportV1Snd    OBJECT-TYPE
            SYNTAX       Unsigned32 
            MAX-ACCESS   read-only
            STATUS       current
            DESCRIPTION
                "Indicates the number of sent report packets of V1 to network.
                "
            ::= { hwDslamNtvMldStatisticEntry 11}

        -- 1.3.6.1.4.1.2011.6.28.115.1.12
        hwDslamNtvMldStatisticReportV2Snd    OBJECT-TYPE
            SYNTAX       Unsigned32 
            MAX-ACCESS   read-only
            STATUS       current
            DESCRIPTION
                "Indicates the number of sent report packets of V2 to network.
                "
            ::= { hwDslamNtvMldStatisticEntry 12}

        -- 1.3.6.1.4.1.2011.6.28.115.1.13
        hwDslamNtvMldStatisticDoneV1Snd    OBJECT-TYPE
            SYNTAX       Unsigned32 
            MAX-ACCESS   read-only
            STATUS       current
            DESCRIPTION
                "Indicates the number of sent done packets of V1 to network.
                "
            ::= { hwDslamNtvMldStatisticEntry 13}

        -- 1.3.6.1.4.1.2011.6.28.116
        hwDslamNtvUserMldStatTable    OBJECT-TYPE
            SYNTAX          SEQUENCE OF HwDslamNtvUserMldStatEntry
            MAX-ACCESS      not-accessible
            STATUS          current
            DESCRIPTION
                "Indicates the statistics of MLD packets sent and received by a multicast user.
                 The index of this table is hwDslamNtvUserMldStatUserIndex.
                "
            ::= { hwDslamNtv 116 }

        -- 1.3.6.1.4.1.2011.6.28.116.1
        hwDslamNtvUserMldStatEntry    OBJECT-TYPE
            SYNTAX         HwDslamNtvUserMldStatEntry
            MAX-ACCESS     not-accessible
            STATUS         current
            DESCRIPTION
                "Indicates the statistics of MLD packets sent and received by a multicast user.
                 The index of this entry is hwDslamNtvUserMldStatUserIndex.
                "
            INDEX   {
                      hwDslamNtvUserMldStatUserIndex
                    }
            ::= { hwDslamNtvUserMldStatTable  1 }

        HwDslamNtvUserMldStatEntry    ::= 
            SEQUENCE
                {
                hwDslamNtvUserMldStatUserIndex
                    Unsigned32,
                hwDslamNtvUserMldStatOperMode
                    INTEGER,
                hwDslamNtvUserMldStatReportV1Rcv
                    Unsigned32,
                hwDslamNtvUserMldStatReportV2Rcv
                    Unsigned32,
                hwDslamNtvUserMldStatDoneV1Rcv
                    Unsigned32,
                hwDslamNtvUserMldStatInvalidRcv
                    Unsigned32,
                hwDslamNtvUserMldStatQuerySnd
                    Unsigned32
               }
        
        -- 1.3.6.1.4.1.2011.6.28.116.1.1
        hwDslamNtvUserMldStatUserIndex       OBJECT-TYPE
            SYNTAX     Unsigned32
            MAX-ACCESS read-only
            STATUS     current
            DESCRIPTION
                "Indicates the index of a multicast user. Its value and algorithm are the same as those of hwDslamNtvUserIndex.
                "
            ::= { hwDslamNtvUserMldStatEntry 1 }

        -- 1.3.6.1.4.1.2011.6.28.116.1.2
        hwDslamNtvUserMldStatOperMode        OBJECT-TYPE
            SYNTAX   INTEGER
                 {
                 clearStatistic(1),
                 invalid(-1)
                 }
            MAX-ACCESS   read-write
            STATUS       current
            DESCRIPTION
                "Indicates the operation mode. The set operation can clear statistics of user MLD packets.
                 Options:
                 1. clearStatistic(1) -means to clear statistics of user packets
                 2. invalid(-1)       -indicates invalid operation mode
                "
            ::= { hwDslamNtvUserMldStatEntry 2}

        -- 1.3.6.1.4.1.2011.6.28.116.1.3
        hwDslamNtvUserMldStatReportV1Rcv    OBJECT-TYPE
            SYNTAX       Unsigned32
            MAX-ACCESS   read-only
            STATUS       current
            DESCRIPTION
                "Indicates the number of V1 report packets received by the multicast user.
                "
            ::= { hwDslamNtvUserMldStatEntry 3} 

        -- 1.3.6.1.4.1.2011.6.28.116.1.4
        hwDslamNtvUserMldStatReportV2Rcv    OBJECT-TYPE
            SYNTAX       Unsigned32
            MAX-ACCESS   read-only
            STATUS       current
            DESCRIPTION
                "Indicates the number of V2 report packets received by the multicast user.
                "
            ::= { hwDslamNtvUserMldStatEntry 4}

        -- 1.3.6.1.4.1.2011.6.28.116.1.5
        hwDslamNtvUserMldStatDoneV1Rcv    OBJECT-TYPE
            SYNTAX       Unsigned32
            MAX-ACCESS   read-only
            STATUS       current
            DESCRIPTION
                "Indicates the number of V1 done packets received by the multicast user.
                "
            ::= { hwDslamNtvUserMldStatEntry 5}

        -- 1.3.6.1.4.1.2011.6.28.116.1.6
        hwDslamNtvUserMldStatInvalidRcv    OBJECT-TYPE
            SYNTAX       Unsigned32
            MAX-ACCESS   read-only
            STATUS       current
            DESCRIPTION
                "Indicates the number of invalid packets received by the multicast user.
                "
            ::= { hwDslamNtvUserMldStatEntry 6}

        -- 1.3.6.1.4.1.2011.6.28.116.1.7
        hwDslamNtvUserMldStatQuerySnd    OBJECT-TYPE
            SYNTAX       Unsigned32
            MAX-ACCESS   read-only
            STATUS       current
            DESCRIPTION
                "Indicates the number of query packets sent by the multicast user.
                "
            ::= { hwDslamNtvUserMldStatEntry 7}

        -- 1.3.6.1.4.1.2011.6.28.117
        hwDslamNtvMVlanMldStatTable    OBJECT-TYPE
            SYNTAX          SEQUENCE OF HwDslamNtvMVlanMldStatEntry
            MAX-ACCESS      not-accessible
            STATUS          current
            DESCRIPTION
                "Indicates the statistics of MLD packets sent and received in a multicast VLAN.
                 The index of this table is hwDslamNtvMVlanMldStatMVlanIndex.
                "
            ::= { hwDslamNtv 117 }
        
        -- 1.3.6.1.4.1.2011.6.28.117.1
        hwDslamNtvMVlanMldStatEntry    OBJECT-TYPE
            SYNTAX         HwDslamNtvMVlanMldStatEntry
            MAX-ACCESS     not-accessible
            STATUS         current
            DESCRIPTION
                "Indicates the statistics of MLD packets sent and received in a multicast VLAN.
                 The index of this entry is hwDslamNtvMVlanMldStatMVlanIndex.
                "
            INDEX
                {
                hwDslamNtvMVlanMldStatMVlanIndex
                }
            ::= { hwDslamNtvMVlanMldStatTable  1 }

        HwDslamNtvMVlanMldStatEntry    ::=
            SEQUENCE
                {
                hwDslamNtvMVlanMldStatMVlanIndex
                    Unsigned32,
                hwDslamNtvMVlanMldStatOperMode
                    INTEGER,
                hwDslamNtvMVlanMldStatQueryV1Rcv
                    Unsigned32,
                hwDslamNtvMVlanMldStatQueryV2Rcv
                    Unsigned32,
                hwDslamNtvMVlanMldStatReportV1Rcv
                    Unsigned32,
                hwDslamNtvMVlanMldStatReportV2Rcv
                    Unsigned32,
                hwDslamNtvMVlanMldStatDoneV1Rcv
                    Unsigned32,
                hwDslamNtvMVlanMldStatInvalidRcv
                    Unsigned32,
                hwDslamNtvMVlanMldStatQueryV1Snd
                    Unsigned32,
                hwDslamNtvMVlanMldStatQueryV2Snd
                    Unsigned32,
                hwDslamNtvMVlanMldStatReportV1Snd
                    Unsigned32,
                hwDslamNtvMVlanMldStatReportV2Snd
                    Unsigned32,
                hwDslamNtvMVlanMldStatDoneV1Snd
                    Unsigned32,
                hwDslamNtvMVlanMldActiveProgramNum
                    Unsigned32,
                hwDslamNtvMVlanMldActiveUserNum
                    Unsigned32,
                hwDslamNtvMVlanMldStatGenQueryRcvdFromNetwork
                    Counter32,
                hwDslamNtvMVlanMldStatSpecQueryRcvdFromNetwork
                    Counter32,
                hwDslamNtvMVlanMldStatV1JoinRcvdFromUser
                    Counter32,
                hwDslamNtvMVlanMldStatV2JoinRcvdFromUser
                    Counter32,
                hwDslamNtvMVlanMldStatLeaveRcvdFromUser
                    Counter32,
                hwDslamNtvMVlanMldStatGenQuerySentToUser
                    Counter32,
                hwDslamNtvMVlanMldStatSpecQuerySentToUser
                    Counter32,
                hwDslamNtvMVlanMldStatV2JoinSentToNetwork
                    Counter32,
                hwDslamNtvMVlanMldStatLeaveSentToNetwork
                    Counter32,
                hwDslamNtvMVlanMldStatInvalidRcvdFromUser
                    Counter32     
               }

        -- 1.3.6.1.4.1.2011.6.28.117.1.1
        hwDslamNtvMVlanMldStatMVlanIndex       OBJECT-TYPE
            SYNTAX     Unsigned32 (1..256)
            MAX-ACCESS read-only
            STATUS     current
            DESCRIPTION
                "Indicates the multicast VLAN index. Its value and algorithm are the same as those of hwDslamNtvMVLANIndex.
                "
            ::= { hwDslamNtvMVlanMldStatEntry 1 }

        -- 1.3.6.1.4.1.2011.6.28.117.1.2
        hwDslamNtvMVlanMldStatOperMode        OBJECT-TYPE
            SYNTAX   INTEGER
            {
            clearStatistic(1),
            invalid(-1)
            }
            MAX-ACCESS   read-write
            STATUS       current
            DESCRIPTION
                "Indicates the operation mode. The set operation can clear statistics of MLD packets.
                 Options:
                 1. clearStatistic(1) -means to clear statistics of multicast VLAN packets
                 2. invalid(-1)       -indicates invalid
                "
            ::= { hwDslamNtvMVlanMldStatEntry 2}

        -- 1.3.6.1.4.1.2011.6.28.117.1.3
        hwDslamNtvMVlanMldStatQueryV1Rcv    OBJECT-TYPE
            SYNTAX       Unsigned32
            MAX-ACCESS   read-only
            STATUS       current
            DESCRIPTION
                "Indicates the number of V1 query packets received from network in a multicast VLAN.
                "
            ::= { hwDslamNtvMVlanMldStatEntry 3}

        -- 1.3.6.1.4.1.2011.6.28.117.1.4
        hwDslamNtvMVlanMldStatQueryV2Rcv   OBJECT-TYPE
            SYNTAX       Unsigned32
            MAX-ACCESS   read-only
            STATUS       current
            DESCRIPTION
                "Indicates the number of V2 query packets received from network in a multicast VLAN.
                "
            ::= { hwDslamNtvMVlanMldStatEntry 4}
        
        -- 1.3.6.1.4.1.2011.6.28.117.1.5
        hwDslamNtvMVlanMldStatReportV1Rcv    OBJECT-TYPE
            SYNTAX       Unsigned32
            MAX-ACCESS   read-only
            STATUS       current
            DESCRIPTION
                "Indicates the number of V1 report packets received from cascades in a multicast VLAN.
                "
            ::= { hwDslamNtvMVlanMldStatEntry 5}

        -- 1.3.6.1.4.1.2011.6.28.117.1.6
        hwDslamNtvMVlanMldStatReportV2Rcv    OBJECT-TYPE
            SYNTAX       Unsigned32
            MAX-ACCESS   read-only
            STATUS       current
            DESCRIPTION
                "Indicates the number of V2 report packets received from cascades in a multicast VLAN.
                "
            ::= { hwDslamNtvMVlanMldStatEntry 6}

        -- 1.3.6.1.4.1.2011.6.28.117.1.7
        hwDslamNtvMVlanMldStatDoneV1Rcv    OBJECT-TYPE
            SYNTAX       Unsigned32
            MAX-ACCESS   read-only
            STATUS       current
            DESCRIPTION
                "Indicates the number of V1 done packets received from cascades in a multicast VLAN.
                "
            ::= { hwDslamNtvMVlanMldStatEntry 7}

        -- 1.3.6.1.4.1.2011.6.28.117.1.8
        hwDslamNtvMVlanMldStatInvalidRcv    OBJECT-TYPE
            SYNTAX       Unsigned32
            MAX-ACCESS   read-only
            STATUS       current
            DESCRIPTION
                "Indicates the number of invalid packets received from network and cascades in a multicast VLAN.
                "
            ::= { hwDslamNtvMVlanMldStatEntry 8}
        
        -- 1.3.6.1.4.1.2011.6.28.117.1.9
        hwDslamNtvMVlanMldStatQueryV1Snd    OBJECT-TYPE
            SYNTAX       Unsigned32
            MAX-ACCESS   read-only
            STATUS       current
            DESCRIPTION
                "Indicates the number of V1 query packets sent to cascades in a multicast VLAN.
                "
            ::= { hwDslamNtvMVlanMldStatEntry 9}

        -- 1.3.6.1.4.1.2011.6.28.117.1.10
        hwDslamNtvMVlanMldStatQueryV2Snd       OBJECT-TYPE
            SYNTAX       Unsigned32
            MAX-ACCESS   read-only
            STATUS       current
            DESCRIPTION
                "Indicates the number of V2 query packets sent to cascades in a multicast VLAN.
                "
            ::= { hwDslamNtvMVlanMldStatEntry 10}
        
        -- 1.3.6.1.4.1.2011.6.28.117.1.11
        hwDslamNtvMVlanMldStatReportV1Snd    OBJECT-TYPE
            SYNTAX       Unsigned32
            MAX-ACCESS   read-only
            STATUS       current
            DESCRIPTION
                "Indicates the number of V1 report packets sent to network in a multicast VLAN.
                "
            ::= { hwDslamNtvMVlanMldStatEntry 11}

        -- 1.3.6.1.4.1.2011.6.28.117.1.12
        hwDslamNtvMVlanMldStatReportV2Snd    OBJECT-TYPE
            SYNTAX       Unsigned32
            MAX-ACCESS   read-only
            STATUS       current
            DESCRIPTION
                "Indicates the number of V2 report packets sent to network in a multicast VLAN.
                "
            ::= { hwDslamNtvMVlanMldStatEntry 12}

        -- 1.3.6.1.4.1.2011.6.28.117.1.13
        hwDslamNtvMVlanMldStatDoneV1Snd    OBJECT-TYPE
            SYNTAX       Unsigned32
            MAX-ACCESS   read-only
            STATUS       current
            DESCRIPTION
                "Indicates the number of V1 done packets sent to network in a multicast VLAN.
                "
            ::= { hwDslamNtvMVlanMldStatEntry 13}

        -- 1.3.6.1.4.1.2011.6.28.117.1.14
        hwDslamNtvMVlanMldActiveProgramNum    OBJECT-TYPE
            SYNTAX       Unsigned32
            MAX-ACCESS   read-only
            STATUS       current
            DESCRIPTION
                "Indicates the number of online programs in a multicast VLAN.
                "
            ::= { hwDslamNtvMVlanMldStatEntry 14}

        -- 1.3.6.1.4.1.2011.6.28.117.1.15
        hwDslamNtvMVlanMldActiveUserNum    OBJECT-TYPE
            SYNTAX       Unsigned32
            MAX-ACCESS   read-only
            STATUS       current
            DESCRIPTION
                "Indicates the number of online users in a multicast VLAN.
                "
            ::= { hwDslamNtvMVlanMldStatEntry 15}
            
        -- 1.3.6.1.4.1.2011.6.28.117.1.16   
        hwDslamNtvMVlanMldStatGenQueryRcvdFromNetwork       OBJECT-TYPE
            SYNTAX       Counter32
            MAX-ACCESS   read-only
            STATUS       current
            DESCRIPTION
                "Indicates the number of received general query from network in a multicast VLAN. 
                "
            ::= { hwDslamNtvMVlanMldStatEntry 16}

        -- 1.3.6.1.4.1.2011.6.28.117.1.17
        hwDslamNtvMVlanMldStatSpecQueryRcvdFromNetwork       OBJECT-TYPE
            SYNTAX       Counter32
            MAX-ACCESS   read-only
            STATUS       current
            DESCRIPTION
                "Indicates the number of received specific query from network in a multicast VLAN.
                "
            ::= { hwDslamNtvMVlanMldStatEntry 17}

       -- 1.3.6.1.4.1.2011.6.28.117.1.18
       hwDslamNtvMVlanMldStatV1JoinRcvdFromUser       OBJECT-TYPE
            SYNTAX       Counter32
            MAX-ACCESS   read-only
            STATUS       current
            DESCRIPTION
                "Indicates the number of V1 join programs received from users in a multicast VLAN.
                "
            ::= { hwDslamNtvMVlanMldStatEntry 18}

       -- 1.3.6.1.4.1.2011.6.28.117.1.19
       hwDslamNtvMVlanMldStatV2JoinRcvdFromUser       OBJECT-TYPE
            SYNTAX       Counter32
            MAX-ACCESS   read-only
            STATUS       current
            DESCRIPTION
                "Indicates the number of V2 join programs received from users in a multicast VLAN.
                "
            ::= { hwDslamNtvMVlanMldStatEntry 19}

       -- 1.3.6.1.4.1.2011.6.28.117.1.20
       hwDslamNtvMVlanMldStatLeaveRcvdFromUser       OBJECT-TYPE
            SYNTAX       Counter32
            MAX-ACCESS   read-only
            STATUS       current
            DESCRIPTION
                "Indicates the number of leaving programs received from users in a multicast VLAN.
                "
            ::= { hwDslamNtvMVlanMldStatEntry 20}

       -- 1.3.6.1.4.1.2011.6.28.117.1.21
       hwDslamNtvMVlanMldStatGenQuerySentToUser       OBJECT-TYPE
            SYNTAX       Counter32
            MAX-ACCESS   read-only
            STATUS       current
            DESCRIPTION
                "Indicates the number of general query sent to users in a multicast VLAN.
                "
            ::= { hwDslamNtvMVlanMldStatEntry 21}

        -- 1.3.6.1.4.1.2011.6.28.117.1.22
        hwDslamNtvMVlanMldStatSpecQuerySentToUser       OBJECT-TYPE
            SYNTAX       Counter32
            MAX-ACCESS   read-only
            STATUS       current
            DESCRIPTION
                "Indicates the number of specific query sent to users in a multicast VLAN.
                "
            ::= { hwDslamNtvMVlanMldStatEntry 22}

       -- 1.3.6.1.4.1.2011.6.28.117.1.23
       hwDslamNtvMVlanMldStatV2JoinSentToNetwork        OBJECT-TYPE
            SYNTAX       Counter32
            MAX-ACCESS   read-only
            STATUS       current
            DESCRIPTION
                "Indicates the number of V2 join programs sent to network in a multicast VLAN.
                "
            ::= { hwDslamNtvMVlanMldStatEntry 23}

       -- 1.3.6.1.4.1.2011.6.28.117.1.24
       hwDslamNtvMVlanMldStatLeaveSentToNetwork       OBJECT-TYPE
            SYNTAX       Counter32
            MAX-ACCESS   read-only
            STATUS       current
            DESCRIPTION
                "Indicates the number of leaving programs sent to network in a multicast VLAN.
                "
            ::= { hwDslamNtvMVlanMldStatEntry 24}
            
       -- 1.3.6.1.4.1.2011.6.28.117.1.25
       hwDslamNtvMVlanMldStatInvalidRcvdFromUser       OBJECT-TYPE
            SYNTAX       Counter32
            MAX-ACCESS   read-only
            STATUS       current
            DESCRIPTION
                "Indicates the number of invalid packets received from users in a multicast VLAN.
                "
            ::= { hwDslamNtvMVlanMldStatEntry 25}

        hwDslamNtvMVLANIPv6AddrRangeTable OBJECT-TYPE
            SYNTAX SEQUENCE OF HwDslamNtvMVLANIPv6AddrRangeEntry
            MAX-ACCESS not-accessible
            STATUS current
            DESCRIPTION
                "Indicates the range of IPv6 address table.
                 The indexes of this table are hwDslamNtvVlanID and hwDslamNtvMVLANIPv6AddrRangeIndex.
                "
            ::= { hwDslamNtv 118 }

        hwDslamNtvMVLANIPv6AddrRangeEntry OBJECT-TYPE
            SYNTAX HwDslamNtvMVLANIPv6AddrRangeEntry
            MAX-ACCESS not-accessible
            STATUS current
            DESCRIPTION
                "Indicates the range of IPv6 address table.
                 The indexes of this entry are hwDslamNtvVlanID and hwDslamNtvMVLANIPv6AddrRangeIndex.
                "
            INDEX { hwDslamNtvVlanID, hwDslamNtvMVLANIPv6AddrRangeIndex }
            ::= { hwDslamNtvMVLANIPv6AddrRangeTable 1 }

        HwDslamNtvMVLANIPv6AddrRangeEntry ::=
            SEQUENCE 
                { 
                hwDslamNtvMVLANIPv6AddrRangeIndex
                    Integer32,
                hwDslamNtvMVLANIPv6AddrRangeRowStatus
                    RowStatus,
                hwDslamNtvMVLANIPv6AddrRangeDynStartIP
                    Ipv6Address,
                hwDslamNtvMVLANIPv6AddrRangeDynEndIP
                    Ipv6Address
                }

        hwDslamNtvMVLANIPv6AddrRangeIndex OBJECT-TYPE
            SYNTAX Integer32 (-1 | 1)
            MAX-ACCESS read-only
            STATUS current
            DESCRIPTION
                "Indicates the index of IPv6 address range, 
                 Range: 1-1,-1 
                 You can also fill -1 and the system will automatically allocate an index.
                "
            ::= { hwDslamNtvMVLANIPv6AddrRangeEntry 1 }

        hwDslamNtvMVLANIPv6AddrRangeRowStatus OBJECT-TYPE
            SYNTAX RowStatus
            MAX-ACCESS read-create
            STATUS current
            DESCRIPTION
                "Row status, used to query, create, and delete an IPv6 address range. 
                 It supports the active(1), createAndGo(4), and destroy(6) operations.
                 During query, the value of this leaf is always active(1).
                 During deletion, specify the value of this leaf to destroy(6).
                 During creation, specify the value of this leaf to createAndGo(4).
                "
            ::= { hwDslamNtvMVLANIPv6AddrRangeEntry 2 }

        hwDslamNtvMVLANIPv6AddrRangeDynStartIP OBJECT-TYPE
            SYNTAX Ipv6Address
            MAX-ACCESS read-write
            STATUS current
            DESCRIPTION
                "Indicates the start IPv6 address of the programs that can be generated dynamically.
                "
            ::= { hwDslamNtvMVLANIPv6AddrRangeEntry 3 }

        hwDslamNtvMVLANIPv6AddrRangeDynEndIP OBJECT-TYPE
            SYNTAX Ipv6Address
            MAX-ACCESS read-write
            STATUS current
            DESCRIPTION
                "Indicates the end IPv6 address of the programs that can be generated dynamically.
                "
            ::= { hwDslamNtvMVLANIPv6AddrRangeEntry 4 }    
            
        -- 1.3.6.1.4.1.2011.6.28.119
        hwDslamNtvIgmpProcessPreferred OBJECT-TYPE
            SYNTAX   INTEGER
                {
                igmpPolicy(1),
                igmpHost(2)
                }
            MAX-ACCESS  read-write
            STATUS      current
            DESCRIPTION
                "Indicates the policy for processing the IGMP packets of the traffic stream. 
                 Options:
                 1. igmpPolicy(1) -indicates that IGMP packets are processed based on IGMP policy configuration
                 2. igmpHost(2)   -indicates that IGMP packets are processed based on IGMP host configuration
                 Default: igmpPolicy(1)
                "
            ::= { hwDslamNtv 119 }
        
        -- 1.3.6.1.4.1.2011.6.28.120    
        hwDslamNtvBandwidthCalcMode OBJECT-TYPE
            SYNTAX  INTEGER
            	{ 
            	userDefinedBase(1),
            	lineRateBase(2)
            	}
            MAX-ACCESS read-write
            STATUS current
            DESCRIPTION
                "Indicates multicast bandwidth calculation mode for BTV user CAC. 
                 Options:
                 1. userDefinedBase(1) -indicates multicast bandwidth calculation is according to user-defined configulation of the BTV user
                 2. lineRateBase(2)    -indicates multicast bandwidth calculation is according to the DSL line rate of the BTV user
                 Default: userDefinedBase(1)
                "
            ::= { hwDslamNtv 120 }
            
        -- 1.3.6.1.4.1.2011.6.28.121    
        hwDslamNtvGlobalCfg   OBJECT IDENTIFIER ::= { hwDslamNtv 121 }
        
        -- 1.3.6.1.4.1.2011.6.28.121.1
        hwDslamNtvGlobalCfgPreviewRecognitionTime  OBJECT-TYPE
            SYNTAX      Integer32 (-1|1..120)
            UNITS        "second"
            MAX-ACCESS  read-write
            STATUS      current
            DESCRIPTION
                "Indicates the preview recognition time. If it is not configured (the value is -1), the preview recognition time is equal to the system recognition time.
                 Range: 1-120, -1
                 Default: -1
                 Unit: second
                "
            ::= { hwDslamNtvGlobalCfg 1 }
        
        -- 1.3.6.1.4.1.2011.6.28.121.2
        hwDslamNtvGlobalCfgLogRecognitionTime  OBJECT-TYPE
            SYNTAX      Integer32 (-1|1..120)
            UNITS        "second"
            MAX-ACCESS  read-write
            STATUS      current
            DESCRIPTION
                "Indicates the log recognition time. If it is not configured (the value is -1), the log recognition time is equal to the system recognition time.
                 Range: 1-120, -1
                 Default: -1
                 Unit: second
                "
            ::= { hwDslamNtvGlobalCfg 2 }
        
        -- 1.3.6.1.4.1.2011.6.28.121.3
        hwDslamNtvGlobalCfgIgmpSyslog OBJECT-TYPE
            SYNTAX      INTEGER
                {
                enable(1),
                disable(2)
                }
            MAX-ACCESS  read-write
            STATUS      current
            DESCRIPTION
                "Indicates the common multicast syslog switch.
                 Options:
                 1. enable(1)  -indicates the syslog switch is on
                 2. disable(2) -indicates the syslog switch is off
                 Default: enable(1)
                "
            ::= { hwDslamNtvGlobalCfg 3 }
        
        -- 1.3.6.1.4.1.2011.6.28.121.4
	      hwDslamNtvGlobalCfgIgmpLogRecord OBJECT-TYPE
            SYNTAX      INTEGER
                {
                user(1),
                mac(2)
                }
            MAX-ACCESS  read-write
            STATUS      current
            DESCRIPTION
                "Indicates the object for the IGMP local log and CDR record.
                 Options:
                 1. user(1) -indicates the record object is based on the IGMP user
                 2. mac(2)  -indicates the record object is based on the terminal MAC address
                 Default: user(1)
                "
            ::= { hwDslamNtvGlobalCfg 4 }
            
        -- 1.3.6.1.4.1.2011.6.28.121.5
        hwDslamNtvGlobalCfgIgmpRouterAlertToV2User OBJECT-TYPE
            SYNTAX  INTEGER
                {
                enable(1),
                disable(2)
                }
            MAX-ACCESS  read-write
            STATUS      current
            DESCRIPTION
                "Specify whether to carry the router alert option in the IGMPv2 packets sent to users.
                 Options:
                 1. enable(1)  -send IGMPv2 packets that carry the router alert option to users
                 2. disable(2) -send IGMPv2 packets that do not carry the router alert option to users
                 Default: enable(1)
                "
            ::= { hwDslamNtvGlobalCfg 5 }    
            
        -- 1.3.6.1.4.1.2011.6.28.121.6
        hwDslamNtvMcastVlanTagTransformUserVlan OBJECT-TYPE
            SYNTAX      Integer32 (-1|1..4095)
            MAX-ACCESS  read-write
            STATUS      current
            DESCRIPTION
                "If hwDslamNtvMcastVlanTagMode is singleTranslate, this value indicates that the user VLAN is translated.
                 If hwDslamNtvMcastVlanTagMode is single or dual, the returned value for hwDslamNtvMcastVlanTagMode is -1, which indicates the leaf does not take effect.                
                "
            ::= { hwDslamNtvGlobalCfg 6 }     

         -- 1.3.6.1.4.1.2011.6.28.122           
        hwDslamNtvMFSExtTable OBJECT-TYPE
            SYNTAX SEQUENCE OF HwDslamNtvMFSExtEntry
            MAX-ACCESS not-accessible
            STATUS current
            DESCRIPTION
                "Indicates the multicast flow staticstics table.
                 The indexes of this table are hwDslamNtvMFSExtMVlanId, hwDslamNtvMFSExtAddrType,
                 hwDslamNtvMFSExtProgramIp and hwDslamNtvMFSExtSourceIp.
                "
            ::= { hwDslamNtv 122 }

        hwDslamNtvMFSExtEntry OBJECT-TYPE
            SYNTAX HwDslamNtvMFSExtEntry
            MAX-ACCESS not-accessible
            STATUS current
            DESCRIPTION
                "Indicates the multicast flow staticstics table.
                 The indexes of this entry are hwDslamNtvMFSExtMVlanId, hwDslamNtvMFSExtAddrType,
                 hwDslamNtvMFSExtProgramIp and hwDslamNtvMFSExtSourceIp.
                "
            INDEX { hwDslamNtvMFSExtMVlanId, hwDslamNtvMFSExtAddrType, hwDslamNtvMFSExtProgramIp, hwDslamNtvMFSExtSourceIp }
            ::= { hwDslamNtvMFSExtTable 1 }
            
        HwDslamNtvMFSExtEntry ::=
            SEQUENCE 
                { 
                hwDslamNtvMFSExtMVlanId
                    Integer32,
                hwDslamNtvMFSExtAddrType
                    InetAddressType,
                hwDslamNtvMFSExtProgramIp
                    InetAddress,
                hwDslamNtvMFSExtSourceIp
                    InetAddress,
                hwDslamNtvMFSExtResult
                    Counter32
                }            
 
        hwDslamNtvMFSExtMVlanId OBJECT-TYPE
            SYNTAX     Integer32(1..4093|4097)
            MAX-ACCESS not-accessible
            STATUS current
            DESCRIPTION
                "Indicates the multicast VLAN ID, 
                 Range: 1-4093,4097.
                 When this index is not required, the value 4097 must be input, 
                 indicating that the index is unnecessary during the process of the MIB table.
                "
            ::= { hwDslamNtvMFSExtEntry 1 }           
            
        hwDslamNtvMFSExtAddrType OBJECT-TYPE
            SYNTAX InetAddressType
            MAX-ACCESS not-accessible
            STATUS current
            DESCRIPTION
                "Indicates the address type.
                 Options:
                 1. IPv4(1) -indicates the address type is IPv4 
                 2. IPv6(2) -indicates the address type is IPv6
                "
            ::= { hwDslamNtvMFSExtEntry 2 }
            
         hwDslamNtvMFSExtProgramIp OBJECT-TYPE
            SYNTAX InetAddress
            MAX-ACCESS not-accessible
            STATUS current
            DESCRIPTION
                "Indicates the group IP address of the program. 
                 The format of this index is consistent with that of the address type.
                "
            ::= { hwDslamNtvMFSExtEntry 3 }           
            
         hwDslamNtvMFSExtSourceIp OBJECT-TYPE
            SYNTAX InetAddress
            MAX-ACCESS not-accessible
            STATUS current
            DESCRIPTION
                "Indicates the source IP address of the program.
                 The format of this index is consistent with that of the address type.
                 When hwDslamNtvMFSExtSourceIp is not used as an index,
                 if the address type is IPv4, 
                 input 255.255.255.255, 
                 which means this index is unnecessary during the process of the MIB table;
                 if the address type is IPv6,
                 input FFFF:FFFF:FFFF:FFFF:FFFF:FFFF:FFFF:FFFF, 
                 which means this index is unnecessary during the process of the MIB table. 
                 Currently, the program source IP addresss cannot be used as an index for querying IPv6 multicast traffic.
                 Therefore, you can only input FFFF:FFFF:FFFF:FFFF:FFFF:FFFF:FFFF:FFFF, which means this index is invalid.
                "
            ::= { hwDslamNtvMFSExtEntry 4 }    
            
         hwDslamNtvMFSExtResult OBJECT-TYPE
            SYNTAX Counter32
            MAX-ACCESS read-only
            STATUS current
            DESCRIPTION
                "Indicates the multicast flow statistics results. 
                 Unit: kbps
                "
            ::= { hwDslamNtvMFSExtEntry 5 }    
          
          hwDslamNtvMVlanMembershipTable OBJECT-TYPE
            SYNTAX SEQUENCE OF HwDslamNtvMVlanMembershipEntry
            MAX-ACCESS not-accessible
            STATUS current
            DESCRIPTION
                "Indicates the member relationship between the multicast VLAN and the multicast user.
                 The indexes of this table are hwDslamNtvVlanID and hwDslamNtvUserIndex. 
                "
            ::= { hwDslamNtv 124 }
        
          hwDslamNtvMVlanMembershipEntry OBJECT-TYPE
            SYNTAX HwDslamNtvMVlanMembershipEntry
            MAX-ACCESS not-accessible
            STATUS current
            DESCRIPTION
                "Indicates the member relationship between the multicast VLAN and the multicast user.
                 The indexes of this entry are hwDslamNtvVlanID and hwDslamNtvUserIndex.
                "
            INDEX 
                { 
                hwDslamNtvVlanID,
                hwDslamNtvUserIndex
                }
            ::= { hwDslamNtvMVlanMembershipTable 1 }
        
          HwDslamNtvMVlanMembershipEntry ::= 
            SEQUENCE 
                {
                hwDslamNtvMVlanMembershipStatus 
                    INTEGER{ enable(1),disable(2) }
                }
         
          hwDslamNtvMVlanMembershipStatus OBJECT-TYPE
            SYNTAX  INTEGER{ enable(1),disable(2) }
            MAX-ACCESS read-write
            STATUS current
            DESCRIPTION
                "Indicates the member relationship between the multicast VLAN and the multicast user. Options:
                 1. enable(1)  -indicates that the user is a member of the multicast VLAN.
                 2. disable(2) -indicates that the user is not a member of the multicast VLAN.
                "
            ::= { hwDslamNtvMVlanMembershipEntry 1 }

	  hwDslamNtvBoardStatisticTable OBJECT-TYPE
            SYNTAX SEQUENCE OF HwDslamNtvBoardStatisticEntry
            MAX-ACCESS not-accessible
            STATUS current
            DESCRIPTION
                "Indicates the IPTV performance statistics of the specific board.
                 The indexes of this table are hwDslamNtvBoardStatisticFrameID and hwDslamNtvBoardStatisticSlotID. 
                "
            ::= { hwDslamNtv 125 }
        
          hwDslamNtvBoardStatisticEntry OBJECT-TYPE
            SYNTAX         HwDslamNtvBoardStatisticEntry
            MAX-ACCESS     not-accessible
            STATUS         current
            DESCRIPTION
                "Indicates the IPTV performance statistics of the specific board.
                 The indexes of this entry are hwDslamNtvBoardStatisticFrameID and hwDslamNtvBoardStatisticSlotID. 
                "
            INDEX
                {
                hwDslamNtvBoardStatisticFrameID,
		hwDslamNtvBoardStatisticSlotID
                }
            ::= { hwDslamNtvBoardStatisticTable  1 }

          HwDslamNtvBoardStatisticEntry    ::=
            SEQUENCE
                {
                hwDslamNtvBoardStatisticFrameID
                    Unsigned32,
                hwDslamNtvBoardStatisticSlotID
                    Unsigned32,
                hwDslamNtvBoardStatisticOperMode
                    INTEGER,
                hwDslamNtvReportsStatisticBoardInSecond1
                    Unsigned32,
                hwDslamNtvReportsStatisticBoardInSecond2
                    Unsigned32,
                hwDslamNtvReportsStatisticBoardInSecond3
                    Unsigned32,
                hwDslamNtvReportsStatisticBoardInSecond4
                    Unsigned32,
                hwDslamNtvReportsStatisticBoardInSecond5
                    Unsigned32,
                hwDslamNtvReportsStatisticBoardInSecond6
                    Unsigned32,
                hwDslamNtvReportsStatisticBoardInSecond7
                    Unsigned32,
                hwDslamNtvReportsStatisticBoardInSecond8
                    Unsigned32,
	        hwDslamNtvReportsStatisticBoardInSecond9
                    Unsigned32
               }

          hwDslamNtvBoardStatisticFrameID OBJECT-TYPE
            SYNTAX       Unsigned32 (0..1024)
            MAX-ACCESS   not-accessible
            STATUS       current
            DESCRIPTION
                "Indicates the frame ID of the specific board.
                "
            ::= { hwDslamNtvBoardStatisticEntry 1}
	  
	  hwDslamNtvBoardStatisticSlotID OBJECT-TYPE
            SYNTAX       Unsigned32 (0..255)
            MAX-ACCESS   not-accessible
            STATUS       current
            DESCRIPTION
                "Indicates the slot ID of the specific board.
                "
            ::= { hwDslamNtvBoardStatisticEntry 2} 
	    
          hwDslamNtvBoardStatisticOperMode OBJECT-TYPE
            SYNTAX   INTEGER
                 { 
                 clearStatistic(1),
                 invalid(-1) 
                 }
            MAX-ACCESS   read-write
            STATUS       current
            DESCRIPTION
                "Indicates the operation mode of performance statistics. 
                 Options: 
                 1. clearStatistic(1) -indicates clearing statistics
                 2. invalid(-1)       -indicates invalid operation mode 
                "
            ::= { hwDslamNtvBoardStatisticEntry 3}
	    
	  hwDslamNtvReportsStatisticBoardInSecond1 OBJECT-TYPE
	        SYNTAX       Unsigned32
            MAX-ACCESS   read-only
            STATUS       current
            DESCRIPTION
                "Indicates the number of report packets at the 4th second before the PIR.
                "
            ::= { hwDslamNtvBoardStatisticEntry 4}
	    
	  hwDslamNtvReportsStatisticBoardInSecond2 OBJECT-TYPE
	    SYNTAX       Unsigned32
            MAX-ACCESS   read-only
            STATUS       current
            DESCRIPTION
                "Indicates the number of report packets at the 3rd second before the PIR.
                "
            ::= { hwDslamNtvBoardStatisticEntry 5}
	    
	  hwDslamNtvReportsStatisticBoardInSecond3 OBJECT-TYPE
	    SYNTAX       Unsigned32
            MAX-ACCESS   read-only
            STATUS       current
            DESCRIPTION
                "Indicates the number of report packets at the 2nd second before the PIR.
                "
            ::= { hwDslamNtvBoardStatisticEntry 6}
	    
	  hwDslamNtvReportsStatisticBoardInSecond4 OBJECT-TYPE
	    SYNTAX       Unsigned32
            MAX-ACCESS   read-only
            STATUS       current
            DESCRIPTION
                "Indicates the number of report packets at the 1st second before the PIR.
                "
            ::= { hwDslamNtvBoardStatisticEntry 7}
	    
	  hwDslamNtvReportsStatisticBoardInSecond5 OBJECT-TYPE
	    SYNTAX       Unsigned32
            MAX-ACCESS   read-only
            STATUS       current
            DESCRIPTION
                "Indicates the number of report packets at the current second of the PIR.
                "
            ::= { hwDslamNtvBoardStatisticEntry 8}
	    
	  hwDslamNtvReportsStatisticBoardInSecond6 OBJECT-TYPE
	    SYNTAX       Unsigned32
            MAX-ACCESS   read-only
            STATUS       current
            DESCRIPTION
                "Indicates the number of report packets at the 1st second after the PIR.
                "
            ::= { hwDslamNtvBoardStatisticEntry 9}
	    
	  hwDslamNtvReportsStatisticBoardInSecond7 OBJECT-TYPE
	    SYNTAX       Unsigned32
            MAX-ACCESS   read-only
            STATUS       current
            DESCRIPTION
                "Indicates the number of report packets at the 2nd second after the PIR.
                "
            ::= { hwDslamNtvBoardStatisticEntry 10}
	    
	  hwDslamNtvReportsStatisticBoardInSecond8 OBJECT-TYPE
	    SYNTAX       Unsigned32
            MAX-ACCESS   read-only
            STATUS       current
            DESCRIPTION
                "Indicates the number of report packets at the 3rd second after the PIR.
                "
            ::= { hwDslamNtvBoardStatisticEntry 11}
	    
	  hwDslamNtvReportsStatisticBoardInSecond9 OBJECT-TYPE
	    SYNTAX       Unsigned32
            MAX-ACCESS   read-only
            STATUS       current
            DESCRIPTION
                "Indicates the number of report packets at the 4th second after the PIR.
                "
            ::= { hwDslamNtvBoardStatisticEntry 12}
	    
          hwMulticastPortStatisticTable OBJECT-TYPE
            SYNTAX SEQUENCE OF HwMulticastPortStatisticEntry
            MAX-ACCESS not-accessible
            STATUS current
            DESCRIPTION
                "Indicates traffic statistics based on the port and the multicast group.
                 The index of this table is ifIndex. 
                "
            ::= { hwDslamNtv 126 }
        
          hwMulticastPortStatisticEntry OBJECT-TYPE
            SYNTAX HwMulticastPortStatisticEntry
            MAX-ACCESS not-accessible
            STATUS current
            DESCRIPTION
                "Indicates traffic statistics based on the port and the multicast group.
                 The index of this entry is ifIndex. 
                "
            INDEX 
                { 
                ifIndex
                }
            ::= { hwMulticastPortStatisticTable 1 }
        
          HwMulticastPortStatisticEntry ::= 
            SEQUENCE 
                {
                hwMulticastPortStatisticRowStatus 
                    RowStatus,
                hwMulticastPortStatisticCountClear 
                    INTEGER,
                hwMulticastPortStatisticIpAddressType
                    InetAddressType,
                hwMulticastPortStatisticSourceIpAddr
                    InetAddress,
                hwMulticastPortStatisticProgramIpAddr
                    InetAddress,
                hwMulticastPortStatisticVlan
                    Integer32,
                hwMulticastPortStatisticTransmitPackets
                    Counter64,
                hwMulticastPortStatisticTransmitBytes
                    Counter64,
                hwMulticastPortStatisticTransmitRate
                    Counter64,
                hwMulticastPortStatisticTransmitSpeed
                    Counter64
                }
         
          hwMulticastPortStatisticRowStatus OBJECT-TYPE
            SYNTAX  RowStatus
            MAX-ACCESS read-create
            STATUS current
            DESCRIPTION
                "Row status, used to create and delete a task of query  statistic 
		 multicast flow. 
                 It supports the active(1), createAndGo(4), and destroy(6) operations.
                 During query, the value of this leaf is always active(1).
                 During deletion, specify the value of this leaf to destroy(6).
                 During creation, specify the value of this leaf to createAndGo(4).
                 To modify the parameters of a statistic multicast task, this leaf need not be issued together.
                 Options:
                 1.active(1) - when this leaf is queried, the value is fixed to active(1)
                 2.createAndGo(4) -deliver a multicast channel traffic statistic to a specified port
                 3.destroy(6)     -delete the multicast channel traffic statistic delivered to the specified port.
                "
            ::= { hwMulticastPortStatisticEntry 1 }
	    
          hwMulticastPortStatisticCountClear OBJECT-TYPE
            SYNTAX  INTEGER
                {
                cleared(1),
                invalid(-1)
                }
            MAX-ACCESS read-write
            STATUS current
            DESCRIPTION
                "Options:
                 1.cleared(1)  -reset the multicast channel traffic statistic delivered to the specified port
                 2.invalid(-1) -in the query operation, this leaf is fixed to invalid(-1).
                "
            ::= { hwMulticastPortStatisticEntry 2 }  
	    
          hwMulticastPortStatisticIpAddressType OBJECT-TYPE
            SYNTAX  InetAddressType
            MAX-ACCESS read-write
            STATUS current
            DESCRIPTION
                "Indicates the address type, it is optional.
                 Options:
                 1. IPv4(1) -indicates the address type is IPv4 
                 2. IPv6(2) -indicates the address type is IPv6
                "
            ::= { hwMulticastPortStatisticEntry 3 }  
	    
          hwMulticastPortStatisticSourceIpAddr OBJECT-TYPE
            SYNTAX  InetAddress
            MAX-ACCESS read-write
            STATUS current
            DESCRIPTION
                "Indicates the Source IP address, it is optional.
                 The format of this index is consistent with that of the address type.
                 When hwMulticastPortStatisticSourceIpAddr is not used,
                 if the address type is IPv4, 255.255.255.255 means this IP address is invalid ;
                 if the address type is IPv6, FFFF:FFFF:FFFF:FFFF:FFFF:FFFF:FFFF:FFFF means this IP address is invalid. 
                "
            ::= { hwMulticastPortStatisticEntry 4 }  
	    
          hwMulticastPortStatisticProgramIpAddr OBJECT-TYPE
            SYNTAX  InetAddress
            MAX-ACCESS read-write
            STATUS current
            DESCRIPTION
                "Indicates the Program IP address, it is necessary.
                 The format of this index is consistent with that of the address type.
                "
            ::= { hwMulticastPortStatisticEntry 5 }  
	    
          hwMulticastPortStatisticVlan OBJECT-TYPE
            SYNTAX  Integer32 (1..4093)
            MAX-ACCESS read-write
            STATUS current
            DESCRIPTION
                "Indicates the VLAN where the program resides.
                "
            ::= { hwMulticastPortStatisticEntry 6 }  
	    
          hwMulticastPortStatisticTransmitPackets OBJECT-TYPE
            SYNTAX   Counter64
            MAX-ACCESS read-only
            STATUS current
            DESCRIPTION
                "Indicates the multicast flow statistics results.
                 Indicates the total transmitted packets.                    
                "
            ::= { hwMulticastPortStatisticEntry 7 }  
	    
          hwMulticastPortStatisticTransmitBytes OBJECT-TYPE
            SYNTAX   Counter64
            MAX-ACCESS read-only
            STATUS current
            DESCRIPTION
                "Indicates the multicast flow statistics results.
                 Indicates the total transmitted bytes.    
                "
            ::= { hwMulticastPortStatisticEntry 8 }  
	    
          hwMulticastPortStatisticTransmitRate OBJECT-TYPE
            SYNTAX   Counter64
            UNITS  "pps"
            MAX-ACCESS read-only
            STATUS current
            DESCRIPTION
                "Indicates the multicast flow statistics results.
                 Indicates the transmitted rate.    
                 Unit:packets/s
                "
            ::= { hwMulticastPortStatisticEntry 9 }  
	    
          hwMulticastPortStatisticTransmitSpeed OBJECT-TYPE
            SYNTAX   Counter64
            UNITS  "kbps"
            MAX-ACCESS read-only
            STATUS current
            DESCRIPTION
                "Indicates the multicast flow statistics results.
                 Indicates the transmitted speed.    
                 Unit:kbit/s
                "
            ::= { hwMulticastPortStatisticEntry 10 }  
         
          hwDslamNtvChannelBandwidthCACTable OBJECT-TYPE
            SYNTAX SEQUENCE OF HwDslamNtvChannelBandwidthCACEntry
            MAX-ACCESS not-accessible
            STATUS current
            DESCRIPTION
                "Sets the channel bandwidth; queries the allocated and used bandwidth of a channel.
                 The indexes of this table are ifIndex and hwDslamNtvChannelBandwidthCACChannelID.
                "
            ::= { hwDslamNtv 127 }
        
          hwDslamNtvChannelBandwidthCACEntry OBJECT-TYPE
            SYNTAX HwDslamNtvChannelBandwidthCACEntry
            MAX-ACCESS not-accessible
            STATUS current
            DESCRIPTION
                "Sets the channel bandwidth; queries the allocated and used bandwidth of a channel.
                 The indexes of this entry are ifIndex and hwDslamNtvChannelBandwidthCACChannelID.
                "
            INDEX 
                { 
                ifIndex,
                hwDslamNtvChannelBandwidthCACChannelID
                }
            ::= { hwDslamNtvChannelBandwidthCACTable 1 }
        
          HwDslamNtvChannelBandwidthCACEntry ::= 
             SEQUENCE 
                 {
                 hwDslamNtvChannelBandwidthCACChannelID 
                     INTEGER,
                 hwDslamNtvChannelAssignBandwidth 
                     Unsigned32,
                 hwDslamNtvChannelUsedBandwidth 
                     Unsigned32,
                 hwDslamNtvChannelAncpVideoBandwidth 
                     Unsigned32,
                 hwDslamNtvChannelAncpMcastBandwidth
                     Unsigned32
                 }       
        
	  hwDslamNtvChannelBandwidthCACChannelID        OBJECT-TYPE
            SYNTAX   INTEGER
            {
            the1gChannel(1),
            the10gChannel(2)
            }
            MAX-ACCESS   not-accessible
            STATUS       current
            DESCRIPTION
                "Indicates the channel.
                 Options:
                 1. the1gChannel(1)    -indicates the 1g channel
                 2. the10gChannel(2)   -indicates the 10g channel
                "
            ::= { hwDslamNtvChannelBandwidthCACEntry 1 }
        
          hwDslamNtvChannelAssignBandwidth  OBJECT-TYPE
            SYNTAX Unsigned32
            MAX-ACCESS read-write
            STATUS current
            DESCRIPTION
                "Indicates the allocable channel bandwidth. 
                 If the bandwidth is not limited, the returned value for hwDslamNtvChannelAssignBandwidth is 4294967295.
                 Unit: kbit/s
                "
            ::= { hwDslamNtvChannelBandwidthCACEntry 2 } 
                
          hwDslamNtvChannelUsedBandwidth  OBJECT-TYPE
            SYNTAX Unsigned32
            MAX-ACCESS read-only
            STATUS current
            DESCRIPTION
                "Indicates the used bandwidth of the channel.
		 Unit: kbit/s
                "
            ::= { hwDslamNtvChannelBandwidthCACEntry 3 } 
                
          hwDslamNtvChannelAncpVideoBandwidth  OBJECT-TYPE
            SYNTAX Unsigned32
            MAX-ACCESS read-only
            STATUS current
            DESCRIPTION
                "Indicates the total ANCP video bandwidth. When ANCP CAC is disabled or not supported,
                 the returned value for hwDslamNtvChannelAncpVideoBandwidth is 4294967295.
                 Unit: kbit/s.
                "
            ::= { hwDslamNtvChannelBandwidthCACEntry 4 }
        
          hwDslamNtvChannelAncpMcastBandwidth  OBJECT-TYPE
            SYNTAX Unsigned32
            MAX-ACCESS read-only
            STATUS current
            DESCRIPTION
                "Indicates the ANCP multicast video bandwidth. When ANCP CAC is disabled or not supported, 
                 the returned value for hwDslamNtvChannelAncpMcastBandwidth is 4294967295.
                 Unit: kbit/s.
                "
            ::= { hwDslamNtvChannelBandwidthCACEntry 5 }
	    
END
