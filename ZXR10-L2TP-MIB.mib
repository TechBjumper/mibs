--  ************************************************
--  $Id: ZXR10-L2TP.mib 1 2009-10-14 16:46:21Z wangxu $
--
--  ZXR10-L2TP.mib: ZXR10 L2TP query  MIB file
--
--  Oct. 2009, Wangxu
--
--  Copyright(c) 2009 by ZTE Corporaton
--  All rights reservered
--
--  ************************************************

ZXR10-L2TP-MIB DEFINITIONS ::= BEGIN

IMPORTS
    MODULE-IDENTITY,
    OBJECT-TYPE,
    Gauge32, IpAddress,
    enterprises
        FROM SNMPv2-SMI 
    DisplayString                FROM SNMPv2-TC; 

  
  zxr10L2TP MODULE-IDENTITY  
        LAST-UPDATED "201303120000Z"  -- Mar 13, 2013
        ORGANIZATION "ZTE Corporation"
          CONTACT-INFO
              "ZTE Corporation
              Nanjing Institute of ZTE Corporation

              No.68 Zijinghua Rd. Yuhuatai District, Nanjing, China

              Tel: +86-25-52870000"

         DESCRIPTION
             "ZXROS v4.8.22 L2tp query and configuration MIB"
             
         REVISION "201303120000Z"  -- Mar 12, 2013
         DESCRIPTION
         "Modify TFTP to FTP"
         REVISION "200910150000Z"  -- Oct 15, 2009
         DESCRIPTION
         ""
         ::= { zxr10 335}

    zte       OBJECT IDENTIFIER ::= { enterprises 3902 }  
    zxr10     OBJECT IDENTIFIER ::= { zte 3} 
    l2tpStatsGlobal OBJECT IDENTIFIER ::= { zxr10L2TP 1 } 
    zxr10L2TPUploadFtpGroup  OBJECT IDENTIFIER ::= { zxr10L2TP 2 }
    zxr10L2TPTunnelStatUploadFtpInfo   OBJECT IDENTIFIER ::= { zxr10L2TPUploadFtpGroup 1 }
    zxr10L2TPSessionStatUploadFtpInfo  OBJECT IDENTIFIER ::= { zxr10L2TPUploadFtpGroup 2 }

    
    l2tpStatsActiveTunnels   OBJECT-TYPE
        SYNTAX         Gauge32
        MAX-ACCESS     read-only
        STATUS         current
        DESCRIPTION
           "This object returns the number of tunnels that
            are currently active."
        ::= { l2tpStatsGlobal 7 }
        
    l2tpStatsActiveSessions  OBJECT-TYPE
        SYNTAX         Gauge32
        MAX-ACCESS     read-only
        STATUS         current
        DESCRIPTION
           "This object returns the number of sessions that
            are currently active."
        ::= { l2tpStatsGlobal 11 }   
  
  --- tunnel upload  ftp mib   
    
  zxr10L2TPTunnelStatUploadFtpAddr  OBJECT-TYPE
        SYNTAX      IpAddress
        MAX-ACCESS  read-write
        STATUS      current
        DESCRIPTION
            "The IP Address for the FTP server used for uploading files." 
        ::= { zxr10L2TPTunnelStatUploadFtpInfo 1 }
        
    zxr10L2TPTunnelStatUploadFtpUserName  OBJECT-TYPE
        SYNTAX      DisplayString (SIZE (0..31))
        MAX-ACCESS  read-write
        STATUS      current
        DESCRIPTION
            "The FTP username."
        ::= { zxr10L2TPTunnelStatUploadFtpInfo 2 }
        
    zxr10L2TPTunnelStatUploadFtpUserPassword  OBJECT-TYPE
        SYNTAX      DisplayString (SIZE (0..31))
        MAX-ACCESS  read-write
        STATUS      current
        DESCRIPTION
            "The FTP User Password."
        ::= { zxr10L2TPTunnelStatUploadFtpInfo 3 }
 
    zxr10L2TPTunnelStatUploadFtpFileName  OBJECT-TYPE
        SYNTAX      DisplayString (SIZE (0..32))
        MAX-ACCESS  read-write
        STATUS      current
        DESCRIPTION
            "The FTP file path and name."
        ::= { zxr10L2TPTunnelStatUploadFtpInfo 4 }   
        
    zxr10L2TPTunnelStatUploadFtpExecuteStatus  OBJECT-TYPE
        SYNTAX      INTEGER { 
            notstarted           (1),
            inprogress           (2),
            success              (3),
            userorpasswordfailed (4),
            requestbedenied      (5),
            datatransfailed      (6)
            }
        MAX-ACCESS  read-only
        STATUS      current
        DESCRIPTION
            " Save flash operatioanl status."
        ::= { zxr10L2TPTunnelStatUploadFtpInfo 5 }

    zxr10L2TPTunnelStatUploadFtpExecutePercent  OBJECT-TYPE
      SYNTAX      DisplayString (SIZE (1..5))
        MAX-ACCESS  read-only
        STATUS      current
        DESCRIPTION
            " Store Data Percent."
       ::= { zxr10L2TPTunnelStatUploadFtpInfo 6 }
  
    --- session upload  ftp mib   
    
  zxr10L2TPSessionStatUploadFtpAddr  OBJECT-TYPE
        SYNTAX      IpAddress
        MAX-ACCESS  read-write
        STATUS      current
        DESCRIPTION
            "The IP Address for the FTP server used for uploading files." 
        ::= { zxr10L2TPSessionStatUploadFtpInfo 1 }
        
    zxr10L2TPSessionStatUploadFtpUserName  OBJECT-TYPE
        SYNTAX      DisplayString (SIZE (0..31))
        MAX-ACCESS  read-write
        STATUS      current
        DESCRIPTION
            "The FTP username."
        ::= { zxr10L2TPSessionStatUploadFtpInfo 2 }
        
    zxr10L2TPSessionStatUploadFtpUserPassword  OBJECT-TYPE
        SYNTAX      DisplayString (SIZE (0..31))
        MAX-ACCESS  read-write
        STATUS      current
        DESCRIPTION
            "The FTP User Password."
        ::= { zxr10L2TPSessionStatUploadFtpInfo 3 }
 
    zxr10L2TPSessionStatUploadFtpFileName  OBJECT-TYPE
        SYNTAX      DisplayString (SIZE (0..32))
        MAX-ACCESS  read-write
        STATUS      current
        DESCRIPTION
            "The FTP file path and name."
        ::= { zxr10L2TPSessionStatUploadFtpInfo 4 }   
        
    zxr10L2TPSessionStatUploadFtpExecuteStatus  OBJECT-TYPE
        SYNTAX      INTEGER { 
            notstarted           (1),
            inprogress           (2),
            success              (3),
            userorpasswordfailed (4),
            requestbedenied      (5),
            datatransfailed      (6)
            }
        MAX-ACCESS  read-only
        STATUS      current
        DESCRIPTION
            " Save flash operatioanl status."
        ::= { zxr10L2TPSessionStatUploadFtpInfo 5 }

    zxr10L2TPSessionStatUploadFtpExecutePercent  OBJECT-TYPE
      SYNTAX      DisplayString (SIZE (1..5))
        MAX-ACCESS  read-only
        STATUS      current
        DESCRIPTION
            " Store Data Percent."
       ::= { zxr10L2TPSessionStatUploadFtpInfo 6 }
    
        

END
